DHS-MIB DEFINITIONS ::= BEGIN

IMPORTS
    MODULE-IDENTITY, NOTIFICATION-TYPE, OBJECT-IDENTITY, enterprises
        FROM SNMPv2-SMI
    MODULE-COMPLIANCE, NOTIFICATION-GROUP
        FROM SNMPv2-CONF;

dhsMIB MODULE-IDENTITY
    LAST-UPDATED "202609110000Z"
    ORGANIZATION
        "BY-SYSTEMS SPRL"
    CONTACT-INFO
        "BY-SYSTEMS SPRL"
    DESCRIPTION
        "The identity, objects and notifications of dhs, the BY-SYSTEMS
         broadcast control gateway, under IANA Private Enterprise Number 54981.
         Generated by `dhs producer snmp mib` from the tree the agent serves."
    REVISION    "202609110000Z"
    DESCRIPTION
        "Initial version: the agent's identity and the test notification."
    ::= { bySystems 2 }

bySystems OBJECT IDENTIFIER ::= { enterprises 54981 }

dhsProducts OBJECT-IDENTITY
    STATUS      current
    DESCRIPTION
        "The products BY-SYSTEMS registers; each is a sysObjectID value."
    ::= { bySystems 1 }

dhsAgent OBJECT-IDENTITY
    STATUS      current
    DESCRIPTION
        "The dhs SNMP agent. It is the sysObjectID.0 the agent reports and
         the enterprise its SNMPv1 traps carry."
    ::= { dhsProducts 1 }

dhsAgentNotifications OBJECT IDENTIFIER ::= { dhsAgent 0 }

dhsTestNotification NOTIFICATION-TYPE
    STATUS      current
    DESCRIPTION
        "Sent on demand by `dhs producer snmp trap` to prove a receiver is
         reachable before anything depends on it. It reports no event and
         carries no objects. In SNMPv1 it is enterprise dhsAgent, generic 6,
         specific 1."
    ::= { dhsAgentNotifications 1 }

dhsObjects OBJECT IDENTIFIER ::= { dhsMIB 1 }

dhsConformance OBJECT IDENTIFIER ::= { dhsMIB 2 }

dhsGroups OBJECT IDENTIFIER ::= { dhsConformance 1 }

dhsNotificationGroup NOTIFICATION-GROUP
    NOTIFICATIONS { dhsTestNotification }
    STATUS      current
    DESCRIPTION
        "Every notification DHS-MIB defines."
    ::= { dhsGroups 2 }

dhsCompliances OBJECT IDENTIFIER ::= { dhsConformance 2 }

dhsCompliance MODULE-COMPLIANCE
    STATUS      current
    DESCRIPTION
        "An agent implementing DHS-MIB implements all of it."
    MODULE      -- this module
        MANDATORY-GROUPS { dhsNotificationGroup }
    ::= { dhsCompliances 1 }

END
