-- ************************************************************************************
-- Snell&Wilcox Card:IQSRT20
--        Module Id#:398
--       Command Set:5
--          Filename:SNELL-IQSRT20-CMD-MIB.mib
--            Author:Jonathan Riches
--              Date:04/07/2005
--              Time:09:50
--
-- Copyright (c) 2005 Snell & Wilcox Ltd
-- All rights reserved.
--
-- ************************************************************************************

SNELL-IQSRT20-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQSRT20,
    moduleIQSRT20MIB
        FROM SNELL-WILCOX-PRODUCT-REG;

 moduleIQSRT20CmdMi MODULE-IDENTITY
    LAST-UPDATED "0507040950Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQSRT20MIB 1 }




--********************************************************************************
--*
--*  Snell Wilcox Card:
--*  command set:
--*  list commands/menus:
--*
--******************************************************************************
	iqsrt20CmdTable OBJECT-TYPE
		SYNTAX			SEQUENCE OF Iqsrt20CmdEntry
		MAX-ACCESS		not-accessible
		STATUS			current
		DESCRIPTION
				"Note the instance of this table is relected in the command set Version"
		::= { moduleIQSRT20 1 }

	iqsrt20CmdEntry OBJECT-TYPE
		SYNTAX		Iqsrt20CmdEntry
		MAX-ACCESS		not-accessible
		STATUS			current
		DESCRIPTION
				"Entry in command table."
		INDEX	{ iqsrt20SlotIndex }
		::= { iqsrt20CmdTable 1 }

	Iqsrt20CmdEntry ::=
		SEQUENCE {
			iqsrt20SlotIndex
				Unsigned32,
			iqsrt20InputSel
				INTEGER,
			iqsrt20Display
				INTEGER,
			iqsrt20DisplayResetEDHStats
				INTEGER,
			iqsrt20DisplayResetRTErrors
				INTEGER,
			iqsrt20AutoCycleCycleListItem1
				INTEGER,
			iqsrt20AutoCycleCycleListItem2
				INTEGER,
			iqsrt20AutoCycleCycleListItem3
				INTEGER,
			iqsrt20AutoCycleCycleListItem4
				INTEGER,
			iqsrt20AutoCycleCycleTime
				INTEGER,
			iqsrt20SetupInputNamesInput1
				RollCallString,
			iqsrt20SetupInputNamesInput2
				RollCallString,
			iqsrt20SetupInputNamesInput3
				RollCallString,
			iqsrt20SetupInputNamesInput4
				RollCallString,
			iqsrt20RollTrackInput1OnRTAddress
				RollCallString,
			iqsrt20RollTrackInput1OnRTParams
				RollCallString,
			iqsrt20RollTrackInput1OffRTAddress
				RollCallString,
			iqsrt20RollTrackInput1OffRTParams
				RollCallString,
			iqsrt20RollTrackInput2OnRTAddress
				RollCallString,
			iqsrt20RollTrackInput2OnRTParams
				RollCallString,
			iqsrt20RollTrackInput2OffRTAddress
				RollCallString,
			iqsrt20RollTrackInput2OffRTParams
				RollCallString,
			iqsrt20RollTrackInput3OnRTAddress
				RollCallString,
			iqsrt20RollTrackInput3OnRTParams
				RollCallString,
			iqsrt20RollTrackInput3OffRTAddress
				RollCallString,
			iqsrt20RollTrackInput3OffRTParams
				RollCallString,
			iqsrt20RollTrackInput4OnRTAddress
				RollCallString,
			iqsrt20RollTrackInput4OnRTParams
				RollCallString,
			iqsrt20RollTrackInput4OffRTAddress
				RollCallString,
			iqsrt20RollTrackInput4OffRTParams
				RollCallString,
			iqsrt20SetupInhibitInputsInput1
				INTEGER,
			iqsrt20SetupInhibitInputsInput2
				INTEGER,
			iqsrt20SetupInhibitInputsInput3
				INTEGER,
			iqsrt20SetupInhibitInputsInput4
				INTEGER,
			iqsrt20SetupPresetUnit
				INTEGER,
			iqsrt20SetupLoggingInputStatus
				INTEGER,
			iqsrt20SetupLoggingInputName
				INTEGER,
			iqsrt20SetupLoggingEDHErrors
				INTEGER,
			iqsrt20SetupSoftwareVersion
				RollCallString,
			iqsrt20SetupSerialNumber
				RollCallString
		}

	iqsrt20SlotIndex OBJECT-TYPE
		SYNTAX		Unsigned32
		MAX-ACCESS		not-accessible
		STATUS			current
		DESCRIPTION
				"The unique Index value for each slot.  Its value
					ranges between 1 and the value of slotNumber."
		::= { iqsrt20CmdEntry 0 }


	iqsrt20InputSel OBJECT-TYPE
		SYNTAX		INTEGER {
							val_Select_1(0),
							val_Select_2(1),
							val_Select_3(2),
							val_Select_4(3)
							}
		MAX-ACCESS		read-write
		STATUS			current
		DESCRIPTION
				"TYPE: - RadiobuttonList
					Input Sel  cmdID= 4 
					Select 1  value= 0  
					Select 2  value= 1  
					Select 3  value= 2  
					Select 4  value= 3  "
		::= { iqsrt20CmdEntry 4 }


	iqsrt20Display OBJECT-TYPE
		SYNTAX		INTEGER {
							val_Show_Status(0),
							val_Show_EDH_Stats(1),
							val_Show_RT_Errors(2)
							}
		MAX-ACCESS		read-write
		STATUS			current
		DESCRIPTION
				"TYPE: - Button
					Show Status  cmdID= 5  value= 0  
					Show EDH Stats  cmdID= 5  value= 1  
					Show RT Errors  cmdID= 5  value= 2  "
		::= { iqsrt20CmdEntry 5 }


	iqsrt20DisplayResetEDHStats OBJECT-TYPE
		SYNTAX		INTEGER { noAction(0),val_Reset_EDH_Stats(1) }
		MAX-ACCESS		read-write
		STATUS			current
		DESCRIPTION
				"TYPE: - Button
					Reset EDH Stats  cmdID= 6  value= 1  "
		::= { iqsrt20CmdEntry 6 }


	iqsrt20DisplayResetRTErrors OBJECT-TYPE
		SYNTAX		INTEGER { noAction(0),val_Reset_RT_Errors(1) }
		MAX-ACCESS		read-write
		STATUS			current
		DESCRIPTION
				"TYPE: - Button
					Reset RT Errors  cmdID= 26  value= 1  "
		::= { iqsrt20CmdEntry 26 }


	iqsrt20AutoCycleCycleListItem1 OBJECT-TYPE
		SYNTAX		INTEGER
		MAX-ACCESS		read-write
		STATUS			current
		DESCRIPTION
				"TYPE: - Number
					Item 1  cmdID= 7  min= 0  max= 8  step= 1  format= %.0f  div_scale= 1 
					Min = 0  Max = 8  Step = 1 "
		::= { iqsrt20CmdEntry 7 }


	iqsrt20AutoCycleCycleListItem2 OBJECT-TYPE
		SYNTAX		INTEGER
		MAX-ACCESS		read-write
		STATUS			current
		DESCRIPTION
				"TYPE: - Number
					Item 2  cmdID= 8  min= 0  max= 8  step= 1  format= %.0f  div_scale= 1 
					Min = 0  Max = 8  Step = 1 "
		::= { iqsrt20CmdEntry 8 }


	iqsrt20AutoCycleCycleListItem3 OBJECT-TYPE
		SYNTAX		INTEGER
		MAX-ACCESS		read-write
		STATUS			current
		DESCRIPTION
				"TYPE: - Number
					Item 3  cmdID= 9  min= 0  max= 8  step= 1  format= %.0f  div_scale= 1 
					Min = 0  Max = 8  Step = 1 "
		::= { iqsrt20CmdEntry 9 }


	iqsrt20AutoCycleCycleListItem4 OBJECT-TYPE
		SYNTAX		INTEGER
		MAX-ACCESS		read-write
		STATUS			current
		DESCRIPTION
				"TYPE: - Number
					Item 4  cmdID= 10  min= 0  max= 8  step= 1  format= %.0f  div_scale= 1 
					Min = 0  Max = 8  Step = 1 "
		::= { iqsrt20CmdEntry 10 }


	iqsrt20AutoCycleCycleTime OBJECT-TYPE
		SYNTAX		INTEGER
		MAX-ACCESS		read-write
		STATUS			current
		DESCRIPTION
				"TYPE: - Number
					CycleTime  cmdID= 15  min= 0  max= 32000  step= 1  format= %.0f Frames  div_scale= 1 
					Min = 0 Frames  Max = 32000 Frames  Step = 1 Frames "
		::= { iqsrt20CmdEntry 15 }


	iqsrt20SetupInputNamesInput1 OBJECT-TYPE
		SYNTAX		RollCallString
		MAX-ACCESS		read-write
		STATUS			current
		DESCRIPTION
				"TYPE: - Editstring
					Input 1  cmdID= 16  "
		::= { iqsrt20CmdEntry 16 }


	iqsrt20SetupInputNamesInput2 OBJECT-TYPE
		SYNTAX		RollCallString
		MAX-ACCESS		read-write
		STATUS			current
		DESCRIPTION
				"TYPE: - Editstring
					Input 2  cmdID= 17  "
		::= { iqsrt20CmdEntry 17 }


	iqsrt20SetupInputNamesInput3 OBJECT-TYPE
		SYNTAX		RollCallString
		MAX-ACCESS		read-write
		STATUS			current
		DESCRIPTION
				"TYPE: - Editstring
					Input 3  cmdID= 18  "
		::= { iqsrt20CmdEntry 18 }


	iqsrt20SetupInputNamesInput4 OBJECT-TYPE
		SYNTAX		RollCallString
		MAX-ACCESS		read-write
		STATUS			current
		DESCRIPTION
				"TYPE: - Editstring
					Input 4  cmdID= 19  "
		::= { iqsrt20CmdEntry 19 }


	iqsrt20RollTrackInput1OnRTAddress OBJECT-TYPE
		SYNTAX		RollCallString
		MAX-ACCESS		read-write
		STATUS			current
		DESCRIPTION
				"TYPE: - Editstring
					On RT Address  cmdID= 35  "
		::= { iqsrt20CmdEntry 35 }


	iqsrt20RollTrackInput1OnRTParams OBJECT-TYPE
		SYNTAX		RollCallString
		MAX-ACCESS		read-write
		STATUS			current
		DESCRIPTION
				"TYPE: - Editstring
					On RT Params  cmdID= 51  "
		::= { iqsrt20CmdEntry 51 }


	iqsrt20RollTrackInput1OffRTAddress OBJECT-TYPE
		SYNTAX		RollCallString
		MAX-ACCESS		read-write
		STATUS			current
		DESCRIPTION
				"TYPE: - Editstring
					Off RT Address  cmdID= 43  "
		::= { iqsrt20CmdEntry 43 }


	iqsrt20RollTrackInput1OffRTParams OBJECT-TYPE
		SYNTAX		RollCallString
		MAX-ACCESS		read-write
		STATUS			current
		DESCRIPTION
				"TYPE: - Editstring
					Off RT Params  cmdID= 59  "
		::= { iqsrt20CmdEntry 59 }


	iqsrt20RollTrackInput2OnRTAddress OBJECT-TYPE
		SYNTAX		RollCallString
		MAX-ACCESS		read-write
		STATUS			current
		DESCRIPTION
				"TYPE: - Editstring
					On RT Address  cmdID= 36  "
		::= { iqsrt20CmdEntry 36 }


	iqsrt20RollTrackInput2OnRTParams OBJECT-TYPE
		SYNTAX		RollCallString
		MAX-ACCESS		read-write
		STATUS			current
		DESCRIPTION
				"TYPE: - Editstring
					On RT Params  cmdID= 52  "
		::= { iqsrt20CmdEntry 52 }


	iqsrt20RollTrackInput2OffRTAddress OBJECT-TYPE
		SYNTAX		RollCallString
		MAX-ACCESS		read-write
		STATUS			current
		DESCRIPTION
				"TYPE: - Editstring
					Off RT Address  cmdID= 44  "
		::= { iqsrt20CmdEntry 44 }


	iqsrt20RollTrackInput2OffRTParams OBJECT-TYPE
		SYNTAX		RollCallString
		MAX-ACCESS		read-write
		STATUS			current
		DESCRIPTION
				"TYPE: - Editstring
					Off RT Params  cmdID= 60  "
		::= { iqsrt20CmdEntry 60 }


	iqsrt20RollTrackInput3OnRTAddress OBJECT-TYPE
		SYNTAX		RollCallString
		MAX-ACCESS		read-write
		STATUS			current
		DESCRIPTION
				"TYPE: - Editstring
					On RT Address  cmdID= 37  "
		::= { iqsrt20CmdEntry 37 }


	iqsrt20RollTrackInput3OnRTParams OBJECT-TYPE
		SYNTAX		RollCallString
		MAX-ACCESS		read-write
		STATUS			current
		DESCRIPTION
				"TYPE: - Editstring
					On RT Params  cmdID= 53  "
		::= { iqsrt20CmdEntry 53 }


	iqsrt20RollTrackInput3OffRTAddress OBJECT-TYPE
		SYNTAX		RollCallString
		MAX-ACCESS		read-write
		STATUS			current
		DESCRIPTION
				"TYPE: - Editstring
					Off RT Address  cmdID= 45  "
		::= { iqsrt20CmdEntry 45 }


	iqsrt20RollTrackInput3OffRTParams OBJECT-TYPE
		SYNTAX		RollCallString
		MAX-ACCESS		read-write
		STATUS			current
		DESCRIPTION
				"TYPE: - Editstring
					Off RT Params  cmdID= 61  "
		::= { iqsrt20CmdEntry 61 }


	iqsrt20RollTrackInput4OnRTAddress OBJECT-TYPE
		SYNTAX		RollCallString
		MAX-ACCESS		read-write
		STATUS			current
		DESCRIPTION
				"TYPE: - Editstring
					On RT Address  cmdID= 38  "
		::= { iqsrt20CmdEntry 38 }


	iqsrt20RollTrackInput4OnRTParams OBJECT-TYPE
		SYNTAX		RollCallString
		MAX-ACCESS		read-write
		STATUS			current
		DESCRIPTION
				"TYPE: - Editstring
					On RT Params  cmdID= 54  "
		::= { iqsrt20CmdEntry 54 }


	iqsrt20RollTrackInput4OffRTAddress OBJECT-TYPE
		SYNTAX		RollCallString
		MAX-ACCESS		read-write
		STATUS			current
		DESCRIPTION
				"TYPE: - Editstring
					Off RT Address  cmdID= 46  "
		::= { iqsrt20CmdEntry 46 }


	iqsrt20RollTrackInput4OffRTParams OBJECT-TYPE
		SYNTAX		RollCallString
		MAX-ACCESS		read-write
		STATUS			current
		DESCRIPTION
				"TYPE: - Editstring
					Off RT Params  cmdID= 62  "
		::= { iqsrt20CmdEntry 62 }


	iqsrt20SetupInhibitInputsInput1 OBJECT-TYPE
		SYNTAX		INTEGER { disable(0), enable(1) }
		MAX-ACCESS		read-write
		STATUS			current
		DESCRIPTION
				"TYPE: - Checkbox
					Input 1  cmdID= 27 "
		::= { iqsrt20CmdEntry 27 }


	iqsrt20SetupInhibitInputsInput2 OBJECT-TYPE
		SYNTAX		INTEGER { disable(0), enable(1) }
		MAX-ACCESS		read-write
		STATUS			current
		DESCRIPTION
				"TYPE: - Checkbox
					Input 2  cmdID= 28 "
		::= { iqsrt20CmdEntry 28 }


	iqsrt20SetupInhibitInputsInput3 OBJECT-TYPE
		SYNTAX		INTEGER { disable(0), enable(1) }
		MAX-ACCESS		read-write
		STATUS			current
		DESCRIPTION
				"TYPE: - Checkbox
					Input 3  cmdID= 29 "
		::= { iqsrt20CmdEntry 29 }


	iqsrt20SetupInhibitInputsInput4 OBJECT-TYPE
		SYNTAX		INTEGER { disable(0), enable(1) }
		MAX-ACCESS		read-write
		STATUS			current
		DESCRIPTION
				"TYPE: - Checkbox
					Input 4  cmdID= 30 "
		::= { iqsrt20CmdEntry 30 }


	iqsrt20SetupPresetUnit OBJECT-TYPE
		SYNTAX		INTEGER { noAction(0),val_Preset_Unit(1) }
		MAX-ACCESS		read-write
		STATUS			current
		DESCRIPTION
				"TYPE: - Button
					Preset Unit  cmdID= 3  value= 1  "
		::= { iqsrt20CmdEntry 3 }


	iqsrt20SetupLoggingInputStatus OBJECT-TYPE
		SYNTAX		INTEGER { disable(0), enable(1) }
		MAX-ACCESS		read-write
		STATUS			current
		DESCRIPTION
				"TYPE: - Checkbox
					Input Status  cmdID= 24 "
		::= { iqsrt20CmdEntry 24 }


	iqsrt20SetupLoggingInputName OBJECT-TYPE
		SYNTAX		INTEGER { disable(0), enable(1) }
		MAX-ACCESS		read-write
		STATUS			current
		DESCRIPTION
				"TYPE: - Checkbox
					Input Name  cmdID= 67 "
		::= { iqsrt20CmdEntry 67 }


	iqsrt20SetupLoggingEDHErrors OBJECT-TYPE
		SYNTAX		INTEGER { disable(0), enable(1) }
		MAX-ACCESS		read-write
		STATUS			current
		DESCRIPTION
				"TYPE: - Checkbox
					EDH Errors  cmdID= 25 "
		::= { iqsrt20CmdEntry 25 }


	iqsrt20SetupSoftwareVersion OBJECT-TYPE
		SYNTAX		RollCallString
		MAX-ACCESS		read-only
		STATUS			current
		DESCRIPTION
				"TYPE: - Display
					Software Version  cmdID= 2  format=   "
		::= { iqsrt20CmdEntry 2 }


	iqsrt20SetupSerialNumber OBJECT-TYPE
		SYNTAX		RollCallString
		MAX-ACCESS		read-only
		STATUS			current
		DESCRIPTION
				"TYPE: - Display
					Serial Number  cmdID= 1  format=   "
		::= { iqsrt20CmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: CH
--
-- MIB ref		: swCardEventLogSlotXX       .2.67.72
-- absolute OID	: 1.3.6.1.4.1.7995.2.6.1.1.XX.2.67.72
-- Vary			: YES
--
-- Value(s)		: 1
--				: 2
--              : 3
--              : 4
-- Comments		: 
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: 525
--				: 625
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary Number	: YES
-- Value(s)		: 
--				: 
-- Comments		: 
--
---------------------------------------------------------------------------------------------------
-- Header		: CH_NAME
--
-- MIB ref		: swCardEventLogSlotXX       .7.67.72.95.78.65.77.69
-- absolute OID	: 1.3.6.1.4.1.7995.2.6.1.1.XX.7.67.72.95.78.65.77.69
-- Vary			: YES
--
-- Value(s)		: INPUT_1
--				: INPUT_2
--				: INPUT_3
--				: INPUT_4
-- Comments		: 
--
---------------------------------------------------------------------------------------------------
