-- ************************************************************************************
-- Snell&Wilcox Card:IQDLY21
--        Module Id#:403
--       Command Set:6
--          Filename:SNELL-IQDLY21-CMD-MIB.mib
--            Author:b baker
--              Date:12/01/2009
--              Time:13:11
--
-- Copyright (c) 2005 Snell & Wilcox Ltd
-- All rights reserved.
--
-- ************************************************************************************

SNELL-IQDLY21-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDLY21,
    moduleIQDLY21MIB
        FROM SNELL-WILCOX-PRODUCT-REG;

 moduleIQDLY21CmdMi MODULE-IDENTITY
    LAST-UPDATED "0901121311Z"
    ORGANIZATION "Snell & Wilcox Ltd"
    CONTACT-INFO
        "Primary Author:b baker

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDLY21MIB 1 }




--********************************************************************************
--*
--*  Snell Wilcox Card:
--*  command set:
--*  list commands/menus:
--*
--******************************************************************************
	iqdly21CmdTable OBJECT-TYPE
		SYNTAX			SEQUENCE OF Iqdly21CmdEntry
		MAX-ACCESS		not-accessible
		STATUS			current
		DESCRIPTION
				"Note the instance of this table is relected in the command set Version"
		::= { moduleIQDLY21 1 }

	iqdly21CmdEntry OBJECT-TYPE
		SYNTAX		Iqdly21CmdEntry
		MAX-ACCESS		not-accessible
		STATUS			current
		DESCRIPTION
				"Entry in command table."
		INDEX	{ iqdly21SlotIndex }
		::= { iqdly21CmdTable 1 }

	Iqdly21CmdEntry ::=
		SEQUENCE {
			iqdly21SlotIndex
				Unsigned32,
			iqdly21AudioAESOutputAES1Source
				INTEGER,
			iqdly21AudioAESOutputAES2Source
				INTEGER,
			iqdly21AudioAnalogOutAnalog1Source
				INTEGER,
			iqdly21AudioProcAmpStereo13324
				INTEGER,
			iqdly21ProcAmpAES1LGainAES1L
				INTEGER,
			iqdly21ProcAmpAES1LInvert
				INTEGER,
			iqdly21ProcAmpAES1LMute
				INTEGER,
			iqdly21ProcAmpAES1RGainAES1R
				INTEGER,
			iqdly21ProcAmpAES1RInvert
				INTEGER,
			iqdly21ProcAmpAES1RMute
				INTEGER,
			iqdly21AudioProcAmpStereo2
				INTEGER,
			iqdly21ProcAmpAES2LGainAES2L
				INTEGER,
			iqdly21ProcAmpAES2LInvert
				INTEGER,
			iqdly21ProcAmpAES2LMute
				INTEGER,
			iqdly21ProcAmpAES2RGainAES2R
				INTEGER,
			iqdly21ProcAmpAES2RInvert
				INTEGER,
			iqdly21ProcAmpAES2RMute
				INTEGER,
			iqdly21AudioProcAmpStereo13326
				INTEGER,
			iqdly21ProcAmpAnalog1LGainAnalog1L
				INTEGER,
			iqdly21ProcAmpAnalog1LInvert
				INTEGER,
			iqdly21ProcAmpAnalog1LMute
				INTEGER,
			iqdly21ProcAmpAnalog1RGainAnalog1R
				INTEGER,
			iqdly21ProcAmpAnalog1RInvert
				INTEGER,
			iqdly21ProcAmpAnalog1RMute
				INTEGER,
			iqdly21Mixer1Mix1Source1
				INTEGER,
			iqdly21MixMixer1Gain1
				INTEGER,
			iqdly21Mixer1Mix1Source2
				INTEGER,
			iqdly21MixMixer1Gain2
				INTEGER,
			iqdly21Mixer1Mix1Source3
				INTEGER,
			iqdly21MixMixer1Gain3
				INTEGER,
			iqdly21Mixer1Mix1Source4
				INTEGER,
			iqdly21MixMixer1Gain4
				INTEGER,
			iqdly21Mixer2Mix2Source1
				INTEGER,
			iqdly21MixMixer2Gain1
				INTEGER,
			iqdly21Mixer2Mix2Source2
				INTEGER,
			iqdly21MixMixer2Gain2
				INTEGER,
			iqdly21Mixer2Mix2Source3
				INTEGER,
			iqdly21MixMixer2Gain3
				INTEGER,
			iqdly21Mixer2Mix2Source4
				INTEGER,
			iqdly21MixMixer2Gain4
				INTEGER,
			iqdly21Mixer3Mix3Source1
				INTEGER,
			iqdly21MixMixer3Gain1
				INTEGER,
			iqdly21Mixer3Mix3Source2
				INTEGER,
			iqdly21MixMixer3Gain2
				INTEGER,
			iqdly21Mixer3Mix3Source3
				INTEGER,
			iqdly21MixMixer3Gain3
				INTEGER,
			iqdly21Mixer3Mix3Source4
				INTEGER,
			iqdly21MixMixer3Gain4
				INTEGER,
			iqdly21Mixer4Mix4Source1
				INTEGER,
			iqdly21MixMixer4Gain1
				INTEGER,
			iqdly21Mixer4Mix4Source2
				INTEGER,
			iqdly21MixMixer4Gain2
				INTEGER,
			iqdly21Mixer4Mix4Source3
				INTEGER,
			iqdly21MixMixer4Gain3
				INTEGER,
			iqdly21Mixer4Mix4Source4
				INTEGER,
			iqdly21MixMixer4Gain4
				INTEGER,
			iqdly21BusSourceBusALSource
				INTEGER,
			iqdly21BusSourceBusARSource
				INTEGER,
			iqdly21BusSourceBusBLSource
				INTEGER,
			iqdly21BusSourceBusBRSource
				INTEGER,
			iqdly21BusSourceBusCLSource
				INTEGER,
			iqdly21BusSourceBusCRSource
				INTEGER,
			iqdly21BusSourceBusDLSource
				INTEGER,
			iqdly21BusSourceBusDRSource
				INTEGER,
			iqdly21BusesBusProcAmpStereoA
				INTEGER,
			iqdly21BusProcAmpBusALGainBusAL
				INTEGER,
			iqdly21BusProcAmpBusALInvert
				INTEGER,
			iqdly21BusProcAmpBusALMute
				INTEGER,
			iqdly21BusProcAmpBusARGainBusAR
				INTEGER,
			iqdly21BusProcAmpBusARInvert
				INTEGER,
			iqdly21BusProcAmpBusARMute
				INTEGER,
			iqdly21BusesBusProcAmpStereoB
				INTEGER,
			iqdly21BusProcAmpBusBLGainBusBL
				INTEGER,
			iqdly21BusProcAmpBusBLInvert
				INTEGER,
			iqdly21BusProcAmpBusBLMute
				INTEGER,
			iqdly21BusProcAmpBusBRGainBusBR
				INTEGER,
			iqdly21BusProcAmpBusBRInvert
				INTEGER,
			iqdly21BusProcAmpBusBRMute
				INTEGER,
			iqdly21BusesBusProcAmpStereoC
				INTEGER,
			iqdly21BusProcAmpBusCLGainBusCL
				INTEGER,
			iqdly21BusProcAmpBusCLInvert
				INTEGER,
			iqdly21BusProcAmpBusCLMute
				INTEGER,
			iqdly21BusProcAmpBusCRGainBusCR
				INTEGER,
			iqdly21BusProcAmpBusCRInvert
				INTEGER,
			iqdly21BusProcAmpBusCRMute
				INTEGER,
			iqdly21BusesBusProcAmpStereoD
				INTEGER,
			iqdly21BusProcAmpBusDLGainBusDL
				INTEGER,
			iqdly21BusProcAmpBusDLInvert
				INTEGER,
			iqdly21BusProcAmpBusDLMute
				INTEGER,
			iqdly21BusProcAmpBusDRGainBusDR
				INTEGER,
			iqdly21BusProcAmpBusDRInvert
				INTEGER,
			iqdly21BusProcAmpBusDRMute
				INTEGER,
			iqdly21AudioDelayAESInput1Delay
				INTEGER,
			iqdly21AudioDelayAESInput2Delay
				INTEGER,
			iqdly21AudioDelayAnalogIn1Delay
				INTEGER,
			iqdly21DelayDelaySelectManual
				INTEGER,
			iqdly21DelayDelaySelectRolltrack14
				INTEGER,
			iqdly21DelayDelaySelectRolltrack15
				INTEGER,
			iqdly21DelayDelaySelectRolltrack16
				INTEGER,
			iqdly21DelayDelaySelectRolltrack17
				INTEGER,
			iqdly21DelayDelaySelectGPIDelaySelect
				INTEGER,
			iqdly21DelayDelayStatus
				INTEGER,
			iqdly21DelayDelayStatusRolltrack14
				RollCallString,
			iqdly21DelayDelayStatusRolltrack15
				RollCallString,
			iqdly21DelayDelayStatusRolltrack16
				RollCallString,
			iqdly21DelayDelayStatusRolltrack17
				RollCallString,
			iqdly21DelayDelayStatusGPIDelayDisplay
				RollCallString,
			iqdly21DelayDelayStatusTotalDelayDisplay
				RollCallString,
			iqdly21AudioMonitorSilenceLevel
				INTEGER,
			iqdly21AudioMonitorLowLevel
				INTEGER,
			iqdly21AudioMonitorHighLevel
				INTEGER,
			iqdly21AudioMonitorOverloadLevel
				INTEGER,
			iqdly21AudioMonitorWarningTimer
				INTEGER,
			iqdly21Genlock
				INTEGER,
			iqdly21GenlockFreerunFreq
				INTEGER,
			iqdly21UserMemMemory1Save1
				INTEGER,
			iqdly21UserMemMemory1Recall1
				INTEGER,
			iqdly21UserMemMemory1Clear1
				INTEGER,
			iqdly21UserMemMemory1Name1
				RollCallString,
			iqdly21UserMemMemory2Save2
				INTEGER,
			iqdly21UserMemMemory2Recall2
				INTEGER,
			iqdly21UserMemMemory2Clear2
				INTEGER,
			iqdly21UserMemMemory2Name2
				RollCallString,
			iqdly21UserMemMemory3Save3
				INTEGER,
			iqdly21UserMemMemory3Recall3
				INTEGER,
			iqdly21UserMemMemory3Clear3
				INTEGER,
			iqdly21UserMemMemory3Name3
				RollCallString,
			iqdly21UserMemMemory4Save4
				INTEGER,
			iqdly21UserMemMemory4Recall4
				INTEGER,
			iqdly21UserMemMemory4Clear4
				INTEGER,
			iqdly21UserMemMemory4Name4
				RollCallString,
			iqdly21UserMemMemory5Save5
				INTEGER,
			iqdly21UserMemMemory5Recall5
				INTEGER,
			iqdly21UserMemMemory5Clear5
				INTEGER,
			iqdly21UserMemMemory5Name5
				RollCallString,
			iqdly21UserMemMemory6Save6
				INTEGER,
			iqdly21UserMemMemory6Recall6
				INTEGER,
			iqdly21UserMemMemory6Clear6
				INTEGER,
			iqdly21UserMemMemory6Name6
				RollCallString,
			iqdly21UserMemMemory7Save7
				INTEGER,
			iqdly21UserMemMemory7Recall7
				INTEGER,
			iqdly21UserMemMemory7Clear7
				INTEGER,
			iqdly21UserMemMemory7Name7
				RollCallString,
			iqdly21UserMemMemory8Save8
				INTEGER,
			iqdly21UserMemMemory8Recall8
				INTEGER,
			iqdly21UserMemMemory8Clear8
				INTEGER,
			iqdly21UserMemMemory8Name8
				RollCallString,
			iqdly21SetupAudioToneIdentEnable
				INTEGER,
			iqdly21SetupAudioToneFrequency
				INTEGER,
			iqdly21SetupAudioToneFrequencyR
				INTEGER,
			iqdly21SetupAudioToneHeadRoom
				INTEGER,
			iqdly21SetupAudioToneLineUp
				INTEGER,
			iqdly21SetupAudioToneADCLineUp
				INTEGER,
			iqdly21SetupSlewRate
				INTEGER,
			iqdly21SetupChannelStatus
				RollCallString,
			iqdly21GPIIOGPIInputDisableInputs
				INTEGER,
			iqdly21GPIIOGPIInputInputTimerEnable
				INTEGER,
			iqdly21GPIIOGPIInputTimerActiveHigh
				INTEGER,
			iqdly21GPIIOGPIInputInputSelection
				INTEGER,
			iqdly21GPIIOGPIInputGPIInStatus
				RollCallString,
			iqdly21GPIIOGPIOutputOutActiveHigh
				INTEGER,
			iqdly21GPIIOGPIOutputOutputSelection
				INTEGER,
			iqdly21GPIIOGPIOutputGPIOutStatus
				RollCallString,
			iqdly21GPIIOGPIInputOutputGPIO1
				INTEGER,
			iqdly21SetupGPIIOInputSelection
				INTEGER,
			iqdly21SetupGPIIOOutputSelection
				INTEGER,
			iqdly21SetupRollTrackRollTrackIndex1495
				INTEGER,
			iqdly21SetupRollTrackRollTrackSource1496
				INTEGER,
			iqdly21SetupRollTrackRollTrackDisable
				INTEGER,
			iqdly21SetupRollTrackRollTrackAddress1497
				RollCallString,
			iqdly21SetupRollTrackRollTrackCommand1498
				RollCallString,
			iqdly21SetupRollTrackRollTrackSending
				RollCallString,
			iqdly21SetupRollTrackRollTrackStatus
				RollCallString,
			iqdly21SetupRollTrackRollTrackIndex2870
				INTEGER,
			iqdly21SetupRollTrackRollTrackSource2871
				INTEGER,
			iqdly21SetupRollTrackRollTrackAddress2872
				RollCallString,
			iqdly21SetupRollTrackRollTrackCommand2873
				RollCallString,
			iqdly21SetupLoggingReference
				INTEGER,
			iqdly21SetupLoggingRollTrack
				INTEGER,
			iqdly21SetupLoggingAES1
				INTEGER,
			iqdly21SetupLoggingAES2
				INTEGER,
			iqdly21SetupLoggingBusAL
				INTEGER,
			iqdly21SetupLoggingBusAR
				INTEGER,
			iqdly21SetupLoggingBusBL
				INTEGER,
			iqdly21SetupLoggingBusBR
				INTEGER,
			iqdly21SetupLoggingBusCL
				INTEGER,
			iqdly21SetupLoggingBusCR
				INTEGER,
			iqdly21SetupLoggingBusDL
				INTEGER,
			iqdly21SetupLoggingBusDR
				INTEGER,
			iqdly21SetupLoggingFault
				INTEGER,
			iqdly21SetupLoggingStatusEXTREF
				RollCallString,
			iqdly21SetupLoggingStatusROLLTRACK
				RollCallString,
			iqdly21SetupLoggingStatusAES1
				RollCallString,
			iqdly21SetupLoggingStatusAES2
				RollCallString,
			iqdly21SetupLoggingStatusBUSAL
				RollCallString,
			iqdly21SetupLoggingStatusBUSAR
				RollCallString,
			iqdly21SetupLoggingStatusBUSBL
				RollCallString,
			iqdly21SetupLoggingStatusBUSBR
				RollCallString,
			iqdly21SetupLoggingStatusBUSCL
				RollCallString,
			iqdly21SetupLoggingStatusBUSCR
				RollCallString,
			iqdly21SetupLoggingStatusBUSDL
				RollCallString,
			iqdly21SetupLoggingStatusBUSDR
				RollCallString,
			iqdly21SetupLoggingStatusFAULT
				RollCallString,
			iqdly21SetupUnitSoftwareVersion
				RollCallString,
			iqdly21SetupUnitSerialNo
				RollCallString,
			iqdly21SetupUnitPresetUnit
				INTEGER,
			iqdly21SetupUnitRestart
				INTEGER,
			iqdly21SetupUnitBuildNo
				RollCallString
		}

	iqdly21SlotIndex OBJECT-TYPE
		SYNTAX		Unsigned32
		MAX-ACCESS		not-accessible
		STATUS			current
		DESCRIPTION
				"The unique Index value for each slot.  Its value
					ranges between 1 and the value of slotNumber."
		::= { iqdly21CmdEntry 0 }


	iqdly21AudioAESOutputAES1Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- AES Output
					AES 1 Source  cmdID= 2951 
					BUS A  value= 0  
					BUS B  value= 1  
					BUS C  value= 2  
					BUS D  value= 3  
					AES 1 Direct  value= 4  
					AES 2 Direct  value= 5  
					Test tone  value= 6  
					Silence  value= 7  "
		::= { iqdly21CmdEntry 2951 }


	iqdly21AudioAESOutputAES2Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- AES Output
					AES 2 Source  cmdID= 2952 
					BUS A  value= 0  
					BUS B  value= 1  
					BUS C  value= 2  
					BUS D  value= 3  
					AES 1 Direct  value= 4  
					AES 2 Direct  value= 5  
					Test tone  value= 6  
					Silence  value= 7  "
		::= { iqdly21CmdEntry 2952 }


	iqdly21AudioAnalogOutAnalog1Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Analog Out
					Analog 1 Source  cmdID= 2961 
					BUS A  value= 0  
					BUS B  value= 1  
					BUS C  value= 2  
					BUS D  value= 3  
					Test tone  value= 4  
					Silence  value= 5  "
		::= { iqdly21CmdEntry 2961 }


	iqdly21AudioProcAmpStereo13324 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqdly21CmdEntry 3324 }


	iqdly21ProcAmpAES1LGainAES1L OBJECT-TYPE
		SYNTAX		INTEGER
		MAX-ACCESS		read-write
		STATUS			current
		DESCRIPTION
				"TYPE: - Number
				 PAGE: - Audio- ProcAmp
					Gain AES 1L  cmdID= 3088  min= -180  max= 180  step= 1  format= %0.1fdB  div_scale= 10 
					Min = -18.0dB  Max = 18.0dB  Step = 0.1dB "
		::= { iqdly21CmdEntry 3088 }


	iqdly21ProcAmpAES1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqdly21CmdEntry 3168 }


	iqdly21ProcAmpAES1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqdly21CmdEntry 3248 }


	iqdly21ProcAmpAES1RGainAES1R OBJECT-TYPE
		SYNTAX		INTEGER
		MAX-ACCESS		read-write
		STATUS			current
		DESCRIPTION
				"TYPE: - Number
				 PAGE: - Audio- ProcAmp
					Gain AES 1R  cmdID= 3089  min= -180  max= 180  step= 1  format= %0.1fdB  div_scale= 10 
					Min = -18.0dB  Max = 18.0dB  Step = 0.1dB "
		::= { iqdly21CmdEntry 3089 }


	iqdly21ProcAmpAES1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqdly21CmdEntry 3169 }


	iqdly21ProcAmpAES1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqdly21CmdEntry 3249 }


	iqdly21AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqdly21CmdEntry 3325 }


	iqdly21ProcAmpAES2LGainAES2L OBJECT-TYPE
		SYNTAX		INTEGER
		MAX-ACCESS		read-write
		STATUS			current
		DESCRIPTION
				"TYPE: - Number
				 PAGE: - Audio- ProcAmp
					Gain AES 2L  cmdID= 3090  min= -180  max= 180  step= 1  format= %0.1fdB  div_scale= 10 
					Min = -18.0dB  Max = 18.0dB  Step = 0.1dB "
		::= { iqdly21CmdEntry 3090 }


	iqdly21ProcAmpAES2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqdly21CmdEntry 3170 }


	iqdly21ProcAmpAES2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqdly21CmdEntry 3250 }


	iqdly21ProcAmpAES2RGainAES2R OBJECT-TYPE
		SYNTAX		INTEGER
		MAX-ACCESS		read-write
		STATUS			current
		DESCRIPTION
				"TYPE: - Number
				 PAGE: - Audio- ProcAmp
					Gain AES 2R  cmdID= 3091  min= -180  max= 180  step= 1  format= %0.1fdB  div_scale= 10 
					Min = -18.0dB  Max = 18.0dB  Step = 0.1dB "
		::= { iqdly21CmdEntry 3091 }


	iqdly21ProcAmpAES2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqdly21CmdEntry 3171 }


	iqdly21ProcAmpAES2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqdly21CmdEntry 3251 }


	iqdly21AudioProcAmpStereo13326 OBJECT-TYPE
		SYNTAX		INTEGER { disable(0), enable(1) }
		MAX-ACCESS		read-write
		STATUS			current
		DESCRIPTION
				"TYPE: - Checkbox
				 PAGE: - Audio- ProcAmp
					Stereo 1  cmdID= 3326 "
		::= { iqdly21CmdEntry 3326 }


	iqdly21ProcAmpAnalog1LGainAnalog1L OBJECT-TYPE
		SYNTAX		INTEGER
		MAX-ACCESS		read-write
		STATUS			current
		DESCRIPTION
				"TYPE: - Number
				 PAGE: - Audio- ProcAmp
					Gain Analog 1L  cmdID= 3092  min= -180  max= 180  step= 1  format= %0.1fdB  div_scale= 10 
					Min = -18.0dB  Max = 18.0dB  Step = 0.1dB "
		::= { iqdly21CmdEntry 3092 }


	iqdly21ProcAmpAnalog1LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqdly21CmdEntry 3172 }


	iqdly21ProcAmpAnalog1LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqdly21CmdEntry 3252 }


	iqdly21ProcAmpAnalog1RGainAnalog1R OBJECT-TYPE
		SYNTAX		INTEGER
		MAX-ACCESS		read-write
		STATUS			current
		DESCRIPTION
				"TYPE: - Number
				 PAGE: - Audio- ProcAmp
					Gain Analog 1R  cmdID= 3093  min= -180  max= 180  step= 1  format= %0.1fdB  div_scale= 10 
					Min = -18.0dB  Max = 18.0dB  Step = 0.1dB "
		::= { iqdly21CmdEntry 3093 }


	iqdly21ProcAmpAnalog1RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqdly21CmdEntry 3173 }


	iqdly21ProcAmpAnalog1RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqdly21CmdEntry 3253 }


	iqdly21Mixer1Mix1Source1 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 1- Mix1 Source1
					Mix1 Source1  cmdID= 3440 
					AES 1L  value= 0  
					AES 1R  value= 1  
					AES 2L  value= 2  
					AES 2R  value= 3  
					Analog 1L  value= 4  
					Analog 1R  value= 5  "
		::= { iqdly21CmdEntry 3440 }


	iqdly21MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1 
					Min = -71dB  Max = 0dB  Step = 1dB "
		::= { iqdly21CmdEntry 3360 }


	iqdly21Mixer1Mix1Source2 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 1- Mix1 Source2
					Mix1 Source2  cmdID= 3441 
					AES 1L  value= 0  
					AES 1R  value= 1  
					AES 2L  value= 2  
					AES 2R  value= 3  
					Analog 1L  value= 4  
					Analog 1R  value= 5  "
		::= { iqdly21CmdEntry 3441 }


	iqdly21MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1 
					Min = -71dB  Max = 0dB  Step = 1dB "
		::= { iqdly21CmdEntry 3361 }


	iqdly21Mixer1Mix1Source3 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 1- Mix1 Source3
					Mix1 Source3  cmdID= 3442 
					AES 1L  value= 0  
					AES 1R  value= 1  
					AES 2L  value= 2  
					AES 2R  value= 3  
					Analog 1L  value= 4  
					Analog 1R  value= 5  "
		::= { iqdly21CmdEntry 3442 }


	iqdly21MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1 
					Min = -71dB  Max = 0dB  Step = 1dB "
		::= { iqdly21CmdEntry 3362 }


	iqdly21Mixer1Mix1Source4 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 1- Mix1 Source4
					Mix1 Source4  cmdID= 3443 
					AES 1L  value= 0  
					AES 1R  value= 1  
					AES 2L  value= 2  
					AES 2R  value= 3  
					Analog 1L  value= 4  
					Analog 1R  value= 5  "
		::= { iqdly21CmdEntry 3443 }


	iqdly21MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1 
					Min = -71dB  Max = 0dB  Step = 1dB "
		::= { iqdly21CmdEntry 3363 }


	iqdly21Mixer2Mix2Source1 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 2- Mix2 Source1
					Mix2 Source1  cmdID= 3444 
					AES 1L  value= 0  
					AES 1R  value= 1  
					AES 2L  value= 2  
					AES 2R  value= 3  
					Analog 1L  value= 4  
					Analog 1R  value= 5  "
		::= { iqdly21CmdEntry 3444 }


	iqdly21MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1 
					Min = -71dB  Max = 0dB  Step = 1dB "
		::= { iqdly21CmdEntry 3364 }


	iqdly21Mixer2Mix2Source2 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 2- Mix2 Source2
					Mix2 Source2  cmdID= 3445 
					AES 1L  value= 0  
					AES 1R  value= 1  
					AES 2L  value= 2  
					AES 2R  value= 3  
					Analog 1L  value= 4  
					Analog 1R  value= 5  "
		::= { iqdly21CmdEntry 3445 }


	iqdly21MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1 
					Min = -71dB  Max = 0dB  Step = 1dB "
		::= { iqdly21CmdEntry 3365 }


	iqdly21Mixer2Mix2Source3 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 2- Mix2 Source3
					Mix2 Source3  cmdID= 3446 
					AES 1L  value= 0  
					AES 1R  value= 1  
					AES 2L  value= 2  
					AES 2R  value= 3  
					Analog 1L  value= 4  
					Analog 1R  value= 5  "
		::= { iqdly21CmdEntry 3446 }


	iqdly21MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1 
					Min = -71dB  Max = 0dB  Step = 1dB "
		::= { iqdly21CmdEntry 3366 }


	iqdly21Mixer2Mix2Source4 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 2- Mix2 Source4
					Mix2 Source4  cmdID= 3447 
					AES 1L  value= 0  
					AES 1R  value= 1  
					AES 2L  value= 2  
					AES 2R  value= 3  
					Analog 1L  value= 4  
					Analog 1R  value= 5  "
		::= { iqdly21CmdEntry 3447 }


	iqdly21MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1 
					Min = -71dB  Max = 0dB  Step = 1dB "
		::= { iqdly21CmdEntry 3367 }


	iqdly21Mixer3Mix3Source1 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 3- Mix3 Source1
					Mix3 Source1  cmdID= 3448 
					AES 1L  value= 0  
					AES 1R  value= 1  
					AES 2L  value= 2  
					AES 2R  value= 3  
					Analog 1L  value= 4  
					Analog 1R  value= 5  "
		::= { iqdly21CmdEntry 3448 }


	iqdly21MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1 
					Min = -71dB  Max = 0dB  Step = 1dB "
		::= { iqdly21CmdEntry 3368 }


	iqdly21Mixer3Mix3Source2 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 3- Mix3 Source2
					Mix3 Source2  cmdID= 3449 
					AES 1L  value= 0  
					AES 1R  value= 1  
					AES 2L  value= 2  
					AES 2R  value= 3  
					Analog 1L  value= 4  
					Analog 1R  value= 5  "
		::= { iqdly21CmdEntry 3449 }


	iqdly21MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1 
					Min = -71dB  Max = 0dB  Step = 1dB "
		::= { iqdly21CmdEntry 3369 }


	iqdly21Mixer3Mix3Source3 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 3- Mix3 Source3
					Mix3 Source3  cmdID= 3450 
					AES 1L  value= 0  
					AES 1R  value= 1  
					AES 2L  value= 2  
					AES 2R  value= 3  
					Analog 1L  value= 4  
					Analog 1R  value= 5  "
		::= { iqdly21CmdEntry 3450 }


	iqdly21MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1 
					Min = -71dB  Max = 0dB  Step = 1dB "
		::= { iqdly21CmdEntry 3370 }


	iqdly21Mixer3Mix3Source4 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 3- Mix3 Source4
					Mix3 Source4  cmdID= 3451 
					AES 1L  value= 0  
					AES 1R  value= 1  
					AES 2L  value= 2  
					AES 2R  value= 3  
					Analog 1L  value= 4  
					Analog 1R  value= 5  "
		::= { iqdly21CmdEntry 3451 }


	iqdly21MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1 
					Min = -71dB  Max = 0dB  Step = 1dB "
		::= { iqdly21CmdEntry 3371 }


	iqdly21Mixer4Mix4Source1 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 4- Mix4 Source1
					Mix4 Source1  cmdID= 3452 
					AES 1L  value= 0  
					AES 1R  value= 1  
					AES 2L  value= 2  
					AES 2R  value= 3  
					Analog 1L  value= 4  
					Analog 1R  value= 5  "
		::= { iqdly21CmdEntry 3452 }


	iqdly21MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1 
					Min = -71dB  Max = 0dB  Step = 1dB "
		::= { iqdly21CmdEntry 3372 }


	iqdly21Mixer4Mix4Source2 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 4- Mix4 Source2
					Mix4 Source2  cmdID= 3453 
					AES 1L  value= 0  
					AES 1R  value= 1  
					AES 2L  value= 2  
					AES 2R  value= 3  
					Analog 1L  value= 4  
					Analog 1R  value= 5  "
		::= { iqdly21CmdEntry 3453 }


	iqdly21MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1 
					Min = -71dB  Max = 0dB  Step = 1dB "
		::= { iqdly21CmdEntry 3373 }


	iqdly21Mixer4Mix4Source3 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 4- Mix4 Source3
					Mix4 Source3  cmdID= 3454 
					AES 1L  value= 0  
					AES 1R  value= 1  
					AES 2L  value= 2  
					AES 2R  value= 3  
					Analog 1L  value= 4  
					Analog 1R  value= 5  "
		::= { iqdly21CmdEntry 3454 }


	iqdly21MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1 
					Min = -71dB  Max = 0dB  Step = 1dB "
		::= { iqdly21CmdEntry 3374 }


	iqdly21Mixer4Mix4Source4 OBJECT-TYPE
		SYNTAX		INTEGER {
							val_AES_1L(0),
							val_AES_1R(1),
							val_AES_2L(2),
							val_AES_2R(3),
							val_Analog_1L(4),
							val_Analog_1R(5)
							}
		MAX-ACCESS		read-write
		STATUS			current
		DESCRIPTION
				"TYPE: - RadiobuttonList
				 PAGE: - Audio- Mix- Mixer 4- Mix4 Source4
					Mix4 Source4  cmdID= 3455 
					AES 1L  value= 0  
					AES 1R  value= 1  
					AES 2L  value= 2  
					AES 2R  value= 3  
					Analog 1L  value= 4  
					Analog 1R  value= 5  "
		::= { iqdly21CmdEntry 3455 }


	iqdly21MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1 
					Min = -71dB  Max = 0dB  Step = 1dB "
		::= { iqdly21CmdEntry 3375 }


	iqdly21BusSourceBusALSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusAL Source
					BusAL Source  cmdID= 3520 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3520 }


	iqdly21BusSourceBusARSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusAR Source
					BusAR Source  cmdID= 3521 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3521 }


	iqdly21BusSourceBusBLSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusBL Source
					BusBL Source  cmdID= 3522 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3522 }


	iqdly21BusSourceBusBRSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusBR Source
					BusBR Source  cmdID= 3523 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3523 }


	iqdly21BusSourceBusCLSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusCL Source
					BusCL Source  cmdID= 3524 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3524 }


	iqdly21BusSourceBusCRSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusCR Source
					BusCR Source  cmdID= 3525 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3525 }


	iqdly21BusSourceBusDLSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusDL Source
					BusDL Source  cmdID= 3526 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3526 }


	iqdly21BusSourceBusDRSource OBJECT-TYPE
		SYNTAX		INTEGER {
							val_AES_1L(0),
							val_AES_1R(1),
							val_AES_2L(2),
							val_AES_2R(3),
							val_Analog_1L(4),
							val_Analog_1R(5),
							val_MIX_1(6),
							val_MIX_2(7),
							val_MIX_3(8),
							val_MIX_4(9)
							}
		MAX-ACCESS		read-write
		STATUS			current
		DESCRIPTION
				"TYPE: - RadiobuttonList
				 PAGE: - Audio- Buses- Bus Source- BusDR Source
					BusDR Source  cmdID= 3527 
					AES 1L  value= 0  
					AES 1R  value= 1  
					AES 2L  value= 2  
					AES 2R  value= 3  
					Analog 1L  value= 4  
					Analog 1R  value= 5  
					MIX 1  value= 6  
					MIX 2  value= 7  
					MIX 3  value= 8  
					MIX 4  value= 9  "
		::= { iqdly21CmdEntry 3527 }


	iqdly21BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqdly21CmdEntry 3320 }


	iqdly21BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10 
					Min = -18.0dB  Max = 18.0dB  Step = 0.1dB "
		::= { iqdly21CmdEntry 3080 }


	iqdly21BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqdly21CmdEntry 3160 }


	iqdly21BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqdly21CmdEntry 3240 }


	iqdly21BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10 
					Min = -18.0dB  Max = 18.0dB  Step = 0.1dB "
		::= { iqdly21CmdEntry 3081 }


	iqdly21BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqdly21CmdEntry 3161 }


	iqdly21BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqdly21CmdEntry 3241 }


	iqdly21BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqdly21CmdEntry 3321 }


	iqdly21BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10 
					Min = -18.0dB  Max = 18.0dB  Step = 0.1dB "
		::= { iqdly21CmdEntry 3082 }


	iqdly21BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqdly21CmdEntry 3162 }


	iqdly21BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqdly21CmdEntry 3242 }


	iqdly21BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10 
					Min = -18.0dB  Max = 18.0dB  Step = 0.1dB "
		::= { iqdly21CmdEntry 3083 }


	iqdly21BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqdly21CmdEntry 3163 }


	iqdly21BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqdly21CmdEntry 3243 }


	iqdly21BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqdly21CmdEntry 3322 }


	iqdly21BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10 
					Min = -18.0dB  Max = 18.0dB  Step = 0.1dB "
		::= { iqdly21CmdEntry 3084 }


	iqdly21BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqdly21CmdEntry 3164 }


	iqdly21BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqdly21CmdEntry 3244 }


	iqdly21BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10 
					Min = -18.0dB  Max = 18.0dB  Step = 0.1dB "
		::= { iqdly21CmdEntry 3085 }


	iqdly21BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqdly21CmdEntry 3165 }


	iqdly21BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqdly21CmdEntry 3245 }


	iqdly21BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqdly21CmdEntry 3323 }


	iqdly21BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10 
					Min = -18.0dB  Max = 18.0dB  Step = 0.1dB "
		::= { iqdly21CmdEntry 3086 }


	iqdly21BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqdly21CmdEntry 3166 }


	iqdly21BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqdly21CmdEntry 3246 }


	iqdly21BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10 
					Min = -18.0dB  Max = 18.0dB  Step = 0.1dB "
		::= { iqdly21CmdEntry 3087 }


	iqdly21BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqdly21CmdEntry 3167 }


	iqdly21BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqdly21CmdEntry 3247 }


	iqdly21AudioDelayAESInput1Delay OBJECT-TYPE
		SYNTAX		INTEGER
		MAX-ACCESS		read-write
		STATUS			current
		DESCRIPTION
				"TYPE: - Number
				 PAGE: - Audio- Delay
					AES Input 1 Delay  cmdID= 2928  min= 0  max= 1500  step= 1  format= %0.0f ms  div_scale= 1 
					Min = 0 ms  Max = 1500 ms  Step = 1 ms "
		::= { iqdly21CmdEntry 2928 }


	iqdly21AudioDelayAESInput2Delay OBJECT-TYPE
		SYNTAX		INTEGER
		MAX-ACCESS		read-write
		STATUS			current
		DESCRIPTION
				"TYPE: - Number
				 PAGE: - Audio- Delay
					AES Input 2 Delay  cmdID= 2929  min= 0  max= 1500  step= 1  format= %0.0f ms  div_scale= 1 
					Min = 0 ms  Max = 1500 ms  Step = 1 ms "
		::= { iqdly21CmdEntry 2929 }


	iqdly21AudioDelayAnalogIn1Delay OBJECT-TYPE
		SYNTAX		INTEGER
		MAX-ACCESS		read-write
		STATUS			current
		DESCRIPTION
				"TYPE: - Number
				 PAGE: - Audio- Delay
					Analog In 1 Delay  cmdID= 2930  min= 0  max= 1500  step= 1  format= %0.0f ms  div_scale= 1 
					Min = 0 ms  Max = 1500 ms  Step = 1 ms "
		::= { iqdly21CmdEntry 2930 }


	iqdly21DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqdly21CmdEntry 2568 }


	iqdly21DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqdly21CmdEntry 2569 }


	iqdly21DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqdly21CmdEntry 2570 }


	iqdly21DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqdly21CmdEntry 2571 }


	iqdly21DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqdly21CmdEntry 2572 }


	iqdly21DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqdly21CmdEntry 3051 }


	iqdly21DelayDelayStatus OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1 
					Manual  cmdID= 2573  format=   
					Min = -40 ms  Max = 1500 ms  Step =   1 ms "
		::= { iqdly21CmdEntry 2573 }


	iqdly21DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqdly21CmdEntry 14 }


	iqdly21DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqdly21CmdEntry 15 }


	iqdly21DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqdly21CmdEntry 16 }


	iqdly21DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqdly21CmdEntry 17 }


	iqdly21DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqdly21CmdEntry 3052 }


	iqdly21DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqdly21CmdEntry 2979 }


	iqdly21AudioMonitorSilenceLevel OBJECT-TYPE
		SYNTAX		INTEGER
		MAX-ACCESS		read-write
		STATUS			current
		DESCRIPTION
				"TYPE: - Number
				 PAGE: - Audio- Monitor
					Silence Level  cmdID= 3056  min= -80  max= 0  step= 1  format= %1.1f dB  div_scale= 1 
					Min = -80.0 dB  Max = 0.0 dB  Step = 1.0 dB "
		::= { iqdly21CmdEntry 3056 }


	iqdly21AudioMonitorLowLevel OBJECT-TYPE
		SYNTAX		INTEGER
		MAX-ACCESS		read-write
		STATUS			current
		DESCRIPTION
				"TYPE: - Number
				 PAGE: - Audio- Monitor
					Low Level  cmdID= 2517  min= -80  max= 0  step= 1  format= %1.1f dB  div_scale= 1 
					Min = -80.0 dB  Max = 0.0 dB  Step = 1.0 dB "
		::= { iqdly21CmdEntry 2517 }


	iqdly21AudioMonitorHighLevel OBJECT-TYPE
		SYNTAX		INTEGER
		MAX-ACCESS		read-write
		STATUS			current
		DESCRIPTION
				"TYPE: - Number
				 PAGE: - Audio- Monitor
					High Level  cmdID= 3057  min= -80  max= 0  step= 1  format= %1.1f dB  div_scale= 1 
					Min = -80.0 dB  Max = 0.0 dB  Step = 1.0 dB "
		::= { iqdly21CmdEntry 3057 }


	iqdly21AudioMonitorOverloadLevel OBJECT-TYPE
		SYNTAX		INTEGER
		MAX-ACCESS		read-write
		STATUS			current
		DESCRIPTION
				"TYPE: - Number
				 PAGE: - Audio- Monitor
					Overload Level  cmdID= 3058  min= -80  max= 0  step= 1  format= %1.1f dB  div_scale= 1 
					Min = -80.0 dB  Max = 0.0 dB  Step = 1.0 dB "
		::= { iqdly21CmdEntry 3058 }


	iqdly21AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1 
					Min = 1 sec  Max = 20 sec  Step = 1 sec "
		::= { iqdly21CmdEntry 2518 }


	iqdly21Genlock OBJECT-TYPE
		SYNTAX		INTEGER {
							val_Lock_to_Reference(0),
							val_Lock_to_Input(1),
							val_Free_Run(2)
							}
		MAX-ACCESS		read-write
		STATUS			current
		DESCRIPTION
				"TYPE: - Button
				 PAGE: - Genlock
					Lock to Reference  cmdID= 1049  value= 0  
					Lock to Input  cmdID= 1049  value= 1  
					Free Run  cmdID= 1049  value= 2  "
		::= { iqdly21CmdEntry 1049 }


	iqdly21GenlockFreerunFreq OBJECT-TYPE
		SYNTAX		INTEGER
		MAX-ACCESS		read-write
		STATUS			current
		DESCRIPTION
				"TYPE: - Number
				 PAGE: - Genlock
					Freerun Freq  cmdID= 2449  min= -60  max= 60  step= 1  format=   %.0f  div_scale= 1 
					Min =   -60  Max =   60  Step =   1 "
		::= { iqdly21CmdEntry 2449 }


	iqdly21UserMemMemory1Save1 OBJECT-TYPE
		SYNTAX		INTEGER { noAction(0),val_Save_1(1) }
		MAX-ACCESS		read-write
		STATUS			current
		DESCRIPTION
				"TYPE: - Button
				 PAGE: - User Mem
					Save 1  cmdID= 1600  value= 1  "
		::= { iqdly21CmdEntry 1600 }


	iqdly21UserMemMemory1Recall1 OBJECT-TYPE
		SYNTAX		INTEGER { noAction(0),val_Recall_1(1) }
		MAX-ACCESS		read-write
		STATUS			current
		DESCRIPTION
				"TYPE: - Button
				 PAGE: - User Mem
					Recall 1  cmdID= 1601  value= 1  "
		::= { iqdly21CmdEntry 1601 }


	iqdly21UserMemMemory1Clear1 OBJECT-TYPE
		SYNTAX		INTEGER { noAction(0),val_Clear_1(1) }
		MAX-ACCESS		read-write
		STATUS			current
		DESCRIPTION
				"TYPE: - Button
				 PAGE: - User Mem
					Clear 1  cmdID= 1602  value= 1  "
		::= { iqdly21CmdEntry 1602 }


	iqdly21UserMemMemory1Name1 OBJECT-TYPE
		SYNTAX		RollCallString
		MAX-ACCESS		read-write
		STATUS			current
		DESCRIPTION
				"TYPE: - Editstring
				 PAGE: - User Mem
					Name 1  cmdID= 1603  "
		::= { iqdly21CmdEntry 1603 }


	iqdly21UserMemMemory2Save2 OBJECT-TYPE
		SYNTAX		INTEGER { noAction(0),val_Save_2(1) }
		MAX-ACCESS		read-write
		STATUS			current
		DESCRIPTION
				"TYPE: - Button
				 PAGE: - User Mem
					Save 2  cmdID= 1604  value= 1  "
		::= { iqdly21CmdEntry 1604 }


	iqdly21UserMemMemory2Recall2 OBJECT-TYPE
		SYNTAX		INTEGER { noAction(0),val_Recall_2(1) }
		MAX-ACCESS		read-write
		STATUS			current
		DESCRIPTION
				"TYPE: - Button
				 PAGE: - User Mem
					Recall 2  cmdID= 1605  value= 1  "
		::= { iqdly21CmdEntry 1605 }


	iqdly21UserMemMemory2Clear2 OBJECT-TYPE
		SYNTAX		INTEGER { noAction(0),val_Clear_2(1) }
		MAX-ACCESS		read-write
		STATUS			current
		DESCRIPTION
				"TYPE: - Button
				 PAGE: - User Mem
					Clear 2  cmdID= 1606  value= 1  "
		::= { iqdly21CmdEntry 1606 }


	iqdly21UserMemMemory2Name2 OBJECT-TYPE
		SYNTAX		RollCallString
		MAX-ACCESS		read-write
		STATUS			current
		DESCRIPTION
				"TYPE: - Editstring
				 PAGE: - User Mem
					Name 2  cmdID= 1607  "
		::= { iqdly21CmdEntry 1607 }


	iqdly21UserMemMemory3Save3 OBJECT-TYPE
		SYNTAX		INTEGER { noAction(0),val_Save_3(1) }
		MAX-ACCESS		read-write
		STATUS			current
		DESCRIPTION
				"TYPE: - Button
				 PAGE: - User Mem
					Save 3  cmdID= 1608  value= 1  "
		::= { iqdly21CmdEntry 1608 }


	iqdly21UserMemMemory3Recall3 OBJECT-TYPE
		SYNTAX		INTEGER { noAction(0),val_Recall_3(1) }
		MAX-ACCESS		read-write
		STATUS			current
		DESCRIPTION
				"TYPE: - Button
				 PAGE: - User Mem
					Recall 3  cmdID= 1609  value= 1  "
		::= { iqdly21CmdEntry 1609 }


	iqdly21UserMemMemory3Clear3 OBJECT-TYPE
		SYNTAX		INTEGER { noAction(0),val_Clear_3(1) }
		MAX-ACCESS		read-write
		STATUS			current
		DESCRIPTION
				"TYPE: - Button
				 PAGE: - User Mem
					Clear 3  cmdID= 1610  value= 1  "
		::= { iqdly21CmdEntry 1610 }


	iqdly21UserMemMemory3Name3 OBJECT-TYPE
		SYNTAX		RollCallString
		MAX-ACCESS		read-write
		STATUS			current
		DESCRIPTION
				"TYPE: - Editstring
				 PAGE: - User Mem
					Name 3  cmdID= 1611  "
		::= { iqdly21CmdEntry 1611 }


	iqdly21UserMemMemory4Save4 OBJECT-TYPE
		SYNTAX		INTEGER { noAction(0),val_Save_4(1) }
		MAX-ACCESS		read-write
		STATUS			current
		DESCRIPTION
				"TYPE: - Button
				 PAGE: - User Mem
					Save 4  cmdID= 1612  value= 1  "
		::= { iqdly21CmdEntry 1612 }


	iqdly21UserMemMemory4Recall4 OBJECT-TYPE
		SYNTAX		INTEGER { noAction(0),val_Recall_4(1) }
		MAX-ACCESS		read-write
		STATUS			current
		DESCRIPTION
				"TYPE: - Button
				 PAGE: - User Mem
					Recall 4  cmdID= 1613  value= 1  "
		::= { iqdly21CmdEntry 1613 }


	iqdly21UserMemMemory4Clear4 OBJECT-TYPE
		SYNTAX		INTEGER { noAction(0),val_Clear_4(1) }
		MAX-ACCESS		read-write
		STATUS			current
		DESCRIPTION
				"TYPE: - Button
				 PAGE: - User Mem
					Clear 4  cmdID= 1614  value= 1  "
		::= { iqdly21CmdEntry 1614 }


	iqdly21UserMemMemory4Name4 OBJECT-TYPE
		SYNTAX		RollCallString
		MAX-ACCESS		read-write
		STATUS			current
		DESCRIPTION
				"TYPE: - Editstring
				 PAGE: - User Mem
					Name 4  cmdID= 1615  "
		::= { iqdly21CmdEntry 1615 }


	iqdly21UserMemMemory5Save5 OBJECT-TYPE
		SYNTAX		INTEGER { noAction(0),val_Save_5(1) }
		MAX-ACCESS		read-write
		STATUS			current
		DESCRIPTION
				"TYPE: - Button
				 PAGE: - User Mem
					Save 5  cmdID= 1616  value= 1  "
		::= { iqdly21CmdEntry 1616 }


	iqdly21UserMemMemory5Recall5 OBJECT-TYPE
		SYNTAX		INTEGER { noAction(0),val_Recall_5(1) }
		MAX-ACCESS		read-write
		STATUS			current
		DESCRIPTION
				"TYPE: - Button
				 PAGE: - User Mem
					Recall 5  cmdID= 1617  value= 1  "
		::= { iqdly21CmdEntry 1617 }


	iqdly21UserMemMemory5Clear5 OBJECT-TYPE
		SYNTAX		INTEGER { noAction(0),val_Clear_5(1) }
		MAX-ACCESS		read-write
		STATUS			current
		DESCRIPTION
				"TYPE: - Button
				 PAGE: - User Mem
					Clear 5  cmdID= 1618  value= 1  "
		::= { iqdly21CmdEntry 1618 }


	iqdly21UserMemMemory5Name5 OBJECT-TYPE
		SYNTAX		RollCallString
		MAX-ACCESS		read-write
		STATUS			current
		DESCRIPTION
				"TYPE: - Editstring
				 PAGE: - User Mem
					Name 5  cmdID= 1619  "
		::= { iqdly21CmdEntry 1619 }


	iqdly21UserMemMemory6Save6 OBJECT-TYPE
		SYNTAX		INTEGER { noAction(0),val_Save_6(1) }
		MAX-ACCESS		read-write
		STATUS			current
		DESCRIPTION
				"TYPE: - Button
				 PAGE: - User Mem
					Save 6  cmdID= 1620  value= 1  "
		::= { iqdly21CmdEntry 1620 }


	iqdly21UserMemMemory6Recall6 OBJECT-TYPE
		SYNTAX		INTEGER { noAction(0),val_Recall_6(1) }
		MAX-ACCESS		read-write
		STATUS			current
		DESCRIPTION
				"TYPE: - Button
				 PAGE: - User Mem
					Recall 6  cmdID= 1621  value= 1  "
		::= { iqdly21CmdEntry 1621 }


	iqdly21UserMemMemory6Clear6 OBJECT-TYPE
		SYNTAX		INTEGER { noAction(0),val_Clear_6(1) }
		MAX-ACCESS		read-write
		STATUS			current
		DESCRIPTION
				"TYPE: - Button
				 PAGE: - User Mem
					Clear 6  cmdID= 1622  value= 1  "
		::= { iqdly21CmdEntry 1622 }


	iqdly21UserMemMemory6Name6 OBJECT-TYPE
		SYNTAX		RollCallString
		MAX-ACCESS		read-write
		STATUS			current
		DESCRIPTION
				"TYPE: - Editstring
				 PAGE: - User Mem
					Name 6  cmdID= 1623  "
		::= { iqdly21CmdEntry 1623 }


	iqdly21UserMemMemory7Save7 OBJECT-TYPE
		SYNTAX		INTEGER { noAction(0),val_Save_7(1) }
		MAX-ACCESS		read-write
		STATUS			current
		DESCRIPTION
				"TYPE: - Button
				 PAGE: - User Mem
					Save 7  cmdID= 1624  value= 1  "
		::= { iqdly21CmdEntry 1624 }


	iqdly21UserMemMemory7Recall7 OBJECT-TYPE
		SYNTAX		INTEGER { noAction(0),val_Recall_7(1) }
		MAX-ACCESS		read-write
		STATUS			current
		DESCRIPTION
				"TYPE: - Button
				 PAGE: - User Mem
					Recall 7  cmdID= 1625  value= 1  "
		::= { iqdly21CmdEntry 1625 }


	iqdly21UserMemMemory7Clear7 OBJECT-TYPE
		SYNTAX		INTEGER { noAction(0),val_Clear_7(1) }
		MAX-ACCESS		read-write
		STATUS			current
		DESCRIPTION
				"TYPE: - Button
				 PAGE: - User Mem
					Clear 7  cmdID= 1626  value= 1  "
		::= { iqdly21CmdEntry 1626 }


	iqdly21UserMemMemory7Name7 OBJECT-TYPE
		SYNTAX		RollCallString
		MAX-ACCESS		read-write
		STATUS			current
		DESCRIPTION
				"TYPE: - Editstring
				 PAGE: - User Mem
					Name 7  cmdID= 1627  "
		::= { iqdly21CmdEntry 1627 }


	iqdly21UserMemMemory8Save8 OBJECT-TYPE
		SYNTAX		INTEGER { noAction(0),val_Save_8(1) }
		MAX-ACCESS		read-write
		STATUS			current
		DESCRIPTION
				"TYPE: - Button
				 PAGE: - User Mem
					Save 8  cmdID= 1628  value= 1  "
		::= { iqdly21CmdEntry 1628 }


	iqdly21UserMemMemory8Recall8 OBJECT-TYPE
		SYNTAX		INTEGER { noAction(0),val_Recall_8(1) }
		MAX-ACCESS		read-write
		STATUS			current
		DESCRIPTION
				"TYPE: - Button
				 PAGE: - User Mem
					Recall 8  cmdID= 1629  value= 1  "
		::= { iqdly21CmdEntry 1629 }


	iqdly21UserMemMemory8Clear8 OBJECT-TYPE
		SYNTAX		INTEGER { noAction(0),val_Clear_8(1) }
		MAX-ACCESS		read-write
		STATUS			current
		DESCRIPTION
				"TYPE: - Button
				 PAGE: - User Mem
					Clear 8  cmdID= 1630  value= 1  "
		::= { iqdly21CmdEntry 1630 }


	iqdly21UserMemMemory8Name8 OBJECT-TYPE
		SYNTAX		RollCallString
		MAX-ACCESS		read-write
		STATUS			current
		DESCRIPTION
				"TYPE: - Editstring
				 PAGE: - User Mem
					Name 8  cmdID= 1631  "
		::= { iqdly21CmdEntry 1631 }


	iqdly21SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqdly21CmdEntry 2489 }


	iqdly21SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1 
					Min = 100.0 Hz  Max = 15000.0 Hz  Step = 100.0 Hz "
		::= { iqdly21CmdEntry 2487 }


	iqdly21SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1 
					Min = 100.0 Hz  Max = 15000.0 Hz  Step = 100.0 Hz "
		::= { iqdly21CmdEntry 2488 }


	iqdly21SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1 
					Min = 4.0 dB  Max = 24.0 dB  Step = 1.0 dB "
		::= { iqdly21CmdEntry 3055 }


	iqdly21SetupAudioToneLineUp OBJECT-TYPE
		SYNTAX		INTEGER
		MAX-ACCESS		read-write
		STATUS			current
		DESCRIPTION
				"TYPE: - Number
				 PAGE: - Setup- Audio Tone
					Line Up  cmdID= 2598  min= -200  max= 200  step= 10  format= %2.0f dBu  div_scale= 10 
					Min = -20 dBu  Max = 20 dBu  Step =  1 dBu "
		::= { iqdly21CmdEntry 2598 }


	iqdly21SetupAudioToneADCLineUp OBJECT-TYPE
		SYNTAX		INTEGER
		MAX-ACCESS		read-write
		STATUS			current
		DESCRIPTION
				"TYPE: - Number
				 PAGE: - Setup- Audio Tone
					ADC Line Up  cmdID= 3545  min= -200  max= 200  step= 10  format= %2.0f dBu  div_scale= 10 
					Min = -20 dBu  Max = 20 dBu  Step =  1 dBu "
		::= { iqdly21CmdEntry 3545 }


	iqdly21SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972 
					Instant  value= 0  
					Fast  value= 1  
					Medium  value= 2  
					Slow  value= 3  
					Slowest  value= 4  "
		::= { iqdly21CmdEntry 2972 }


	iqdly21SetupChannelStatus OBJECT-TYPE
		SYNTAX		RollCallString
		MAX-ACCESS		read-write
		STATUS			current
		DESCRIPTION
				"TYPE: - Editstring
				 PAGE: - Setup
					Channel Status  cmdID= 3060  "
		::= { iqdly21CmdEntry 3060 }


	iqdly21GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqdly21CmdEntry 2605 }


	iqdly21GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqdly21CmdEntry 3053 }


	iqdly21GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqdly21CmdEntry 3054 }


	iqdly21GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 11  step= 1  format= %.0f  div_scale= 1 
					Min = -1  Max = 11  Step = 1 "
		::= { iqdly21CmdEntry 2011 }


	iqdly21GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqdly21CmdEntry 2048 }


	iqdly21GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqdly21CmdEntry 3540 }


	iqdly21GPIIOGPIOutputOutputSelection OBJECT-TYPE
		SYNTAX		INTEGER {
							val_AES_1_Present(0),
							val_AES_2_Present(1),
							val_Delay(2),
							val_Unused(3)
							}
		MAX-ACCESS		read-write
		STATUS			current
		DESCRIPTION
				"TYPE: - RadiobuttonList
				 PAGE: - Setup- GPI I/O
					Output Selection  cmdID= 2013 
					AES 1 Present  value= 0  
					AES 2 Present  value= 1  
					Delay  value= 2  
					Unused  value= 3  "
		::= { iqdly21CmdEntry 2013 }


	iqdly21GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqdly21CmdEntry 2049 }


	iqdly21GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqdly21CmdEntry 2014 }


	iqdly21SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 11  step= 1  format= %.0f  div_scale= 1 
					Min = -1  Max = 11  Step = 1 "
		::= { iqdly21CmdEntry 2875 }


	iqdly21SetupGPIIOOutputSelection OBJECT-TYPE
		SYNTAX		INTEGER {
							val_AES_1_Present(0),
							val_AES_2_Present(1),
							val_Delay(2),
							val_Unused(3)
							}
		MAX-ACCESS		read-write
		STATUS			current
		DESCRIPTION
				"TYPE: - RadiobuttonList
				 PAGE: - Setup- GPI I/O
					Output Selection  cmdID= 2877 
					AES 1 Present  value= 0  
					AES 2 Present  value= 1  
					Delay  value= 2  
					Unused  value= 3  "
		::= { iqdly21CmdEntry 2877 }


	iqdly21SetupRollTrackRollTrackIndex1495 OBJECT-TYPE
		SYNTAX		INTEGER
		MAX-ACCESS		read-write
		STATUS			current
		DESCRIPTION
				"TYPE: - Number
				 PAGE: - Setup- RollTrack
					RollTrack Index  cmdID= 1495  min= 0  max= 69  step= 1  format= %.0f  div_scale= 1 
					Min = 0  Max = 69  Step = 1 "
		::= { iqdly21CmdEntry 1495 }


	iqdly21SetupRollTrackRollTrackSource1496 OBJECT-TYPE
		SYNTAX		INTEGER
		MAX-ACCESS		read-write
		STATUS			current
		DESCRIPTION
				"TYPE: - Number
				 PAGE: - Setup- RollTrack
					RollTrack Source  cmdID= 1496  min= -1  max= 12  step= 1  format= %.0f  div_scale= 1 
					Min = -1  Max = 12  Step = 1 "
		::= { iqdly21CmdEntry 1496 }


	iqdly21SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqdly21CmdEntry 1513 }


	iqdly21SetupRollTrackRollTrackAddress1497 OBJECT-TYPE
		SYNTAX		RollCallString
		MAX-ACCESS		read-write
		STATUS			current
		DESCRIPTION
				"TYPE: - Editstring
				 PAGE: - Setup- RollTrack
					RollTrack Address  cmdID= 1497  "
		::= { iqdly21CmdEntry 1497 }


	iqdly21SetupRollTrackRollTrackCommand1498 OBJECT-TYPE
		SYNTAX		RollCallString
		MAX-ACCESS		read-write
		STATUS			current
		DESCRIPTION
				"TYPE: - Editstring
				 PAGE: - Setup- RollTrack
					RollTrack Command  cmdID= 1498  "
		::= { iqdly21CmdEntry 1498 }


	iqdly21SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqdly21CmdEntry 1514 }


	iqdly21SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqdly21CmdEntry 1511 }


	iqdly21SetupRollTrackRollTrackIndex2870 OBJECT-TYPE
		SYNTAX		INTEGER
		MAX-ACCESS		read-write
		STATUS			current
		DESCRIPTION
				"TYPE: - Number
				 PAGE: - Setup- RollTrack
					RollTrack Index  cmdID= 2870  min= 0  max= 69  step= 1  format= %.0f  div_scale= 1 
					Min = 0  Max = 69  Step = 1 "
		::= { iqdly21CmdEntry 2870 }


	iqdly21SetupRollTrackRollTrackSource2871 OBJECT-TYPE
		SYNTAX		INTEGER
		MAX-ACCESS		read-write
		STATUS			current
		DESCRIPTION
				"TYPE: - Number
				 PAGE: - Setup- RollTrack
					RollTrack Source  cmdID= 2871  min= -1  max= 12  step= 1  format= %.0f  div_scale= 1 
					Min = -1  Max = 12  Step = 1 "
		::= { iqdly21CmdEntry 2871 }


	iqdly21SetupRollTrackRollTrackAddress2872 OBJECT-TYPE
		SYNTAX		RollCallString
		MAX-ACCESS		read-write
		STATUS			current
		DESCRIPTION
				"TYPE: - Editstring
				 PAGE: - Setup- RollTrack
					RollTrack Address  cmdID= 2872  "
		::= { iqdly21CmdEntry 2872 }


	iqdly21SetupRollTrackRollTrackCommand2873 OBJECT-TYPE
		SYNTAX		RollCallString
		MAX-ACCESS		read-write
		STATUS			current
		DESCRIPTION
				"TYPE: - Editstring
				 PAGE: - Setup- RollTrack
					RollTrack Command  cmdID= 2873  "
		::= { iqdly21CmdEntry 2873 }


	iqdly21SetupLoggingReference OBJECT-TYPE
		SYNTAX		INTEGER { disable(0), enable(1) }
		MAX-ACCESS		read-write
		STATUS			current
		DESCRIPTION
				"TYPE: - Checkbox
				 PAGE: - Setup- Logging
					Reference  cmdID= 1062 "
		::= { iqdly21CmdEntry 1062 }


	iqdly21SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqdly21CmdEntry 1106 }


	iqdly21SetupLoggingAES1 OBJECT-TYPE
		SYNTAX		INTEGER { disable(0), enable(1) }
		MAX-ACCESS		read-write
		STATUS			current
		DESCRIPTION
				"TYPE: - Checkbox
				 PAGE: - Setup- Logging
					AES 1  cmdID= 1108 "
		::= { iqdly21CmdEntry 1108 }


	iqdly21SetupLoggingAES2 OBJECT-TYPE
		SYNTAX		INTEGER { disable(0), enable(1) }
		MAX-ACCESS		read-write
		STATUS			current
		DESCRIPTION
				"TYPE: - Checkbox
				 PAGE: - Setup- Logging
					AES 2  cmdID= 1109 "
		::= { iqdly21CmdEntry 1109 }


	iqdly21SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqdly21CmdEntry 1112 }


	iqdly21SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqdly21CmdEntry 1113 }


	iqdly21SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqdly21CmdEntry 1114 }


	iqdly21SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqdly21CmdEntry 1115 }


	iqdly21SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqdly21CmdEntry 1116 }


	iqdly21SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqdly21CmdEntry 1117 }


	iqdly21SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqdly21CmdEntry 1118 }


	iqdly21SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqdly21CmdEntry 1119 }


	iqdly21SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqdly21CmdEntry 1069 }


	iqdly21SetupLoggingStatusEXTREF OBJECT-TYPE
		SYNTAX		RollCallString
		MAX-ACCESS		read-only
		STATUS			current
		DESCRIPTION
				"TYPE: - Display
				 PAGE: - Setup- Logging Status
					EXTREF=  cmdID= 2986  format=   "
		::= { iqdly21CmdEntry 2986 }


	iqdly21SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqdly21CmdEntry 2989 }


	iqdly21SetupLoggingStatusAES1 OBJECT-TYPE
		SYNTAX		RollCallString
		MAX-ACCESS		read-only
		STATUS			current
		DESCRIPTION
				"TYPE: - Display
				 PAGE: - Setup- Logging Status
					AES1=  cmdID= 2994  format=   "
		::= { iqdly21CmdEntry 2994 }


	iqdly21SetupLoggingStatusAES2 OBJECT-TYPE
		SYNTAX		RollCallString
		MAX-ACCESS		read-only
		STATUS			current
		DESCRIPTION
				"TYPE: - Display
				 PAGE: - Setup- Logging Status
					AES2=  cmdID= 2995  format=   "
		::= { iqdly21CmdEntry 2995 }


	iqdly21SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqdly21CmdEntry 2998 }


	iqdly21SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqdly21CmdEntry 2999 }


	iqdly21SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqdly21CmdEntry 3000 }


	iqdly21SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqdly21CmdEntry 3001 }


	iqdly21SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqdly21CmdEntry 3002 }


	iqdly21SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqdly21CmdEntry 3003 }


	iqdly21SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqdly21CmdEntry 3004 }


	iqdly21SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqdly21CmdEntry 3005 }


	iqdly21SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqdly21CmdEntry 2990 }


	iqdly21SetupUnitSoftwareVersion OBJECT-TYPE
		SYNTAX		RollCallString
		MAX-ACCESS		read-only
		STATUS			current
		DESCRIPTION
				"TYPE: - Display
				 PAGE: - Setup- Unit
					Software Version  cmdID= 2  format=   "
		::= { iqdly21CmdEntry 2 }


	iqdly21SetupUnitSerialNo OBJECT-TYPE
		SYNTAX		RollCallString
		MAX-ACCESS		read-only
		STATUS			current
		DESCRIPTION
				"TYPE: - Display
				 PAGE: - Setup- Unit
					Serial No  cmdID= 1  format=   "
		::= { iqdly21CmdEntry 1 }


	iqdly21SetupUnitPresetUnit OBJECT-TYPE
		SYNTAX		INTEGER { noAction(0),val_Preset_Unit(1) }
		MAX-ACCESS		read-write
		STATUS			current
		DESCRIPTION
				"TYPE: - Button
				 PAGE: - Setup- Unit
					Preset Unit  cmdID= 3  value= 1  "
		::= { iqdly21CmdEntry 3 }


	iqdly21SetupUnitRestart OBJECT-TYPE
		SYNTAX		INTEGER { noAction(0),val_Restart(1) }
		MAX-ACCESS		read-write
		STATUS			current
		DESCRIPTION
				"TYPE: - Button
				 PAGE: - Setup- Unit
					Restart  cmdID= 4  value= 1  "
		::= { iqdly21CmdEntry 4 }


	iqdly21SetupUnitBuildNo OBJECT-TYPE
		SYNTAX		RollCallString
		MAX-ACCESS		read-only
		STATUS			current
		DESCRIPTION
				"TYPE: - Display
				 PAGE: - Setup- Unit
					Build No  cmdID= 5  format=   "
		::= { iqdly21CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: AES_1
--
-- MIB ref		: swCardEventLogSlotXX       .5.65.69.83.95.49
-- absolute OID	: 1.3.6.1.4.1.7995.2.6.1.1.XX.5.65.69.83.95.49
-- Vary			: YES
--
-- Value(s)		: LOST
--				: 
-- Comments		: 
--
---------------------------------------------------------------------------------------------------
-- Header		: AES_2
--
-- MIB ref		: swCardEventLogSlotXX       .5.65.69.83.95.50
-- absolute OID	: 1.3.6.1.4.1.7995.2.6.1.1.XX.5.65.69.83.95.50
-- Vary			: YES
--
-- Value(s)		: LOST
--				: 
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE
--				: 
-- Comments		: 
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: WARNING.SILENT
--				: 
-- Comments		: 
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: WARNING.SILENT
--				: 
-- Comments		: 
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: WARNING.SILENT
--				: 
-- Comments		: 
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: WARNING.SILENT
--				: 
-- Comments		: 
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: WARNING.SILENT
--				: 
-- Comments		: 
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: WARNING.SILENT
--				: 
-- Comments		: 
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: WARNING.SILENT
--				: 
-- Comments		: 
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: WARNING.SILENT
--				: 
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: NONE
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2009-01-12T13:05:15Z
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
