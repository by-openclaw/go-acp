-- ************************************************************************************
-- Snell Card:IQDBE02
--        Module Id#:564
--       Command Set:6
--          Filename:SNELL-IQDBE02-CMD-MIB.mib
--            Author:Jonathan Riches
--              Date:22/04/2010
--              Time:14:14
--
-- Copyright (c) 2010 Snell Ltd
-- All rights reserved.
--
-- ************************************************************************************

SNELL-IQDBE02-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDBE02,
    moduleIQDBE02MIB
        FROM SNELL-WILCOX-PRODUCT-REG;

 moduleIQDBE02CmdMi MODULE-IDENTITY
    LAST-UPDATED "1004221414Z"
    ORGANIZATION "Snell Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell card, command set  translations."
    ::= { moduleIQDBE02MIB 1 }




--********************************************************************************
--*
--*  Snell Card:
--*  command set:
--*  list commands/menus:
--*
--******************************************************************************
	iqdbe02CmdTable OBJECT-TYPE
		SYNTAX			SEQUENCE OF Iqdbe02CmdEntry
		MAX-ACCESS		not-accessible
		STATUS			current
		DESCRIPTION
				"Note the instance of this table is relected in the command set Version"
		::= { moduleIQDBE02 1 }

	iqdbe02CmdEntry OBJECT-TYPE
		SYNTAX		Iqdbe02CmdEntry
		MAX-ACCESS		not-accessible
		STATUS			current
		DESCRIPTION
				"Entry in command table."
		INDEX	{ iqdbe02SlotIndex }
		::= { iqdbe02CmdTable 1 }

	Iqdbe02CmdEntry ::=
		SEQUENCE {
			iqdbe02SlotIndex
				Unsigned32,
			iqdbe02MenuInputIPLoss
				INTEGER,
			iqdbe02InputValidStdsAllValid
				INTEGER,
			iqdbe02InputValidStdsAllInvalid
				INTEGER,
			iqdbe02InputValidStds108023sF
				INTEGER,
			iqdbe02InputValidStds108023p
				INTEGER,
			iqdbe02InputValidStds108024sF
				INTEGER,
			iqdbe02InputValidStds108024p
				INTEGER,
			iqdbe02InputValidStds108025i
				INTEGER,
			iqdbe02InputValidStds108025p
				INTEGER,
			iqdbe02InputValidStds103529i
				INTEGER,
			iqdbe02InputValidStds108029i
				INTEGER,
			iqdbe02InputValidStds108029p
				INTEGER,
			iqdbe02InputValidStds103530i
				INTEGER,
			iqdbe02InputValidStds108030i
				INTEGER,
			iqdbe02InputValidStds108030p
				INTEGER,
			iqdbe02InputValidStds72050p
				INTEGER,
			iqdbe02InputValidStds72059p
				INTEGER,
			iqdbe02InputValidStds72060p
				INTEGER,
			iqdbe02InputValidStds62525i
				INTEGER,
			iqdbe02InputValidStds52529i
				INTEGER,
			iqdbe02InputErrorsCRCErrs
				RollCallString,
			iqdbe02InputErrorsCRCErrSec
				RollCallString,
			iqdbe02InputErrorsANCErrs
				RollCallString,
			iqdbe02InputErrorsANCErrSec
				RollCallString,
			iqdbe02InputErrorsResetSec
				RollCallString,
			iqdbe02InputErrorsErrorReset
				INTEGER,
			iqdbe02AudioOutputOutputStandard
				INTEGER,
			iqdbe02AudioOutputSelectStandard
				INTEGER,
			iqdbe02OutputVideoProcAmpsMasterGain
				INTEGER,
			iqdbe02OutputVideoProcAmpsYGain
				INTEGER,
			iqdbe02OutputVideoProcAmpsCGain
				INTEGER,
			iqdbe02OutputVideoProcAmpsBlackLevel
				INTEGER,
			iqdbe02AudioOutputDefaultOutput
				INTEGER,
			iqdbe02AudioOutputDefaultOPStd
				INTEGER,
			iqdbe02AudioDelayASourcesManual
				INTEGER,
			iqdbe02AudioDelayASourcesGPIPWM
				INTEGER,
			iqdbe02AudioDelayASourcesRollTrack14
				INTEGER,
			iqdbe02AudioDelayASourcesRollTrack15
				INTEGER,
			iqdbe02AudioDelayASourcesRollTrack16
				INTEGER,
			iqdbe02AudioDelayASourcesRollTrack17
				INTEGER,
			iqdbe02AudDelaysAudioDelayAAdjustCoarseDelay
				INTEGER,
			iqdbe02AudDelaysAudioDelayACurrentAudioDelay
				RollCallString,
			iqdbe02AudioDelayBSourcesManual
				INTEGER,
			iqdbe02AudioDelayBSourcesGPIPWM
				INTEGER,
			iqdbe02AudioDelayBSourcesRollTrack14
				INTEGER,
			iqdbe02AudioDelayBSourcesRollTrack15
				INTEGER,
			iqdbe02AudioDelayBSourcesRollTrack16
				INTEGER,
			iqdbe02AudioDelayBSourcesRollTrack17
				INTEGER,
			iqdbe02AudDelaysAudioDelayBAdjustCoarseDelay
				INTEGER,
			iqdbe02AudDelaysAudioDelayBCurrentAudioDelay
				RollCallString,
			iqdbe02AudDelaysAESDelaySelectDelay1
				INTEGER,
			iqdbe02AudDelaysAESDelaySelectInternal1
				INTEGER,
			iqdbe02AudDelaysAESDelaySelectAutoDolbyEPhase1
				INTEGER,
			iqdbe02AudDelaysAESDelaySelectDelayLimit1
				RollCallString,
			iqdbe02AudDelaysAESDelaySelectAES1FineDelay
				INTEGER,
			iqdbe02AudDelaysAESDelaySelectDelay2
				INTEGER,
			iqdbe02AudDelaysAESDelaySelectInternal2
				INTEGER,
			iqdbe02AudDelaysAESDelaySelectAutoDolbyEPhase2
				INTEGER,
			iqdbe02AudDelaysAESDelaySelectDelayLimit2
				RollCallString,
			iqdbe02AudDelaysAESDelaySelectAES2FineDelay
				INTEGER,
			iqdbe02AudDelaysAESDelaySelectDelay3
				INTEGER,
			iqdbe02AudDelaysAESDelaySelectInternal3
				INTEGER,
			iqdbe02AudDelaysAESDelaySelectAutoDolbyEPhase3
				INTEGER,
			iqdbe02AudDelaysAESDelaySelectDelayLimit3
				RollCallString,
			iqdbe02AudDelaysAESDelaySelectAES3FineDelay
				INTEGER,
			iqdbe02AudDelaysAESDelaySelectDelay4
				INTEGER,
			iqdbe02AudDelaysAESDelaySelectInternal4
				INTEGER,
			iqdbe02AudDelaysAESDelaySelectAutoDolbyEPhase4
				INTEGER,
			iqdbe02AudDelaysAESDelaySelectDelayLimit4
				RollCallString,
			iqdbe02AudDelaysAESDelaySelectAES4FineDelay
				INTEGER,
			iqdbe02AudDelaysAESDelaySelectDelay5
				INTEGER,
			iqdbe02AudDelaysAESDelaySelectInternal5
				INTEGER,
			iqdbe02AudDelaysAESDelaySelectAutoDolbyEPhase5
				INTEGER,
			iqdbe02AudDelaysAESDelaySelectDelayLimit5
				RollCallString,
			iqdbe02AudDelaysAESDelaySelectAES5FineDelay
				INTEGER,
			iqdbe02AudDelaysAESDelaySelectDelay6
				INTEGER,
			iqdbe02AudDelaysAESDelaySelectInternal6
				INTEGER,
			iqdbe02AudDelaysAESDelaySelectAutoDolbyEPhase6
				INTEGER,
			iqdbe02AudDelaysAESDelaySelectDelayLimit6
				RollCallString,
			iqdbe02AudDelaysAESDelaySelectAES6FineDelay
				INTEGER,
			iqdbe02AudDelaysAESDelaySelectDelay7
				INTEGER,
			iqdbe02AudDelaysAESDelaySelectInternal7
				INTEGER,
			iqdbe02AudDelaysAESDelaySelectAutoDolbyEPhase7
				INTEGER,
			iqdbe02AudDelaysAESDelaySelectDelayLimit7
				RollCallString,
			iqdbe02AudDelaysAESDelaySelectAES7FineDelay
				INTEGER,
			iqdbe02AudDelaysAESDelaySelectDolbyEncoder
				INTEGER,
			iqdbe02AudDelaysAESDelaySelectInternal
				INTEGER,
			iqdbe02AudDelaysAESDelaySelectAutoDolbyEPhase8
				INTEGER,
			iqdbe02AudDelaysAESDelaySelectDelayLimit8
				RollCallString,
			iqdbe02AudDelaysAESDelaySelectDolbyEncFineDela
				INTEGER,
			iqdbe02AudDelaysEMBDelaySelectDelay1
				INTEGER,
			iqdbe02AudDelaysEMBDelaySelectInternal1
				INTEGER,
			iqdbe02AudDelaysEMBDelaySelectAutoDolbyEPhase1
				INTEGER,
			iqdbe02AudDelaysEMBDelaySelectDelayLimit1
				RollCallString,
			iqdbe02AudDelaysEMBDelaySelectEMB1FineDelay
				INTEGER,
			iqdbe02AudDelaysEMBDelaySelectDelay2
				INTEGER,
			iqdbe02AudDelaysEMBDelaySelectInternal2
				INTEGER,
			iqdbe02AudDelaysEMBDelaySelectAutoDolbyEPhase2
				INTEGER,
			iqdbe02AudDelaysEMBDelaySelectDelayLimit2
				RollCallString,
			iqdbe02AudDelaysEMBDelaySelectEMB2FineDelay
				INTEGER,
			iqdbe02AudDelaysEMBDelaySelectDelay3
				INTEGER,
			iqdbe02AudDelaysEMBDelaySelectInternal3
				INTEGER,
			iqdbe02AudDelaysEMBDelaySelectAutoDolbyEPhase3
				INTEGER,
			iqdbe02AudDelaysEMBDelaySelectDelayLimit3
				RollCallString,
			iqdbe02AudDelaysEMBDelaySelectEMB3FineDelay
				INTEGER,
			iqdbe02AudDelaysEMBDelaySelectDelay4
				INTEGER,
			iqdbe02AudDelaysEMBDelaySelectInternal4
				INTEGER,
			iqdbe02AudDelaysEMBDelaySelectAutoDolbyEPhase4
				INTEGER,
			iqdbe02AudDelaysEMBDelaySelectDelayLimit4
				RollCallString,
			iqdbe02AudDelaysEMBDelaySelectEMB4FineDelay
				INTEGER,
			iqdbe02AudDelaysEMBDelaySelectDelay5
				INTEGER,
			iqdbe02AudDelaysEMBDelaySelectInternal5
				INTEGER,
			iqdbe02AudDelaysEMBDelaySelectAutoDolbyEPhase5
				INTEGER,
			iqdbe02AudDelaysEMBDelaySelectDelayLimit5
				RollCallString,
			iqdbe02AudDelaysEMBDelaySelectEMB5FineDelay
				INTEGER,
			iqdbe02AudDelaysEMBDelaySelectDelay6
				INTEGER,
			iqdbe02AudDelaysEMBDelaySelectInternal6
				INTEGER,
			iqdbe02AudDelaysEMBDelaySelectAutoDolbyEPhase6
				INTEGER,
			iqdbe02AudDelaysEMBDelaySelectDelayLimit6
				RollCallString,
			iqdbe02AudDelaysEMBDelaySelectEMB6FineDelay
				INTEGER,
			iqdbe02AudDelaysEMBDelaySelectDelay7
				INTEGER,
			iqdbe02AudDelaysEMBDelaySelectInternal7
				INTEGER,
			iqdbe02AudDelaysEMBDelaySelectAutoDolbyEPhase7
				INTEGER,
			iqdbe02AudDelaysEMBDelaySelectDelayLimit7
				RollCallString,
			iqdbe02AudDelaysEMBDelaySelectEMB7FineDelay
				INTEGER,
			iqdbe02AudDelaysEMBDelaySelectDelay8
				INTEGER,
			iqdbe02AudDelaysEMBDelaySelectInternal8
				INTEGER,
			iqdbe02AudDelaysEMBDelaySelectDelayLimit8
				RollCallString,
			iqdbe02AudDelaysEMBDelaySelectAutoDolbyEPhase8
				INTEGER,
			iqdbe02AudDelaysEMBDelaySelectEMB8FineDelay
				INTEGER,
			iqdbe02AudioAudDelaysRollTrack14
				RollCallString,
			iqdbe02AudioAudDelaysRollTrack15
				RollCallString,
			iqdbe02AudioAudDelaysRollTrack16
				RollCallString,
			iqdbe02AudioAudDelaysRollTrack17
				RollCallString,
			iqdbe02AudioAudDelaysCrashSRCLimit
				INTEGER,
			iqdbe02EmbCtrlGroupGroup1Audio
				INTEGER,
			iqdbe02EmbCtrlGroupGroup2Audio
				INTEGER,
			iqdbe02EmbCtrlGroupGroup3Audio
				INTEGER,
			iqdbe02EmbCtrlGroupGroup4Audio
				INTEGER,
			iqdbe02EmbCtrlChannelPair1LActive
				INTEGER,
			iqdbe02EmbCtrlChannelPair1RActive
				INTEGER,
			iqdbe02EmbCtrlChannelPair2LActive
				INTEGER,
			iqdbe02EmbCtrlChannelPair2RActive
				INTEGER,
			iqdbe02EmbCtrlChannelPair3LActive
				INTEGER,
			iqdbe02EmbCtrlChannelPair3RActive
				INTEGER,
			iqdbe02EmbCtrlChannelPair4LActive
				INTEGER,
			iqdbe02EmbCtrlChannelPair4RActive
				INTEGER,
			iqdbe02EmbCtrlChannelPair5LActive
				INTEGER,
			iqdbe02EmbCtrlChannelPair5RActive
				INTEGER,
			iqdbe02EmbCtrlChannelPair6LActive
				INTEGER,
			iqdbe02EmbCtrlChannelPair6RActive
				INTEGER,
			iqdbe02EmbCtrlChannelPair7LActive
				INTEGER,
			iqdbe02EmbCtrlChannelPair7RActive
				INTEGER,
			iqdbe02EmbCtrlChannelPair8LActive
				INTEGER,
			iqdbe02EmbCtrlChannelPair8RActive
				INTEGER,
			iqdbe02AudioEmbCtrlEmbedderPriority
				INTEGER,
			iqdbe02EmbGainEmbedPair1Embed1MuteL
				INTEGER,
			iqdbe02EmbGainEmbedPair1Embed1MuteR
				INTEGER,
			iqdbe02EmbGainEmbedPair1Embed1LGain
				INTEGER,
			iqdbe02EmbGainEmbedPair1Embed1RGain
				INTEGER,
			iqdbe02EmbGainEmbedPair1Stereo
				INTEGER,
			iqdbe02EmbGainEmbedPair1Embed1InvertL
				INTEGER,
			iqdbe02EmbGainEmbedPair1Embed1InvertR
				INTEGER,
			iqdbe02EmbGainEmbedPair1Embed1LClip
				RollCallString,
			iqdbe02EmbGainEmbedPair1Embed1RClip
				RollCallString,
			iqdbe02EmbGainEmbedPair2Embed2MuteL
				INTEGER,
			iqdbe02EmbGainEmbedPair2Embed2MuteR
				INTEGER,
			iqdbe02EmbGainEmbedPair2Embed2LGain
				INTEGER,
			iqdbe02EmbGainEmbedPair2Embed2RGain
				INTEGER,
			iqdbe02EmbGainEmbedPair2Stereo
				INTEGER,
			iqdbe02EmbGainEmbedPair2Embed2InvertL
				INTEGER,
			iqdbe02EmbGainEmbedPair2Embed2InvertR
				INTEGER,
			iqdbe02EmbGainEmbedPair2Embed2LClip
				RollCallString,
			iqdbe02EmbGainEmbedPair2Embed2RClip
				RollCallString,
			iqdbe02EmbGainEmbedPair3Embed3MuteL
				INTEGER,
			iqdbe02EmbGainEmbedPair3Embed3MuteR
				INTEGER,
			iqdbe02EmbGainEmbedPair3Embed3LGain
				INTEGER,
			iqdbe02EmbGainEmbedPair3Embed3RGain
				INTEGER,
			iqdbe02EmbGainEmbedPair3Stereo
				INTEGER,
			iqdbe02EmbGainEmbedPair3Embed3InvertL
				INTEGER,
			iqdbe02EmbGainEmbedPair3Embed3InvertR
				INTEGER,
			iqdbe02EmbGainEmbedPair3Embed3LClip
				RollCallString,
			iqdbe02EmbGainEmbedPair3Embed3RClip
				RollCallString,
			iqdbe02EmbGainEmbedPair4Embed4MuteL
				INTEGER,
			iqdbe02EmbGainEmbedPair4Embed4MuteR
				INTEGER,
			iqdbe02EmbGainEmbedPair4Embed4LGain
				INTEGER,
			iqdbe02EmbGainEmbedPair4Embed4RGain
				INTEGER,
			iqdbe02EmbGainEmbedPair4Stereo
				INTEGER,
			iqdbe02EmbGainEmbedPair4Embed4InvertL
				INTEGER,
			iqdbe02EmbGainEmbedPair4Embed4InvertR
				INTEGER,
			iqdbe02EmbGainEmbedPair4Embed4LClip
				RollCallString,
			iqdbe02EmbGainEmbedPair4Embed4RClip
				RollCallString,
			iqdbe02EmbGainEmbedPair5Embed5MuteL
				INTEGER,
			iqdbe02EmbGainEmbedPair5Embed5MuteR
				INTEGER,
			iqdbe02EmbGainEmbedPair5Embed5LGain
				INTEGER,
			iqdbe02EmbGainEmbedPair5Embed5RGain
				INTEGER,
			iqdbe02EmbGainEmbedPair5Stereo
				INTEGER,
			iqdbe02EmbGainEmbedPair5Embed5InvertL
				INTEGER,
			iqdbe02EmbGainEmbedPair5Embed5InvertR
				INTEGER,
			iqdbe02EmbGainEmbedPair5Embed5LClip
				RollCallString,
			iqdbe02EmbGainEmbedPair5Embed5RClip
				RollCallString,
			iqdbe02EmbGainEmbedPair6Embed6MuteL
				INTEGER,
			iqdbe02EmbGainEmbedPair6Embed6MuteR
				INTEGER,
			iqdbe02EmbGainEmbedPair6Embed6LGain
				INTEGER,
			iqdbe02EmbGainEmbedPair6Embed6RGain
				INTEGER,
			iqdbe02EmbGainEmbedPair6Stereo
				INTEGER,
			iqdbe02EmbGainEmbedPair6Embed6InvertL
				INTEGER,
			iqdbe02EmbGainEmbedPair6Embed6InvertR
				INTEGER,
			iqdbe02EmbGainEmbedPair6Embed6LClip
				RollCallString,
			iqdbe02EmbGainEmbedPair6Embed6RClip
				RollCallString,
			iqdbe02EmbGainEmbedPair7Embed7MuteL
				INTEGER,
			iqdbe02EmbGainEmbedPair7Embed7MuteR
				INTEGER,
			iqdbe02EmbGainEmbedPair7Embed7LGain
				INTEGER,
			iqdbe02EmbGainEmbedPair7Embed7RGain
				INTEGER,
			iqdbe02EmbGainEmbedPair7Stereo
				INTEGER,
			iqdbe02EmbGainEmbedPair7Embed7InvertL
				INTEGER,
			iqdbe02EmbGainEmbedPair7Embed7InvertR
				INTEGER,
			iqdbe02EmbGainEmbedPair7Embed7LClip
				RollCallString,
			iqdbe02EmbGainEmbedPair7Embed7RClip
				RollCallString,
			iqdbe02EmbGainEmbedPair8Embed8MuteL
				INTEGER,
			iqdbe02EmbGainEmbedPair8Embed8MuteR
				INTEGER,
			iqdbe02EmbGainEmbedPair8Embed8LGain
				INTEGER,
			iqdbe02EmbGainEmbedPair8Embed8RGain
				INTEGER,
			iqdbe02EmbGainEmbedPair8Stereo
				INTEGER,
			iqdbe02EmbGainEmbedPair8Embed8InvertL
				INTEGER,
			iqdbe02EmbGainEmbedPair8Embed8InvertR
				INTEGER,
			iqdbe02EmbGainEmbedPair8Embed8LClip
				RollCallString,
			iqdbe02EmbGainEmbedPair8Embed8RClip
				RollCallString,
			iqdbe02EmbOutEmbedPair1Left
				INTEGER,
			iqdbe02EmbOutEmbedPair1Right
				INTEGER,
			iqdbe02EmbOutEmbedPair1LinkLRSelection
				INTEGER,
			iqdbe02EmbOutEmbedPair2Left
				INTEGER,
			iqdbe02EmbOutEmbedPair2Right
				INTEGER,
			iqdbe02EmbOutEmbedPair2LinkLRSelection
				INTEGER,
			iqdbe02EmbOutEmbedPair3Left
				INTEGER,
			iqdbe02EmbOutEmbedPair3Right
				INTEGER,
			iqdbe02EmbOutEmbedPair3LinkLRSelection
				INTEGER,
			iqdbe02EmbOutEmbedPair4Left
				INTEGER,
			iqdbe02EmbOutEmbedPair4Right
				INTEGER,
			iqdbe02EmbOutEmbedPair4LinkLRSelection
				INTEGER,
			iqdbe02EmbOutEmbedPair5Left
				INTEGER,
			iqdbe02EmbOutEmbedPair5Right
				INTEGER,
			iqdbe02EmbOutEmbedPair5LinkLRSelection
				INTEGER,
			iqdbe02EmbOutEmbedPair6Left
				INTEGER,
			iqdbe02EmbOutEmbedPair6Right
				INTEGER,
			iqdbe02EmbOutEmbedPair6LinkLRSelection
				INTEGER,
			iqdbe02EmbOutEmbedPair7Left
				INTEGER,
			iqdbe02EmbOutEmbedPair7Right
				INTEGER,
			iqdbe02EmbOutEmbedPair7LinkLRSelection
				INTEGER,
			iqdbe02EmbOutEmbedPair8Left
				INTEGER,
			iqdbe02EmbOutEmbedPair8Right
				INTEGER,
			iqdbe02EmbOutEmbedPair8LinkLRSelection
				INTEGER,
			iqdbe02AudioEmbModeInput1
				INTEGER,
			iqdbe02AudioEmbModeInput2
				INTEGER,
			iqdbe02AudioEmbModeInput3
				INTEGER,
			iqdbe02AudioEmbModeInput4
				INTEGER,
			iqdbe02AudioEmbModeInput5
				INTEGER,
			iqdbe02AudioEmbModeInput6
				INTEGER,
			iqdbe02AudioEmbModeInput7
				INTEGER,
			iqdbe02AudioEmbModeInput8
				INTEGER,
			iqdbe02EmbNamesDisembederNamesDisembed1
				RollCallString,
			iqdbe02EmbNamesDisembederNamesDisembed1R
				RollCallString,
			iqdbe02EmbNamesDisembederNamesDisembed2
				RollCallString,
			iqdbe02EmbNamesDisembederNamesDisembed2R
				RollCallString,
			iqdbe02EmbNamesDisembederNamesDisembed3
				RollCallString,
			iqdbe02EmbNamesDisembederNamesDisembed3R
				RollCallString,
			iqdbe02EmbNamesDisembederNamesDisembed4
				RollCallString,
			iqdbe02EmbNamesDisembederNamesDisembed4R
				RollCallString,
			iqdbe02EmbNamesDisembederNamesDisembed5
				RollCallString,
			iqdbe02EmbNamesDisembederNamesDisembed5R
				RollCallString,
			iqdbe02EmbNamesDisembederNamesDisembed6
				RollCallString,
			iqdbe02EmbNamesDisembederNamesDisembed6R
				RollCallString,
			iqdbe02EmbNamesDisembederNamesDisembed7
				RollCallString,
			iqdbe02EmbNamesDisembederNamesDisembed7R
				RollCallString,
			iqdbe02EmbNamesDisembederNamesDisembed8
				RollCallString,
			iqdbe02EmbNamesDisembederNamesDisembed8R
				RollCallString,
			iqdbe02EmbNamesEmbeddedOPNamesEmbed1
				RollCallString,
			iqdbe02EmbNamesEmbeddedOPNamesEmbed1R
				RollCallString,
			iqdbe02EmbNamesEmbeddedOPNamesEmbed2
				RollCallString,
			iqdbe02EmbNamesEmbeddedOPNamesEmbed2R
				RollCallString,
			iqdbe02EmbNamesEmbeddedOPNamesEmbed3
				RollCallString,
			iqdbe02EmbNamesEmbeddedOPNamesEmbed3R
				RollCallString,
			iqdbe02EmbNamesEmbeddedOPNamesEmbed4
				RollCallString,
			iqdbe02EmbNamesEmbeddedOPNamesEmbed4R
				RollCallString,
			iqdbe02EmbNamesEmbeddedOPNamesEmbed5
				RollCallString,
			iqdbe02EmbNamesEmbeddedOPNamesEmbed5R
				RollCallString,
			iqdbe02EmbNamesEmbeddedOPNamesEmbed6
				RollCallString,
			iqdbe02EmbNamesEmbeddedOPNamesEmbed6R
				RollCallString,
			iqdbe02EmbNamesEmbeddedOPNamesEmbed7
				RollCallString,
			iqdbe02EmbNamesEmbeddedOPNamesEmbed7R
				RollCallString,
			iqdbe02EmbNamesEmbeddedOPNamesEmbed8
				RollCallString,
			iqdbe02EmbNamesEmbeddedOPNamesEmbed8R
				RollCallString,
			iqdbe02EmbNamesIPNamesStereoDisemb1
				INTEGER,
			iqdbe02EmbNamesIPNamesStereoDisemb2
				INTEGER,
			iqdbe02EmbNamesIPNamesStereoDisemb3
				INTEGER,
			iqdbe02EmbNamesIPNamesStereoDisemb4
				INTEGER,
			iqdbe02EmbNamesIPNamesStereoDisemb5
				INTEGER,
			iqdbe02EmbNamesIPNamesStereoDisemb6
				INTEGER,
			iqdbe02EmbNamesIPNamesStereoDisemb7
				INTEGER,
			iqdbe02EmbNamesIPNamesStereoDisemb8
				INTEGER,
			iqdbe02EmbNamesOPNamesStereoEmbed1
				INTEGER,
			iqdbe02EmbNamesOPNamesStereoEmbed2
				INTEGER,
			iqdbe02EmbNamesOPNamesStereoEmbed3
				INTEGER,
			iqdbe02EmbNamesOPNamesStereoEmbed4
				INTEGER,
			iqdbe02EmbNamesOPNamesStereoEmbed5
				INTEGER,
			iqdbe02EmbNamesOPNamesStereoEmbed6
				INTEGER,
			iqdbe02EmbNamesOPNamesStereoEmbed7
				INTEGER,
			iqdbe02EmbNamesOPNamesStereoEmbed8
				INTEGER,
			iqdbe02AudioMixNamesMix1
				RollCallString,
			iqdbe02AudioMixNamesMix2
				RollCallString,
			iqdbe02AudioMixNamesMix3
				RollCallString,
			iqdbe02AudioMixNamesMix4
				RollCallString,
			iqdbe02Mix1RoutingSource1
				INTEGER,
			iqdbe02Mix1RoutingInvert1
				INTEGER,
			iqdbe02Mix1RoutingSource2
				INTEGER,
			iqdbe02Mix1RoutingInvert2
				INTEGER,
			iqdbe02Mix1RoutingSource3
				INTEGER,
			iqdbe02Mix1RoutingInvert3
				INTEGER,
			iqdbe02Mix1RoutingSource4
				INTEGER,
			iqdbe02Mix1RoutingInvert4
				INTEGER,
			iqdbe02Mix1GainGain1
				INTEGER,
			iqdbe02Mix1GainMute1
				INTEGER,
			iqdbe02Mix1GainGain2
				INTEGER,
			iqdbe02Mix1GainMute2
				INTEGER,
			iqdbe02Mix1GainGain3
				INTEGER,
			iqdbe02Mix1GainMute3
				INTEGER,
			iqdbe02Mix1GainGain4
				INTEGER,
			iqdbe02Mix1GainMute4
				INTEGER,
			iqdbe02Mix1GainInp1Clip
				RollCallString,
			iqdbe02Mix1GainInp2Clip
				RollCallString,
			iqdbe02Mix1GainInp3Clip
				RollCallString,
			iqdbe02Mix1GainInp4Clip
				RollCallString,
			iqdbe02Mix1GainOPClip
				RollCallString,
			iqdbe02Mix2RoutingSource1
				INTEGER,
			iqdbe02Mix2RoutingInvert1
				INTEGER,
			iqdbe02Mix2RoutingSource2
				INTEGER,
			iqdbe02Mix2RoutingInvert2
				INTEGER,
			iqdbe02Mix2RoutingSource3
				INTEGER,
			iqdbe02Mix2RoutingInvert3
				INTEGER,
			iqdbe02Mix2RoutingSource4
				INTEGER,
			iqdbe02Mix2RoutingInvert4
				INTEGER,
			iqdbe02Mix2GainGain1
				INTEGER,
			iqdbe02Mix2GainMute1
				INTEGER,
			iqdbe02Mix2GainGain2
				INTEGER,
			iqdbe02Mix2GainMute2
				INTEGER,
			iqdbe02Mix2GainGain3
				INTEGER,
			iqdbe02Mix2GainMute3
				INTEGER,
			iqdbe02Mix2GainGain4
				INTEGER,
			iqdbe02Mix2GainMute4
				INTEGER,
			iqdbe02Mix2GainInp1Clip
				RollCallString,
			iqdbe02Mix2GainInp2Clip
				RollCallString,
			iqdbe02Mix2GainInp3Clip
				RollCallString,
			iqdbe02Mix2GainInp4Clip
				RollCallString,
			iqdbe02Mix2GainOPClip
				RollCallString,
			iqdbe02Mix3RoutingSource1
				INTEGER,
			iqdbe02Mix3RoutingInvert1
				INTEGER,
			iqdbe02Mix3RoutingSource2
				INTEGER,
			iqdbe02Mix3RoutingInvert2
				INTEGER,
			iqdbe02Mix3RoutingSource3
				INTEGER,
			iqdbe02Mix3RoutingInvert3
				INTEGER,
			iqdbe02Mix3RoutingSource4
				INTEGER,
			iqdbe02Mix3RoutingInvert4
				INTEGER,
			iqdbe02Mix3GainGain1
				INTEGER,
			iqdbe02Mix3GainMute1
				INTEGER,
			iqdbe02Mix3GainGain2
				INTEGER,
			iqdbe02Mix3GainMute2
				INTEGER,
			iqdbe02Mix3GainGain3
				INTEGER,
			iqdbe02Mix3GainMute3
				INTEGER,
			iqdbe02Mix3GainGain4
				INTEGER,
			iqdbe02Mix3GainMute4
				INTEGER,
			iqdbe02Mix3GainInp1Clip
				RollCallString,
			iqdbe02Mix3GainInp2Clip
				RollCallString,
			iqdbe02Mix3GainInp3Clip
				RollCallString,
			iqdbe02Mix3GainInp4Clip
				RollCallString,
			iqdbe02Mix3GainOPClip
				RollCallString,
			iqdbe02Mix4RoutingSource1
				INTEGER,
			iqdbe02Mix4RoutingInvert1
				INTEGER,
			iqdbe02Mix4RoutingSource2
				INTEGER,
			iqdbe02Mix4RoutingInvert2
				INTEGER,
			iqdbe02Mix4RoutingSource3
				INTEGER,
			iqdbe02Mix4RoutingInvert3
				INTEGER,
			iqdbe02Mix4RoutingSource4
				INTEGER,
			iqdbe02Mix4RoutingInvert4
				INTEGER,
			iqdbe02Mix4GainGain1
				INTEGER,
			iqdbe02Mix4GainMute1
				INTEGER,
			iqdbe02Mix4GainGain2
				INTEGER,
			iqdbe02Mix4GainMute2
				INTEGER,
			iqdbe02Mix4GainGain3
				INTEGER,
			iqdbe02Mix4GainMute3
				INTEGER,
			iqdbe02Mix4GainGain4
				INTEGER,
			iqdbe02Mix4GainMute4
				INTEGER,
			iqdbe02Mix4GainInp1Clip
				RollCallString,
			iqdbe02Mix4GainInp2Clip
				RollCallString,
			iqdbe02Mix4GainInp3Clip
				RollCallString,
			iqdbe02Mix4GainInp4Clip
				RollCallString,
			iqdbe02Mix4GainOPClip
				RollCallString,
			iqdbe02AESGainAESOut1AESOut1MuteL
				INTEGER,
			iqdbe02AESGainAESOut1AESOut1MuteR
				INTEGER,
			iqdbe02AESGainAESOut1AESOut1LGain
				INTEGER,
			iqdbe02AESGainAESOut1AESOut1RGain
				INTEGER,
			iqdbe02AESGainAESOut1Stereo
				INTEGER,
			iqdbe02AESGainAESOut1AESOut1InvertL
				INTEGER,
			iqdbe02AESGainAESOut1AESOut1InvertR
				INTEGER,
			iqdbe02AESGainAESOut1AESOut1LClip
				RollCallString,
			iqdbe02AESGainAESOut1AESOut1RClip
				RollCallString,
			iqdbe02AESGainAESOut2AESOut2MuteL
				INTEGER,
			iqdbe02AESGainAESOut2AESOut2MuteR
				INTEGER,
			iqdbe02AESGainAESOut2AESOut2LGain
				INTEGER,
			iqdbe02AESGainAESOut2AESOut2RGain
				INTEGER,
			iqdbe02AESGainAESOut2Stereo
				INTEGER,
			iqdbe02AESGainAESOut2AESOut2InvertL
				INTEGER,
			iqdbe02AESGainAESOut2AESOut2InvertR
				INTEGER,
			iqdbe02AESGainAESOut2AESOut2LClip
				RollCallString,
			iqdbe02AESGainAESOut2AESOut2RClip
				RollCallString,
			iqdbe02AESGainAESOut3AESOut3MuteL
				INTEGER,
			iqdbe02AESGainAESOut3AESOut3MuteR
				INTEGER,
			iqdbe02AESGainAESOut3AESOut3LGain
				INTEGER,
			iqdbe02AESGainAESOut3AESOut3RGain
				INTEGER,
			iqdbe02AESGainAESOut3Stereo
				INTEGER,
			iqdbe02AESGainAESOut3AESOut3InvertL
				INTEGER,
			iqdbe02AESGainAESOut3AESOut3InvertR
				INTEGER,
			iqdbe02AESGainAESOut3AESOut3LClip
				RollCallString,
			iqdbe02AESGainAESOut3AESOut3RClip
				RollCallString,
			iqdbe02AESGainAESOut4AESOut4MuteL
				INTEGER,
			iqdbe02AESGainAESOut4AESOut4MuteR
				INTEGER,
			iqdbe02AESGainAESOut4AESOut4LGain
				INTEGER,
			iqdbe02AESGainAESOut4AESOut4RGain
				INTEGER,
			iqdbe02AESGainAESOut4Stereo
				INTEGER,
			iqdbe02AESGainAESOut4AESOut4InvertL
				INTEGER,
			iqdbe02AESGainAESOut4AESOut4InvertR
				INTEGER,
			iqdbe02AESGainAESOut4AESOut4LClip
				RollCallString,
			iqdbe02AESGainAESOut4AESOut4RClip
				RollCallString,
			iqdbe02AESGainAESOut5AESOut5MuteL
				INTEGER,
			iqdbe02AESGainAESOut5AESOut5MuteR
				INTEGER,
			iqdbe02AESGainAESOut5AESOut5LGain
				INTEGER,
			iqdbe02AESGainAESOut5AESOut5RGain
				INTEGER,
			iqdbe02AESGainAESOut5Stereo
				INTEGER,
			iqdbe02AESGainAESOut5AESOut5InvertL
				INTEGER,
			iqdbe02AESGainAESOut5AESOut5InvertR
				INTEGER,
			iqdbe02AESGainAESOut5AESOut5LClip
				RollCallString,
			iqdbe02AESGainAESOut5AESOut5RClip
				RollCallString,
			iqdbe02AESGainAESOut6AESOut6MuteL
				INTEGER,
			iqdbe02AESGainAESOut6AESOut6MuteR
				INTEGER,
			iqdbe02AESGainAESOut6AESOut6LGain
				INTEGER,
			iqdbe02AESGainAESOut6AESOut6RGain
				INTEGER,
			iqdbe02AESGainAESOut6Stereo
				INTEGER,
			iqdbe02AESGainAESOut6AESOut6InvertL
				INTEGER,
			iqdbe02AESGainAESOut6AESOut6InvertR
				INTEGER,
			iqdbe02AESGainAESOut6AESOut6LClip
				RollCallString,
			iqdbe02AESGainAESOut6AESOut6RClip
				RollCallString,
			iqdbe02AESGainAESOut7AESOut7MuteL
				INTEGER,
			iqdbe02AESGainAESOut7AESOut7MuteR
				INTEGER,
			iqdbe02AESGainAESOut7AESOut7LGain
				INTEGER,
			iqdbe02AESGainAESOut7AESOut7RGain
				INTEGER,
			iqdbe02AESGainAESOut7Stereo
				INTEGER,
			iqdbe02AESGainAESOut7AESOut7InvertL
				INTEGER,
			iqdbe02AESGainAESOut7AESOut7InvertR
				INTEGER,
			iqdbe02AESGainAESOut7AESOut7LClip
				RollCallString,
			iqdbe02AESGainAESOut7AESOut7RClip
				RollCallString,
			iqdbe02AESGainAESOut8AESOut8MuteL
				INTEGER,
			iqdbe02AESGainAESOut8AESOut8MuteR
				INTEGER,
			iqdbe02AESGainAESOut8AESOut8LGain
				INTEGER,
			iqdbe02AESGainAESOut8AESOut8RGain
				INTEGER,
			iqdbe02AESGainAESOut8Stereo
				INTEGER,
			iqdbe02AESGainAESOut8AESOut8InvertL
				INTEGER,
			iqdbe02AESGainAESOut8AESOut8InvertR
				INTEGER,
			iqdbe02AESGainAESOut8AESOut8LClip
				RollCallString,
			iqdbe02AESGainAESOut8AESOut8RClip
				RollCallString,
			iqdbe02AESOutAESOut1Left
				INTEGER,
			iqdbe02AESOutAESOut1Right
				INTEGER,
			iqdbe02AESOutAESOut1LinkLRSelection
				INTEGER,
			iqdbe02AESOutAESOut2Left
				INTEGER,
			iqdbe02AESOutAESOut2Right
				INTEGER,
			iqdbe02AESOutAESOut2LinkLRSelection
				INTEGER,
			iqdbe02AESOutAESOut3Left
				INTEGER,
			iqdbe02AESOutAESOut3Right
				INTEGER,
			iqdbe02AESOutAESOut3LinkLRSelection
				INTEGER,
			iqdbe02AESOutAESOut4Left
				INTEGER,
			iqdbe02AESOutAESOut4Right
				INTEGER,
			iqdbe02AESOutAESOut4LinkLRSelection
				INTEGER,
			iqdbe02AESOutAESOut5Left
				INTEGER,
			iqdbe02AESOutAESOut5Right
				INTEGER,
			iqdbe02AESOutAESOut5LinkLRSelection
				INTEGER,
			iqdbe02AESOutAESOut6Left
				INTEGER,
			iqdbe02AESOutAESOut6Right
				INTEGER,
			iqdbe02AESOutAESOut6LinkLRSelection
				INTEGER,
			iqdbe02AESOutAESOut7Left
				INTEGER,
			iqdbe02AESOutAESOut7Right
				INTEGER,
			iqdbe02AESOutAESOut7LinkLRSelection
				INTEGER,
			iqdbe02AESOutAESOut8Left
				INTEGER,
			iqdbe02AESOutAESOut8Right
				INTEGER,
			iqdbe02AESOutAESOut8LinkLRSelection
				INTEGER,
			iqdbe02AESOutMonitoropLeft
				INTEGER,
			iqdbe02AESOutMonitoropRight
				INTEGER,
			iqdbe02AESOutMonitoropLinkLRSelection
				INTEGER,
			iqdbe02AESOutAESPortNamesAESPort1Stereo
				INTEGER,
			iqdbe02AESOutAESPortNamesAESPort1L
				RollCallString,
			iqdbe02AESOutAESPortNamesAESPort1R
				RollCallString,
			iqdbe02AESOutAESPortNamesAESPort2Stereo
				INTEGER,
			iqdbe02AESOutAESPortNamesAESPort2L
				RollCallString,
			iqdbe02AESOutAESPortNamesAESPort2R
				RollCallString,
			iqdbe02AESOutAESPortNamesAESPort3Stereo
				INTEGER,
			iqdbe02AESOutAESPortNamesAESPort3L
				RollCallString,
			iqdbe02AESOutAESPortNamesAESPort3R
				RollCallString,
			iqdbe02AESOutAESPortNamesAESPort4Stereo
				INTEGER,
			iqdbe02AESOutAESPortNamesAESPort4L
				RollCallString,
			iqdbe02AESOutAESPortNamesAESPort4R
				RollCallString,
			iqdbe02AESOutAESPortNamesAESPort5Stereo
				INTEGER,
			iqdbe02AESOutAESPortNamesAESPort5L
				RollCallString,
			iqdbe02AESOutAESPortNamesAESPort5R
				RollCallString,
			iqdbe02AESOutAESPortNamesAESPort6Stereo
				INTEGER,
			iqdbe02AESOutAESPortNamesAESPort6L
				RollCallString,
			iqdbe02AESOutAESPortNamesAESPort6R
				RollCallString,
			iqdbe02AESOutAESPortNamesAESPort7Stereo
				INTEGER,
			iqdbe02AESOutAESPortNamesAESPort7L
				RollCallString,
			iqdbe02AESOutAESPortNamesAESPort7R
				RollCallString,
			iqdbe02AESOutAESPortNamesAESPort8Stereo
				INTEGER,
			iqdbe02AESOutAESPortNamesAESPort8L
				RollCallString,
			iqdbe02AESOutAESPortNamesAESPort8R
				RollCallString,
			iqdbe02AESBusAESDataModeInput1
				INTEGER,
			iqdbe02AESBusAESDataModeInput2
				INTEGER,
			iqdbe02AESBusAESDataModeInput3
				INTEGER,
			iqdbe02AESBusAESDataModeInput4
				INTEGER,
			iqdbe02AESBusAESDataModeInput5
				INTEGER,
			iqdbe02AESBusAESDataModeInput6
				INTEGER,
			iqdbe02AESBusAESDataModeInput7
				INTEGER,
			iqdbe02AESBusAESDataModeInput8
				INTEGER,
			iqdbe02AESBusAESBusNamesAESBus1Stereo
				INTEGER,
			iqdbe02AESBusAESBusNamesAESBus1
				RollCallString,
			iqdbe02AESBusAESBusNamesAESBus1R
				RollCallString,
			iqdbe02AESBusAESBusNamesAESBus2Stereo
				INTEGER,
			iqdbe02AESBusAESBusNamesAESBus2
				RollCallString,
			iqdbe02AESBusAESBusNamesAESBus2R
				RollCallString,
			iqdbe02AESBusAESBusNamesAESBus3Stereo
				INTEGER,
			iqdbe02AESBusAESBusNamesAESBus3
				RollCallString,
			iqdbe02AESBusAESBusNamesAESBus3R
				RollCallString,
			iqdbe02AESBusAESBusNamesAESBus4Stereo
				INTEGER,
			iqdbe02AESBusAESBusNamesAESBus4
				RollCallString,
			iqdbe02AESBusAESBusNamesAESBus4R
				RollCallString,
			iqdbe02AESBusAESBusNamesAESBus5Stereo
				INTEGER,
			iqdbe02AESBusAESBusNamesAESBus5
				RollCallString,
			iqdbe02AESBusAESBusNamesAESBus5R
				RollCallString,
			iqdbe02AESBusAESBusNamesAESBus6Stereo
				INTEGER,
			iqdbe02AESBusAESBusNamesAESBus6
				RollCallString,
			iqdbe02AESBusAESBusNamesAESBus6R
				RollCallString,
			iqdbe02AESBusAESBusNamesAESBus7Stereo
				INTEGER,
			iqdbe02AESBusAESBusNamesAESBus7
				RollCallString,
			iqdbe02AESBusAESBusNamesAESBus7R
				RollCallString,
			iqdbe02AESBusAESBusNamesAESBus8Stereo
				INTEGER,
			iqdbe02AESBusAESBusNamesAESBus8
				RollCallString,
			iqdbe02AESBusAESBusNamesAESBus8R
				RollCallString,
			iqdbe02AESBusAESBusRoutingSource1
				INTEGER,
			iqdbe02AESBusAESBusRoutingSource2
				INTEGER,
			iqdbe02AESBusAESBusRoutingSource3
				INTEGER,
			iqdbe02AESBusAESBusRoutingSource4
				INTEGER,
			iqdbe02AESBusAESBusRoutingSource5
				INTEGER,
			iqdbe02AESBusAESBusRoutingSource6
				INTEGER,
			iqdbe02AESBusAESBusRoutingSource7
				INTEGER,
			iqdbe02AESBusAESBusRoutingSource8
				INTEGER,
			iqdbe02AESPortsAESDirectionAESPort1Dir
				INTEGER,
			iqdbe02AESPortsAESDirectionAESPort2Dir
				INTEGER,
			iqdbe02AESPortsAESDirectionAESPort3Dir
				INTEGER,
			iqdbe02AESPortsAESDirectionAESPort4Dir
				INTEGER,
			iqdbe02AESPortsAESDirectionAESPort5Dir
				INTEGER,
			iqdbe02AESPortsAESDirectionAESPort6Dir
				INTEGER,
			iqdbe02AESPortsAESDirectionAESPort7Dir
				INTEGER,
			iqdbe02AESPortsAESDirectionAESPort8Dir
				INTEGER,
			iqdbe02AudioDolbyETimingSelAudioPair
				INTEGER,
			iqdbe02AudioDolbyETimingRelativeTiming
				RollCallString,
			iqdbe02AudioDolbyETimingStatus
				RollCallString,
			iqdbe02AudioDolbyETimingError
				RollCallString,
			iqdbe02DolbyETimingDolbyELineStandard
				INTEGER,
			iqdbe02DolbyETimingDolbyELineAutoLineNo
				INTEGER,
			iqdbe02DolbyELineUserDolbyELinePair1
				INTEGER,
			iqdbe02DolbyELineUserDolbyELinePair2
				INTEGER,
			iqdbe02DolbyELineUserDolbyELinePair3
				INTEGER,
			iqdbe02DolbyELineUserDolbyELinePair4
				INTEGER,
			iqdbe02DolbyELineUserDolbyELinePair5
				INTEGER,
			iqdbe02DolbyELineUserDolbyELinePair6
				INTEGER,
			iqdbe02DolbyELineUserDolbyELinePair7
				INTEGER,
			iqdbe02DolbyELineUserDolbyELinePair8
				INTEGER,
			iqdbe02InputChanAssignDolbyAA1
				INTEGER,
			iqdbe02InputChanAssignDolbyAA2
				INTEGER,
			iqdbe02InputChanAssignDolbyALinkLR
				INTEGER,
			iqdbe02InputChanAssignDolbyBB3
				INTEGER,
			iqdbe02InputChanAssignDolbyBB4
				INTEGER,
			iqdbe02InputChanAssignDolbyBLinkLR
				INTEGER,
			iqdbe02InputChanAssignDolbyCC5
				INTEGER,
			iqdbe02InputChanAssignDolbyCC6
				INTEGER,
			iqdbe02InputChanAssignDolbyCLinkLR
				INTEGER,
			iqdbe02AudioDolbyEncoderEncodingMode
				INTEGER,
			iqdbe02AudioDolbyEncoderDataRate
				INTEGER,
			iqdbe02AudioDolbyEncoderReversionMode
				INTEGER,
			iqdbe02AudioDolbyEncoderEncoderLatency
				INTEGER,
			iqdbe02DolbyEncoderMetadataSourceMetadataSource
				INTEGER,
			iqdbe02DolbyEncoderMetadataSourceExternalProgConf
				RollCallString,
			iqdbe02DolbyEncoderMetadataSourceExtProgNamept1
				RollCallString,
			iqdbe02DolbyEncoderMetadataSourceExtProgNamept2
				RollCallString,
			iqdbe02DolbyEncoderInternalMetadataChannelMode
				INTEGER,
			iqdbe02DolbyEncoderInternalMetadataInputAssignAB
				RollCallString,
			iqdbe02DolbyEncoderInternalMetadataInputAssignC
				RollCallString,
			iqdbe02DolbyEncoderInternalMetadataDialogueNorm
				INTEGER,
			iqdbe02DolbyEncoderInternalMetadataLFEChannel
				INTEGER,
			iqdbe02DolbyEncoderInternalMetadataBitstreamMode
				INTEGER,
			iqdbe02DolbyEncoderInternalMetadataRFMode
				INTEGER,
			iqdbe02DolbyEncoderInternalMetadataLineMode
				INTEGER,
			iqdbe02InternalMetadataAudioProdInfoExists
				INTEGER,
			iqdbe02InternalMetadataAudioProdInfoMixLevel
				INTEGER,
			iqdbe02InternalMetadataAudioProdInfoRoomType
				INTEGER,
			iqdbe02DolbyEncoderInternalMetadataSurroundMode
				INTEGER,
			iqdbe02DolbyEncoderInternalMetadataCenterMixLevel
				INTEGER,
			iqdbe02DolbyEncoderInternalMetadataSurroundMixLevel
				INTEGER,
			iqdbe02DolbyEncoderInternalMetadataCopyrightProtect
				INTEGER,
			iqdbe02InternalMetadataExtendedBSI1ExtBSI1Exists
				INTEGER,
			iqdbe02InternalMetadataExtendedBSI1StereoDownmixMode
				INTEGER,
			iqdbe02InternalMetadataExtendedBSI1LtRtCenterDownmix
				INTEGER,
			iqdbe02InternalMetadataExtendedBSI1LoRoCenterDownmix
				INTEGER,
			iqdbe02InternalMetadataExtendedBSI1LtRtSurroundDownm
				INTEGER,
			iqdbe02InternalMetadataExtendedBSI1LoRoSurroundDownm
				INTEGER,
			iqdbe02InternalMetadataExtendedBSI2ExtBSI2Exists
				INTEGER,
			iqdbe02InternalMetadataExtendedBSI2SurroundExMode
				INTEGER,
			iqdbe02InternalMetadataExtendedBSI2LowpassFilter
				INTEGER,
			iqdbe02InternalMetadataExtendedBSI2LFEFilter
				INTEGER,
			iqdbe02InternalMetadataExtendedBSI2SurrPhaseShiftFi
				INTEGER,
			iqdbe02InternalMetadataExtendedBSI2Surr3dBAttenuator
				INTEGER,
			iqdbe02DolbyEncoderInternalMetadataDolbyEncReset
				INTEGER,
			iqdbe02InternalMetadataPresetIntMD
				INTEGER,
			iqdbe02InternalMetadataUserPresetSelectUserPreset
				INTEGER,
			iqdbe02InternalMetadataUserPreset
				INTEGER,
			iqdbe02InternalMetadataUserPresetUserPresetName
				RollCallString,
			iqdbe02DolbyEncoderOutputMetadataChannelMode
				RollCallString,
			iqdbe02DolbyEncoderOutputMetadataLFEChannel
				RollCallString,
			iqdbe02DolbyEncoderOutputMetadataDialogueNorm
				RollCallString,
			iqdbe02DolbyEncoderOutputMetadataBitstreamMode
				RollCallString,
			iqdbe02DolbyEncoderOutputMetadataRFMode
				RollCallString,
			iqdbe02DolbyEncoderOutputMetadataLineMode
				RollCallString,
			iqdbe02DolbyEncoderOutputMetadataCenterMixLevel
				RollCallString,
			iqdbe02DolbyEncoderOutputMetadataSurroundMixLevel
				RollCallString,
			iqdbe02DolbyEncoderOutputMetadataSurrondMode
				RollCallString,
			iqdbe02DolbyEncoderOutputMetadataCopyright
				RollCallString,
			iqdbe02OutputMetadataAudioProdInfoExists
				RollCallString,
			iqdbe02OutputMetadataAudioProdInfoMixLevel
				RollCallString,
			iqdbe02OutputMetadataAudioProdInfoRoomType
				RollCallString,
			iqdbe02OutputMetadataExtendedBSI1Exists
				RollCallString,
			iqdbe02OutputMetadataExtendedBSI1StereoDownmixMode
				RollCallString,
			iqdbe02OutputMetadataExtendedBSI1LtRtCenMixLevel
				RollCallString,
			iqdbe02OutputMetadataExtendedBSI1LtRtSurMixLevel
				RollCallString,
			iqdbe02OutputMetadataExtendedBSI1LoRoCenMixLevel
				RollCallString,
			iqdbe02OutputMetadataExtendedBSI1LoRoSurMixLevel
				RollCallString,
			iqdbe02OutputMetadataExtendedBSI2Exists
				RollCallString,
			iqdbe02OutputMetadataExtendedBSI2SurExMode
				RollCallString,
			iqdbe02OutputMetadataExtendedBSI2LowpassFilter
				RollCallString,
			iqdbe02OutputMetadataExtendedBSI2LFEFilter
				RollCallString,
			iqdbe02OutputMetadataExtendedBSI2SurPhshiftFilter
				RollCallString,
			iqdbe02OutputMetadataExtendedBSI2Sur3dBAttenuator
				RollCallString,
			iqdbe02AudioDolbyEncoderFirmwareVersion
				RollCallString,
			iqdbe02AudioDolbyEncoderBitstreamFormat
				INTEGER,
			iqdbe02AudioDolbyEncoderDDStreamNumber
				INTEGER,
			iqdbe02AudioVidDelayInternalDelay
				RollCallString,
			iqdbe02AudioVidDelayDelayMode
				INTEGER,
			iqdbe02VidDelaySetDelayDelayFrames
				INTEGER,
			iqdbe02VidDelaySetDelayVerticalTiming
				INTEGER,
			iqdbe02VidDelaySetDelayHorizontalTiming
				INTEGER,
			iqdbe02VidDelaySetDelayDelayms
				INTEGER,
			iqdbe02UtilsPatternsPatternEnable
				INTEGER,
			iqdbe02UtilsPatternsScrollPattern
				INTEGER,
			iqdbe02UtilsPatternsPatternType
				INTEGER,
			iqdbe02AudioUtilsANCblankonMismat
				INTEGER,
			iqdbe02UtilsFreezeForceFreeze
				INTEGER,
			iqdbe02UtilsFreezeFreezeType
				INTEGER,
			iqdbe02UtilsMonochrome
				INTEGER,
			iqdbe02UtilsMonochromeMonochromeType
				INTEGER,
			iqdbe02UtilsVBIBlankingANCMode
				INTEGER,
			iqdbe02UtilsVBIBlankingStandard
				INTEGER,
			iqdbe02UtilsVBIBlankingBlankAll
				INTEGER,
			iqdbe02UtilsVBIBlankingPassAll
				INTEGER,
			iqdbe02UtilsVBIBlankingBlank1
				INTEGER,
			iqdbe02UtilsVBIBlankingBlank2
				INTEGER,
			iqdbe02UtilsVBIBlankingBlank3
				INTEGER,
			iqdbe02UtilsVBIBlankingBlank4
				INTEGER,
			iqdbe02UtilsVBIBlankingBlank5
				INTEGER,
			iqdbe02UtilsVBIBlankingBlank6
				INTEGER,
			iqdbe02UtilsVBIBlankingBlank7
				INTEGER,
			iqdbe02UtilsVBIBlankingBlank8
				INTEGER,
			iqdbe02UtilsVBIBlankingBlank9
				INTEGER,
			iqdbe02UtilsVBIBlankingBlank10
				INTEGER,
			iqdbe02UtilsVBIBlankingBlank11
				INTEGER,
			iqdbe02UtilsVBIBlankingBlank12
				INTEGER,
			iqdbe02UtilsVBIBlankingBlank13
				INTEGER,
			iqdbe02UtilsVBIBlankingBlank14
				INTEGER,
			iqdbe02UtilsVBIBlankingBlank15
				INTEGER,
			iqdbe02UtilsVBIBlankingBlank16
				INTEGER,
			iqdbe02UtilsVBIBlankingBlank17
				INTEGER,
			iqdbe02UtilsVBIBlankingBlank18
				INTEGER,
			iqdbe02UtilsVBIBlankingBlank19
				INTEGER,
			iqdbe02UtilsVBIBlankingBlank20
				INTEGER,
			iqdbe02UtilsVBIBlankingBlank21
				INTEGER,
			iqdbe02UtilsVBIBlankingBlank22
				INTEGER,
			iqdbe02UtilsVBIBlankingBlank23
				INTEGER,
			iqdbe02UtilsVBIBlankingBlank24
				INTEGER,
			iqdbe02UtilsVBIBlankingBlank25
				INTEGER,
			iqdbe02UtilsVBIBlankingBlank26
				INTEGER,
			iqdbe02UtilsVBIBlankingBlank27
				INTEGER,
			iqdbe02UtilsVBIBlankingBlank28
				INTEGER,
			iqdbe02UtilsVBIBlankingBlank29
				INTEGER,
			iqdbe02UtilsVBIBlankingBlank30
				INTEGER,
			iqdbe02UtilsVBIBlankingBlank31
				INTEGER,
			iqdbe02UtilsVBIBlankingBlank32
				INTEGER,
			iqdbe02UtilsVBIBlankingBlank33
				INTEGER,
			iqdbe02UtilsVBIBlankingBlank34
				INTEGER,
			iqdbe02RecallMemory
				INTEGER,
			iqdbe02SelMemory
				INTEGER,
			iqdbe02SaveMemory
				INTEGER,
			iqdbe02ClearMemory
				INTEGER,
			iqdbe02MemoryNameChangeName
				RollCallString,
			iqdbe02MemoryNameLastUserMemory
				RollCallString,
			iqdbe02MemoryName1
				RollCallString,
			iqdbe02MemoryName2
				RollCallString,
			iqdbe02MemoryName3
				RollCallString,
			iqdbe02MemoryName4
				RollCallString,
			iqdbe02MemoryName5
				RollCallString,
			iqdbe02MemoryName6
				RollCallString,
			iqdbe02MemoryName7
				RollCallString,
			iqdbe02MemoryName8
				RollCallString,
			iqdbe02MemoryName9
				RollCallString,
			iqdbe02MemoryName10
				RollCallString,
			iqdbe02MemoryName11
				RollCallString,
			iqdbe02MemoryName12
				RollCallString,
			iqdbe02MemoryName13
				RollCallString,
			iqdbe02MemoryName14
				RollCallString,
			iqdbe02MemoryName15
				RollCallString,
			iqdbe02MemoryName16
				RollCallString,
			iqdbe02LoggingVideoLoggingLogInput1Type
				INTEGER,
			iqdbe02LoggingVideoLoggingInput1Type
				RollCallString,
			iqdbe02LoggingVideoLoggingLogInput1Status
				INTEGER,
			iqdbe02LoggingVideoLoggingInput1Status
				RollCallString,
			iqdbe02LoggingVideoLoggingLogInput1Std
				INTEGER,
			iqdbe02LoggingVideoLoggingInput1Std
				RollCallString,
			iqdbe02LoggingVideoLoggingLogInput1Errors
				INTEGER,
			iqdbe02LoggingVideoLoggingInput1Errors
				RollCallString,
			iqdbe02LoggingVideoLoggingLogInput1ErrSecs
				INTEGER,
			iqdbe02LoggingVideoLoggingInput1ErrSecs
				RollCallString,
			iqdbe02LoggingVideoLoggingLogInput1ANCErr
				INTEGER,
			iqdbe02LoggingVideoLoggingInput1ANCErrors
				RollCallString,
			iqdbe02LoggingVideoLoggingLogInput1ANCErrSec
				INTEGER,
			iqdbe02LoggingVideoLoggingInput1ANCErrSecs
				RollCallString,
			iqdbe02LoggingVideoLoggingLogOutputState
				INTEGER,
			iqdbe02LoggingVideoLoggingOutputState
				RollCallString,
			iqdbe02LoggingVideoLoggingLogOutputType
				INTEGER,
			iqdbe02LoggingVideoLoggingOutputType
				RollCallString,
			iqdbe02LoggingVideoLoggingLogOutputStandard
				INTEGER,
			iqdbe02LoggingVideoLoggingOutputStandard
				RollCallString,
			iqdbe02LoggingVideoLoggingLogoutputANCstat
				INTEGER,
			iqdbe02LoggingVideoLoggingOutputANCstate
				RollCallString,
			iqdbe02LoggingEmbAudLoggingLogInp1Emb1stat
				INTEGER,
			iqdbe02LoggingEmbAudLoggingInp1Emb1state
				RollCallString,
			iqdbe02LoggingEmbAudLoggingLogInp1Emb2stat
				INTEGER,
			iqdbe02LoggingEmbAudLoggingInp1Emb2state
				RollCallString,
			iqdbe02LoggingEmbAudLoggingLogInp1Emb3stat
				INTEGER,
			iqdbe02LoggingEmbAudLoggingInp1Emb3state
				RollCallString,
			iqdbe02LoggingEmbAudLoggingLogInp1Emb4stat
				INTEGER,
			iqdbe02LoggingEmbAudLoggingInp1Emb4state
				RollCallString,
			iqdbe02LoggingEmbAudLoggingLogInp1Emb5stat
				INTEGER,
			iqdbe02LoggingEmbAudLoggingInp1Emb5state
				RollCallString,
			iqdbe02LoggingEmbAudLoggingLogInp1Emb6stat
				INTEGER,
			iqdbe02LoggingEmbAudLoggingInp1Emb6state
				RollCallString,
			iqdbe02LoggingEmbAudLoggingLogInp1Emb7stat
				INTEGER,
			iqdbe02LoggingEmbAudLoggingInp1Emb7state
				RollCallString,
			iqdbe02LoggingEmbAudLoggingLogInp1Emb8stat
				INTEGER,
			iqdbe02LoggingEmbAudLoggingInp1Emb8state
				RollCallString,
			iqdbe02LoggingEmbAudLoggingLogInp1Emb1type
				INTEGER,
			iqdbe02LoggingEmbAudLoggingInp1Emb1type
				RollCallString,
			iqdbe02LoggingEmbAudLoggingLogInp1Emb2type
				INTEGER,
			iqdbe02LoggingEmbAudLoggingInp1Emb2type
				RollCallString,
			iqdbe02LoggingEmbAudLoggingLogInp1Emb3type
				INTEGER,
			iqdbe02LoggingEmbAudLoggingInp1Emb3type
				RollCallString,
			iqdbe02LoggingEmbAudLoggingLogInp1Emb4type
				INTEGER,
			iqdbe02LoggingEmbAudLoggingInp1Emb4type
				RollCallString,
			iqdbe02LoggingEmbAudLoggingLogInp1Emb5type
				INTEGER,
			iqdbe02LoggingEmbAudLoggingInp1Emb5type
				RollCallString,
			iqdbe02LoggingEmbAudLoggingLogInp1Emb6type
				INTEGER,
			iqdbe02LoggingEmbAudLoggingInp1Emb6type
				RollCallString,
			iqdbe02LoggingEmbAudLoggingLogInp1Emb7type
				INTEGER,
			iqdbe02LoggingEmbAudLoggingInp1Emb7type
				RollCallString,
			iqdbe02LoggingEmbAudLoggingLogInp1Emb8type
				INTEGER,
			iqdbe02LoggingEmbAudLoggingInp1Emb8type
				RollCallString,
			iqdbe02LoggingOPAudLoggingLogOutEmb1state
				INTEGER,
			iqdbe02LoggingOPAudLoggingOutEmb1state
				RollCallString,
			iqdbe02LoggingOPAudLoggingLogOutEmb2state
				INTEGER,
			iqdbe02LoggingOPAudLoggingOutEmb2state
				RollCallString,
			iqdbe02LoggingOPAudLoggingLogOutEmb3state
				INTEGER,
			iqdbe02LoggingOPAudLoggingOutEmb3state
				RollCallString,
			iqdbe02LoggingOPAudLoggingLogOutEmb4state
				INTEGER,
			iqdbe02LoggingOPAudLoggingOutEmb4state
				RollCallString,
			iqdbe02LoggingOPAudLoggingLogOutEmb5state
				INTEGER,
			iqdbe02LoggingOPAudLoggingOutEmb5state
				RollCallString,
			iqdbe02LoggingOPAudLoggingLogOutEmb6state
				INTEGER,
			iqdbe02LoggingOPAudLoggingOutEmb6state
				RollCallString,
			iqdbe02LoggingOPAudLoggingLogOutEmb7state
				INTEGER,
			iqdbe02LoggingOPAudLoggingOutEmb7state
				RollCallString,
			iqdbe02LoggingOPAudLoggingLogOutEmb8state
				INTEGER,
			iqdbe02LoggingOPAudLoggingOutEmb8state
				RollCallString,
			iqdbe02LoggingOPAudLoggingLogOutEmb1type
				INTEGER,
			iqdbe02LoggingOPAudLoggingOutEmb1type
				RollCallString,
			iqdbe02LoggingOPAudLoggingLogOutEmb2type
				INTEGER,
			iqdbe02LoggingOPAudLoggingOutEmb2type
				RollCallString,
			iqdbe02LoggingOPAudLoggingLogOutEmb3type
				INTEGER,
			iqdbe02LoggingOPAudLoggingOutEmb3type
				RollCallString,
			iqdbe02LoggingOPAudLoggingLogOutEmb4type
				INTEGER,
			iqdbe02LoggingOPAudLoggingOutEmb4type
				RollCallString,
			iqdbe02LoggingOPAudLoggingLogOutEmb5type
				INTEGER,
			iqdbe02LoggingOPAudLoggingOutEmb5type
				RollCallString,
			iqdbe02LoggingOPAudLoggingLogOutEmb6type
				INTEGER,
			iqdbe02LoggingOPAudLoggingOutEmb6type
				RollCallString,
			iqdbe02LoggingOPAudLoggingLogOutEmb7type
				INTEGER,
			iqdbe02LoggingOPAudLoggingOutEmb7type
				RollCallString,
			iqdbe02LoggingOPAudLoggingLogOutEmb8type
				INTEGER,
			iqdbe02LoggingOPAudLoggingOutEmb8type
				RollCallString,
			iqdbe02LoggingOPAudLevelLoggiLogOutEmb1LLev
				INTEGER,
			iqdbe02LoggingOPAudLevelLoggiOutEmb1LLevel
				RollCallString,
			iqdbe02LoggingOPAudLevelLoggiLogOutEmb1RLev
				INTEGER,
			iqdbe02LoggingOPAudLevelLoggiOutEmb1RLevel
				RollCallString,
			iqdbe02LoggingOPAudLevelLoggiLogOutEmb2LLev
				INTEGER,
			iqdbe02LoggingOPAudLevelLoggiOutEmb2LLevel
				RollCallString,
			iqdbe02LoggingOPAudLevelLoggiLogOutEmb2RLev
				INTEGER,
			iqdbe02LoggingOPAudLevelLoggiOutEmb2RLevel
				RollCallString,
			iqdbe02LoggingOPAudLevelLoggiLogOutEmb3LLev
				INTEGER,
			iqdbe02LoggingOPAudLevelLoggiOutEmb3LLevel
				RollCallString,
			iqdbe02LoggingOPAudLevelLoggiLogOutEmb3RLev
				INTEGER,
			iqdbe02LoggingOPAudLevelLoggiOutEmb3RLevel
				RollCallString,
			iqdbe02LoggingOPAudLevelLoggiLogOutEmb4LLev
				INTEGER,
			iqdbe02LoggingOPAudLevelLoggiOutEmb4LLevel
				RollCallString,
			iqdbe02LoggingOPAudLevelLoggiLogOutEmb4RLev
				INTEGER,
			iqdbe02LoggingOPAudLevelLoggiOutEmb4RLevel
				RollCallString,
			iqdbe02LoggingOPAudLevelLoggiLogOutEmb5LLev
				INTEGER,
			iqdbe02LoggingOPAudLevelLoggiOutEmb5LLevel
				RollCallString,
			iqdbe02LoggingOPAudLevelLoggiLogOutEmb5RLev
				INTEGER,
			iqdbe02LoggingOPAudLevelLoggiOutEmb5RLevel
				RollCallString,
			iqdbe02LoggingOPAudLevelLoggiLogOutEmb6LLev
				INTEGER,
			iqdbe02LoggingOPAudLevelLoggiOutEmb6LLevel
				RollCallString,
			iqdbe02LoggingOPAudLevelLoggiLogOutEmb6RLev
				INTEGER,
			iqdbe02LoggingOPAudLevelLoggiOutEmb6RLevel
				RollCallString,
			iqdbe02LoggingOPAudLevelLoggiLogOutEmb7LLev
				INTEGER,
			iqdbe02LoggingOPAudLevelLoggiOutEmb7LLevel
				RollCallString,
			iqdbe02LoggingOPAudLevelLoggiLogOutEmb7RLev
				INTEGER,
			iqdbe02LoggingOPAudLevelLoggiOutEmb7RLevel
				RollCallString,
			iqdbe02LoggingOPAudLevelLoggiLogOutEmb8LLev
				INTEGER,
			iqdbe02LoggingOPAudLevelLoggiOutEmb8LLevel
				RollCallString,
			iqdbe02LoggingOPAudLevelLoggiLogOutEmb8RLev
				INTEGER,
			iqdbe02LoggingOPAudLevelLoggiOutEmb8RLevel
				RollCallString,
			iqdbe02LoggingOPDolbyELoggingLogEmbDolbyE1
				INTEGER,
			iqdbe02LoggingOPDolbyELoggingEmbDolbyE1
				RollCallString,
			iqdbe02LoggingOPDolbyELoggingLogEmbDolbyE2
				INTEGER,
			iqdbe02LoggingOPDolbyELoggingEmbDolbyE2
				RollCallString,
			iqdbe02LoggingOPDolbyELoggingLogEmbDolbyE3
				INTEGER,
			iqdbe02LoggingOPDolbyELoggingEmbDolbyE3
				RollCallString,
			iqdbe02LoggingOPDolbyELoggingLogEmbDolbyE4
				INTEGER,
			iqdbe02LoggingOPDolbyELoggingEmbDolbyE4
				RollCallString,
			iqdbe02LoggingOPDolbyELoggingLogEmbDolbyE5
				INTEGER,
			iqdbe02LoggingOPDolbyELoggingEmbDolbyE5
				RollCallString,
			iqdbe02LoggingOPDolbyELoggingLogEmbDolbyE6
				INTEGER,
			iqdbe02LoggingOPDolbyELoggingEmbDolbyE6
				RollCallString,
			iqdbe02LoggingOPDolbyELoggingLogEmbDolbyE7
				INTEGER,
			iqdbe02LoggingOPDolbyELoggingEmbDolbyE7
				RollCallString,
			iqdbe02LoggingOPDolbyELoggingLogEmbDolbyE8
				INTEGER,
			iqdbe02LoggingOPDolbyELoggingEmbDolbyE8
				RollCallString,
			iqdbe02LoggingAESInputLoggingLogAESInput1sta
				INTEGER,
			iqdbe02LoggingAESInputLoggingAESInput1state
				RollCallString,
			iqdbe02LoggingAESInputLoggingLogAESInput2sta
				INTEGER,
			iqdbe02LoggingAESInputLoggingAESInput2state
				RollCallString,
			iqdbe02LoggingAESInputLoggingLogAESInput3sta
				INTEGER,
			iqdbe02LoggingAESInputLoggingAESInput3state
				RollCallString,
			iqdbe02LoggingAESInputLoggingLogAESInput4sta
				INTEGER,
			iqdbe02LoggingAESInputLoggingAESInput4state
				RollCallString,
			iqdbe02LoggingAESInputLoggingLogAESInput5sta
				INTEGER,
			iqdbe02LoggingAESInputLoggingAESInput5state
				RollCallString,
			iqdbe02LoggingAESInputLoggingLogAESInput6sta
				INTEGER,
			iqdbe02LoggingAESInputLoggingAESInput6state
				RollCallString,
			iqdbe02LoggingAESInputLoggingLogAESInput7sta
				INTEGER,
			iqdbe02LoggingAESInputLoggingAESInput7state
				RollCallString,
			iqdbe02LoggingAESInputLoggingLogAESInput8sta
				INTEGER,
			iqdbe02LoggingAESInputLoggingAESInput8state
				RollCallString,
			iqdbe02LoggingAESInputLoggingLogAESInput1typ
				INTEGER,
			iqdbe02LoggingAESInputLoggingAESInput1type
				RollCallString,
			iqdbe02LoggingAESInputLoggingLogAESInput2typ
				INTEGER,
			iqdbe02LoggingAESInputLoggingAESInput2type
				RollCallString,
			iqdbe02LoggingAESInputLoggingLogAESInput3typ
				INTEGER,
			iqdbe02LoggingAESInputLoggingAESInput3type
				RollCallString,
			iqdbe02LoggingAESInputLoggingLogAESInput4typ
				INTEGER,
			iqdbe02LoggingAESInputLoggingAESInput4type
				RollCallString,
			iqdbe02LoggingAESInputLoggingLogAESInput5typ
				INTEGER,
			iqdbe02LoggingAESInputLoggingAESInput5type
				RollCallString,
			iqdbe02LoggingAESInputLoggingLogAESInput6typ
				INTEGER,
			iqdbe02LoggingAESInputLoggingAESInput6type
				RollCallString,
			iqdbe02LoggingAESInputLoggingLogAESInput7typ
				INTEGER,
			iqdbe02LoggingAESInputLoggingAESInput7type
				RollCallString,
			iqdbe02LoggingAESInputLoggingLogAESInput8typ
				INTEGER,
			iqdbe02LoggingAESInputLoggingAESInput8type
				RollCallString,
			iqdbe02LoggingAESOutputLoggingLogAESOutput1st
				INTEGER,
			iqdbe02LoggingAESOutputLoggingAESOutput1state
				RollCallString,
			iqdbe02LoggingAESOutputLoggingLogAESOutput2st
				INTEGER,
			iqdbe02LoggingAESOutputLoggingAESOutput2state
				RollCallString,
			iqdbe02LoggingAESOutputLoggingLogAESOutput3st
				INTEGER,
			iqdbe02LoggingAESOutputLoggingAESOutput3state
				RollCallString,
			iqdbe02LoggingAESOutputLoggingLogAESOutput4st
				INTEGER,
			iqdbe02LoggingAESOutputLoggingAESOutput4state
				RollCallString,
			iqdbe02LoggingAESOutputLoggingLogAESOutput5st
				INTEGER,
			iqdbe02LoggingAESOutputLoggingAESOutput5state
				RollCallString,
			iqdbe02LoggingAESOutputLoggingLogAESOutput6st
				INTEGER,
			iqdbe02LoggingAESOutputLoggingAESOutput6state
				RollCallString,
			iqdbe02LoggingAESOutputLoggingLogAESOutput7st
				INTEGER,
			iqdbe02LoggingAESOutputLoggingAESOutput7state
				RollCallString,
			iqdbe02LoggingAESOutputLoggingLogAESOutput8st
				INTEGER,
			iqdbe02LoggingAESOutputLoggingAESOutput8state
				RollCallString,
			iqdbe02LoggingAESOutputLoggingLogAESOutput1ty
				INTEGER,
			iqdbe02LoggingAESOutputLoggingAESOutput1type
				RollCallString,
			iqdbe02LoggingAESOutputLoggingLogAESOutput2ty
				INTEGER,
			iqdbe02LoggingAESOutputLoggingAESOutput2type
				RollCallString,
			iqdbe02LoggingAESOutputLoggingLogAESOutput3ty
				INTEGER,
			iqdbe02LoggingAESOutputLoggingAESOutput3type
				RollCallString,
			iqdbe02LoggingAESOutputLoggingLogAESOutput4ty
				INTEGER,
			iqdbe02LoggingAESOutputLoggingAESOutput4type
				RollCallString,
			iqdbe02LoggingAESOutputLoggingLogAESOutput5ty
				INTEGER,
			iqdbe02LoggingAESOutputLoggingAESOutput5type
				RollCallString,
			iqdbe02LoggingAESOutputLoggingLogAESOutput6ty
				INTEGER,
			iqdbe02LoggingAESOutputLoggingAESOutput6type
				RollCallString,
			iqdbe02LoggingAESOutputLoggingLogAESOutput7ty
				INTEGER,
			iqdbe02LoggingAESOutputLoggingAESOutput7type
				RollCallString,
			iqdbe02LoggingAESOutputLoggingLogAESOutput8ty
				INTEGER,
			iqdbe02LoggingAESOutputLoggingAESOutput8type
				RollCallString,
			iqdbe02LoggingDolbyEncoderLogChannelMode
				INTEGER,
			iqdbe02LoggingDolbyEncoderChannelMode
				RollCallString,
			iqdbe02LoggingDolbyEncoderLogSource
				INTEGER,
			iqdbe02LoggingDolbyEncoderSource
				RollCallString,
			iqdbe02LoggingDolbyEncoderLogStatus
				INTEGER,
			iqdbe02LoggingDolbyEncoderStatus
				RollCallString,
			iqdbe02LoggingDolbyEncoderLogAC3
				INTEGER,
			iqdbe02LoggingDolbyEncoderAC3
				RollCallString,
			iqdbe02LoggingDolbyEncoderLogExBSI
				INTEGER,
			iqdbe02LoggingDolbyEncoderExBSI
				RollCallString,
			iqdbe02LoggingDolbyEncoderLogDataRate
				INTEGER,
			iqdbe02LoggingDolbyEncoderDataRate
				RollCallString,
			iqdbe02LoggingMiscLoggingLogSerialNo
				INTEGER,
			iqdbe02LoggingMiscLoggingSerialNo
				RollCallString,
			iqdbe02LoggingMiscLoggingLogOSVersion
				INTEGER,
			iqdbe02LoggingMiscLoggingOSVersion
				RollCallString,
			iqdbe02LoggingMiscLoggingLogBuildNo
				INTEGER,
			iqdbe02LoggingMiscLoggingBuildNo
				RollCallString,
			iqdbe02LoggingMiscLoggingLogHardwareVer
				INTEGER,
			iqdbe02LoggingMiscLoggingHardwareVer
				RollCallString,
			iqdbe02LoggingMiscLoggingLogFirmwareVer
				INTEGER,
			iqdbe02LoggingMiscLoggingFirmwareVer
				RollCallString,
			iqdbe02LoggingMiscLoggingLogUpTime
				INTEGER,
			iqdbe02LoggingMiscLoggingUpTime
				RollCallString,
			iqdbe02RollCallRollTrackDisableAll
				INTEGER,
			iqdbe02RollCallRollTrackIndex
				INTEGER,
			iqdbe02RollCallRollTrackSource
				INTEGER,
			iqdbe02RollCallRollTrackAddress
				RollCallString,
			iqdbe02RollCallRollTrackCommand
				RollCallString,
			iqdbe02RollCallRollTrackStatus
				RollCallString,
			iqdbe02RollCallRollTrackSending
				RollCallString,
			iqdbe02AudioSetupUnitStatusDisplay
				INTEGER,
			iqdbe02AudioSetupProduct
				RollCallString,
			iqdbe02AudioSetupRelease
				RollCallString,
			iqdbe02AudioSetupBuild
				RollCallString,
			iqdbe02AudioSetupKOS
				RollCallString,
			iqdbe02AudioSetupSerialNo
				RollCallString,
			iqdbe02AudioSetupFirmware
				RollCallString,
			iqdbe02AudioSetupPCB
				RollCallString,
			iqdbe02AudioSetupFactoryDefault
				INTEGER,
			iqdbe02AudioSetupRestart
				INTEGER,
			iqdbe02AudioSetupDefaultSettings
				INTEGER,
			iqdbe02AudioSetupSerialNumber
				RollCallString,
			iqdbe02AudioSetupBoardID
				INTEGER,
			iqdbe02AudioSetupSaveID
				INTEGER,
			iqdbe02AudioEngineerEngineerPassword
				RollCallString,
			iqdbe02AudioEngineerShowEngineer
				INTEGER,
			iqdbe02EngineerPageOptions1
				INTEGER,
			iqdbe02EngineerPageOptions2
				INTEGER,
			iqdbe02EngineerPageOptions3
				INTEGER,
			iqdbe02EngineerEngineerPageUndoChanges
				INTEGER,
			iqdbe02EngineerEngineerPageLineNumber
				RollCallString,
			iqdbe02EngineerEngineerPageSampleNumber
				RollCallString,
			iqdbe02EngineerEngineerPageDolbyModuleUpdate
				INTEGER,
			iqdbe02EngineerPaAutoalignEmbeddedInputs
				INTEGER,
			iqdbe02EngineerPaAutoalignAESInputs
				INTEGER,
			iqdbe02MenuAudioShowEngineer2
				INTEGER,
			iqdbe02MenuAudioUseEmbDelayFbac
				INTEGER
		}

	iqdbe02SlotIndex OBJECT-TYPE
		SYNTAX		Unsigned32
		MAX-ACCESS		not-accessible
		STATUS			current
		DESCRIPTION
				"The unique Index value for each slot.  Its value
					ranges between 1 and the value of slotNumber."
		::= { iqdbe02CmdEntry 0 }


	iqdbe02MenuInputIPLoss OBJECT-TYPE
		SYNTAX		INTEGER {
							val_No_Input(0),
							val_In_Out_Std_Mismatch(1)
							}
		MAX-ACCESS		read-write
		STATUS			current
		DESCRIPTION
				"TYPE: - RadiobuttonList
				 PAGE: - Input
					I/P Loss  cmdID= 33030
					No Input  value= 0
					In/Out Std.Mismatch  value= 1  "
		::= { iqdbe02CmdEntry 33030 }


	iqdbe02InputValidStdsAllValid OBJECT-TYPE
		SYNTAX		INTEGER { noAction(0),val_All_Valid(1) }
		MAX-ACCESS		read-write
		STATUS			current
		DESCRIPTION
				"TYPE: - Button
				 PAGE: - Input
					All Valid  cmdID= 32900  value= 1  "
		::= { iqdbe02CmdEntry 32900 }


	iqdbe02InputValidStdsAllInvalid OBJECT-TYPE
		SYNTAX		INTEGER { noAction(0),val_All_Invalid(1) }
		MAX-ACCESS		read-write
		STATUS			current
		DESCRIPTION
				"TYPE: - Button
				 PAGE: - Input
					All Invalid  cmdID= 32901  value= 1  "
		::= { iqdbe02CmdEntry 32901 }


	iqdbe02InputValidStds108023sF OBJECT-TYPE
		SYNTAX		INTEGER { disable(0), enable(1) }
		MAX-ACCESS		read-write
		STATUS			current
		DESCRIPTION
				"TYPE: - Checkbox
				 PAGE: - Input
					1080/23sF  cmdID= 32916 "
		::= { iqdbe02CmdEntry 32916 }


	iqdbe02InputValidStds108023p OBJECT-TYPE
		SYNTAX		INTEGER { disable(0), enable(1) }
		MAX-ACCESS		read-write
		STATUS			current
		DESCRIPTION
				"TYPE: - Checkbox
				 PAGE: - Input
					1080/23p  cmdID= 32915 "
		::= { iqdbe02CmdEntry 32915 }


	iqdbe02InputValidStds108024sF OBJECT-TYPE
		SYNTAX		INTEGER { disable(0), enable(1) }
		MAX-ACCESS		read-write
		STATUS			current
		DESCRIPTION
				"TYPE: - Checkbox
				 PAGE: - Input
					1080/24sF  cmdID= 32917 "
		::= { iqdbe02CmdEntry 32917 }


	iqdbe02InputValidStds108024p OBJECT-TYPE
		SYNTAX		INTEGER { disable(0), enable(1) }
		MAX-ACCESS		read-write
		STATUS			current
		DESCRIPTION
				"TYPE: - Checkbox
				 PAGE: - Input
					1080/24p  cmdID= 32914 "
		::= { iqdbe02CmdEntry 32914 }


	iqdbe02InputValidStds108025i OBJECT-TYPE
		SYNTAX		INTEGER { disable(0), enable(1) }
		MAX-ACCESS		read-write
		STATUS			current
		DESCRIPTION
				"TYPE: - Checkbox
				 PAGE: - Input
					1080/25i  cmdID= 32910 "
		::= { iqdbe02CmdEntry 32910 }


	iqdbe02InputValidStds108025p OBJECT-TYPE
		SYNTAX		INTEGER { disable(0), enable(1) }
		MAX-ACCESS		read-write
		STATUS			current
		DESCRIPTION
				"TYPE: - Checkbox
				 PAGE: - Input
					1080/25p  cmdID= 32911 "
		::= { iqdbe02CmdEntry 32911 }


	iqdbe02InputValidStds103529i OBJECT-TYPE
		SYNTAX		INTEGER { disable(0), enable(1) }
		MAX-ACCESS		read-write
		STATUS			current
		DESCRIPTION
				"TYPE: - Checkbox
				 PAGE: - Input
					1035/29i  cmdID= 32921 "
		::= { iqdbe02CmdEntry 32921 }


	iqdbe02InputValidStds108029i OBJECT-TYPE
		SYNTAX		INTEGER { disable(0), enable(1) }
		MAX-ACCESS		read-write
		STATUS			current
		DESCRIPTION
				"TYPE: - Checkbox
				 PAGE: - Input
					1080/29i  cmdID= 32919 "
		::= { iqdbe02CmdEntry 32919 }


	iqdbe02InputValidStds108029p OBJECT-TYPE
		SYNTAX		INTEGER { disable(0), enable(1) }
		MAX-ACCESS		read-write
		STATUS			current
		DESCRIPTION
				"TYPE: - Checkbox
				 PAGE: - Input
					1080/29p  cmdID= 32918 "
		::= { iqdbe02CmdEntry 32918 }


	iqdbe02InputValidStds103530i OBJECT-TYPE
		SYNTAX		INTEGER { disable(0), enable(1) }
		MAX-ACCESS		read-write
		STATUS			current
		DESCRIPTION
				"TYPE: - Checkbox
				 PAGE: - Input
					1035/30i  cmdID= 32920 "
		::= { iqdbe02CmdEntry 32920 }


	iqdbe02InputValidStds108030i OBJECT-TYPE
		SYNTAX		INTEGER { disable(0), enable(1) }
		MAX-ACCESS		read-write
		STATUS			current
		DESCRIPTION
				"TYPE: - Checkbox
				 PAGE: - Input
					1080/30i  cmdID= 32912 "
		::= { iqdbe02CmdEntry 32912 }


	iqdbe02InputValidStds108030p OBJECT-TYPE
		SYNTAX		INTEGER { disable(0), enable(1) }
		MAX-ACCESS		read-write
		STATUS			current
		DESCRIPTION
				"TYPE: - Checkbox
				 PAGE: - Input
					1080/30p  cmdID= 32913 "
		::= { iqdbe02CmdEntry 32913 }


	iqdbe02InputValidStds72050p OBJECT-TYPE
		SYNTAX		INTEGER { disable(0), enable(1) }
		MAX-ACCESS		read-write
		STATUS			current
		DESCRIPTION
				"TYPE: - Checkbox
				 PAGE: - Input
					720/50p  cmdID= 32922 "
		::= { iqdbe02CmdEntry 32922 }


	iqdbe02InputValidStds72059p OBJECT-TYPE
		SYNTAX		INTEGER { disable(0), enable(1) }
		MAX-ACCESS		read-write
		STATUS			current
		DESCRIPTION
				"TYPE: - Checkbox
				 PAGE: - Input
					720/59p  cmdID= 32924 "
		::= { iqdbe02CmdEntry 32924 }


	iqdbe02InputValidStds72060p OBJECT-TYPE
		SYNTAX		INTEGER { disable(0), enable(1) }
		MAX-ACCESS		read-write
		STATUS			current
		DESCRIPTION
				"TYPE: - Checkbox
				 PAGE: - Input
					720/60p  cmdID= 32923 "
		::= { iqdbe02CmdEntry 32923 }


	iqdbe02InputValidStds62525i OBJECT-TYPE
		SYNTAX		INTEGER { disable(0), enable(1) }
		MAX-ACCESS		read-write
		STATUS			current
		DESCRIPTION
				"TYPE: - Checkbox
				 PAGE: - Input
					625/25i  cmdID= 32925 "
		::= { iqdbe02CmdEntry 32925 }


	iqdbe02InputValidStds52529i OBJECT-TYPE
		SYNTAX		INTEGER { disable(0), enable(1) }
		MAX-ACCESS		read-write
		STATUS			current
		DESCRIPTION
				"TYPE: - Checkbox
				 PAGE: - Input
					525/29i  cmdID= 32926 "
		::= { iqdbe02CmdEntry 32926 }


	iqdbe02InputErrorsCRCErrs OBJECT-TYPE
		SYNTAX		RollCallString
		MAX-ACCESS		read-only
		STATUS			current
		DESCRIPTION
				"TYPE: - Display
				 PAGE: - Input
					CRC Errs  cmdID= 33050  format=   "
		::= { iqdbe02CmdEntry 33050 }


	iqdbe02InputErrorsCRCErrSec OBJECT-TYPE
		SYNTAX		RollCallString
		MAX-ACCESS		read-only
		STATUS			current
		DESCRIPTION
				"TYPE: - Display
				 PAGE: - Input
					CRC ErrSec  cmdID= 33051  format=   "
		::= { iqdbe02CmdEntry 33051 }


	iqdbe02InputErrorsANCErrs OBJECT-TYPE
		SYNTAX		RollCallString
		MAX-ACCESS		read-only
		STATUS			current
		DESCRIPTION
				"TYPE: - Display
				 PAGE: - Input
					ANC Errs  cmdID= 33053  format=   "
		::= { iqdbe02CmdEntry 33053 }


	iqdbe02InputErrorsANCErrSec OBJECT-TYPE
		SYNTAX		RollCallString
		MAX-ACCESS		read-only
		STATUS			current
		DESCRIPTION
				"TYPE: - Display
				 PAGE: - Input
					ANC ErrSec  cmdID= 33054  format=   "
		::= { iqdbe02CmdEntry 33054 }


	iqdbe02InputErrorsResetSec OBJECT-TYPE
		SYNTAX		RollCallString
		MAX-ACCESS		read-only
		STATUS			current
		DESCRIPTION
				"TYPE: - Display
				 PAGE: - Input
					ResetSec  cmdID= 33055  format=   "
		::= { iqdbe02CmdEntry 33055 }


	iqdbe02InputErrorsErrorReset OBJECT-TYPE
		SYNTAX		INTEGER { noAction(0),val_Error_Reset(1) }
		MAX-ACCESS		read-write
		STATUS			current
		DESCRIPTION
				"TYPE: - Button
				 PAGE: - Input
					Error Reset  cmdID= 33052  value= 1  "
		::= { iqdbe02CmdEntry 33052 }


	iqdbe02AudioOutputOutputStandard OBJECT-TYPE
		SYNTAX		INTEGER {
							val_Manual(0),
							val_Follows_Input(1)
							}
		MAX-ACCESS		read-write
		STATUS			current
		DESCRIPTION
				"TYPE: - RadiobuttonList
					Output Standard  cmdID= 33011
					Manual  value= 0
					Follows Input  value= 1  "
		::= { iqdbe02CmdEntry 33011 }


	iqdbe02AudioOutputSelectStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Select Standard  cmdID= 33010
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe02CmdEntry 33010 }


	iqdbe02OutputVideoProcAmpsMasterGain OBJECT-TYPE
		SYNTAX		INTEGER
		MAX-ACCESS		read-write
		STATUS			current
		DESCRIPTION
				"TYPE: - Number
					Master Gain  cmdID= 33000  min= -600  max= 600  step= 10  format= %0.1f dB  div_scale= 100
					Min = -6.0 dB  Max = 6.0 dB  Step = 0.1 dB "
		::= { iqdbe02CmdEntry 33000 }


	iqdbe02OutputVideoProcAmpsYGain OBJECT-TYPE
		SYNTAX		INTEGER
		MAX-ACCESS		read-write
		STATUS			current
		DESCRIPTION
				"TYPE: - Number
					Y Gain  cmdID= 33001  min= -600  max= 600  step= 10  format= %0.1f dB  div_scale= 100
					Min = -6.0 dB  Max = 6.0 dB  Step = 0.1 dB "
		::= { iqdbe02CmdEntry 33001 }


	iqdbe02OutputVideoProcAmpsCGain OBJECT-TYPE
		SYNTAX		INTEGER
		MAX-ACCESS		read-write
		STATUS			current
		DESCRIPTION
				"TYPE: - Number
					C Gain  cmdID= 33003  min= -600  max= 600  step= 10  format= %0.1f dB  div_scale= 100
					Min = -6.0 dB  Max = 6.0 dB  Step = 0.1 dB "
		::= { iqdbe02CmdEntry 33003 }


	iqdbe02OutputVideoProcAmpsBlackLevel OBJECT-TYPE
		SYNTAX		INTEGER
		MAX-ACCESS		read-write
		STATUS			current
		DESCRIPTION
				"TYPE: - Number
					Black Level  cmdID= 33002  min= -200  max= 200  step= 1  format= %0.0f mV  div_scale= 1
					Min = -200 mV  Max = 200 mV  Step = 1 mV "
		::= { iqdbe02CmdEntry 33002 }


	iqdbe02AudioOutputDefaultOutput OBJECT-TYPE
		SYNTAX		INTEGER {
							val_Freeze_Frame(1),
							val_Freeze_Field(5),
							val_Black(2),
							val_Input(3),
							val_Out_Pattern(4)
							}
		MAX-ACCESS		read-write
		STATUS			current
		DESCRIPTION
				"TYPE: - RadiobuttonList
					Default Output  cmdID= 33031
					Freeze Frame  value= 1
					Freeze Field  value= 5
					Black  value= 2
					Input  value= 3
					Out Pattern  value= 4  "
		::= { iqdbe02CmdEntry 33031 }


	iqdbe02AudioOutputDefaultOPStd OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Default O/P Std.  cmdID= 33012
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe02CmdEntry 33012 }


	iqdbe02AudioDelayASourcesManual OBJECT-TYPE
		SYNTAX		INTEGER { disable(0), enable(1) }
		MAX-ACCESS		read-write
		STATUS			current
		DESCRIPTION
				"TYPE: - Checkbox
				 PAGE: - Aud.Delays
					Manual  cmdID= 38041 "
		::= { iqdbe02CmdEntry 38041 }


	iqdbe02AudioDelayASourcesGPIPWM OBJECT-TYPE
		SYNTAX		INTEGER { disable(0), enable(1) }
		MAX-ACCESS		read-write
		STATUS			current
		DESCRIPTION
				"TYPE: - Checkbox
				 PAGE: - Aud.Delays
					GPI PWM  cmdID= 38042 "
		::= { iqdbe02CmdEntry 38042 }


	iqdbe02AudioDelayASourcesRollTrack14 OBJECT-TYPE
		SYNTAX		INTEGER { disable(0), enable(1) }
		MAX-ACCESS		read-write
		STATUS			current
		DESCRIPTION
				"TYPE: - Checkbox
				 PAGE: - Aud.Delays
					RollTrack14  cmdID= 38044 "
		::= { iqdbe02CmdEntry 38044 }


	iqdbe02AudioDelayASourcesRollTrack15 OBJECT-TYPE
		SYNTAX		INTEGER { disable(0), enable(1) }
		MAX-ACCESS		read-write
		STATUS			current
		DESCRIPTION
				"TYPE: - Checkbox
				 PAGE: - Aud.Delays
					RollTrack15  cmdID= 38045 "
		::= { iqdbe02CmdEntry 38045 }


	iqdbe02AudioDelayASourcesRollTrack16 OBJECT-TYPE
		SYNTAX		INTEGER { disable(0), enable(1) }
		MAX-ACCESS		read-write
		STATUS			current
		DESCRIPTION
				"TYPE: - Checkbox
				 PAGE: - Aud.Delays
					RollTrack16  cmdID= 38046 "
		::= { iqdbe02CmdEntry 38046 }


	iqdbe02AudioDelayASourcesRollTrack17 OBJECT-TYPE
		SYNTAX		INTEGER { disable(0), enable(1) }
		MAX-ACCESS		read-write
		STATUS			current
		DESCRIPTION
				"TYPE: - Checkbox
				 PAGE: - Aud.Delays
					RollTrack17  cmdID= 38047 "
		::= { iqdbe02CmdEntry 38047 }


	iqdbe02AudDelaysAudioDelayAAdjustCoarseDelay OBJECT-TYPE
		SYNTAX		INTEGER
		MAX-ACCESS		read-write
		STATUS			current
		DESCRIPTION
				"TYPE: - Number
				 PAGE: - Aud.Delays
					Adjust Coarse Delay  cmdID= 38043  min= -4000  max= 200000  step= 25  format= %0.2f ms  div_scale= 100
					Min = -40.00 ms  Max = 2000.00 ms  Step = 0.25 ms "
		::= { iqdbe02CmdEntry 38043 }


	iqdbe02AudDelaysAudioDelayACurrentAudioDelay OBJECT-TYPE
		SYNTAX		RollCallString
		MAX-ACCESS		read-only
		STATUS			current
		DESCRIPTION
				"TYPE: - Display
				 PAGE: - Aud.Delays
					Current Audio Delay  cmdID= 38048  format=   "
		::= { iqdbe02CmdEntry 38048 }


	iqdbe02AudioDelayBSourcesManual OBJECT-TYPE
		SYNTAX		INTEGER { disable(0), enable(1) }
		MAX-ACCESS		read-write
		STATUS			current
		DESCRIPTION
				"TYPE: - Checkbox
				 PAGE: - Aud.Delays
					Manual  cmdID= 38061 "
		::= { iqdbe02CmdEntry 38061 }


	iqdbe02AudioDelayBSourcesGPIPWM OBJECT-TYPE
		SYNTAX		INTEGER { disable(0), enable(1) }
		MAX-ACCESS		read-write
		STATUS			current
		DESCRIPTION
				"TYPE: - Checkbox
				 PAGE: - Aud.Delays
					GPI PWM  cmdID= 38062 "
		::= { iqdbe02CmdEntry 38062 }


	iqdbe02AudioDelayBSourcesRollTrack14 OBJECT-TYPE
		SYNTAX		INTEGER { disable(0), enable(1) }
		MAX-ACCESS		read-write
		STATUS			current
		DESCRIPTION
				"TYPE: - Checkbox
				 PAGE: - Aud.Delays
					RollTrack14  cmdID= 38064 "
		::= { iqdbe02CmdEntry 38064 }


	iqdbe02AudioDelayBSourcesRollTrack15 OBJECT-TYPE
		SYNTAX		INTEGER { disable(0), enable(1) }
		MAX-ACCESS		read-write
		STATUS			current
		DESCRIPTION
				"TYPE: - Checkbox
				 PAGE: - Aud.Delays
					RollTrack15  cmdID= 38065 "
		::= { iqdbe02CmdEntry 38065 }


	iqdbe02AudioDelayBSourcesRollTrack16 OBJECT-TYPE
		SYNTAX		INTEGER { disable(0), enable(1) }
		MAX-ACCESS		read-write
		STATUS			current
		DESCRIPTION
				"TYPE: - Checkbox
				 PAGE: - Aud.Delays
					RollTrack16  cmdID= 38066 "
		::= { iqdbe02CmdEntry 38066 }


	iqdbe02AudioDelayBSourcesRollTrack17 OBJECT-TYPE
		SYNTAX		INTEGER { disable(0), enable(1) }
		MAX-ACCESS		read-write
		STATUS			current
		DESCRIPTION
				"TYPE: - Checkbox
				 PAGE: - Aud.Delays
					RollTrack17  cmdID= 38067 "
		::= { iqdbe02CmdEntry 38067 }


	iqdbe02AudDelaysAudioDelayBAdjustCoarseDelay OBJECT-TYPE
		SYNTAX		INTEGER
		MAX-ACCESS		read-write
		STATUS			current
		DESCRIPTION
				"TYPE: - Number
				 PAGE: - Aud.Delays
					Adjust Coarse Delay  cmdID= 38063  min= -4000  max= 200000  step= 25  format= %0.2f ms  div_scale= 100
					Min = -40.00 ms  Max = 2000.00 ms  Step = 0.25 ms "
		::= { iqdbe02CmdEntry 38063 }


	iqdbe02AudDelaysAudioDelayBCurrentAudioDelay OBJECT-TYPE
		SYNTAX		RollCallString
		MAX-ACCESS		read-only
		STATUS			current
		DESCRIPTION
				"TYPE: - Display
				 PAGE: - Aud.Delays
					Current Audio Delay  cmdID= 38068  format=   "
		::= { iqdbe02CmdEntry 38068 }


	iqdbe02AudDelaysAESDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-1  cmdID= 38600
					Min  value= 0
					Delay A  value= 1
					Delay B  value= 2  "
		::= { iqdbe02CmdEntry 38600 }


	iqdbe02AudDelaysAESDelaySelectInternal1 OBJECT-TYPE
		SYNTAX		INTEGER { disable(0), enable(1) }
		MAX-ACCESS		read-write
		STATUS			current
		DESCRIPTION
				"TYPE: - Checkbox
				 PAGE: - Aud.Delays
					Internal-1  cmdID= 38620 "
		::= { iqdbe02CmdEntry 38620 }


	iqdbe02AudDelaysAESDelaySelectAutoDolbyEPhase1 OBJECT-TYPE
		SYNTAX		INTEGER { disable(0), enable(1) }
		MAX-ACCESS		read-write
		STATUS			current
		DESCRIPTION
				"TYPE: - Checkbox
				 PAGE: - Aud.Delays
					Auto Dolby-E Phase  cmdID= 38118 "
		::= { iqdbe02CmdEntry 38118 }


	iqdbe02AudDelaysAESDelaySelectDelayLimit1 OBJECT-TYPE
		SYNTAX		RollCallString
		MAX-ACCESS		read-only
		STATUS			current
		DESCRIPTION
				"TYPE: - Display
				 PAGE: - Aud.Delays
					Delay Limit  cmdID= 38300  format=   "
		::= { iqdbe02CmdEntry 38300 }


	iqdbe02AudDelaysAESDelaySelectAES1FineDelay OBJECT-TYPE
		SYNTAX		INTEGER
		MAX-ACCESS		read-write
		STATUS			current
		DESCRIPTION
				"TYPE: - Number
				 PAGE: - Aud.Delays
					AES 1 Fine Delay  cmdID= 38130  min= -2450  max= 2450  step= 52  format= %0.3f ms  div_scale= 10000
					Min = -0.245 ms  Max = 0.245 ms  Step = 0.005 ms "
		::= { iqdbe02CmdEntry 38130 }


	iqdbe02AudDelaysAESDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-2  cmdID= 38601
					Min  value= 0
					Delay A  value= 1
					Delay B  value= 2  "
		::= { iqdbe02CmdEntry 38601 }


	iqdbe02AudDelaysAESDelaySelectInternal2 OBJECT-TYPE
		SYNTAX		INTEGER { disable(0), enable(1) }
		MAX-ACCESS		read-write
		STATUS			current
		DESCRIPTION
				"TYPE: - Checkbox
				 PAGE: - Aud.Delays
					Internal-2  cmdID= 38621 "
		::= { iqdbe02CmdEntry 38621 }


	iqdbe02AudDelaysAESDelaySelectAutoDolbyEPhase2 OBJECT-TYPE
		SYNTAX		INTEGER { disable(0), enable(1) }
		MAX-ACCESS		read-write
		STATUS			current
		DESCRIPTION
				"TYPE: - Checkbox
				 PAGE: - Aud.Delays
					Auto Dolby-E Phase  cmdID= 38119 "
		::= { iqdbe02CmdEntry 38119 }


	iqdbe02AudDelaysAESDelaySelectDelayLimit2 OBJECT-TYPE
		SYNTAX		RollCallString
		MAX-ACCESS		read-only
		STATUS			current
		DESCRIPTION
				"TYPE: - Display
				 PAGE: - Aud.Delays
					Delay Limit  cmdID= 38301  format=   "
		::= { iqdbe02CmdEntry 38301 }


	iqdbe02AudDelaysAESDelaySelectAES2FineDelay OBJECT-TYPE
		SYNTAX		INTEGER
		MAX-ACCESS		read-write
		STATUS			current
		DESCRIPTION
				"TYPE: - Number
				 PAGE: - Aud.Delays
					AES 2 Fine Delay  cmdID= 38131  min= -2450  max= 2450  step= 52  format= %0.3f ms  div_scale= 10000
					Min = -0.245 ms  Max = 0.245 ms  Step = 0.005 ms "
		::= { iqdbe02CmdEntry 38131 }


	iqdbe02AudDelaysAESDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-3  cmdID= 38602
					Min  value= 0
					Delay A  value= 1
					Delay B  value= 2  "
		::= { iqdbe02CmdEntry 38602 }


	iqdbe02AudDelaysAESDelaySelectInternal3 OBJECT-TYPE
		SYNTAX		INTEGER { disable(0), enable(1) }
		MAX-ACCESS		read-write
		STATUS			current
		DESCRIPTION
				"TYPE: - Checkbox
				 PAGE: - Aud.Delays
					Internal-3  cmdID= 38622 "
		::= { iqdbe02CmdEntry 38622 }


	iqdbe02AudDelaysAESDelaySelectAutoDolbyEPhase3 OBJECT-TYPE
		SYNTAX		INTEGER { disable(0), enable(1) }
		MAX-ACCESS		read-write
		STATUS			current
		DESCRIPTION
				"TYPE: - Checkbox
				 PAGE: - Aud.Delays
					Auto Dolby-E Phase  cmdID= 38120 "
		::= { iqdbe02CmdEntry 38120 }


	iqdbe02AudDelaysAESDelaySelectDelayLimit3 OBJECT-TYPE
		SYNTAX		RollCallString
		MAX-ACCESS		read-only
		STATUS			current
		DESCRIPTION
				"TYPE: - Display
				 PAGE: - Aud.Delays
					Delay Limit  cmdID= 38302  format=   "
		::= { iqdbe02CmdEntry 38302 }


	iqdbe02AudDelaysAESDelaySelectAES3FineDelay OBJECT-TYPE
		SYNTAX		INTEGER
		MAX-ACCESS		read-write
		STATUS			current
		DESCRIPTION
				"TYPE: - Number
				 PAGE: - Aud.Delays
					AES 3 Fine Delay  cmdID= 38132  min= -2450  max= 2450  step= 52  format= %0.3f ms  div_scale= 10000
					Min = -0.245 ms  Max = 0.245 ms  Step = 0.005 ms "
		::= { iqdbe02CmdEntry 38132 }


	iqdbe02AudDelaysAESDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-4  cmdID= 38603
					Min  value= 0
					Delay A  value= 1
					Delay B  value= 2  "
		::= { iqdbe02CmdEntry 38603 }


	iqdbe02AudDelaysAESDelaySelectInternal4 OBJECT-TYPE
		SYNTAX		INTEGER { disable(0), enable(1) }
		MAX-ACCESS		read-write
		STATUS			current
		DESCRIPTION
				"TYPE: - Checkbox
				 PAGE: - Aud.Delays
					Internal-4  cmdID= 38623 "
		::= { iqdbe02CmdEntry 38623 }


	iqdbe02AudDelaysAESDelaySelectAutoDolbyEPhase4 OBJECT-TYPE
		SYNTAX		INTEGER { disable(0), enable(1) }
		MAX-ACCESS		read-write
		STATUS			current
		DESCRIPTION
				"TYPE: - Checkbox
				 PAGE: - Aud.Delays
					Auto Dolby-E Phase  cmdID= 38121 "
		::= { iqdbe02CmdEntry 38121 }


	iqdbe02AudDelaysAESDelaySelectDelayLimit4 OBJECT-TYPE
		SYNTAX		RollCallString
		MAX-ACCESS		read-only
		STATUS			current
		DESCRIPTION
				"TYPE: - Display
				 PAGE: - Aud.Delays
					Delay Limit  cmdID= 38303  format=   "
		::= { iqdbe02CmdEntry 38303 }


	iqdbe02AudDelaysAESDelaySelectAES4FineDelay OBJECT-TYPE
		SYNTAX		INTEGER
		MAX-ACCESS		read-write
		STATUS			current
		DESCRIPTION
				"TYPE: - Number
				 PAGE: - Aud.Delays
					AES 4 Fine Delay  cmdID= 38133  min= -2450  max= 2450  step= 52  format= %0.3f ms  div_scale= 10000
					Min = -0.245 ms  Max = 0.245 ms  Step = 0.005 ms "
		::= { iqdbe02CmdEntry 38133 }


	iqdbe02AudDelaysAESDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-5  cmdID= 38604
					Min  value= 0
					Delay A  value= 1
					Delay B  value= 2  "
		::= { iqdbe02CmdEntry 38604 }


	iqdbe02AudDelaysAESDelaySelectInternal5 OBJECT-TYPE
		SYNTAX		INTEGER { disable(0), enable(1) }
		MAX-ACCESS		read-write
		STATUS			current
		DESCRIPTION
				"TYPE: - Checkbox
				 PAGE: - Aud.Delays
					Internal-5  cmdID= 38624 "
		::= { iqdbe02CmdEntry 38624 }


	iqdbe02AudDelaysAESDelaySelectAutoDolbyEPhase5 OBJECT-TYPE
		SYNTAX		INTEGER { disable(0), enable(1) }
		MAX-ACCESS		read-write
		STATUS			current
		DESCRIPTION
				"TYPE: - Checkbox
				 PAGE: - Aud.Delays
					Auto Dolby-E Phase  cmdID= 38122 "
		::= { iqdbe02CmdEntry 38122 }


	iqdbe02AudDelaysAESDelaySelectDelayLimit5 OBJECT-TYPE
		SYNTAX		RollCallString
		MAX-ACCESS		read-only
		STATUS			current
		DESCRIPTION
				"TYPE: - Display
				 PAGE: - Aud.Delays
					Delay Limit  cmdID= 38304  format=   "
		::= { iqdbe02CmdEntry 38304 }


	iqdbe02AudDelaysAESDelaySelectAES5FineDelay OBJECT-TYPE
		SYNTAX		INTEGER
		MAX-ACCESS		read-write
		STATUS			current
		DESCRIPTION
				"TYPE: - Number
				 PAGE: - Aud.Delays
					AES 5 Fine Delay  cmdID= 38134  min= -2450  max= 2450  step= 52  format= %0.3f ms  div_scale= 10000
					Min = -0.245 ms  Max = 0.245 ms  Step = 0.005 ms "
		::= { iqdbe02CmdEntry 38134 }


	iqdbe02AudDelaysAESDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-6  cmdID= 38605
					Min  value= 0
					Delay A  value= 1
					Delay B  value= 2  "
		::= { iqdbe02CmdEntry 38605 }


	iqdbe02AudDelaysAESDelaySelectInternal6 OBJECT-TYPE
		SYNTAX		INTEGER { disable(0), enable(1) }
		MAX-ACCESS		read-write
		STATUS			current
		DESCRIPTION
				"TYPE: - Checkbox
				 PAGE: - Aud.Delays
					Internal-6  cmdID= 38625 "
		::= { iqdbe02CmdEntry 38625 }


	iqdbe02AudDelaysAESDelaySelectAutoDolbyEPhase6 OBJECT-TYPE
		SYNTAX		INTEGER { disable(0), enable(1) }
		MAX-ACCESS		read-write
		STATUS			current
		DESCRIPTION
				"TYPE: - Checkbox
				 PAGE: - Aud.Delays
					Auto Dolby-E Phase  cmdID= 38123 "
		::= { iqdbe02CmdEntry 38123 }


	iqdbe02AudDelaysAESDelaySelectDelayLimit6 OBJECT-TYPE
		SYNTAX		RollCallString
		MAX-ACCESS		read-only
		STATUS			current
		DESCRIPTION
				"TYPE: - Display
				 PAGE: - Aud.Delays
					Delay Limit  cmdID= 38305  format=   "
		::= { iqdbe02CmdEntry 38305 }


	iqdbe02AudDelaysAESDelaySelectAES6FineDelay OBJECT-TYPE
		SYNTAX		INTEGER
		MAX-ACCESS		read-write
		STATUS			current
		DESCRIPTION
				"TYPE: - Number
				 PAGE: - Aud.Delays
					AES 6 Fine Delay  cmdID= 38135  min= -2450  max= 2450  step= 52  format= %0.3f ms  div_scale= 10000
					Min = -0.245 ms  Max = 0.245 ms  Step = 0.005 ms "
		::= { iqdbe02CmdEntry 38135 }


	iqdbe02AudDelaysAESDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-7  cmdID= 38606
					Min  value= 0
					Delay A  value= 1
					Delay B  value= 2  "
		::= { iqdbe02CmdEntry 38606 }


	iqdbe02AudDelaysAESDelaySelectInternal7 OBJECT-TYPE
		SYNTAX		INTEGER { disable(0), enable(1) }
		MAX-ACCESS		read-write
		STATUS			current
		DESCRIPTION
				"TYPE: - Checkbox
				 PAGE: - Aud.Delays
					Internal-7  cmdID= 38626 "
		::= { iqdbe02CmdEntry 38626 }


	iqdbe02AudDelaysAESDelaySelectAutoDolbyEPhase7 OBJECT-TYPE
		SYNTAX		INTEGER { disable(0), enable(1) }
		MAX-ACCESS		read-write
		STATUS			current
		DESCRIPTION
				"TYPE: - Checkbox
				 PAGE: - Aud.Delays
					Auto Dolby-E Phase  cmdID= 38124 "
		::= { iqdbe02CmdEntry 38124 }


	iqdbe02AudDelaysAESDelaySelectDelayLimit7 OBJECT-TYPE
		SYNTAX		RollCallString
		MAX-ACCESS		read-only
		STATUS			current
		DESCRIPTION
				"TYPE: - Display
				 PAGE: - Aud.Delays
					Delay Limit  cmdID= 38306  format=   "
		::= { iqdbe02CmdEntry 38306 }


	iqdbe02AudDelaysAESDelaySelectAES7FineDelay OBJECT-TYPE
		SYNTAX		INTEGER
		MAX-ACCESS		read-write
		STATUS			current
		DESCRIPTION
				"TYPE: - Number
				 PAGE: - Aud.Delays
					AES 7 Fine Delay  cmdID= 38136  min= -2450  max= 2450  step= 52  format= %0.3f ms  div_scale= 10000
					Min = -0.245 ms  Max = 0.245 ms  Step = 0.005 ms "
		::= { iqdbe02CmdEntry 38136 }


	iqdbe02AudDelaysAESDelaySelectDolbyEncoder OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Dolby Encoder  cmdID= 38607
					Min  value= 0
					Delay A  value= 1
					Delay B  value= 2  "
		::= { iqdbe02CmdEntry 38607 }


	iqdbe02AudDelaysAESDelaySelectInternal OBJECT-TYPE
		SYNTAX		INTEGER { disable(0), enable(1) }
		MAX-ACCESS		read-write
		STATUS			current
		DESCRIPTION
				"TYPE: - Checkbox
				 PAGE: - Aud.Delays
					Internal  cmdID= 38627 "
		::= { iqdbe02CmdEntry 38627 }


	iqdbe02AudDelaysAESDelaySelectAutoDolbyEPhase8 OBJECT-TYPE
		SYNTAX		INTEGER { disable(0), enable(1) }
		MAX-ACCESS		read-write
		STATUS			current
		DESCRIPTION
				"TYPE: - Checkbox
				 PAGE: - Aud.Delays
					Auto Dolby-E Phase  cmdID= 38125 "
		::= { iqdbe02CmdEntry 38125 }


	iqdbe02AudDelaysAESDelaySelectDelayLimit8 OBJECT-TYPE
		SYNTAX		RollCallString
		MAX-ACCESS		read-only
		STATUS			current
		DESCRIPTION
				"TYPE: - Display
				 PAGE: - Aud.Delays
					Delay Limit  cmdID= 38307  format=   "
		::= { iqdbe02CmdEntry 38307 }


	iqdbe02AudDelaysAESDelaySelectDolbyEncFineDela OBJECT-TYPE
		SYNTAX		INTEGER
		MAX-ACCESS		read-write
		STATUS			current
		DESCRIPTION
				"TYPE: - Number
				 PAGE: - Aud.Delays
					Dolby Enc Fine Dela  cmdID= 38137  min= -2450  max= 2450  step= 52  format= %0.3f ms  div_scale= 10000
					Min = -0.245 ms  Max = 0.245 ms  Step = 0.005 ms "
		::= { iqdbe02CmdEntry 38137 }


	iqdbe02AudDelaysEMBDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-1  cmdID= 38080
					Min  value= 0
					Delay A  value= 1
					Delay B  value= 2  "
		::= { iqdbe02CmdEntry 38080 }


	iqdbe02AudDelaysEMBDelaySelectInternal1 OBJECT-TYPE
		SYNTAX		INTEGER { disable(0), enable(1) }
		MAX-ACCESS		read-write
		STATUS			current
		DESCRIPTION
				"TYPE: - Checkbox
				 PAGE: - Aud.Delays
					Internal-1  cmdID= 38100 "
		::= { iqdbe02CmdEntry 38100 }


	iqdbe02AudDelaysEMBDelaySelectAutoDolbyEPhase1 OBJECT-TYPE
		SYNTAX		INTEGER { disable(0), enable(1) }
		MAX-ACCESS		read-write
		STATUS			current
		DESCRIPTION
				"TYPE: - Checkbox
				 PAGE: - Aud.Delays
					Auto Dolby-E Phase  cmdID= 38110 "
		::= { iqdbe02CmdEntry 38110 }


	iqdbe02AudDelaysEMBDelaySelectDelayLimit1 OBJECT-TYPE
		SYNTAX		RollCallString
		MAX-ACCESS		read-only
		STATUS			current
		DESCRIPTION
				"TYPE: - Display
				 PAGE: - Aud.Delays
					Delay Limit  cmdID= 38308  format=   "
		::= { iqdbe02CmdEntry 38308 }


	iqdbe02AudDelaysEMBDelaySelectEMB1FineDelay OBJECT-TYPE
		SYNTAX		INTEGER
		MAX-ACCESS		read-write
		STATUS			current
		DESCRIPTION
				"TYPE: - Number
				 PAGE: - Aud.Delays
					EMB 1 Fine Delay  cmdID= 38138  min= -2450  max= 2450  step= 52  format= %0.3f ms  div_scale= 10000
					Min = -0.245 ms  Max = 0.245 ms  Step = 0.005 ms "
		::= { iqdbe02CmdEntry 38138 }


	iqdbe02AudDelaysEMBDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-2  cmdID= 38081
					Min  value= 0
					Delay A  value= 1
					Delay B  value= 2  "
		::= { iqdbe02CmdEntry 38081 }


	iqdbe02AudDelaysEMBDelaySelectInternal2 OBJECT-TYPE
		SYNTAX		INTEGER { disable(0), enable(1) }
		MAX-ACCESS		read-write
		STATUS			current
		DESCRIPTION
				"TYPE: - Checkbox
				 PAGE: - Aud.Delays
					Internal-2  cmdID= 38101 "
		::= { iqdbe02CmdEntry 38101 }


	iqdbe02AudDelaysEMBDelaySelectAutoDolbyEPhase2 OBJECT-TYPE
		SYNTAX		INTEGER { disable(0), enable(1) }
		MAX-ACCESS		read-write
		STATUS			current
		DESCRIPTION
				"TYPE: - Checkbox
				 PAGE: - Aud.Delays
					Auto Dolby-E Phase  cmdID= 38111 "
		::= { iqdbe02CmdEntry 38111 }


	iqdbe02AudDelaysEMBDelaySelectDelayLimit2 OBJECT-TYPE
		SYNTAX		RollCallString
		MAX-ACCESS		read-only
		STATUS			current
		DESCRIPTION
				"TYPE: - Display
				 PAGE: - Aud.Delays
					Delay Limit  cmdID= 38309  format=   "
		::= { iqdbe02CmdEntry 38309 }


	iqdbe02AudDelaysEMBDelaySelectEMB2FineDelay OBJECT-TYPE
		SYNTAX		INTEGER
		MAX-ACCESS		read-write
		STATUS			current
		DESCRIPTION
				"TYPE: - Number
				 PAGE: - Aud.Delays
					EMB 2 Fine Delay  cmdID= 38139  min= -2450  max= 2450  step= 52  format= %0.3f ms  div_scale= 10000
					Min = -0.245 ms  Max = 0.245 ms  Step = 0.005 ms "
		::= { iqdbe02CmdEntry 38139 }


	iqdbe02AudDelaysEMBDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-3  cmdID= 38082
					Min  value= 0
					Delay A  value= 1
					Delay B  value= 2  "
		::= { iqdbe02CmdEntry 38082 }


	iqdbe02AudDelaysEMBDelaySelectInternal3 OBJECT-TYPE
		SYNTAX		INTEGER { disable(0), enable(1) }
		MAX-ACCESS		read-write
		STATUS			current
		DESCRIPTION
				"TYPE: - Checkbox
				 PAGE: - Aud.Delays
					Internal-3  cmdID= 38102 "
		::= { iqdbe02CmdEntry 38102 }


	iqdbe02AudDelaysEMBDelaySelectAutoDolbyEPhase3 OBJECT-TYPE
		SYNTAX		INTEGER { disable(0), enable(1) }
		MAX-ACCESS		read-write
		STATUS			current
		DESCRIPTION
				"TYPE: - Checkbox
				 PAGE: - Aud.Delays
					Auto Dolby-E Phase  cmdID= 38112 "
		::= { iqdbe02CmdEntry 38112 }


	iqdbe02AudDelaysEMBDelaySelectDelayLimit3 OBJECT-TYPE
		SYNTAX		RollCallString
		MAX-ACCESS		read-only
		STATUS			current
		DESCRIPTION
				"TYPE: - Display
				 PAGE: - Aud.Delays
					Delay Limit  cmdID= 38310  format=   "
		::= { iqdbe02CmdEntry 38310 }


	iqdbe02AudDelaysEMBDelaySelectEMB3FineDelay OBJECT-TYPE
		SYNTAX		INTEGER
		MAX-ACCESS		read-write
		STATUS			current
		DESCRIPTION
				"TYPE: - Number
				 PAGE: - Aud.Delays
					EMB 3 Fine Delay  cmdID= 38140  min= -2450  max= 2450  step= 52  format= %0.3f ms  div_scale= 10000
					Min = -0.245 ms  Max = 0.245 ms  Step = 0.005 ms "
		::= { iqdbe02CmdEntry 38140 }


	iqdbe02AudDelaysEMBDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-4  cmdID= 38083
					Min  value= 0
					Delay A  value= 1
					Delay B  value= 2  "
		::= { iqdbe02CmdEntry 38083 }


	iqdbe02AudDelaysEMBDelaySelectInternal4 OBJECT-TYPE
		SYNTAX		INTEGER { disable(0), enable(1) }
		MAX-ACCESS		read-write
		STATUS			current
		DESCRIPTION
				"TYPE: - Checkbox
				 PAGE: - Aud.Delays
					Internal-4  cmdID= 38103 "
		::= { iqdbe02CmdEntry 38103 }


	iqdbe02AudDelaysEMBDelaySelectAutoDolbyEPhase4 OBJECT-TYPE
		SYNTAX		INTEGER { disable(0), enable(1) }
		MAX-ACCESS		read-write
		STATUS			current
		DESCRIPTION
				"TYPE: - Checkbox
				 PAGE: - Aud.Delays
					Auto Dolby-E Phase  cmdID= 38113 "
		::= { iqdbe02CmdEntry 38113 }


	iqdbe02AudDelaysEMBDelaySelectDelayLimit4 OBJECT-TYPE
		SYNTAX		RollCallString
		MAX-ACCESS		read-only
		STATUS			current
		DESCRIPTION
				"TYPE: - Display
				 PAGE: - Aud.Delays
					Delay Limit  cmdID= 38311  format=   "
		::= { iqdbe02CmdEntry 38311 }


	iqdbe02AudDelaysEMBDelaySelectEMB4FineDelay OBJECT-TYPE
		SYNTAX		INTEGER
		MAX-ACCESS		read-write
		STATUS			current
		DESCRIPTION
				"TYPE: - Number
				 PAGE: - Aud.Delays
					EMB 4 Fine Delay  cmdID= 38141  min= -2450  max= 2450  step= 52  format= %0.3f ms  div_scale= 10000
					Min = -0.245 ms  Max = 0.245 ms  Step = 0.005 ms "
		::= { iqdbe02CmdEntry 38141 }


	iqdbe02AudDelaysEMBDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-5  cmdID= 38084
					Min  value= 0
					Delay A  value= 1
					Delay B  value= 2  "
		::= { iqdbe02CmdEntry 38084 }


	iqdbe02AudDelaysEMBDelaySelectInternal5 OBJECT-TYPE
		SYNTAX		INTEGER { disable(0), enable(1) }
		MAX-ACCESS		read-write
		STATUS			current
		DESCRIPTION
				"TYPE: - Checkbox
				 PAGE: - Aud.Delays
					Internal-5  cmdID= 38104 "
		::= { iqdbe02CmdEntry 38104 }


	iqdbe02AudDelaysEMBDelaySelectAutoDolbyEPhase5 OBJECT-TYPE
		SYNTAX		INTEGER { disable(0), enable(1) }
		MAX-ACCESS		read-write
		STATUS			current
		DESCRIPTION
				"TYPE: - Checkbox
				 PAGE: - Aud.Delays
					Auto Dolby-E Phase  cmdID= 38114 "
		::= { iqdbe02CmdEntry 38114 }


	iqdbe02AudDelaysEMBDelaySelectDelayLimit5 OBJECT-TYPE
		SYNTAX		RollCallString
		MAX-ACCESS		read-only
		STATUS			current
		DESCRIPTION
				"TYPE: - Display
				 PAGE: - Aud.Delays
					Delay Limit  cmdID= 38312  format=   "
		::= { iqdbe02CmdEntry 38312 }


	iqdbe02AudDelaysEMBDelaySelectEMB5FineDelay OBJECT-TYPE
		SYNTAX		INTEGER
		MAX-ACCESS		read-write
		STATUS			current
		DESCRIPTION
				"TYPE: - Number
				 PAGE: - Aud.Delays
					EMB 5 Fine Delay  cmdID= 38142  min= -2450  max= 2450  step= 52  format= %0.3f ms  div_scale= 10000
					Min = -0.245 ms  Max = 0.245 ms  Step = 0.005 ms "
		::= { iqdbe02CmdEntry 38142 }


	iqdbe02AudDelaysEMBDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-6  cmdID= 38085
					Min  value= 0
					Delay A  value= 1
					Delay B  value= 2  "
		::= { iqdbe02CmdEntry 38085 }


	iqdbe02AudDelaysEMBDelaySelectInternal6 OBJECT-TYPE
		SYNTAX		INTEGER { disable(0), enable(1) }
		MAX-ACCESS		read-write
		STATUS			current
		DESCRIPTION
				"TYPE: - Checkbox
				 PAGE: - Aud.Delays
					Internal-6  cmdID= 38105 "
		::= { iqdbe02CmdEntry 38105 }


	iqdbe02AudDelaysEMBDelaySelectAutoDolbyEPhase6 OBJECT-TYPE
		SYNTAX		INTEGER { disable(0), enable(1) }
		MAX-ACCESS		read-write
		STATUS			current
		DESCRIPTION
				"TYPE: - Checkbox
				 PAGE: - Aud.Delays
					Auto Dolby-E Phase  cmdID= 38115 "
		::= { iqdbe02CmdEntry 38115 }


	iqdbe02AudDelaysEMBDelaySelectDelayLimit6 OBJECT-TYPE
		SYNTAX		RollCallString
		MAX-ACCESS		read-only
		STATUS			current
		DESCRIPTION
				"TYPE: - Display
				 PAGE: - Aud.Delays
					Delay Limit  cmdID= 38313  format=   "
		::= { iqdbe02CmdEntry 38313 }


	iqdbe02AudDelaysEMBDelaySelectEMB6FineDelay OBJECT-TYPE
		SYNTAX		INTEGER
		MAX-ACCESS		read-write
		STATUS			current
		DESCRIPTION
				"TYPE: - Number
				 PAGE: - Aud.Delays
					EMB 6 Fine Delay  cmdID= 38143  min= -2450  max= 2450  step= 52  format= %0.3f ms  div_scale= 10000
					Min = -0.245 ms  Max = 0.245 ms  Step = 0.005 ms "
		::= { iqdbe02CmdEntry 38143 }


	iqdbe02AudDelaysEMBDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-7  cmdID= 38086
					Min  value= 0
					Delay A  value= 1
					Delay B  value= 2  "
		::= { iqdbe02CmdEntry 38086 }


	iqdbe02AudDelaysEMBDelaySelectInternal7 OBJECT-TYPE
		SYNTAX		INTEGER { disable(0), enable(1) }
		MAX-ACCESS		read-write
		STATUS			current
		DESCRIPTION
				"TYPE: - Checkbox
				 PAGE: - Aud.Delays
					Internal-7  cmdID= 38106 "
		::= { iqdbe02CmdEntry 38106 }


	iqdbe02AudDelaysEMBDelaySelectAutoDolbyEPhase7 OBJECT-TYPE
		SYNTAX		INTEGER { disable(0), enable(1) }
		MAX-ACCESS		read-write
		STATUS			current
		DESCRIPTION
				"TYPE: - Checkbox
				 PAGE: - Aud.Delays
					Auto Dolby-E Phase  cmdID= 38116 "
		::= { iqdbe02CmdEntry 38116 }


	iqdbe02AudDelaysEMBDelaySelectDelayLimit7 OBJECT-TYPE
		SYNTAX		RollCallString
		MAX-ACCESS		read-only
		STATUS			current
		DESCRIPTION
				"TYPE: - Display
				 PAGE: - Aud.Delays
					Delay Limit  cmdID= 38314  format=   "
		::= { iqdbe02CmdEntry 38314 }


	iqdbe02AudDelaysEMBDelaySelectEMB7FineDelay OBJECT-TYPE
		SYNTAX		INTEGER
		MAX-ACCESS		read-write
		STATUS			current
		DESCRIPTION
				"TYPE: - Number
				 PAGE: - Aud.Delays
					EMB 7 Fine Delay  cmdID= 38144  min= -2450  max= 2450  step= 52  format= %0.3f ms  div_scale= 10000
					Min = -0.245 ms  Max = 0.245 ms  Step = 0.005 ms "
		::= { iqdbe02CmdEntry 38144 }


	iqdbe02AudDelaysEMBDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-8  cmdID= 38087
					Min  value= 0
					Delay A  value= 1
					Delay B  value= 2  "
		::= { iqdbe02CmdEntry 38087 }


	iqdbe02AudDelaysEMBDelaySelectInternal8 OBJECT-TYPE
		SYNTAX		INTEGER { disable(0), enable(1) }
		MAX-ACCESS		read-write
		STATUS			current
		DESCRIPTION
				"TYPE: - Checkbox
				 PAGE: - Aud.Delays
					Internal-8  cmdID= 38107 "
		::= { iqdbe02CmdEntry 38107 }


	iqdbe02AudDelaysEMBDelaySelectDelayLimit8 OBJECT-TYPE
		SYNTAX		RollCallString
		MAX-ACCESS		read-only
		STATUS			current
		DESCRIPTION
				"TYPE: - Display
				 PAGE: - Aud.Delays
					Delay Limit  cmdID= 38315  format=   "
		::= { iqdbe02CmdEntry 38315 }


	iqdbe02AudDelaysEMBDelaySelectAutoDolbyEPhase8 OBJECT-TYPE
		SYNTAX		INTEGER { disable(0), enable(1) }
		MAX-ACCESS		read-write
		STATUS			current
		DESCRIPTION
				"TYPE: - Checkbox
				 PAGE: - Aud.Delays
					Auto Dolby-E Phase  cmdID= 38117 "
		::= { iqdbe02CmdEntry 38117 }


	iqdbe02AudDelaysEMBDelaySelectEMB8FineDelay OBJECT-TYPE
		SYNTAX		INTEGER
		MAX-ACCESS		read-write
		STATUS			current
		DESCRIPTION
				"TYPE: - Number
				 PAGE: - Aud.Delays
					EMB 8 Fine Delay  cmdID= 38145  min= -2450  max= 2450  step= 52  format= %0.3f ms  div_scale= 10000
					Min = -0.245 ms  Max = 0.245 ms  Step = 0.005 ms "
		::= { iqdbe02CmdEntry 38145 }


	iqdbe02AudioAudDelaysRollTrack14 OBJECT-TYPE
		SYNTAX		RollCallString
		MAX-ACCESS		read-only
		STATUS			current
		DESCRIPTION
				"TYPE: - Display
				 PAGE: - Aud.Delays
					RollTrack14  cmdID= 14  format=   "
		::= { iqdbe02CmdEntry 14 }


	iqdbe02AudioAudDelaysRollTrack15 OBJECT-TYPE
		SYNTAX		RollCallString
		MAX-ACCESS		read-only
		STATUS			current
		DESCRIPTION
				"TYPE: - Display
				 PAGE: - Aud.Delays
					RollTrack15  cmdID= 15  format=   "
		::= { iqdbe02CmdEntry 15 }


	iqdbe02AudioAudDelaysRollTrack16 OBJECT-TYPE
		SYNTAX		RollCallString
		MAX-ACCESS		read-only
		STATUS			current
		DESCRIPTION
				"TYPE: - Display
				 PAGE: - Aud.Delays
					RollTrack16  cmdID= 16  format=   "
		::= { iqdbe02CmdEntry 16 }


	iqdbe02AudioAudDelaysRollTrack17 OBJECT-TYPE
		SYNTAX		RollCallString
		MAX-ACCESS		read-only
		STATUS			current
		DESCRIPTION
				"TYPE: - Display
				 PAGE: - Aud.Delays
					RollTrack17  cmdID= 17  format=   "
		::= { iqdbe02CmdEntry 17 }


	iqdbe02AudioAudDelaysCrashSRCLimit OBJECT-TYPE
		SYNTAX		INTEGER
		MAX-ACCESS		read-write
		STATUS			current
		DESCRIPTION
				"TYPE: - Number
				 PAGE: - Aud.Delays
					Crash SRC Limit  cmdID= 38678  min= 0  max= 80  step= 1  format= %0.0f ms  div_scale= 1
					Min = 0 ms  Max = 80 ms  Step = 1 ms "
		::= { iqdbe02CmdEntry 38678 }


	iqdbe02EmbCtrlGroupGroup1Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 1 Audio  cmdID= 37450
					Pass  value= 0
					Blank  value= 2
					Embed  value= 1  "
		::= { iqdbe02CmdEntry 37450 }


	iqdbe02EmbCtrlGroupGroup2Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 2 Audio  cmdID= 37451
					Pass  value= 0
					Blank  value= 2
					Embed  value= 1  "
		::= { iqdbe02CmdEntry 37451 }


	iqdbe02EmbCtrlGroupGroup3Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 3 Audio  cmdID= 37452
					Pass  value= 0
					Blank  value= 2
					Embed  value= 1  "
		::= { iqdbe02CmdEntry 37452 }


	iqdbe02EmbCtrlGroupGroup4Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 4 Audio  cmdID= 37453
					Pass  value= 0
					Blank  value= 2
					Embed  value= 1  "
		::= { iqdbe02CmdEntry 37453 }


	iqdbe02EmbCtrlChannelPair1LActive OBJECT-TYPE
		SYNTAX		INTEGER { disable(0), enable(1) }
		MAX-ACCESS		read-write
		STATUS			current
		DESCRIPTION
				"TYPE: - Checkbox
				 PAGE: - Emb.Ctrl
					Pair 1-L Active  cmdID= 37431 "
		::= { iqdbe02CmdEntry 37431 }


	iqdbe02EmbCtrlChannelPair1RActive OBJECT-TYPE
		SYNTAX		INTEGER { disable(0), enable(1) }
		MAX-ACCESS		read-write
		STATUS			current
		DESCRIPTION
				"TYPE: - Checkbox
				 PAGE: - Emb.Ctrl
					Pair 1-R Active  cmdID= 37432 "
		::= { iqdbe02CmdEntry 37432 }


	iqdbe02EmbCtrlChannelPair2LActive OBJECT-TYPE
		SYNTAX		INTEGER { disable(0), enable(1) }
		MAX-ACCESS		read-write
		STATUS			current
		DESCRIPTION
				"TYPE: - Checkbox
				 PAGE: - Emb.Ctrl
					Pair 2-L Active  cmdID= 37433 "
		::= { iqdbe02CmdEntry 37433 }


	iqdbe02EmbCtrlChannelPair2RActive OBJECT-TYPE
		SYNTAX		INTEGER { disable(0), enable(1) }
		MAX-ACCESS		read-write
		STATUS			current
		DESCRIPTION
				"TYPE: - Checkbox
				 PAGE: - Emb.Ctrl
					Pair 2-R Active  cmdID= 37434 "
		::= { iqdbe02CmdEntry 37434 }


	iqdbe02EmbCtrlChannelPair3LActive OBJECT-TYPE
		SYNTAX		INTEGER { disable(0), enable(1) }
		MAX-ACCESS		read-write
		STATUS			current
		DESCRIPTION
				"TYPE: - Checkbox
				 PAGE: - Emb.Ctrl
					Pair 3-L Active  cmdID= 37435 "
		::= { iqdbe02CmdEntry 37435 }


	iqdbe02EmbCtrlChannelPair3RActive OBJECT-TYPE
		SYNTAX		INTEGER { disable(0), enable(1) }
		MAX-ACCESS		read-write
		STATUS			current
		DESCRIPTION
				"TYPE: - Checkbox
				 PAGE: - Emb.Ctrl
					Pair 3-R Active  cmdID= 37436 "
		::= { iqdbe02CmdEntry 37436 }


	iqdbe02EmbCtrlChannelPair4LActive OBJECT-TYPE
		SYNTAX		INTEGER { disable(0), enable(1) }
		MAX-ACCESS		read-write
		STATUS			current
		DESCRIPTION
				"TYPE: - Checkbox
				 PAGE: - Emb.Ctrl
					Pair 4-L Active  cmdID= 37437 "
		::= { iqdbe02CmdEntry 37437 }


	iqdbe02EmbCtrlChannelPair4RActive OBJECT-TYPE
		SYNTAX		INTEGER { disable(0), enable(1) }
		MAX-ACCESS		read-write
		STATUS			current
		DESCRIPTION
				"TYPE: - Checkbox
				 PAGE: - Emb.Ctrl
					Pair 4-R Active  cmdID= 37438 "
		::= { iqdbe02CmdEntry 37438 }


	iqdbe02EmbCtrlChannelPair5LActive OBJECT-TYPE
		SYNTAX		INTEGER { disable(0), enable(1) }
		MAX-ACCESS		read-write
		STATUS			current
		DESCRIPTION
				"TYPE: - Checkbox
				 PAGE: - Emb.Ctrl
					Pair 5-L Active  cmdID= 37439 "
		::= { iqdbe02CmdEntry 37439 }


	iqdbe02EmbCtrlChannelPair5RActive OBJECT-TYPE
		SYNTAX		INTEGER { disable(0), enable(1) }
		MAX-ACCESS		read-write
		STATUS			current
		DESCRIPTION
				"TYPE: - Checkbox
				 PAGE: - Emb.Ctrl
					Pair 5-R Active  cmdID= 37440 "
		::= { iqdbe02CmdEntry 37440 }


	iqdbe02EmbCtrlChannelPair6LActive OBJECT-TYPE
		SYNTAX		INTEGER { disable(0), enable(1) }
		MAX-ACCESS		read-write
		STATUS			current
		DESCRIPTION
				"TYPE: - Checkbox
				 PAGE: - Emb.Ctrl
					Pair 6-L Active  cmdID= 37441 "
		::= { iqdbe02CmdEntry 37441 }


	iqdbe02EmbCtrlChannelPair6RActive OBJECT-TYPE
		SYNTAX		INTEGER { disable(0), enable(1) }
		MAX-ACCESS		read-write
		STATUS			current
		DESCRIPTION
				"TYPE: - Checkbox
				 PAGE: - Emb.Ctrl
					Pair 6-R Active  cmdID= 37442 "
		::= { iqdbe02CmdEntry 37442 }


	iqdbe02EmbCtrlChannelPair7LActive OBJECT-TYPE
		SYNTAX		INTEGER { disable(0), enable(1) }
		MAX-ACCESS		read-write
		STATUS			current
		DESCRIPTION
				"TYPE: - Checkbox
				 PAGE: - Emb.Ctrl
					Pair 7-L Active  cmdID= 37443 "
		::= { iqdbe02CmdEntry 37443 }


	iqdbe02EmbCtrlChannelPair7RActive OBJECT-TYPE
		SYNTAX		INTEGER { disable(0), enable(1) }
		MAX-ACCESS		read-write
		STATUS			current
		DESCRIPTION
				"TYPE: - Checkbox
				 PAGE: - Emb.Ctrl
					Pair 7-R Active  cmdID= 37444 "
		::= { iqdbe02CmdEntry 37444 }


	iqdbe02EmbCtrlChannelPair8LActive OBJECT-TYPE
		SYNTAX		INTEGER { disable(0), enable(1) }
		MAX-ACCESS		read-write
		STATUS			current
		DESCRIPTION
				"TYPE: - Checkbox
				 PAGE: - Emb.Ctrl
					Pair 8-L Active  cmdID= 37445 "
		::= { iqdbe02CmdEntry 37445 }


	iqdbe02EmbCtrlChannelPair8RActive OBJECT-TYPE
		SYNTAX		INTEGER { disable(0), enable(1) }
		MAX-ACCESS		read-write
		STATUS			current
		DESCRIPTION
				"TYPE: - Checkbox
				 PAGE: - Emb.Ctrl
					Pair 8-R Active  cmdID= 37446 "
		::= { iqdbe02CmdEntry 37446 }


	iqdbe02AudioEmbCtrlEmbedderPriority OBJECT-TYPE
		SYNTAX		INTEGER {
							val_Normal(0),
							val_Audio_Dolby_E(1)
							}
		MAX-ACCESS		read-write
		STATUS			current
		DESCRIPTION
				"TYPE: - RadiobuttonList
				 PAGE: - Emb.Ctrl
					Embedder Priority  cmdID= 37460
					Normal  value= 0
					Audio (Dolby-E)  value= 1  "
		::= { iqdbe02CmdEntry 37460 }


	iqdbe02EmbGainEmbedPair1Embed1MuteL OBJECT-TYPE
		SYNTAX		INTEGER { disable(0), enable(1) }
		MAX-ACCESS		read-write
		STATUS			current
		DESCRIPTION
				"TYPE: - Checkbox
				 PAGE: - Emb.Gain
					Embed 1 Mute L  cmdID= 37340 "
		::= { iqdbe02CmdEntry 37340 }


	iqdbe02EmbGainEmbedPair1Embed1MuteR OBJECT-TYPE
		SYNTAX		INTEGER { disable(0), enable(1) }
		MAX-ACCESS		read-write
		STATUS			current
		DESCRIPTION
				"TYPE: - Checkbox
				 PAGE: - Emb.Gain
					Embed 1 Mute R  cmdID= 37341 "
		::= { iqdbe02CmdEntry 37341 }


	iqdbe02EmbGainEmbedPair1Embed1LGain OBJECT-TYPE
		SYNTAX		INTEGER
		MAX-ACCESS		read-write
		STATUS			current
		DESCRIPTION
				"TYPE: - Number
				 PAGE: - Emb.Gain
					Embed 1 L Gain  cmdID= 37320  min= -661  max= 120  step= 1  format= %0.1f dB  div_scale= 10
					Min = -66.1 dB  Max = 12.0 dB  Step = 0.1 dB "
		::= { iqdbe02CmdEntry 37320 }


	iqdbe02EmbGainEmbedPair1Embed1RGain OBJECT-TYPE
		SYNTAX		INTEGER
		MAX-ACCESS		read-write
		STATUS			current
		DESCRIPTION
				"TYPE: - Number
				 PAGE: - Emb.Gain
					Embed 1 R Gain  cmdID= 37321  min= -661  max= 120  step= 1  format= %0.1f dB  div_scale= 10
					Min = -66.1 dB  Max = 12.0 dB  Step = 0.1 dB "
		::= { iqdbe02CmdEntry 37321 }


	iqdbe02EmbGainEmbedPair1Stereo OBJECT-TYPE
		SYNTAX		INTEGER { disable(0), enable(1) }
		MAX-ACCESS		read-write
		STATUS			current
		DESCRIPTION
				"TYPE: - Checkbox
				 PAGE: - Emb.Gain
					Stereo  cmdID= 37380 "
		::= { iqdbe02CmdEntry 37380 }


	iqdbe02EmbGainEmbedPair1Embed1InvertL OBJECT-TYPE
		SYNTAX		INTEGER { disable(0), enable(1) }
		MAX-ACCESS		read-write
		STATUS			current
		DESCRIPTION
				"TYPE: - Checkbox
				 PAGE: - Emb.Gain
					Embed 1 Invert L  cmdID= 37360 "
		::= { iqdbe02CmdEntry 37360 }


	iqdbe02EmbGainEmbedPair1Embed1InvertR OBJECT-TYPE
		SYNTAX		INTEGER { disable(0), enable(1) }
		MAX-ACCESS		read-write
		STATUS			current
		DESCRIPTION
				"TYPE: - Checkbox
				 PAGE: - Emb.Gain
					Embed 1 Invert R  cmdID= 37361 "
		::= { iqdbe02CmdEntry 37361 }


	iqdbe02EmbGainEmbedPair1Embed1LClip OBJECT-TYPE
		SYNTAX		RollCallString
		MAX-ACCESS		read-only
		STATUS			current
		DESCRIPTION
				"TYPE: - Display
				 PAGE: - Emb.Gain
					Embed 1-L Clip  cmdID= 37540  format=   "
		::= { iqdbe02CmdEntry 37540 }


	iqdbe02EmbGainEmbedPair1Embed1RClip OBJECT-TYPE
		SYNTAX		RollCallString
		MAX-ACCESS		read-only
		STATUS			current
		DESCRIPTION
				"TYPE: - Display
				 PAGE: - Emb.Gain
					Embed 1-R Clip  cmdID= 37541  format=   "
		::= { iqdbe02CmdEntry 37541 }


	iqdbe02EmbGainEmbedPair2Embed2MuteL OBJECT-TYPE
		SYNTAX		INTEGER { disable(0), enable(1) }
		MAX-ACCESS		read-write
		STATUS			current
		DESCRIPTION
				"TYPE: - Checkbox
				 PAGE: - Emb.Gain
					Embed 2 Mute L  cmdID= 37342 "
		::= { iqdbe02CmdEntry 37342 }


	iqdbe02EmbGainEmbedPair2Embed2MuteR OBJECT-TYPE
		SYNTAX		INTEGER { disable(0), enable(1) }
		MAX-ACCESS		read-write
		STATUS			current
		DESCRIPTION
				"TYPE: - Checkbox
				 PAGE: - Emb.Gain
					Embed 2 Mute R  cmdID= 37343 "
		::= { iqdbe02CmdEntry 37343 }


	iqdbe02EmbGainEmbedPair2Embed2LGain OBJECT-TYPE
		SYNTAX		INTEGER
		MAX-ACCESS		read-write
		STATUS			current
		DESCRIPTION
				"TYPE: - Number
				 PAGE: - Emb.Gain
					Embed 2 L Gain  cmdID= 37322  min= -661  max= 120  step= 1  format= %0.1f dB  div_scale= 10
					Min = -66.1 dB  Max = 12.0 dB  Step = 0.1 dB "
		::= { iqdbe02CmdEntry 37322 }


	iqdbe02EmbGainEmbedPair2Embed2RGain OBJECT-TYPE
		SYNTAX		INTEGER
		MAX-ACCESS		read-write
		STATUS			current
		DESCRIPTION
				"TYPE: - Number
				 PAGE: - Emb.Gain
					Embed 2 R Gain  cmdID= 37323  min= -661  max= 120  step= 1  format= %0.1f dB  div_scale= 10
					Min = -66.1 dB  Max = 12.0 dB  Step = 0.1 dB "
		::= { iqdbe02CmdEntry 37323 }


	iqdbe02EmbGainEmbedPair2Stereo OBJECT-TYPE
		SYNTAX		INTEGER { disable(0), enable(1) }
		MAX-ACCESS		read-write
		STATUS			current
		DESCRIPTION
				"TYPE: - Checkbox
				 PAGE: - Emb.Gain
					Stereo  cmdID= 37381 "
		::= { iqdbe02CmdEntry 37381 }


	iqdbe02EmbGainEmbedPair2Embed2InvertL OBJECT-TYPE
		SYNTAX		INTEGER { disable(0), enable(1) }
		MAX-ACCESS		read-write
		STATUS			current
		DESCRIPTION
				"TYPE: - Checkbox
				 PAGE: - Emb.Gain
					Embed 2 Invert L  cmdID= 37362 "
		::= { iqdbe02CmdEntry 37362 }


	iqdbe02EmbGainEmbedPair2Embed2InvertR OBJECT-TYPE
		SYNTAX		INTEGER { disable(0), enable(1) }
		MAX-ACCESS		read-write
		STATUS			current
		DESCRIPTION
				"TYPE: - Checkbox
				 PAGE: - Emb.Gain
					Embed 2 Invert R  cmdID= 37363 "
		::= { iqdbe02CmdEntry 37363 }


	iqdbe02EmbGainEmbedPair2Embed2LClip OBJECT-TYPE
		SYNTAX		RollCallString
		MAX-ACCESS		read-only
		STATUS			current
		DESCRIPTION
				"TYPE: - Display
				 PAGE: - Emb.Gain
					Embed 2-L Clip  cmdID= 37542  format=   "
		::= { iqdbe02CmdEntry 37542 }


	iqdbe02EmbGainEmbedPair2Embed2RClip OBJECT-TYPE
		SYNTAX		RollCallString
		MAX-ACCESS		read-only
		STATUS			current
		DESCRIPTION
				"TYPE: - Display
				 PAGE: - Emb.Gain
					Embed 2-R Clip  cmdID= 37543  format=   "
		::= { iqdbe02CmdEntry 37543 }


	iqdbe02EmbGainEmbedPair3Embed3MuteL OBJECT-TYPE
		SYNTAX		INTEGER { disable(0), enable(1) }
		MAX-ACCESS		read-write
		STATUS			current
		DESCRIPTION
				"TYPE: - Checkbox
				 PAGE: - Emb.Gain
					Embed 3 Mute L  cmdID= 37344 "
		::= { iqdbe02CmdEntry 37344 }


	iqdbe02EmbGainEmbedPair3Embed3MuteR OBJECT-TYPE
		SYNTAX		INTEGER { disable(0), enable(1) }
		MAX-ACCESS		read-write
		STATUS			current
		DESCRIPTION
				"TYPE: - Checkbox
				 PAGE: - Emb.Gain
					Embed 3 Mute R  cmdID= 37345 "
		::= { iqdbe02CmdEntry 37345 }


	iqdbe02EmbGainEmbedPair3Embed3LGain OBJECT-TYPE
		SYNTAX		INTEGER
		MAX-ACCESS		read-write
		STATUS			current
		DESCRIPTION
				"TYPE: - Number
				 PAGE: - Emb.Gain
					Embed 3 L Gain  cmdID= 37324  min= -661  max= 120  step= 1  format= %0.1f dB  div_scale= 10
					Min = -66.1 dB  Max = 12.0 dB  Step = 0.1 dB "
		::= { iqdbe02CmdEntry 37324 }


	iqdbe02EmbGainEmbedPair3Embed3RGain OBJECT-TYPE
		SYNTAX		INTEGER
		MAX-ACCESS		read-write
		STATUS			current
		DESCRIPTION
				"TYPE: - Number
				 PAGE: - Emb.Gain
					Embed 3 R Gain  cmdID= 37325  min= -661  max= 120  step= 1  format= %0.1f dB  div_scale= 10
					Min = -66.1 dB  Max = 12.0 dB  Step = 0.1 dB "
		::= { iqdbe02CmdEntry 37325 }


	iqdbe02EmbGainEmbedPair3Stereo OBJECT-TYPE
		SYNTAX		INTEGER { disable(0), enable(1) }
		MAX-ACCESS		read-write
		STATUS			current
		DESCRIPTION
				"TYPE: - Checkbox
				 PAGE: - Emb.Gain
					Stereo  cmdID= 37382 "
		::= { iqdbe02CmdEntry 37382 }


	iqdbe02EmbGainEmbedPair3Embed3InvertL OBJECT-TYPE
		SYNTAX		INTEGER { disable(0), enable(1) }
		MAX-ACCESS		read-write
		STATUS			current
		DESCRIPTION
				"TYPE: - Checkbox
				 PAGE: - Emb.Gain
					Embed 3 Invert L  cmdID= 37364 "
		::= { iqdbe02CmdEntry 37364 }


	iqdbe02EmbGainEmbedPair3Embed3InvertR OBJECT-TYPE
		SYNTAX		INTEGER { disable(0), enable(1) }
		MAX-ACCESS		read-write
		STATUS			current
		DESCRIPTION
				"TYPE: - Checkbox
				 PAGE: - Emb.Gain
					Embed 3 Invert R  cmdID= 37365 "
		::= { iqdbe02CmdEntry 37365 }


	iqdbe02EmbGainEmbedPair3Embed3LClip OBJECT-TYPE
		SYNTAX		RollCallString
		MAX-ACCESS		read-only
		STATUS			current
		DESCRIPTION
				"TYPE: - Display
				 PAGE: - Emb.Gain
					Embed 3-L Clip  cmdID= 37544  format=   "
		::= { iqdbe02CmdEntry 37544 }


	iqdbe02EmbGainEmbedPair3Embed3RClip OBJECT-TYPE
		SYNTAX		RollCallString
		MAX-ACCESS		read-only
		STATUS			current
		DESCRIPTION
				"TYPE: - Display
				 PAGE: - Emb.Gain
					Embed 3-R Clip  cmdID= 37545  format=   "
		::= { iqdbe02CmdEntry 37545 }


	iqdbe02EmbGainEmbedPair4Embed4MuteL OBJECT-TYPE
		SYNTAX		INTEGER { disable(0), enable(1) }
		MAX-ACCESS		read-write
		STATUS			current
		DESCRIPTION
				"TYPE: - Checkbox
				 PAGE: - Emb.Gain
					Embed 4 Mute L  cmdID= 37346 "
		::= { iqdbe02CmdEntry 37346 }


	iqdbe02EmbGainEmbedPair4Embed4MuteR OBJECT-TYPE
		SYNTAX		INTEGER { disable(0), enable(1) }
		MAX-ACCESS		read-write
		STATUS			current
		DESCRIPTION
				"TYPE: - Checkbox
				 PAGE: - Emb.Gain
					Embed 4 Mute R  cmdID= 37347 "
		::= { iqdbe02CmdEntry 37347 }


	iqdbe02EmbGainEmbedPair4Embed4LGain OBJECT-TYPE
		SYNTAX		INTEGER
		MAX-ACCESS		read-write
		STATUS			current
		DESCRIPTION
				"TYPE: - Number
				 PAGE: - Emb.Gain
					Embed 4 L Gain  cmdID= 37326  min= -661  max= 120  step= 1  format= %0.1f dB  div_scale= 10
					Min = -66.1 dB  Max = 12.0 dB  Step = 0.1 dB "
		::= { iqdbe02CmdEntry 37326 }


	iqdbe02EmbGainEmbedPair4Embed4RGain OBJECT-TYPE
		SYNTAX		INTEGER
		MAX-ACCESS		read-write
		STATUS			current
		DESCRIPTION
				"TYPE: - Number
				 PAGE: - Emb.Gain
					Embed 4 R Gain  cmdID= 37327  min= -661  max= 120  step= 1  format= %0.1f dB  div_scale= 10
					Min = -66.1 dB  Max = 12.0 dB  Step = 0.1 dB "
		::= { iqdbe02CmdEntry 37327 }


	iqdbe02EmbGainEmbedPair4Stereo OBJECT-TYPE
		SYNTAX		INTEGER { disable(0), enable(1) }
		MAX-ACCESS		read-write
		STATUS			current
		DESCRIPTION
				"TYPE: - Checkbox
				 PAGE: - Emb.Gain
					Stereo  cmdID= 37383 "
		::= { iqdbe02CmdEntry 37383 }


	iqdbe02EmbGainEmbedPair4Embed4InvertL OBJECT-TYPE
		SYNTAX		INTEGER { disable(0), enable(1) }
		MAX-ACCESS		read-write
		STATUS			current
		DESCRIPTION
				"TYPE: - Checkbox
				 PAGE: - Emb.Gain
					Embed 4 Invert L  cmdID= 37366 "
		::= { iqdbe02CmdEntry 37366 }


	iqdbe02EmbGainEmbedPair4Embed4InvertR OBJECT-TYPE
		SYNTAX		INTEGER { disable(0), enable(1) }
		MAX-ACCESS		read-write
		STATUS			current
		DESCRIPTION
				"TYPE: - Checkbox
				 PAGE: - Emb.Gain
					Embed 4 Invert R  cmdID= 37367 "
		::= { iqdbe02CmdEntry 37367 }


	iqdbe02EmbGainEmbedPair4Embed4LClip OBJECT-TYPE
		SYNTAX		RollCallString
		MAX-ACCESS		read-only
		STATUS			current
		DESCRIPTION
				"TYPE: - Display
				 PAGE: - Emb.Gain
					Embed 4-L Clip  cmdID= 37546  format=   "
		::= { iqdbe02CmdEntry 37546 }


	iqdbe02EmbGainEmbedPair4Embed4RClip OBJECT-TYPE
		SYNTAX		RollCallString
		MAX-ACCESS		read-only
		STATUS			current
		DESCRIPTION
				"TYPE: - Display
				 PAGE: - Emb.Gain
					Embed 4-R Clip  cmdID= 37547  format=   "
		::= { iqdbe02CmdEntry 37547 }


	iqdbe02EmbGainEmbedPair5Embed5MuteL OBJECT-TYPE
		SYNTAX		INTEGER { disable(0), enable(1) }
		MAX-ACCESS		read-write
		STATUS			current
		DESCRIPTION
				"TYPE: - Checkbox
				 PAGE: - Emb.Gain
					Embed 5 Mute L  cmdID= 37348 "
		::= { iqdbe02CmdEntry 37348 }


	iqdbe02EmbGainEmbedPair5Embed5MuteR OBJECT-TYPE
		SYNTAX		INTEGER { disable(0), enable(1) }
		MAX-ACCESS		read-write
		STATUS			current
		DESCRIPTION
				"TYPE: - Checkbox
				 PAGE: - Emb.Gain
					Embed 5 Mute R  cmdID= 37349 "
		::= { iqdbe02CmdEntry 37349 }


	iqdbe02EmbGainEmbedPair5Embed5LGain OBJECT-TYPE
		SYNTAX		INTEGER
		MAX-ACCESS		read-write
		STATUS			current
		DESCRIPTION
				"TYPE: - Number
				 PAGE: - Emb.Gain
					Embed 5 L Gain  cmdID= 37328  min= -661  max= 120  step= 1  format= %0.1f dB  div_scale= 10
					Min = -66.1 dB  Max = 12.0 dB  Step = 0.1 dB "
		::= { iqdbe02CmdEntry 37328 }


	iqdbe02EmbGainEmbedPair5Embed5RGain OBJECT-TYPE
		SYNTAX		INTEGER
		MAX-ACCESS		read-write
		STATUS			current
		DESCRIPTION
				"TYPE: - Number
				 PAGE: - Emb.Gain
					Embed 5 R Gain  cmdID= 37329  min= -661  max= 120  step= 1  format= %0.1f dB  div_scale= 10
					Min = -66.1 dB  Max = 12.0 dB  Step = 0.1 dB "
		::= { iqdbe02CmdEntry 37329 }


	iqdbe02EmbGainEmbedPair5Stereo OBJECT-TYPE
		SYNTAX		INTEGER { disable(0), enable(1) }
		MAX-ACCESS		read-write
		STATUS			current
		DESCRIPTION
				"TYPE: - Checkbox
				 PAGE: - Emb.Gain
					Stereo  cmdID= 37384 "
		::= { iqdbe02CmdEntry 37384 }


	iqdbe02EmbGainEmbedPair5Embed5InvertL OBJECT-TYPE
		SYNTAX		INTEGER { disable(0), enable(1) }
		MAX-ACCESS		read-write
		STATUS			current
		DESCRIPTION
				"TYPE: - Checkbox
				 PAGE: - Emb.Gain
					Embed 5 Invert L  cmdID= 37368 "
		::= { iqdbe02CmdEntry 37368 }


	iqdbe02EmbGainEmbedPair5Embed5InvertR OBJECT-TYPE
		SYNTAX		INTEGER { disable(0), enable(1) }
		MAX-ACCESS		read-write
		STATUS			current
		DESCRIPTION
				"TYPE: - Checkbox
				 PAGE: - Emb.Gain
					Embed 5 Invert R  cmdID= 37369 "
		::= { iqdbe02CmdEntry 37369 }


	iqdbe02EmbGainEmbedPair5Embed5LClip OBJECT-TYPE
		SYNTAX		RollCallString
		MAX-ACCESS		read-only
		STATUS			current
		DESCRIPTION
				"TYPE: - Display
				 PAGE: - Emb.Gain
					Embed 5-L Clip  cmdID= 37548  format=   "
		::= { iqdbe02CmdEntry 37548 }


	iqdbe02EmbGainEmbedPair5Embed5RClip OBJECT-TYPE
		SYNTAX		RollCallString
		MAX-ACCESS		read-only
		STATUS			current
		DESCRIPTION
				"TYPE: - Display
				 PAGE: - Emb.Gain
					Embed 5-R Clip  cmdID= 37549  format=   "
		::= { iqdbe02CmdEntry 37549 }


	iqdbe02EmbGainEmbedPair6Embed6MuteL OBJECT-TYPE
		SYNTAX		INTEGER { disable(0), enable(1) }
		MAX-ACCESS		read-write
		STATUS			current
		DESCRIPTION
				"TYPE: - Checkbox
				 PAGE: - Emb.Gain
					Embed 6 Mute L  cmdID= 37350 "
		::= { iqdbe02CmdEntry 37350 }


	iqdbe02EmbGainEmbedPair6Embed6MuteR OBJECT-TYPE
		SYNTAX		INTEGER { disable(0), enable(1) }
		MAX-ACCESS		read-write
		STATUS			current
		DESCRIPTION
				"TYPE: - Checkbox
				 PAGE: - Emb.Gain
					Embed 6 Mute R  cmdID= 37351 "
		::= { iqdbe02CmdEntry 37351 }


	iqdbe02EmbGainEmbedPair6Embed6LGain OBJECT-TYPE
		SYNTAX		INTEGER
		MAX-ACCESS		read-write
		STATUS			current
		DESCRIPTION
				"TYPE: - Number
				 PAGE: - Emb.Gain
					Embed 6 L Gain  cmdID= 37330  min= -661  max= 120  step= 1  format= %0.1f dB  div_scale= 10
					Min = -66.1 dB  Max = 12.0 dB  Step = 0.1 dB "
		::= { iqdbe02CmdEntry 37330 }


	iqdbe02EmbGainEmbedPair6Embed6RGain OBJECT-TYPE
		SYNTAX		INTEGER
		MAX-ACCESS		read-write
		STATUS			current
		DESCRIPTION
				"TYPE: - Number
				 PAGE: - Emb.Gain
					Embed 6 R Gain  cmdID= 37331  min= -661  max= 120  step= 1  format= %0.1f dB  div_scale= 10
					Min = -66.1 dB  Max = 12.0 dB  Step = 0.1 dB "
		::= { iqdbe02CmdEntry 37331 }


	iqdbe02EmbGainEmbedPair6Stereo OBJECT-TYPE
		SYNTAX		INTEGER { disable(0), enable(1) }
		MAX-ACCESS		read-write
		STATUS			current
		DESCRIPTION
				"TYPE: - Checkbox
				 PAGE: - Emb.Gain
					Stereo  cmdID= 37385 "
		::= { iqdbe02CmdEntry 37385 }


	iqdbe02EmbGainEmbedPair6Embed6InvertL OBJECT-TYPE
		SYNTAX		INTEGER { disable(0), enable(1) }
		MAX-ACCESS		read-write
		STATUS			current
		DESCRIPTION
				"TYPE: - Checkbox
				 PAGE: - Emb.Gain
					Embed 6 Invert L  cmdID= 37370 "
		::= { iqdbe02CmdEntry 37370 }


	iqdbe02EmbGainEmbedPair6Embed6InvertR OBJECT-TYPE
		SYNTAX		INTEGER { disable(0), enable(1) }
		MAX-ACCESS		read-write
		STATUS			current
		DESCRIPTION
				"TYPE: - Checkbox
				 PAGE: - Emb.Gain
					Embed 6 Invert R  cmdID= 37371 "
		::= { iqdbe02CmdEntry 37371 }


	iqdbe02EmbGainEmbedPair6Embed6LClip OBJECT-TYPE
		SYNTAX		RollCallString
		MAX-ACCESS		read-only
		STATUS			current
		DESCRIPTION
				"TYPE: - Display
				 PAGE: - Emb.Gain
					Embed 6-L Clip  cmdID= 37550  format=   "
		::= { iqdbe02CmdEntry 37550 }


	iqdbe02EmbGainEmbedPair6Embed6RClip OBJECT-TYPE
		SYNTAX		RollCallString
		MAX-ACCESS		read-only
		STATUS			current
		DESCRIPTION
				"TYPE: - Display
				 PAGE: - Emb.Gain
					Embed 6-R Clip  cmdID= 37551  format=   "
		::= { iqdbe02CmdEntry 37551 }


	iqdbe02EmbGainEmbedPair7Embed7MuteL OBJECT-TYPE
		SYNTAX		INTEGER { disable(0), enable(1) }
		MAX-ACCESS		read-write
		STATUS			current
		DESCRIPTION
				"TYPE: - Checkbox
				 PAGE: - Emb.Gain
					Embed 7 Mute L  cmdID= 37352 "
		::= { iqdbe02CmdEntry 37352 }


	iqdbe02EmbGainEmbedPair7Embed7MuteR OBJECT-TYPE
		SYNTAX		INTEGER { disable(0), enable(1) }
		MAX-ACCESS		read-write
		STATUS			current
		DESCRIPTION
				"TYPE: - Checkbox
				 PAGE: - Emb.Gain
					Embed 7 Mute R  cmdID= 37353 "
		::= { iqdbe02CmdEntry 37353 }


	iqdbe02EmbGainEmbedPair7Embed7LGain OBJECT-TYPE
		SYNTAX		INTEGER
		MAX-ACCESS		read-write
		STATUS			current
		DESCRIPTION
				"TYPE: - Number
				 PAGE: - Emb.Gain
					Embed 7 L Gain  cmdID= 37332  min= -661  max= 120  step= 1  format= %0.1f dB  div_scale= 10
					Min = -66.1 dB  Max = 12.0 dB  Step = 0.1 dB "
		::= { iqdbe02CmdEntry 37332 }


	iqdbe02EmbGainEmbedPair7Embed7RGain OBJECT-TYPE
		SYNTAX		INTEGER
		MAX-ACCESS		read-write
		STATUS			current
		DESCRIPTION
				"TYPE: - Number
				 PAGE: - Emb.Gain
					Embed 7 R Gain  cmdID= 37333  min= -661  max= 120  step= 1  format= %0.1f dB  div_scale= 10
					Min = -66.1 dB  Max = 12.0 dB  Step = 0.1 dB "
		::= { iqdbe02CmdEntry 37333 }


	iqdbe02EmbGainEmbedPair7Stereo OBJECT-TYPE
		SYNTAX		INTEGER { disable(0), enable(1) }
		MAX-ACCESS		read-write
		STATUS			current
		DESCRIPTION
				"TYPE: - Checkbox
				 PAGE: - Emb.Gain
					Stereo  cmdID= 37386 "
		::= { iqdbe02CmdEntry 37386 }


	iqdbe02EmbGainEmbedPair7Embed7InvertL OBJECT-TYPE
		SYNTAX		INTEGER { disable(0), enable(1) }
		MAX-ACCESS		read-write
		STATUS			current
		DESCRIPTION
				"TYPE: - Checkbox
				 PAGE: - Emb.Gain
					Embed 7 Invert L  cmdID= 37372 "
		::= { iqdbe02CmdEntry 37372 }


	iqdbe02EmbGainEmbedPair7Embed7InvertR OBJECT-TYPE
		SYNTAX		INTEGER { disable(0), enable(1) }
		MAX-ACCESS		read-write
		STATUS			current
		DESCRIPTION
				"TYPE: - Checkbox
				 PAGE: - Emb.Gain
					Embed 7 Invert R  cmdID= 37373 "
		::= { iqdbe02CmdEntry 37373 }


	iqdbe02EmbGainEmbedPair7Embed7LClip OBJECT-TYPE
		SYNTAX		RollCallString
		MAX-ACCESS		read-only
		STATUS			current
		DESCRIPTION
				"TYPE: - Display
				 PAGE: - Emb.Gain
					Embed 7-L Clip  cmdID= 37552  format=   "
		::= { iqdbe02CmdEntry 37552 }


	iqdbe02EmbGainEmbedPair7Embed7RClip OBJECT-TYPE
		SYNTAX		RollCallString
		MAX-ACCESS		read-only
		STATUS			current
		DESCRIPTION
				"TYPE: - Display
				 PAGE: - Emb.Gain
					Embed 7-R Clip  cmdID= 37553  format=   "
		::= { iqdbe02CmdEntry 37553 }


	iqdbe02EmbGainEmbedPair8Embed8MuteL OBJECT-TYPE
		SYNTAX		INTEGER { disable(0), enable(1) }
		MAX-ACCESS		read-write
		STATUS			current
		DESCRIPTION
				"TYPE: - Checkbox
				 PAGE: - Emb.Gain
					Embed 8 Mute L  cmdID= 37354 "
		::= { iqdbe02CmdEntry 37354 }


	iqdbe02EmbGainEmbedPair8Embed8MuteR OBJECT-TYPE
		SYNTAX		INTEGER { disable(0), enable(1) }
		MAX-ACCESS		read-write
		STATUS			current
		DESCRIPTION
				"TYPE: - Checkbox
				 PAGE: - Emb.Gain
					Embed 8 Mute R  cmdID= 37355 "
		::= { iqdbe02CmdEntry 37355 }


	iqdbe02EmbGainEmbedPair8Embed8LGain OBJECT-TYPE
		SYNTAX		INTEGER
		MAX-ACCESS		read-write
		STATUS			current
		DESCRIPTION
				"TYPE: - Number
				 PAGE: - Emb.Gain
					Embed 8 L Gain  cmdID= 37334  min= -661  max= 120  step= 1  format= %0.1f dB  div_scale= 10
					Min = -66.1 dB  Max = 12.0 dB  Step = 0.1 dB "
		::= { iqdbe02CmdEntry 37334 }


	iqdbe02EmbGainEmbedPair8Embed8RGain OBJECT-TYPE
		SYNTAX		INTEGER
		MAX-ACCESS		read-write
		STATUS			current
		DESCRIPTION
				"TYPE: - Number
				 PAGE: - Emb.Gain
					Embed 8 R Gain  cmdID= 37335  min= -661  max= 120  step= 1  format= %0.1f dB  div_scale= 10
					Min = -66.1 dB  Max = 12.0 dB  Step = 0.1 dB "
		::= { iqdbe02CmdEntry 37335 }


	iqdbe02EmbGainEmbedPair8Stereo OBJECT-TYPE
		SYNTAX		INTEGER { disable(0), enable(1) }
		MAX-ACCESS		read-write
		STATUS			current
		DESCRIPTION
				"TYPE: - Checkbox
				 PAGE: - Emb.Gain
					Stereo  cmdID= 37387 "
		::= { iqdbe02CmdEntry 37387 }


	iqdbe02EmbGainEmbedPair8Embed8InvertL OBJECT-TYPE
		SYNTAX		INTEGER { disable(0), enable(1) }
		MAX-ACCESS		read-write
		STATUS			current
		DESCRIPTION
				"TYPE: - Checkbox
				 PAGE: - Emb.Gain
					Embed 8 Invert L  cmdID= 37374 "
		::= { iqdbe02CmdEntry 37374 }


	iqdbe02EmbGainEmbedPair8Embed8InvertR OBJECT-TYPE
		SYNTAX		INTEGER { disable(0), enable(1) }
		MAX-ACCESS		read-write
		STATUS			current
		DESCRIPTION
				"TYPE: - Checkbox
				 PAGE: - Emb.Gain
					Embed 8 Invert R  cmdID= 37375 "
		::= { iqdbe02CmdEntry 37375 }


	iqdbe02EmbGainEmbedPair8Embed8LClip OBJECT-TYPE
		SYNTAX		RollCallString
		MAX-ACCESS		read-only
		STATUS			current
		DESCRIPTION
				"TYPE: - Display
				 PAGE: - Emb.Gain
					Embed 8-L Clip  cmdID= 37554  format=   "
		::= { iqdbe02CmdEntry 37554 }


	iqdbe02EmbGainEmbedPair8Embed8RClip OBJECT-TYPE
		SYNTAX		RollCallString
		MAX-ACCESS		read-only
		STATUS			current
		DESCRIPTION
				"TYPE: - Display
				 PAGE: - Emb.Gain
					Embed 8-R Clip  cmdID= 37555  format=   "
		::= { iqdbe02CmdEntry 37555 }


	iqdbe02EmbOutEmbedPair1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 1
					Left  cmdID= 37300
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37300 }


	iqdbe02EmbOutEmbedPair1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 1
					Right  cmdID= 37301
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37301 }


	iqdbe02EmbOutEmbedPair1LinkLRSelection OBJECT-TYPE
		SYNTAX		INTEGER { disable(0), enable(1) }
		MAX-ACCESS		read-write
		STATUS			current
		DESCRIPTION
				"TYPE: - Checkbox
				 PAGE: - Embed Pair 1
					Link L+R Selection  cmdID= 37390 "
		::= { iqdbe02CmdEntry 37390 }


	iqdbe02EmbOutEmbedPair2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 2
					Left  cmdID= 37302
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37302 }


	iqdbe02EmbOutEmbedPair2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 2
					Right  cmdID= 37303
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37303 }


	iqdbe02EmbOutEmbedPair2LinkLRSelection OBJECT-TYPE
		SYNTAX		INTEGER { disable(0), enable(1) }
		MAX-ACCESS		read-write
		STATUS			current
		DESCRIPTION
				"TYPE: - Checkbox
				 PAGE: - Embed Pair 2
					Link L+R Selection  cmdID= 37391 "
		::= { iqdbe02CmdEntry 37391 }


	iqdbe02EmbOutEmbedPair3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 3
					Left  cmdID= 37304
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37304 }


	iqdbe02EmbOutEmbedPair3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 3
					Right  cmdID= 37305
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37305 }


	iqdbe02EmbOutEmbedPair3LinkLRSelection OBJECT-TYPE
		SYNTAX		INTEGER { disable(0), enable(1) }
		MAX-ACCESS		read-write
		STATUS			current
		DESCRIPTION
				"TYPE: - Checkbox
				 PAGE: - Embed Pair 3
					Link L+R Selection  cmdID= 37392 "
		::= { iqdbe02CmdEntry 37392 }


	iqdbe02EmbOutEmbedPair4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 4
					Left  cmdID= 37306
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37306 }


	iqdbe02EmbOutEmbedPair4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 4
					Right  cmdID= 37307
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37307 }


	iqdbe02EmbOutEmbedPair4LinkLRSelection OBJECT-TYPE
		SYNTAX		INTEGER { disable(0), enable(1) }
		MAX-ACCESS		read-write
		STATUS			current
		DESCRIPTION
				"TYPE: - Checkbox
				 PAGE: - Embed Pair 4
					Link L+R Selection  cmdID= 37393 "
		::= { iqdbe02CmdEntry 37393 }


	iqdbe02EmbOutEmbedPair5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 5
					Left  cmdID= 37308
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37308 }


	iqdbe02EmbOutEmbedPair5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 5
					Right  cmdID= 37309
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37309 }


	iqdbe02EmbOutEmbedPair5LinkLRSelection OBJECT-TYPE
		SYNTAX		INTEGER { disable(0), enable(1) }
		MAX-ACCESS		read-write
		STATUS			current
		DESCRIPTION
				"TYPE: - Checkbox
				 PAGE: - Embed Pair 5
					Link L+R Selection  cmdID= 37394 "
		::= { iqdbe02CmdEntry 37394 }


	iqdbe02EmbOutEmbedPair6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 6
					Left  cmdID= 37310
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37310 }


	iqdbe02EmbOutEmbedPair6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 6
					Right  cmdID= 37311
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37311 }


	iqdbe02EmbOutEmbedPair6LinkLRSelection OBJECT-TYPE
		SYNTAX		INTEGER { disable(0), enable(1) }
		MAX-ACCESS		read-write
		STATUS			current
		DESCRIPTION
				"TYPE: - Checkbox
				 PAGE: - Embed Pair 6
					Link L+R Selection  cmdID= 37395 "
		::= { iqdbe02CmdEntry 37395 }


	iqdbe02EmbOutEmbedPair7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 7
					Left  cmdID= 37312
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37312 }


	iqdbe02EmbOutEmbedPair7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 7
					Right  cmdID= 37313
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37313 }


	iqdbe02EmbOutEmbedPair7LinkLRSelection OBJECT-TYPE
		SYNTAX		INTEGER { disable(0), enable(1) }
		MAX-ACCESS		read-write
		STATUS			current
		DESCRIPTION
				"TYPE: - Checkbox
				 PAGE: - Embed Pair 7
					Link L+R Selection  cmdID= 37396 "
		::= { iqdbe02CmdEntry 37396 }


	iqdbe02EmbOutEmbedPair8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 8
					Left  cmdID= 37314
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37314 }


	iqdbe02EmbOutEmbedPair8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 8
					Right  cmdID= 37315
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37315 }


	iqdbe02EmbOutEmbedPair8LinkLRSelection OBJECT-TYPE
		SYNTAX		INTEGER { disable(0), enable(1) }
		MAX-ACCESS		read-write
		STATUS			current
		DESCRIPTION
				"TYPE: - Checkbox
				 PAGE: - Embed Pair 8
					Link L+R Selection  cmdID= 37397 "
		::= { iqdbe02CmdEntry 37397 }


	iqdbe02AudioEmbModeInput1 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 1  cmdID= 37420
					PCM  value= 0
					Data  value= 1
					Mixed  value= 2  "
		::= { iqdbe02CmdEntry 37420 }


	iqdbe02AudioEmbModeInput2 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 2  cmdID= 37421
					PCM  value= 0
					Data  value= 1
					Mixed  value= 2  "
		::= { iqdbe02CmdEntry 37421 }


	iqdbe02AudioEmbModeInput3 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 3  cmdID= 37422
					PCM  value= 0
					Data  value= 1
					Mixed  value= 2  "
		::= { iqdbe02CmdEntry 37422 }


	iqdbe02AudioEmbModeInput4 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 4  cmdID= 37423
					PCM  value= 0
					Data  value= 1
					Mixed  value= 2  "
		::= { iqdbe02CmdEntry 37423 }


	iqdbe02AudioEmbModeInput5 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 5  cmdID= 37424
					PCM  value= 0
					Data  value= 1
					Mixed  value= 2  "
		::= { iqdbe02CmdEntry 37424 }


	iqdbe02AudioEmbModeInput6 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 6  cmdID= 37425
					PCM  value= 0
					Data  value= 1
					Mixed  value= 2  "
		::= { iqdbe02CmdEntry 37425 }


	iqdbe02AudioEmbModeInput7 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 7  cmdID= 37426
					PCM  value= 0
					Data  value= 1
					Mixed  value= 2  "
		::= { iqdbe02CmdEntry 37426 }


	iqdbe02AudioEmbModeInput8 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 8  cmdID= 37427
					PCM  value= 0
					Data  value= 1
					Mixed  value= 2  "
		::= { iqdbe02CmdEntry 37427 }


	iqdbe02EmbNamesDisembederNamesDisembed1 OBJECT-TYPE
		SYNTAX		RollCallString
		MAX-ACCESS		read-write
		STATUS			current
		DESCRIPTION
				"TYPE: - Editstring
				 PAGE: - Emb.Names
					Disembed 1  cmdID= 37500  "
		::= { iqdbe02CmdEntry 37500 }


	iqdbe02EmbNamesDisembederNamesDisembed1R OBJECT-TYPE
		SYNTAX		RollCallString
		MAX-ACCESS		read-write
		STATUS			current
		DESCRIPTION
				"TYPE: - Editstring
				 PAGE: - Emb.Names
					Disembed 1-R  cmdID= 37501  "
		::= { iqdbe02CmdEntry 37501 }


	iqdbe02EmbNamesDisembederNamesDisembed2 OBJECT-TYPE
		SYNTAX		RollCallString
		MAX-ACCESS		read-write
		STATUS			current
		DESCRIPTION
				"TYPE: - Editstring
				 PAGE: - Emb.Names
					Disembed 2  cmdID= 37502  "
		::= { iqdbe02CmdEntry 37502 }


	iqdbe02EmbNamesDisembederNamesDisembed2R OBJECT-TYPE
		SYNTAX		RollCallString
		MAX-ACCESS		read-write
		STATUS			current
		DESCRIPTION
				"TYPE: - Editstring
				 PAGE: - Emb.Names
					Disembed 2-R  cmdID= 37503  "
		::= { iqdbe02CmdEntry 37503 }


	iqdbe02EmbNamesDisembederNamesDisembed3 OBJECT-TYPE
		SYNTAX		RollCallString
		MAX-ACCESS		read-write
		STATUS			current
		DESCRIPTION
				"TYPE: - Editstring
				 PAGE: - Emb.Names
					Disembed 3  cmdID= 37504  "
		::= { iqdbe02CmdEntry 37504 }


	iqdbe02EmbNamesDisembederNamesDisembed3R OBJECT-TYPE
		SYNTAX		RollCallString
		MAX-ACCESS		read-write
		STATUS			current
		DESCRIPTION
				"TYPE: - Editstring
				 PAGE: - Emb.Names
					Disembed 3-R  cmdID= 37505  "
		::= { iqdbe02CmdEntry 37505 }


	iqdbe02EmbNamesDisembederNamesDisembed4 OBJECT-TYPE
		SYNTAX		RollCallString
		MAX-ACCESS		read-write
		STATUS			current
		DESCRIPTION
				"TYPE: - Editstring
				 PAGE: - Emb.Names
					Disembed 4  cmdID= 37506  "
		::= { iqdbe02CmdEntry 37506 }


	iqdbe02EmbNamesDisembederNamesDisembed4R OBJECT-TYPE
		SYNTAX		RollCallString
		MAX-ACCESS		read-write
		STATUS			current
		DESCRIPTION
				"TYPE: - Editstring
				 PAGE: - Emb.Names
					Disembed 4-R  cmdID= 37507  "
		::= { iqdbe02CmdEntry 37507 }


	iqdbe02EmbNamesDisembederNamesDisembed5 OBJECT-TYPE
		SYNTAX		RollCallString
		MAX-ACCESS		read-write
		STATUS			current
		DESCRIPTION
				"TYPE: - Editstring
				 PAGE: - Emb.Names
					Disembed 5  cmdID= 37508  "
		::= { iqdbe02CmdEntry 37508 }


	iqdbe02EmbNamesDisembederNamesDisembed5R OBJECT-TYPE
		SYNTAX		RollCallString
		MAX-ACCESS		read-write
		STATUS			current
		DESCRIPTION
				"TYPE: - Editstring
				 PAGE: - Emb.Names
					Disembed 5-R  cmdID= 37509  "
		::= { iqdbe02CmdEntry 37509 }


	iqdbe02EmbNamesDisembederNamesDisembed6 OBJECT-TYPE
		SYNTAX		RollCallString
		MAX-ACCESS		read-write
		STATUS			current
		DESCRIPTION
				"TYPE: - Editstring
				 PAGE: - Emb.Names
					Disembed 6  cmdID= 37510  "
		::= { iqdbe02CmdEntry 37510 }


	iqdbe02EmbNamesDisembederNamesDisembed6R OBJECT-TYPE
		SYNTAX		RollCallString
		MAX-ACCESS		read-write
		STATUS			current
		DESCRIPTION
				"TYPE: - Editstring
				 PAGE: - Emb.Names
					Disembed 6-R  cmdID= 37511  "
		::= { iqdbe02CmdEntry 37511 }


	iqdbe02EmbNamesDisembederNamesDisembed7 OBJECT-TYPE
		SYNTAX		RollCallString
		MAX-ACCESS		read-write
		STATUS			current
		DESCRIPTION
				"TYPE: - Editstring
				 PAGE: - Emb.Names
					Disembed 7  cmdID= 37512  "
		::= { iqdbe02CmdEntry 37512 }


	iqdbe02EmbNamesDisembederNamesDisembed7R OBJECT-TYPE
		SYNTAX		RollCallString
		MAX-ACCESS		read-write
		STATUS			current
		DESCRIPTION
				"TYPE: - Editstring
				 PAGE: - Emb.Names
					Disembed 7-R  cmdID= 37513  "
		::= { iqdbe02CmdEntry 37513 }


	iqdbe02EmbNamesDisembederNamesDisembed8 OBJECT-TYPE
		SYNTAX		RollCallString
		MAX-ACCESS		read-write
		STATUS			current
		DESCRIPTION
				"TYPE: - Editstring
				 PAGE: - Emb.Names
					Disembed 8  cmdID= 37514  "
		::= { iqdbe02CmdEntry 37514 }


	iqdbe02EmbNamesDisembederNamesDisembed8R OBJECT-TYPE
		SYNTAX		RollCallString
		MAX-ACCESS		read-write
		STATUS			current
		DESCRIPTION
				"TYPE: - Editstring
				 PAGE: - Emb.Names
					Disembed 8-R  cmdID= 37515  "
		::= { iqdbe02CmdEntry 37515 }


	iqdbe02EmbNamesEmbeddedOPNamesEmbed1 OBJECT-TYPE
		SYNTAX		RollCallString
		MAX-ACCESS		read-write
		STATUS			current
		DESCRIPTION
				"TYPE: - Editstring
				 PAGE: - Emb.Names
					Embed 1  cmdID= 37520  "
		::= { iqdbe02CmdEntry 37520 }


	iqdbe02EmbNamesEmbeddedOPNamesEmbed1R OBJECT-TYPE
		SYNTAX		RollCallString
		MAX-ACCESS		read-write
		STATUS			current
		DESCRIPTION
				"TYPE: - Editstring
				 PAGE: - Emb.Names
					Embed 1-R  cmdID= 37521  "
		::= { iqdbe02CmdEntry 37521 }


	iqdbe02EmbNamesEmbeddedOPNamesEmbed2 OBJECT-TYPE
		SYNTAX		RollCallString
		MAX-ACCESS		read-write
		STATUS			current
		DESCRIPTION
				"TYPE: - Editstring
				 PAGE: - Emb.Names
					Embed 2  cmdID= 37522  "
		::= { iqdbe02CmdEntry 37522 }


	iqdbe02EmbNamesEmbeddedOPNamesEmbed2R OBJECT-TYPE
		SYNTAX		RollCallString
		MAX-ACCESS		read-write
		STATUS			current
		DESCRIPTION
				"TYPE: - Editstring
				 PAGE: - Emb.Names
					Embed 2-R  cmdID= 37523  "
		::= { iqdbe02CmdEntry 37523 }


	iqdbe02EmbNamesEmbeddedOPNamesEmbed3 OBJECT-TYPE
		SYNTAX		RollCallString
		MAX-ACCESS		read-write
		STATUS			current
		DESCRIPTION
				"TYPE: - Editstring
				 PAGE: - Emb.Names
					Embed 3  cmdID= 37524  "
		::= { iqdbe02CmdEntry 37524 }


	iqdbe02EmbNamesEmbeddedOPNamesEmbed3R OBJECT-TYPE
		SYNTAX		RollCallString
		MAX-ACCESS		read-write
		STATUS			current
		DESCRIPTION
				"TYPE: - Editstring
				 PAGE: - Emb.Names
					Embed 3-R  cmdID= 37525  "
		::= { iqdbe02CmdEntry 37525 }


	iqdbe02EmbNamesEmbeddedOPNamesEmbed4 OBJECT-TYPE
		SYNTAX		RollCallString
		MAX-ACCESS		read-write
		STATUS			current
		DESCRIPTION
				"TYPE: - Editstring
				 PAGE: - Emb.Names
					Embed 4  cmdID= 37526  "
		::= { iqdbe02CmdEntry 37526 }


	iqdbe02EmbNamesEmbeddedOPNamesEmbed4R OBJECT-TYPE
		SYNTAX		RollCallString
		MAX-ACCESS		read-write
		STATUS			current
		DESCRIPTION
				"TYPE: - Editstring
				 PAGE: - Emb.Names
					Embed 4-R  cmdID= 37527  "
		::= { iqdbe02CmdEntry 37527 }


	iqdbe02EmbNamesEmbeddedOPNamesEmbed5 OBJECT-TYPE
		SYNTAX		RollCallString
		MAX-ACCESS		read-write
		STATUS			current
		DESCRIPTION
				"TYPE: - Editstring
				 PAGE: - Emb.Names
					Embed 5  cmdID= 37528  "
		::= { iqdbe02CmdEntry 37528 }


	iqdbe02EmbNamesEmbeddedOPNamesEmbed5R OBJECT-TYPE
		SYNTAX		RollCallString
		MAX-ACCESS		read-write
		STATUS			current
		DESCRIPTION
				"TYPE: - Editstring
				 PAGE: - Emb.Names
					Embed 5-R  cmdID= 37529  "
		::= { iqdbe02CmdEntry 37529 }


	iqdbe02EmbNamesEmbeddedOPNamesEmbed6 OBJECT-TYPE
		SYNTAX		RollCallString
		MAX-ACCESS		read-write
		STATUS			current
		DESCRIPTION
				"TYPE: - Editstring
				 PAGE: - Emb.Names
					Embed 6  cmdID= 37530  "
		::= { iqdbe02CmdEntry 37530 }


	iqdbe02EmbNamesEmbeddedOPNamesEmbed6R OBJECT-TYPE
		SYNTAX		RollCallString
		MAX-ACCESS		read-write
		STATUS			current
		DESCRIPTION
				"TYPE: - Editstring
				 PAGE: - Emb.Names
					Embed 6-R  cmdID= 37531  "
		::= { iqdbe02CmdEntry 37531 }


	iqdbe02EmbNamesEmbeddedOPNamesEmbed7 OBJECT-TYPE
		SYNTAX		RollCallString
		MAX-ACCESS		read-write
		STATUS			current
		DESCRIPTION
				"TYPE: - Editstring
				 PAGE: - Emb.Names
					Embed 7  cmdID= 37532  "
		::= { iqdbe02CmdEntry 37532 }


	iqdbe02EmbNamesEmbeddedOPNamesEmbed7R OBJECT-TYPE
		SYNTAX		RollCallString
		MAX-ACCESS		read-write
		STATUS			current
		DESCRIPTION
				"TYPE: - Editstring
				 PAGE: - Emb.Names
					Embed 7-R  cmdID= 37533  "
		::= { iqdbe02CmdEntry 37533 }


	iqdbe02EmbNamesEmbeddedOPNamesEmbed8 OBJECT-TYPE
		SYNTAX		RollCallString
		MAX-ACCESS		read-write
		STATUS			current
		DESCRIPTION
				"TYPE: - Editstring
				 PAGE: - Emb.Names
					Embed 8  cmdID= 37534  "
		::= { iqdbe02CmdEntry 37534 }


	iqdbe02EmbNamesEmbeddedOPNamesEmbed8R OBJECT-TYPE
		SYNTAX		RollCallString
		MAX-ACCESS		read-write
		STATUS			current
		DESCRIPTION
				"TYPE: - Editstring
				 PAGE: - Emb.Names
					Embed 8-R  cmdID= 37535  "
		::= { iqdbe02CmdEntry 37535 }


	iqdbe02EmbNamesIPNamesStereoDisemb1 OBJECT-TYPE
		SYNTAX		INTEGER { disable(0), enable(1) }
		MAX-ACCESS		read-write
		STATUS			current
		DESCRIPTION
				"TYPE: - Checkbox
				 PAGE: - Emb.Names
					Disemb 1  cmdID= 37400 "
		::= { iqdbe02CmdEntry 37400 }


	iqdbe02EmbNamesIPNamesStereoDisemb2 OBJECT-TYPE
		SYNTAX		INTEGER { disable(0), enable(1) }
		MAX-ACCESS		read-write
		STATUS			current
		DESCRIPTION
				"TYPE: - Checkbox
				 PAGE: - Emb.Names
					Disemb 2  cmdID= 37401 "
		::= { iqdbe02CmdEntry 37401 }


	iqdbe02EmbNamesIPNamesStereoDisemb3 OBJECT-TYPE
		SYNTAX		INTEGER { disable(0), enable(1) }
		MAX-ACCESS		read-write
		STATUS			current
		DESCRIPTION
				"TYPE: - Checkbox
				 PAGE: - Emb.Names
					Disemb 3  cmdID= 37402 "
		::= { iqdbe02CmdEntry 37402 }


	iqdbe02EmbNamesIPNamesStereoDisemb4 OBJECT-TYPE
		SYNTAX		INTEGER { disable(0), enable(1) }
		MAX-ACCESS		read-write
		STATUS			current
		DESCRIPTION
				"TYPE: - Checkbox
				 PAGE: - Emb.Names
					Disemb 4  cmdID= 37403 "
		::= { iqdbe02CmdEntry 37403 }


	iqdbe02EmbNamesIPNamesStereoDisemb5 OBJECT-TYPE
		SYNTAX		INTEGER { disable(0), enable(1) }
		MAX-ACCESS		read-write
		STATUS			current
		DESCRIPTION
				"TYPE: - Checkbox
				 PAGE: - Emb.Names
					Disemb 5  cmdID= 37404 "
		::= { iqdbe02CmdEntry 37404 }


	iqdbe02EmbNamesIPNamesStereoDisemb6 OBJECT-TYPE
		SYNTAX		INTEGER { disable(0), enable(1) }
		MAX-ACCESS		read-write
		STATUS			current
		DESCRIPTION
				"TYPE: - Checkbox
				 PAGE: - Emb.Names
					Disemb 6  cmdID= 37405 "
		::= { iqdbe02CmdEntry 37405 }


	iqdbe02EmbNamesIPNamesStereoDisemb7 OBJECT-TYPE
		SYNTAX		INTEGER { disable(0), enable(1) }
		MAX-ACCESS		read-write
		STATUS			current
		DESCRIPTION
				"TYPE: - Checkbox
				 PAGE: - Emb.Names
					Disemb 7  cmdID= 37406 "
		::= { iqdbe02CmdEntry 37406 }


	iqdbe02EmbNamesIPNamesStereoDisemb8 OBJECT-TYPE
		SYNTAX		INTEGER { disable(0), enable(1) }
		MAX-ACCESS		read-write
		STATUS			current
		DESCRIPTION
				"TYPE: - Checkbox
				 PAGE: - Emb.Names
					Disemb 8  cmdID= 37407 "
		::= { iqdbe02CmdEntry 37407 }


	iqdbe02EmbNamesOPNamesStereoEmbed1 OBJECT-TYPE
		SYNTAX		INTEGER { disable(0), enable(1) }
		MAX-ACCESS		read-write
		STATUS			current
		DESCRIPTION
				"TYPE: - Checkbox
				 PAGE: - Emb.Names
					Embed 1  cmdID= 37410 "
		::= { iqdbe02CmdEntry 37410 }


	iqdbe02EmbNamesOPNamesStereoEmbed2 OBJECT-TYPE
		SYNTAX		INTEGER { disable(0), enable(1) }
		MAX-ACCESS		read-write
		STATUS			current
		DESCRIPTION
				"TYPE: - Checkbox
				 PAGE: - Emb.Names
					Embed 2  cmdID= 37411 "
		::= { iqdbe02CmdEntry 37411 }


	iqdbe02EmbNamesOPNamesStereoEmbed3 OBJECT-TYPE
		SYNTAX		INTEGER { disable(0), enable(1) }
		MAX-ACCESS		read-write
		STATUS			current
		DESCRIPTION
				"TYPE: - Checkbox
				 PAGE: - Emb.Names
					Embed 3  cmdID= 37412 "
		::= { iqdbe02CmdEntry 37412 }


	iqdbe02EmbNamesOPNamesStereoEmbed4 OBJECT-TYPE
		SYNTAX		INTEGER { disable(0), enable(1) }
		MAX-ACCESS		read-write
		STATUS			current
		DESCRIPTION
				"TYPE: - Checkbox
				 PAGE: - Emb.Names
					Embed 4  cmdID= 37413 "
		::= { iqdbe02CmdEntry 37413 }


	iqdbe02EmbNamesOPNamesStereoEmbed5 OBJECT-TYPE
		SYNTAX		INTEGER { disable(0), enable(1) }
		MAX-ACCESS		read-write
		STATUS			current
		DESCRIPTION
				"TYPE: - Checkbox
				 PAGE: - Emb.Names
					Embed 5  cmdID= 37414 "
		::= { iqdbe02CmdEntry 37414 }


	iqdbe02EmbNamesOPNamesStereoEmbed6 OBJECT-TYPE
		SYNTAX		INTEGER { disable(0), enable(1) }
		MAX-ACCESS		read-write
		STATUS			current
		DESCRIPTION
				"TYPE: - Checkbox
				 PAGE: - Emb.Names
					Embed 6  cmdID= 37415 "
		::= { iqdbe02CmdEntry 37415 }


	iqdbe02EmbNamesOPNamesStereoEmbed7 OBJECT-TYPE
		SYNTAX		INTEGER { disable(0), enable(1) }
		MAX-ACCESS		read-write
		STATUS			current
		DESCRIPTION
				"TYPE: - Checkbox
				 PAGE: - Emb.Names
					Embed 7  cmdID= 37416 "
		::= { iqdbe02CmdEntry 37416 }


	iqdbe02EmbNamesOPNamesStereoEmbed8 OBJECT-TYPE
		SYNTAX		INTEGER { disable(0), enable(1) }
		MAX-ACCESS		read-write
		STATUS			current
		DESCRIPTION
				"TYPE: - Checkbox
				 PAGE: - Emb.Names
					Embed 8  cmdID= 37417 "
		::= { iqdbe02CmdEntry 37417 }


	iqdbe02AudioMixNamesMix1 OBJECT-TYPE
		SYNTAX		RollCallString
		MAX-ACCESS		read-write
		STATUS			current
		DESCRIPTION
				"TYPE: - Editstring
					Mix 1  cmdID= 37810  "
		::= { iqdbe02CmdEntry 37810 }


	iqdbe02AudioMixNamesMix2 OBJECT-TYPE
		SYNTAX		RollCallString
		MAX-ACCESS		read-write
		STATUS			current
		DESCRIPTION
				"TYPE: - Editstring
					Mix 2  cmdID= 37811  "
		::= { iqdbe02CmdEntry 37811 }


	iqdbe02AudioMixNamesMix3 OBJECT-TYPE
		SYNTAX		RollCallString
		MAX-ACCESS		read-write
		STATUS			current
		DESCRIPTION
				"TYPE: - Editstring
					Mix 3  cmdID= 37812  "
		::= { iqdbe02CmdEntry 37812 }


	iqdbe02AudioMixNamesMix4 OBJECT-TYPE
		SYNTAX		RollCallString
		MAX-ACCESS		read-write
		STATUS			current
		DESCRIPTION
				"TYPE: - Editstring
					Mix 4  cmdID= 37813  "
		::= { iqdbe02CmdEntry 37813 }


	iqdbe02Mix1RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 1  cmdID= 37600
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37600 }


	iqdbe02Mix1RoutingInvert1 OBJECT-TYPE
		SYNTAX		INTEGER { disable(0), enable(1) }
		MAX-ACCESS		read-write
		STATUS			current
		DESCRIPTION
				"TYPE: - Checkbox
				 PAGE: - Mix 1
					Invert 1  cmdID= 37720 "
		::= { iqdbe02CmdEntry 37720 }


	iqdbe02Mix1RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 2  cmdID= 37601
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37601 }


	iqdbe02Mix1RoutingInvert2 OBJECT-TYPE
		SYNTAX		INTEGER { disable(0), enable(1) }
		MAX-ACCESS		read-write
		STATUS			current
		DESCRIPTION
				"TYPE: - Checkbox
				 PAGE: - Mix 1
					Invert 2  cmdID= 37721 "
		::= { iqdbe02CmdEntry 37721 }


	iqdbe02Mix1RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 3  cmdID= 37602
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37602 }


	iqdbe02Mix1RoutingInvert3 OBJECT-TYPE
		SYNTAX		INTEGER { disable(0), enable(1) }
		MAX-ACCESS		read-write
		STATUS			current
		DESCRIPTION
				"TYPE: - Checkbox
				 PAGE: - Mix 1
					Invert 3  cmdID= 37722 "
		::= { iqdbe02CmdEntry 37722 }


	iqdbe02Mix1RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 4  cmdID= 37603
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37603 }


	iqdbe02Mix1RoutingInvert4 OBJECT-TYPE
		SYNTAX		INTEGER { disable(0), enable(1) }
		MAX-ACCESS		read-write
		STATUS			current
		DESCRIPTION
				"TYPE: - Checkbox
				 PAGE: - Mix 1
					Invert 4  cmdID= 37723 "
		::= { iqdbe02CmdEntry 37723 }


	iqdbe02Mix1GainGain1 OBJECT-TYPE
		SYNTAX		INTEGER
		MAX-ACCESS		read-write
		STATUS			current
		DESCRIPTION
				"TYPE: - Number
				 PAGE: - Mix 1
					Gain 1  cmdID= 37640  min= -360  max= 120  step= 1  format= %0.1f dB  div_scale= 10
					Min = -36.0 dB  Max = 12.0 dB  Step = 0.1 dB "
		::= { iqdbe02CmdEntry 37640 }


	iqdbe02Mix1GainMute1 OBJECT-TYPE
		SYNTAX		INTEGER { disable(0), enable(1) }
		MAX-ACCESS		read-write
		STATUS			current
		DESCRIPTION
				"TYPE: - Checkbox
				 PAGE: - Mix 1
					Mute 1  cmdID= 37680 "
		::= { iqdbe02CmdEntry 37680 }


	iqdbe02Mix1GainGain2 OBJECT-TYPE
		SYNTAX		INTEGER
		MAX-ACCESS		read-write
		STATUS			current
		DESCRIPTION
				"TYPE: - Number
				 PAGE: - Mix 1
					Gain 2  cmdID= 37641  min= -360  max= 120  step= 1  format= %0.1f dB  div_scale= 10
					Min = -36.0 dB  Max = 12.0 dB  Step = 0.1 dB "
		::= { iqdbe02CmdEntry 37641 }


	iqdbe02Mix1GainMute2 OBJECT-TYPE
		SYNTAX		INTEGER { disable(0), enable(1) }
		MAX-ACCESS		read-write
		STATUS			current
		DESCRIPTION
				"TYPE: - Checkbox
				 PAGE: - Mix 1
					Mute 2  cmdID= 37681 "
		::= { iqdbe02CmdEntry 37681 }


	iqdbe02Mix1GainGain3 OBJECT-TYPE
		SYNTAX		INTEGER
		MAX-ACCESS		read-write
		STATUS			current
		DESCRIPTION
				"TYPE: - Number
				 PAGE: - Mix 1
					Gain 3  cmdID= 37642  min= -360  max= 120  step= 1  format= %0.1f dB  div_scale= 10
					Min = -36.0 dB  Max = 12.0 dB  Step = 0.1 dB "
		::= { iqdbe02CmdEntry 37642 }


	iqdbe02Mix1GainMute3 OBJECT-TYPE
		SYNTAX		INTEGER { disable(0), enable(1) }
		MAX-ACCESS		read-write
		STATUS			current
		DESCRIPTION
				"TYPE: - Checkbox
				 PAGE: - Mix 1
					Mute 3  cmdID= 37682 "
		::= { iqdbe02CmdEntry 37682 }


	iqdbe02Mix1GainGain4 OBJECT-TYPE
		SYNTAX		INTEGER
		MAX-ACCESS		read-write
		STATUS			current
		DESCRIPTION
				"TYPE: - Number
				 PAGE: - Mix 1
					Gain 4  cmdID= 37643  min= -360  max= 120  step= 1  format= %0.1f dB  div_scale= 10
					Min = -36.0 dB  Max = 12.0 dB  Step = 0.1 dB "
		::= { iqdbe02CmdEntry 37643 }


	iqdbe02Mix1GainMute4 OBJECT-TYPE
		SYNTAX		INTEGER { disable(0), enable(1) }
		MAX-ACCESS		read-write
		STATUS			current
		DESCRIPTION
				"TYPE: - Checkbox
				 PAGE: - Mix 1
					Mute 4  cmdID= 37683 "
		::= { iqdbe02CmdEntry 37683 }


	iqdbe02Mix1GainInp1Clip OBJECT-TYPE
		SYNTAX		RollCallString
		MAX-ACCESS		read-only
		STATUS			current
		DESCRIPTION
				"TYPE: - Display
				 PAGE: - Mix 1
					Inp1 Clip  cmdID= 37760  format=   "
		::= { iqdbe02CmdEntry 37760 }


	iqdbe02Mix1GainInp2Clip OBJECT-TYPE
		SYNTAX		RollCallString
		MAX-ACCESS		read-only
		STATUS			current
		DESCRIPTION
				"TYPE: - Display
				 PAGE: - Mix 1
					Inp2 Clip  cmdID= 37761  format=   "
		::= { iqdbe02CmdEntry 37761 }


	iqdbe02Mix1GainInp3Clip OBJECT-TYPE
		SYNTAX		RollCallString
		MAX-ACCESS		read-only
		STATUS			current
		DESCRIPTION
				"TYPE: - Display
				 PAGE: - Mix 1
					Inp3 Clip  cmdID= 37762  format=   "
		::= { iqdbe02CmdEntry 37762 }


	iqdbe02Mix1GainInp4Clip OBJECT-TYPE
		SYNTAX		RollCallString
		MAX-ACCESS		read-only
		STATUS			current
		DESCRIPTION
				"TYPE: - Display
				 PAGE: - Mix 1
					Inp4 Clip  cmdID= 37763  format=   "
		::= { iqdbe02CmdEntry 37763 }


	iqdbe02Mix1GainOPClip OBJECT-TYPE
		SYNTAX		RollCallString
		MAX-ACCESS		read-only
		STATUS			current
		DESCRIPTION
				"TYPE: - Display
				 PAGE: - Mix 1
					O/P Clip  cmdID= 37800  format=   "
		::= { iqdbe02CmdEntry 37800 }


	iqdbe02Mix2RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 1  cmdID= 37604
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37604 }


	iqdbe02Mix2RoutingInvert1 OBJECT-TYPE
		SYNTAX		INTEGER { disable(0), enable(1) }
		MAX-ACCESS		read-write
		STATUS			current
		DESCRIPTION
				"TYPE: - Checkbox
				 PAGE: - Mix 2
					Invert 1  cmdID= 37724 "
		::= { iqdbe02CmdEntry 37724 }


	iqdbe02Mix2RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 2  cmdID= 37605
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37605 }


	iqdbe02Mix2RoutingInvert2 OBJECT-TYPE
		SYNTAX		INTEGER { disable(0), enable(1) }
		MAX-ACCESS		read-write
		STATUS			current
		DESCRIPTION
				"TYPE: - Checkbox
				 PAGE: - Mix 2
					Invert 2  cmdID= 37725 "
		::= { iqdbe02CmdEntry 37725 }


	iqdbe02Mix2RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 3  cmdID= 37606
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37606 }


	iqdbe02Mix2RoutingInvert3 OBJECT-TYPE
		SYNTAX		INTEGER { disable(0), enable(1) }
		MAX-ACCESS		read-write
		STATUS			current
		DESCRIPTION
				"TYPE: - Checkbox
				 PAGE: - Mix 2
					Invert 3  cmdID= 37726 "
		::= { iqdbe02CmdEntry 37726 }


	iqdbe02Mix2RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 4  cmdID= 37607
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37607 }


	iqdbe02Mix2RoutingInvert4 OBJECT-TYPE
		SYNTAX		INTEGER { disable(0), enable(1) }
		MAX-ACCESS		read-write
		STATUS			current
		DESCRIPTION
				"TYPE: - Checkbox
				 PAGE: - Mix 2
					Invert 4  cmdID= 37727 "
		::= { iqdbe02CmdEntry 37727 }


	iqdbe02Mix2GainGain1 OBJECT-TYPE
		SYNTAX		INTEGER
		MAX-ACCESS		read-write
		STATUS			current
		DESCRIPTION
				"TYPE: - Number
				 PAGE: - Mix 2
					Gain 1  cmdID= 37644  min= -360  max= 120  step= 1  format= %0.1f dB  div_scale= 10
					Min = -36.0 dB  Max = 12.0 dB  Step = 0.1 dB "
		::= { iqdbe02CmdEntry 37644 }


	iqdbe02Mix2GainMute1 OBJECT-TYPE
		SYNTAX		INTEGER { disable(0), enable(1) }
		MAX-ACCESS		read-write
		STATUS			current
		DESCRIPTION
				"TYPE: - Checkbox
				 PAGE: - Mix 2
					Mute 1  cmdID= 37684 "
		::= { iqdbe02CmdEntry 37684 }


	iqdbe02Mix2GainGain2 OBJECT-TYPE
		SYNTAX		INTEGER
		MAX-ACCESS		read-write
		STATUS			current
		DESCRIPTION
				"TYPE: - Number
				 PAGE: - Mix 2
					Gain 2  cmdID= 37645  min= -360  max= 120  step= 1  format= %0.1f dB  div_scale= 10
					Min = -36.0 dB  Max = 12.0 dB  Step = 0.1 dB "
		::= { iqdbe02CmdEntry 37645 }


	iqdbe02Mix2GainMute2 OBJECT-TYPE
		SYNTAX		INTEGER { disable(0), enable(1) }
		MAX-ACCESS		read-write
		STATUS			current
		DESCRIPTION
				"TYPE: - Checkbox
				 PAGE: - Mix 2
					Mute 2  cmdID= 37685 "
		::= { iqdbe02CmdEntry 37685 }


	iqdbe02Mix2GainGain3 OBJECT-TYPE
		SYNTAX		INTEGER
		MAX-ACCESS		read-write
		STATUS			current
		DESCRIPTION
				"TYPE: - Number
				 PAGE: - Mix 2
					Gain 3  cmdID= 37646  min= -360  max= 120  step= 1  format= %0.1f dB  div_scale= 10
					Min = -36.0 dB  Max = 12.0 dB  Step = 0.1 dB "
		::= { iqdbe02CmdEntry 37646 }


	iqdbe02Mix2GainMute3 OBJECT-TYPE
		SYNTAX		INTEGER { disable(0), enable(1) }
		MAX-ACCESS		read-write
		STATUS			current
		DESCRIPTION
				"TYPE: - Checkbox
				 PAGE: - Mix 2
					Mute 3  cmdID= 37686 "
		::= { iqdbe02CmdEntry 37686 }


	iqdbe02Mix2GainGain4 OBJECT-TYPE
		SYNTAX		INTEGER
		MAX-ACCESS		read-write
		STATUS			current
		DESCRIPTION
				"TYPE: - Number
				 PAGE: - Mix 2
					Gain 4  cmdID= 37647  min= -360  max= 120  step= 1  format= %0.1f dB  div_scale= 10
					Min = -36.0 dB  Max = 12.0 dB  Step = 0.1 dB "
		::= { iqdbe02CmdEntry 37647 }


	iqdbe02Mix2GainMute4 OBJECT-TYPE
		SYNTAX		INTEGER { disable(0), enable(1) }
		MAX-ACCESS		read-write
		STATUS			current
		DESCRIPTION
				"TYPE: - Checkbox
				 PAGE: - Mix 2
					Mute 4  cmdID= 37687 "
		::= { iqdbe02CmdEntry 37687 }


	iqdbe02Mix2GainInp1Clip OBJECT-TYPE
		SYNTAX		RollCallString
		MAX-ACCESS		read-only
		STATUS			current
		DESCRIPTION
				"TYPE: - Display
				 PAGE: - Mix 2
					Inp1 Clip  cmdID= 37764  format=   "
		::= { iqdbe02CmdEntry 37764 }


	iqdbe02Mix2GainInp2Clip OBJECT-TYPE
		SYNTAX		RollCallString
		MAX-ACCESS		read-only
		STATUS			current
		DESCRIPTION
				"TYPE: - Display
				 PAGE: - Mix 2
					Inp2 Clip  cmdID= 37765  format=   "
		::= { iqdbe02CmdEntry 37765 }


	iqdbe02Mix2GainInp3Clip OBJECT-TYPE
		SYNTAX		RollCallString
		MAX-ACCESS		read-only
		STATUS			current
		DESCRIPTION
				"TYPE: - Display
				 PAGE: - Mix 2
					Inp3 Clip  cmdID= 37766  format=   "
		::= { iqdbe02CmdEntry 37766 }


	iqdbe02Mix2GainInp4Clip OBJECT-TYPE
		SYNTAX		RollCallString
		MAX-ACCESS		read-only
		STATUS			current
		DESCRIPTION
				"TYPE: - Display
				 PAGE: - Mix 2
					Inp4 Clip  cmdID= 37767  format=   "
		::= { iqdbe02CmdEntry 37767 }


	iqdbe02Mix2GainOPClip OBJECT-TYPE
		SYNTAX		RollCallString
		MAX-ACCESS		read-only
		STATUS			current
		DESCRIPTION
				"TYPE: - Display
				 PAGE: - Mix 2
					O/P Clip  cmdID= 37801  format=   "
		::= { iqdbe02CmdEntry 37801 }


	iqdbe02Mix3RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 1  cmdID= 37608
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37608 }


	iqdbe02Mix3RoutingInvert1 OBJECT-TYPE
		SYNTAX		INTEGER { disable(0), enable(1) }
		MAX-ACCESS		read-write
		STATUS			current
		DESCRIPTION
				"TYPE: - Checkbox
				 PAGE: - Mix 3
					Invert 1  cmdID= 37728 "
		::= { iqdbe02CmdEntry 37728 }


	iqdbe02Mix3RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 2  cmdID= 37609
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37609 }


	iqdbe02Mix3RoutingInvert2 OBJECT-TYPE
		SYNTAX		INTEGER { disable(0), enable(1) }
		MAX-ACCESS		read-write
		STATUS			current
		DESCRIPTION
				"TYPE: - Checkbox
				 PAGE: - Mix 3
					Invert 2  cmdID= 37729 "
		::= { iqdbe02CmdEntry 37729 }


	iqdbe02Mix3RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 3  cmdID= 37610
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37610 }


	iqdbe02Mix3RoutingInvert3 OBJECT-TYPE
		SYNTAX		INTEGER { disable(0), enable(1) }
		MAX-ACCESS		read-write
		STATUS			current
		DESCRIPTION
				"TYPE: - Checkbox
				 PAGE: - Mix 3
					Invert 3  cmdID= 37730 "
		::= { iqdbe02CmdEntry 37730 }


	iqdbe02Mix3RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 4  cmdID= 37611
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37611 }


	iqdbe02Mix3RoutingInvert4 OBJECT-TYPE
		SYNTAX		INTEGER { disable(0), enable(1) }
		MAX-ACCESS		read-write
		STATUS			current
		DESCRIPTION
				"TYPE: - Checkbox
				 PAGE: - Mix 3
					Invert 4  cmdID= 37731 "
		::= { iqdbe02CmdEntry 37731 }


	iqdbe02Mix3GainGain1 OBJECT-TYPE
		SYNTAX		INTEGER
		MAX-ACCESS		read-write
		STATUS			current
		DESCRIPTION
				"TYPE: - Number
				 PAGE: - Mix 3
					Gain 1  cmdID= 37648  min= -360  max= 120  step= 1  format= %0.1f dB  div_scale= 10
					Min = -36.0 dB  Max = 12.0 dB  Step = 0.1 dB "
		::= { iqdbe02CmdEntry 37648 }


	iqdbe02Mix3GainMute1 OBJECT-TYPE
		SYNTAX		INTEGER { disable(0), enable(1) }
		MAX-ACCESS		read-write
		STATUS			current
		DESCRIPTION
				"TYPE: - Checkbox
				 PAGE: - Mix 3
					Mute 1  cmdID= 37688 "
		::= { iqdbe02CmdEntry 37688 }


	iqdbe02Mix3GainGain2 OBJECT-TYPE
		SYNTAX		INTEGER
		MAX-ACCESS		read-write
		STATUS			current
		DESCRIPTION
				"TYPE: - Number
				 PAGE: - Mix 3
					Gain 2  cmdID= 37649  min= -360  max= 120  step= 1  format= %0.1f dB  div_scale= 10
					Min = -36.0 dB  Max = 12.0 dB  Step = 0.1 dB "
		::= { iqdbe02CmdEntry 37649 }


	iqdbe02Mix3GainMute2 OBJECT-TYPE
		SYNTAX		INTEGER { disable(0), enable(1) }
		MAX-ACCESS		read-write
		STATUS			current
		DESCRIPTION
				"TYPE: - Checkbox
				 PAGE: - Mix 3
					Mute 2  cmdID= 37689 "
		::= { iqdbe02CmdEntry 37689 }


	iqdbe02Mix3GainGain3 OBJECT-TYPE
		SYNTAX		INTEGER
		MAX-ACCESS		read-write
		STATUS			current
		DESCRIPTION
				"TYPE: - Number
				 PAGE: - Mix 3
					Gain 3  cmdID= 37650  min= -360  max= 120  step= 1  format= %0.1f dB  div_scale= 10
					Min = -36.0 dB  Max = 12.0 dB  Step = 0.1 dB "
		::= { iqdbe02CmdEntry 37650 }


	iqdbe02Mix3GainMute3 OBJECT-TYPE
		SYNTAX		INTEGER { disable(0), enable(1) }
		MAX-ACCESS		read-write
		STATUS			current
		DESCRIPTION
				"TYPE: - Checkbox
				 PAGE: - Mix 3
					Mute 3  cmdID= 37690 "
		::= { iqdbe02CmdEntry 37690 }


	iqdbe02Mix3GainGain4 OBJECT-TYPE
		SYNTAX		INTEGER
		MAX-ACCESS		read-write
		STATUS			current
		DESCRIPTION
				"TYPE: - Number
				 PAGE: - Mix 3
					Gain 4  cmdID= 37651  min= -360  max= 120  step= 1  format= %0.1f dB  div_scale= 10
					Min = -36.0 dB  Max = 12.0 dB  Step = 0.1 dB "
		::= { iqdbe02CmdEntry 37651 }


	iqdbe02Mix3GainMute4 OBJECT-TYPE
		SYNTAX		INTEGER { disable(0), enable(1) }
		MAX-ACCESS		read-write
		STATUS			current
		DESCRIPTION
				"TYPE: - Checkbox
				 PAGE: - Mix 3
					Mute 4  cmdID= 37691 "
		::= { iqdbe02CmdEntry 37691 }


	iqdbe02Mix3GainInp1Clip OBJECT-TYPE
		SYNTAX		RollCallString
		MAX-ACCESS		read-only
		STATUS			current
		DESCRIPTION
				"TYPE: - Display
				 PAGE: - Mix 3
					Inp1 Clip  cmdID= 37768  format=   "
		::= { iqdbe02CmdEntry 37768 }


	iqdbe02Mix3GainInp2Clip OBJECT-TYPE
		SYNTAX		RollCallString
		MAX-ACCESS		read-only
		STATUS			current
		DESCRIPTION
				"TYPE: - Display
				 PAGE: - Mix 3
					Inp2 Clip  cmdID= 37769  format=   "
		::= { iqdbe02CmdEntry 37769 }


	iqdbe02Mix3GainInp3Clip OBJECT-TYPE
		SYNTAX		RollCallString
		MAX-ACCESS		read-only
		STATUS			current
		DESCRIPTION
				"TYPE: - Display
				 PAGE: - Mix 3
					Inp3 Clip  cmdID= 37770  format=   "
		::= { iqdbe02CmdEntry 37770 }


	iqdbe02Mix3GainInp4Clip OBJECT-TYPE
		SYNTAX		RollCallString
		MAX-ACCESS		read-only
		STATUS			current
		DESCRIPTION
				"TYPE: - Display
				 PAGE: - Mix 3
					Inp4 Clip  cmdID= 37771  format=   "
		::= { iqdbe02CmdEntry 37771 }


	iqdbe02Mix3GainOPClip OBJECT-TYPE
		SYNTAX		RollCallString
		MAX-ACCESS		read-only
		STATUS			current
		DESCRIPTION
				"TYPE: - Display
				 PAGE: - Mix 3
					O/P Clip  cmdID= 37802  format=   "
		::= { iqdbe02CmdEntry 37802 }


	iqdbe02Mix4RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 1  cmdID= 37612
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37612 }


	iqdbe02Mix4RoutingInvert1 OBJECT-TYPE
		SYNTAX		INTEGER { disable(0), enable(1) }
		MAX-ACCESS		read-write
		STATUS			current
		DESCRIPTION
				"TYPE: - Checkbox
				 PAGE: - Mix 4
					Invert 1  cmdID= 37732 "
		::= { iqdbe02CmdEntry 37732 }


	iqdbe02Mix4RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 2  cmdID= 37613
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37613 }


	iqdbe02Mix4RoutingInvert2 OBJECT-TYPE
		SYNTAX		INTEGER { disable(0), enable(1) }
		MAX-ACCESS		read-write
		STATUS			current
		DESCRIPTION
				"TYPE: - Checkbox
				 PAGE: - Mix 4
					Invert 2  cmdID= 37733 "
		::= { iqdbe02CmdEntry 37733 }


	iqdbe02Mix4RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 3  cmdID= 37614
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37614 }


	iqdbe02Mix4RoutingInvert3 OBJECT-TYPE
		SYNTAX		INTEGER { disable(0), enable(1) }
		MAX-ACCESS		read-write
		STATUS			current
		DESCRIPTION
				"TYPE: - Checkbox
				 PAGE: - Mix 4
					Invert 3  cmdID= 37734 "
		::= { iqdbe02CmdEntry 37734 }


	iqdbe02Mix4RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 4  cmdID= 37615
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 37615 }


	iqdbe02Mix4RoutingInvert4 OBJECT-TYPE
		SYNTAX		INTEGER { disable(0), enable(1) }
		MAX-ACCESS		read-write
		STATUS			current
		DESCRIPTION
				"TYPE: - Checkbox
				 PAGE: - Mix 4
					Invert 4  cmdID= 37735 "
		::= { iqdbe02CmdEntry 37735 }


	iqdbe02Mix4GainGain1 OBJECT-TYPE
		SYNTAX		INTEGER
		MAX-ACCESS		read-write
		STATUS			current
		DESCRIPTION
				"TYPE: - Number
				 PAGE: - Mix 4
					Gain 1  cmdID= 37652  min= -360  max= 120  step= 1  format= %0.1f dB  div_scale= 10
					Min = -36.0 dB  Max = 12.0 dB  Step = 0.1 dB "
		::= { iqdbe02CmdEntry 37652 }


	iqdbe02Mix4GainMute1 OBJECT-TYPE
		SYNTAX		INTEGER { disable(0), enable(1) }
		MAX-ACCESS		read-write
		STATUS			current
		DESCRIPTION
				"TYPE: - Checkbox
				 PAGE: - Mix 4
					Mute 1  cmdID= 37692 "
		::= { iqdbe02CmdEntry 37692 }


	iqdbe02Mix4GainGain2 OBJECT-TYPE
		SYNTAX		INTEGER
		MAX-ACCESS		read-write
		STATUS			current
		DESCRIPTION
				"TYPE: - Number
				 PAGE: - Mix 4
					Gain 2  cmdID= 37653  min= -360  max= 120  step= 1  format= %0.1f dB  div_scale= 10
					Min = -36.0 dB  Max = 12.0 dB  Step = 0.1 dB "
		::= { iqdbe02CmdEntry 37653 }


	iqdbe02Mix4GainMute2 OBJECT-TYPE
		SYNTAX		INTEGER { disable(0), enable(1) }
		MAX-ACCESS		read-write
		STATUS			current
		DESCRIPTION
				"TYPE: - Checkbox
				 PAGE: - Mix 4
					Mute 2  cmdID= 37693 "
		::= { iqdbe02CmdEntry 37693 }


	iqdbe02Mix4GainGain3 OBJECT-TYPE
		SYNTAX		INTEGER
		MAX-ACCESS		read-write
		STATUS			current
		DESCRIPTION
				"TYPE: - Number
				 PAGE: - Mix 4
					Gain 3  cmdID= 37654  min= -360  max= 120  step= 1  format= %0.1f dB  div_scale= 10
					Min = -36.0 dB  Max = 12.0 dB  Step = 0.1 dB "
		::= { iqdbe02CmdEntry 37654 }


	iqdbe02Mix4GainMute3 OBJECT-TYPE
		SYNTAX		INTEGER { disable(0), enable(1) }
		MAX-ACCESS		read-write
		STATUS			current
		DESCRIPTION
				"TYPE: - Checkbox
				 PAGE: - Mix 4
					Mute 3  cmdID= 37694 "
		::= { iqdbe02CmdEntry 37694 }


	iqdbe02Mix4GainGain4 OBJECT-TYPE
		SYNTAX		INTEGER
		MAX-ACCESS		read-write
		STATUS			current
		DESCRIPTION
				"TYPE: - Number
				 PAGE: - Mix 4
					Gain 4  cmdID= 37655  min= -360  max= 120  step= 1  format= %0.1f dB  div_scale= 10
					Min = -36.0 dB  Max = 12.0 dB  Step = 0.1 dB "
		::= { iqdbe02CmdEntry 37655 }


	iqdbe02Mix4GainMute4 OBJECT-TYPE
		SYNTAX		INTEGER { disable(0), enable(1) }
		MAX-ACCESS		read-write
		STATUS			current
		DESCRIPTION
				"TYPE: - Checkbox
				 PAGE: - Mix 4
					Mute 4  cmdID= 37695 "
		::= { iqdbe02CmdEntry 37695 }


	iqdbe02Mix4GainInp1Clip OBJECT-TYPE
		SYNTAX		RollCallString
		MAX-ACCESS		read-only
		STATUS			current
		DESCRIPTION
				"TYPE: - Display
				 PAGE: - Mix 4
					Inp1 Clip  cmdID= 37772  format=   "
		::= { iqdbe02CmdEntry 37772 }


	iqdbe02Mix4GainInp2Clip OBJECT-TYPE
		SYNTAX		RollCallString
		MAX-ACCESS		read-only
		STATUS			current
		DESCRIPTION
				"TYPE: - Display
				 PAGE: - Mix 4
					Inp2 Clip  cmdID= 37773  format=   "
		::= { iqdbe02CmdEntry 37773 }


	iqdbe02Mix4GainInp3Clip OBJECT-TYPE
		SYNTAX		RollCallString
		MAX-ACCESS		read-only
		STATUS			current
		DESCRIPTION
				"TYPE: - Display
				 PAGE: - Mix 4
					Inp3 Clip  cmdID= 37774  format=   "
		::= { iqdbe02CmdEntry 37774 }


	iqdbe02Mix4GainInp4Clip OBJECT-TYPE
		SYNTAX		RollCallString
		MAX-ACCESS		read-only
		STATUS			current
		DESCRIPTION
				"TYPE: - Display
				 PAGE: - Mix 4
					Inp4 Clip  cmdID= 37775  format=   "
		::= { iqdbe02CmdEntry 37775 }


	iqdbe02Mix4GainOPClip OBJECT-TYPE
		SYNTAX		RollCallString
		MAX-ACCESS		read-only
		STATUS			current
		DESCRIPTION
				"TYPE: - Display
				 PAGE: - Mix 4
					O/P Clip  cmdID= 37803  format=   "
		::= { iqdbe02CmdEntry 37803 }


	iqdbe02AESGainAESOut1AESOut1MuteL OBJECT-TYPE
		SYNTAX		INTEGER { disable(0), enable(1) }
		MAX-ACCESS		read-write
		STATUS			current
		DESCRIPTION
				"TYPE: - Checkbox
				 PAGE: - AES Ports- AES Gain
					AES Out 1 Mute L  cmdID= 38280 "
		::= { iqdbe02CmdEntry 38280 }


	iqdbe02AESGainAESOut1AESOut1MuteR OBJECT-TYPE
		SYNTAX		INTEGER { disable(0), enable(1) }
		MAX-ACCESS		read-write
		STATUS			current
		DESCRIPTION
				"TYPE: - Checkbox
				 PAGE: - AES Ports- AES Gain
					AES Out 1 Mute R  cmdID= 38281 "
		::= { iqdbe02CmdEntry 38281 }


	iqdbe02AESGainAESOut1AESOut1LGain OBJECT-TYPE
		SYNTAX		INTEGER
		MAX-ACCESS		read-write
		STATUS			current
		DESCRIPTION
				"TYPE: - Number
				 PAGE: - AES Ports- AES Gain
					AES Out 1 L Gain  cmdID= 38240  min= -661  max= 120  step= 1  format= %0.1f dB  div_scale= 10
					Min = -66.1 dB  Max = 12.0 dB  Step = 0.1 dB "
		::= { iqdbe02CmdEntry 38240 }


	iqdbe02AESGainAESOut1AESOut1RGain OBJECT-TYPE
		SYNTAX		INTEGER
		MAX-ACCESS		read-write
		STATUS			current
		DESCRIPTION
				"TYPE: - Number
				 PAGE: - AES Ports- AES Gain
					AES Out 1 R Gain  cmdID= 38241  min= -661  max= 120  step= 1  format= %0.1f dB  div_scale= 10
					Min = -66.1 dB  Max = 12.0 dB  Step = 0.1 dB "
		::= { iqdbe02CmdEntry 38241 }


	iqdbe02AESGainAESOut1Stereo OBJECT-TYPE
		SYNTAX		INTEGER { disable(0), enable(1) }
		MAX-ACCESS		read-write
		STATUS			current
		DESCRIPTION
				"TYPE: - Checkbox
				 PAGE: - AES Ports- AES Gain
					Stereo  cmdID= 38360 "
		::= { iqdbe02CmdEntry 38360 }


	iqdbe02AESGainAESOut1AESOut1InvertL OBJECT-TYPE
		SYNTAX		INTEGER { disable(0), enable(1) }
		MAX-ACCESS		read-write
		STATUS			current
		DESCRIPTION
				"TYPE: - Checkbox
				 PAGE: - AES Ports- AES Gain
					AES Out 1 Invert L  cmdID= 38320 "
		::= { iqdbe02CmdEntry 38320 }


	iqdbe02AESGainAESOut1AESOut1InvertR OBJECT-TYPE
		SYNTAX		INTEGER { disable(0), enable(1) }
		MAX-ACCESS		read-write
		STATUS			current
		DESCRIPTION
				"TYPE: - Checkbox
				 PAGE: - AES Ports- AES Gain
					AES Out 1 Invert R  cmdID= 38321 "
		::= { iqdbe02CmdEntry 38321 }


	iqdbe02AESGainAESOut1AESOut1LClip OBJECT-TYPE
		SYNTAX		RollCallString
		MAX-ACCESS		read-only
		STATUS			current
		DESCRIPTION
				"TYPE: - Display
				 PAGE: - AES Ports- AES Gain
					AES Out 1-L Clip  cmdID= 38520  format=   "
		::= { iqdbe02CmdEntry 38520 }


	iqdbe02AESGainAESOut1AESOut1RClip OBJECT-TYPE
		SYNTAX		RollCallString
		MAX-ACCESS		read-only
		STATUS			current
		DESCRIPTION
				"TYPE: - Display
				 PAGE: - AES Ports- AES Gain
					AES Out 1-R Clip  cmdID= 38521  format=   "
		::= { iqdbe02CmdEntry 38521 }


	iqdbe02AESGainAESOut2AESOut2MuteL OBJECT-TYPE
		SYNTAX		INTEGER { disable(0), enable(1) }
		MAX-ACCESS		read-write
		STATUS			current
		DESCRIPTION
				"TYPE: - Checkbox
				 PAGE: - AES Ports- AES Gain
					AES Out 2 Mute L  cmdID= 38282 "
		::= { iqdbe02CmdEntry 38282 }


	iqdbe02AESGainAESOut2AESOut2MuteR OBJECT-TYPE
		SYNTAX		INTEGER { disable(0), enable(1) }
		MAX-ACCESS		read-write
		STATUS			current
		DESCRIPTION
				"TYPE: - Checkbox
				 PAGE: - AES Ports- AES Gain
					AES Out 2 Mute R  cmdID= 38283 "
		::= { iqdbe02CmdEntry 38283 }


	iqdbe02AESGainAESOut2AESOut2LGain OBJECT-TYPE
		SYNTAX		INTEGER
		MAX-ACCESS		read-write
		STATUS			current
		DESCRIPTION
				"TYPE: - Number
				 PAGE: - AES Ports- AES Gain
					AES Out 2 L Gain  cmdID= 38242  min= -661  max= 120  step= 1  format= %0.1f dB  div_scale= 10
					Min = -66.1 dB  Max = 12.0 dB  Step = 0.1 dB "
		::= { iqdbe02CmdEntry 38242 }


	iqdbe02AESGainAESOut2AESOut2RGain OBJECT-TYPE
		SYNTAX		INTEGER
		MAX-ACCESS		read-write
		STATUS			current
		DESCRIPTION
				"TYPE: - Number
				 PAGE: - AES Ports- AES Gain
					AES Out 2 R Gain  cmdID= 38243  min= -661  max= 120  step= 1  format= %0.1f dB  div_scale= 10
					Min = -66.1 dB  Max = 12.0 dB  Step = 0.1 dB "
		::= { iqdbe02CmdEntry 38243 }


	iqdbe02AESGainAESOut2Stereo OBJECT-TYPE
		SYNTAX		INTEGER { disable(0), enable(1) }
		MAX-ACCESS		read-write
		STATUS			current
		DESCRIPTION
				"TYPE: - Checkbox
				 PAGE: - AES Ports- AES Gain
					Stereo  cmdID= 38361 "
		::= { iqdbe02CmdEntry 38361 }


	iqdbe02AESGainAESOut2AESOut2InvertL OBJECT-TYPE
		SYNTAX		INTEGER { disable(0), enable(1) }
		MAX-ACCESS		read-write
		STATUS			current
		DESCRIPTION
				"TYPE: - Checkbox
				 PAGE: - AES Ports- AES Gain
					AES Out 2 Invert L  cmdID= 38322 "
		::= { iqdbe02CmdEntry 38322 }


	iqdbe02AESGainAESOut2AESOut2InvertR OBJECT-TYPE
		SYNTAX		INTEGER { disable(0), enable(1) }
		MAX-ACCESS		read-write
		STATUS			current
		DESCRIPTION
				"TYPE: - Checkbox
				 PAGE: - AES Ports- AES Gain
					AES Out 2 Invert R  cmdID= 38323 "
		::= { iqdbe02CmdEntry 38323 }


	iqdbe02AESGainAESOut2AESOut2LClip OBJECT-TYPE
		SYNTAX		RollCallString
		MAX-ACCESS		read-only
		STATUS			current
		DESCRIPTION
				"TYPE: - Display
				 PAGE: - AES Ports- AES Gain
					AES Out 2-L Clip  cmdID= 38522  format=   "
		::= { iqdbe02CmdEntry 38522 }


	iqdbe02AESGainAESOut2AESOut2RClip OBJECT-TYPE
		SYNTAX		RollCallString
		MAX-ACCESS		read-only
		STATUS			current
		DESCRIPTION
				"TYPE: - Display
				 PAGE: - AES Ports- AES Gain
					AES Out 2-R Clip  cmdID= 38523  format=   "
		::= { iqdbe02CmdEntry 38523 }


	iqdbe02AESGainAESOut3AESOut3MuteL OBJECT-TYPE
		SYNTAX		INTEGER { disable(0), enable(1) }
		MAX-ACCESS		read-write
		STATUS			current
		DESCRIPTION
				"TYPE: - Checkbox
				 PAGE: - AES Ports- AES Gain
					AES Out 3 Mute L  cmdID= 38284 "
		::= { iqdbe02CmdEntry 38284 }


	iqdbe02AESGainAESOut3AESOut3MuteR OBJECT-TYPE
		SYNTAX		INTEGER { disable(0), enable(1) }
		MAX-ACCESS		read-write
		STATUS			current
		DESCRIPTION
				"TYPE: - Checkbox
				 PAGE: - AES Ports- AES Gain
					AES Out 3 Mute R  cmdID= 38285 "
		::= { iqdbe02CmdEntry 38285 }


	iqdbe02AESGainAESOut3AESOut3LGain OBJECT-TYPE
		SYNTAX		INTEGER
		MAX-ACCESS		read-write
		STATUS			current
		DESCRIPTION
				"TYPE: - Number
				 PAGE: - AES Ports- AES Gain
					AES Out 3 L Gain  cmdID= 38244  min= -661  max= 120  step= 1  format= %0.1f dB  div_scale= 10
					Min = -66.1 dB  Max = 12.0 dB  Step = 0.1 dB "
		::= { iqdbe02CmdEntry 38244 }


	iqdbe02AESGainAESOut3AESOut3RGain OBJECT-TYPE
		SYNTAX		INTEGER
		MAX-ACCESS		read-write
		STATUS			current
		DESCRIPTION
				"TYPE: - Number
				 PAGE: - AES Ports- AES Gain
					AES Out 3 R Gain  cmdID= 38245  min= -661  max= 120  step= 1  format= %0.1f dB  div_scale= 10
					Min = -66.1 dB  Max = 12.0 dB  Step = 0.1 dB "
		::= { iqdbe02CmdEntry 38245 }


	iqdbe02AESGainAESOut3Stereo OBJECT-TYPE
		SYNTAX		INTEGER { disable(0), enable(1) }
		MAX-ACCESS		read-write
		STATUS			current
		DESCRIPTION
				"TYPE: - Checkbox
				 PAGE: - AES Ports- AES Gain
					Stereo  cmdID= 38362 "
		::= { iqdbe02CmdEntry 38362 }


	iqdbe02AESGainAESOut3AESOut3InvertL OBJECT-TYPE
		SYNTAX		INTEGER { disable(0), enable(1) }
		MAX-ACCESS		read-write
		STATUS			current
		DESCRIPTION
				"TYPE: - Checkbox
				 PAGE: - AES Ports- AES Gain
					AES Out 3 Invert L  cmdID= 38324 "
		::= { iqdbe02CmdEntry 38324 }


	iqdbe02AESGainAESOut3AESOut3InvertR OBJECT-TYPE
		SYNTAX		INTEGER { disable(0), enable(1) }
		MAX-ACCESS		read-write
		STATUS			current
		DESCRIPTION
				"TYPE: - Checkbox
				 PAGE: - AES Ports- AES Gain
					AES Out 3 Invert R  cmdID= 38325 "
		::= { iqdbe02CmdEntry 38325 }


	iqdbe02AESGainAESOut3AESOut3LClip OBJECT-TYPE
		SYNTAX		RollCallString
		MAX-ACCESS		read-only
		STATUS			current
		DESCRIPTION
				"TYPE: - Display
				 PAGE: - AES Ports- AES Gain
					AES Out 3-L Clip  cmdID= 38524  format=   "
		::= { iqdbe02CmdEntry 38524 }


	iqdbe02AESGainAESOut3AESOut3RClip OBJECT-TYPE
		SYNTAX		RollCallString
		MAX-ACCESS		read-only
		STATUS			current
		DESCRIPTION
				"TYPE: - Display
				 PAGE: - AES Ports- AES Gain
					AES Out 3-R Clip  cmdID= 38525  format=   "
		::= { iqdbe02CmdEntry 38525 }


	iqdbe02AESGainAESOut4AESOut4MuteL OBJECT-TYPE
		SYNTAX		INTEGER { disable(0), enable(1) }
		MAX-ACCESS		read-write
		STATUS			current
		DESCRIPTION
				"TYPE: - Checkbox
				 PAGE: - AES Ports- AES Gain
					AES Out 4 Mute L  cmdID= 38286 "
		::= { iqdbe02CmdEntry 38286 }


	iqdbe02AESGainAESOut4AESOut4MuteR OBJECT-TYPE
		SYNTAX		INTEGER { disable(0), enable(1) }
		MAX-ACCESS		read-write
		STATUS			current
		DESCRIPTION
				"TYPE: - Checkbox
				 PAGE: - AES Ports- AES Gain
					AES Out 4 Mute R  cmdID= 38287 "
		::= { iqdbe02CmdEntry 38287 }


	iqdbe02AESGainAESOut4AESOut4LGain OBJECT-TYPE
		SYNTAX		INTEGER
		MAX-ACCESS		read-write
		STATUS			current
		DESCRIPTION
				"TYPE: - Number
				 PAGE: - AES Ports- AES Gain
					AES Out 4 L Gain  cmdID= 38246  min= -661  max= 120  step= 1  format= %0.1f dB  div_scale= 10
					Min = -66.1 dB  Max = 12.0 dB  Step = 0.1 dB "
		::= { iqdbe02CmdEntry 38246 }


	iqdbe02AESGainAESOut4AESOut4RGain OBJECT-TYPE
		SYNTAX		INTEGER
		MAX-ACCESS		read-write
		STATUS			current
		DESCRIPTION
				"TYPE: - Number
				 PAGE: - AES Ports- AES Gain
					AES Out 4 R Gain  cmdID= 38247  min= -661  max= 120  step= 1  format= %0.1f dB  div_scale= 10
					Min = -66.1 dB  Max = 12.0 dB  Step = 0.1 dB "
		::= { iqdbe02CmdEntry 38247 }


	iqdbe02AESGainAESOut4Stereo OBJECT-TYPE
		SYNTAX		INTEGER { disable(0), enable(1) }
		MAX-ACCESS		read-write
		STATUS			current
		DESCRIPTION
				"TYPE: - Checkbox
				 PAGE: - AES Ports- AES Gain
					Stereo  cmdID= 38363 "
		::= { iqdbe02CmdEntry 38363 }


	iqdbe02AESGainAESOut4AESOut4InvertL OBJECT-TYPE
		SYNTAX		INTEGER { disable(0), enable(1) }
		MAX-ACCESS		read-write
		STATUS			current
		DESCRIPTION
				"TYPE: - Checkbox
				 PAGE: - AES Ports- AES Gain
					AES Out 4 Invert L  cmdID= 38326 "
		::= { iqdbe02CmdEntry 38326 }


	iqdbe02AESGainAESOut4AESOut4InvertR OBJECT-TYPE
		SYNTAX		INTEGER { disable(0), enable(1) }
		MAX-ACCESS		read-write
		STATUS			current
		DESCRIPTION
				"TYPE: - Checkbox
				 PAGE: - AES Ports- AES Gain
					AES Out 4 Invert R  cmdID= 38327 "
		::= { iqdbe02CmdEntry 38327 }


	iqdbe02AESGainAESOut4AESOut4LClip OBJECT-TYPE
		SYNTAX		RollCallString
		MAX-ACCESS		read-only
		STATUS			current
		DESCRIPTION
				"TYPE: - Display
				 PAGE: - AES Ports- AES Gain
					AES Out 4-L Clip  cmdID= 38526  format=   "
		::= { iqdbe02CmdEntry 38526 }


	iqdbe02AESGainAESOut4AESOut4RClip OBJECT-TYPE
		SYNTAX		RollCallString
		MAX-ACCESS		read-only
		STATUS			current
		DESCRIPTION
				"TYPE: - Display
				 PAGE: - AES Ports- AES Gain
					AES Out 4-R Clip  cmdID= 38527  format=   "
		::= { iqdbe02CmdEntry 38527 }


	iqdbe02AESGainAESOut5AESOut5MuteL OBJECT-TYPE
		SYNTAX		INTEGER { disable(0), enable(1) }
		MAX-ACCESS		read-write
		STATUS			current
		DESCRIPTION
				"TYPE: - Checkbox
				 PAGE: - AES Ports- AES Gain
					AES Out 5 Mute L  cmdID= 38288 "
		::= { iqdbe02CmdEntry 38288 }


	iqdbe02AESGainAESOut5AESOut5MuteR OBJECT-TYPE
		SYNTAX		INTEGER { disable(0), enable(1) }
		MAX-ACCESS		read-write
		STATUS			current
		DESCRIPTION
				"TYPE: - Checkbox
				 PAGE: - AES Ports- AES Gain
					AES Out 5 Mute R  cmdID= 38289 "
		::= { iqdbe02CmdEntry 38289 }


	iqdbe02AESGainAESOut5AESOut5LGain OBJECT-TYPE
		SYNTAX		INTEGER
		MAX-ACCESS		read-write
		STATUS			current
		DESCRIPTION
				"TYPE: - Number
				 PAGE: - AES Ports- AES Gain
					AES Out 5 L Gain  cmdID= 38248  min= -661  max= 120  step= 1  format= %0.1f dB  div_scale= 10
					Min = -66.1 dB  Max = 12.0 dB  Step = 0.1 dB "
		::= { iqdbe02CmdEntry 38248 }


	iqdbe02AESGainAESOut5AESOut5RGain OBJECT-TYPE
		SYNTAX		INTEGER
		MAX-ACCESS		read-write
		STATUS			current
		DESCRIPTION
				"TYPE: - Number
				 PAGE: - AES Ports- AES Gain
					AES Out 5 R Gain  cmdID= 38249  min= -661  max= 120  step= 1  format= %0.1f dB  div_scale= 10
					Min = -66.1 dB  Max = 12.0 dB  Step = 0.1 dB "
		::= { iqdbe02CmdEntry 38249 }


	iqdbe02AESGainAESOut5Stereo OBJECT-TYPE
		SYNTAX		INTEGER { disable(0), enable(1) }
		MAX-ACCESS		read-write
		STATUS			current
		DESCRIPTION
				"TYPE: - Checkbox
				 PAGE: - AES Ports- AES Gain
					Stereo  cmdID= 38364 "
		::= { iqdbe02CmdEntry 38364 }


	iqdbe02AESGainAESOut5AESOut5InvertL OBJECT-TYPE
		SYNTAX		INTEGER { disable(0), enable(1) }
		MAX-ACCESS		read-write
		STATUS			current
		DESCRIPTION
				"TYPE: - Checkbox
				 PAGE: - AES Ports- AES Gain
					AES Out 5 Invert L  cmdID= 38328 "
		::= { iqdbe02CmdEntry 38328 }


	iqdbe02AESGainAESOut5AESOut5InvertR OBJECT-TYPE
		SYNTAX		INTEGER { disable(0), enable(1) }
		MAX-ACCESS		read-write
		STATUS			current
		DESCRIPTION
				"TYPE: - Checkbox
				 PAGE: - AES Ports- AES Gain
					AES Out 5 Invert R  cmdID= 38329 "
		::= { iqdbe02CmdEntry 38329 }


	iqdbe02AESGainAESOut5AESOut5LClip OBJECT-TYPE
		SYNTAX		RollCallString
		MAX-ACCESS		read-only
		STATUS			current
		DESCRIPTION
				"TYPE: - Display
				 PAGE: - AES Ports- AES Gain
					AES Out 5-L Clip  cmdID= 38528  format=   "
		::= { iqdbe02CmdEntry 38528 }


	iqdbe02AESGainAESOut5AESOut5RClip OBJECT-TYPE
		SYNTAX		RollCallString
		MAX-ACCESS		read-only
		STATUS			current
		DESCRIPTION
				"TYPE: - Display
				 PAGE: - AES Ports- AES Gain
					AES Out 5-R Clip  cmdID= 38529  format=   "
		::= { iqdbe02CmdEntry 38529 }


	iqdbe02AESGainAESOut6AESOut6MuteL OBJECT-TYPE
		SYNTAX		INTEGER { disable(0), enable(1) }
		MAX-ACCESS		read-write
		STATUS			current
		DESCRIPTION
				"TYPE: - Checkbox
				 PAGE: - AES Ports- AES Gain
					AES Out 6 Mute L  cmdID= 38290 "
		::= { iqdbe02CmdEntry 38290 }


	iqdbe02AESGainAESOut6AESOut6MuteR OBJECT-TYPE
		SYNTAX		INTEGER { disable(0), enable(1) }
		MAX-ACCESS		read-write
		STATUS			current
		DESCRIPTION
				"TYPE: - Checkbox
				 PAGE: - AES Ports- AES Gain
					AES Out 6 Mute R  cmdID= 38291 "
		::= { iqdbe02CmdEntry 38291 }


	iqdbe02AESGainAESOut6AESOut6LGain OBJECT-TYPE
		SYNTAX		INTEGER
		MAX-ACCESS		read-write
		STATUS			current
		DESCRIPTION
				"TYPE: - Number
				 PAGE: - AES Ports- AES Gain
					AES Out 6 L Gain  cmdID= 38250  min= -661  max= 120  step= 1  format= %0.1f dB  div_scale= 10
					Min = -66.1 dB  Max = 12.0 dB  Step = 0.1 dB "
		::= { iqdbe02CmdEntry 38250 }


	iqdbe02AESGainAESOut6AESOut6RGain OBJECT-TYPE
		SYNTAX		INTEGER
		MAX-ACCESS		read-write
		STATUS			current
		DESCRIPTION
				"TYPE: - Number
				 PAGE: - AES Ports- AES Gain
					AES Out 6 R Gain  cmdID= 38251  min= -661  max= 120  step= 1  format= %0.1f dB  div_scale= 10
					Min = -66.1 dB  Max = 12.0 dB  Step = 0.1 dB "
		::= { iqdbe02CmdEntry 38251 }


	iqdbe02AESGainAESOut6Stereo OBJECT-TYPE
		SYNTAX		INTEGER { disable(0), enable(1) }
		MAX-ACCESS		read-write
		STATUS			current
		DESCRIPTION
				"TYPE: - Checkbox
				 PAGE: - AES Ports- AES Gain
					Stereo  cmdID= 38365 "
		::= { iqdbe02CmdEntry 38365 }


	iqdbe02AESGainAESOut6AESOut6InvertL OBJECT-TYPE
		SYNTAX		INTEGER { disable(0), enable(1) }
		MAX-ACCESS		read-write
		STATUS			current
		DESCRIPTION
				"TYPE: - Checkbox
				 PAGE: - AES Ports- AES Gain
					AES Out 6 Invert L  cmdID= 38330 "
		::= { iqdbe02CmdEntry 38330 }


	iqdbe02AESGainAESOut6AESOut6InvertR OBJECT-TYPE
		SYNTAX		INTEGER { disable(0), enable(1) }
		MAX-ACCESS		read-write
		STATUS			current
		DESCRIPTION
				"TYPE: - Checkbox
				 PAGE: - AES Ports- AES Gain
					AES Out 6 Invert R  cmdID= 38331 "
		::= { iqdbe02CmdEntry 38331 }


	iqdbe02AESGainAESOut6AESOut6LClip OBJECT-TYPE
		SYNTAX		RollCallString
		MAX-ACCESS		read-only
		STATUS			current
		DESCRIPTION
				"TYPE: - Display
				 PAGE: - AES Ports- AES Gain
					AES Out 6-L Clip  cmdID= 38530  format=   "
		::= { iqdbe02CmdEntry 38530 }


	iqdbe02AESGainAESOut6AESOut6RClip OBJECT-TYPE
		SYNTAX		RollCallString
		MAX-ACCESS		read-only
		STATUS			current
		DESCRIPTION
				"TYPE: - Display
				 PAGE: - AES Ports- AES Gain
					AES Out 6-R Clip  cmdID= 38531  format=   "
		::= { iqdbe02CmdEntry 38531 }


	iqdbe02AESGainAESOut7AESOut7MuteL OBJECT-TYPE
		SYNTAX		INTEGER { disable(0), enable(1) }
		MAX-ACCESS		read-write
		STATUS			current
		DESCRIPTION
				"TYPE: - Checkbox
				 PAGE: - AES Ports- AES Gain
					AES Out 7 Mute L  cmdID= 38292 "
		::= { iqdbe02CmdEntry 38292 }


	iqdbe02AESGainAESOut7AESOut7MuteR OBJECT-TYPE
		SYNTAX		INTEGER { disable(0), enable(1) }
		MAX-ACCESS		read-write
		STATUS			current
		DESCRIPTION
				"TYPE: - Checkbox
				 PAGE: - AES Ports- AES Gain
					AES Out 7 Mute R  cmdID= 38293 "
		::= { iqdbe02CmdEntry 38293 }


	iqdbe02AESGainAESOut7AESOut7LGain OBJECT-TYPE
		SYNTAX		INTEGER
		MAX-ACCESS		read-write
		STATUS			current
		DESCRIPTION
				"TYPE: - Number
				 PAGE: - AES Ports- AES Gain
					AES Out 7 L Gain  cmdID= 38252  min= -661  max= 120  step= 1  format= %0.1f dB  div_scale= 10
					Min = -66.1 dB  Max = 12.0 dB  Step = 0.1 dB "
		::= { iqdbe02CmdEntry 38252 }


	iqdbe02AESGainAESOut7AESOut7RGain OBJECT-TYPE
		SYNTAX		INTEGER
		MAX-ACCESS		read-write
		STATUS			current
		DESCRIPTION
				"TYPE: - Number
				 PAGE: - AES Ports- AES Gain
					AES Out 7 R Gain  cmdID= 38253  min= -661  max= 120  step= 1  format= %0.1f dB  div_scale= 10
					Min = -66.1 dB  Max = 12.0 dB  Step = 0.1 dB "
		::= { iqdbe02CmdEntry 38253 }


	iqdbe02AESGainAESOut7Stereo OBJECT-TYPE
		SYNTAX		INTEGER { disable(0), enable(1) }
		MAX-ACCESS		read-write
		STATUS			current
		DESCRIPTION
				"TYPE: - Checkbox
				 PAGE: - AES Ports- AES Gain
					Stereo  cmdID= 38366 "
		::= { iqdbe02CmdEntry 38366 }


	iqdbe02AESGainAESOut7AESOut7InvertL OBJECT-TYPE
		SYNTAX		INTEGER { disable(0), enable(1) }
		MAX-ACCESS		read-write
		STATUS			current
		DESCRIPTION
				"TYPE: - Checkbox
				 PAGE: - AES Ports- AES Gain
					AES Out 7 Invert L  cmdID= 38332 "
		::= { iqdbe02CmdEntry 38332 }


	iqdbe02AESGainAESOut7AESOut7InvertR OBJECT-TYPE
		SYNTAX		INTEGER { disable(0), enable(1) }
		MAX-ACCESS		read-write
		STATUS			current
		DESCRIPTION
				"TYPE: - Checkbox
				 PAGE: - AES Ports- AES Gain
					AES Out 7 Invert R  cmdID= 38333 "
		::= { iqdbe02CmdEntry 38333 }


	iqdbe02AESGainAESOut7AESOut7LClip OBJECT-TYPE
		SYNTAX		RollCallString
		MAX-ACCESS		read-only
		STATUS			current
		DESCRIPTION
				"TYPE: - Display
				 PAGE: - AES Ports- AES Gain
					AES Out 7-L Clip  cmdID= 38532  format=   "
		::= { iqdbe02CmdEntry 38532 }


	iqdbe02AESGainAESOut7AESOut7RClip OBJECT-TYPE
		SYNTAX		RollCallString
		MAX-ACCESS		read-only
		STATUS			current
		DESCRIPTION
				"TYPE: - Display
				 PAGE: - AES Ports- AES Gain
					AES Out 7-R Clip  cmdID= 38533  format=   "
		::= { iqdbe02CmdEntry 38533 }


	iqdbe02AESGainAESOut8AESOut8MuteL OBJECT-TYPE
		SYNTAX		INTEGER { disable(0), enable(1) }
		MAX-ACCESS		read-write
		STATUS			current
		DESCRIPTION
				"TYPE: - Checkbox
				 PAGE: - AES Ports- AES Gain
					AES Out 8 Mute L  cmdID= 38294 "
		::= { iqdbe02CmdEntry 38294 }


	iqdbe02AESGainAESOut8AESOut8MuteR OBJECT-TYPE
		SYNTAX		INTEGER { disable(0), enable(1) }
		MAX-ACCESS		read-write
		STATUS			current
		DESCRIPTION
				"TYPE: - Checkbox
				 PAGE: - AES Ports- AES Gain
					AES Out 8 Mute R  cmdID= 38295 "
		::= { iqdbe02CmdEntry 38295 }


	iqdbe02AESGainAESOut8AESOut8LGain OBJECT-TYPE
		SYNTAX		INTEGER
		MAX-ACCESS		read-write
		STATUS			current
		DESCRIPTION
				"TYPE: - Number
				 PAGE: - AES Ports- AES Gain
					AES Out 8 L Gain  cmdID= 38254  min= -661  max= 120  step= 1  format= %0.1f dB  div_scale= 10
					Min = -66.1 dB  Max = 12.0 dB  Step = 0.1 dB "
		::= { iqdbe02CmdEntry 38254 }


	iqdbe02AESGainAESOut8AESOut8RGain OBJECT-TYPE
		SYNTAX		INTEGER
		MAX-ACCESS		read-write
		STATUS			current
		DESCRIPTION
				"TYPE: - Number
				 PAGE: - AES Ports- AES Gain
					AES Out 8 R Gain  cmdID= 38255  min= -661  max= 120  step= 1  format= %0.1f dB  div_scale= 10
					Min = -66.1 dB  Max = 12.0 dB  Step = 0.1 dB "
		::= { iqdbe02CmdEntry 38255 }


	iqdbe02AESGainAESOut8Stereo OBJECT-TYPE
		SYNTAX		INTEGER { disable(0), enable(1) }
		MAX-ACCESS		read-write
		STATUS			current
		DESCRIPTION
				"TYPE: - Checkbox
				 PAGE: - AES Ports- AES Gain
					Stereo  cmdID= 38367 "
		::= { iqdbe02CmdEntry 38367 }


	iqdbe02AESGainAESOut8AESOut8InvertL OBJECT-TYPE
		SYNTAX		INTEGER { disable(0), enable(1) }
		MAX-ACCESS		read-write
		STATUS			current
		DESCRIPTION
				"TYPE: - Checkbox
				 PAGE: - AES Ports- AES Gain
					AES Out 8 Invert L  cmdID= 38334 "
		::= { iqdbe02CmdEntry 38334 }


	iqdbe02AESGainAESOut8AESOut8InvertR OBJECT-TYPE
		SYNTAX		INTEGER { disable(0), enable(1) }
		MAX-ACCESS		read-write
		STATUS			current
		DESCRIPTION
				"TYPE: - Checkbox
				 PAGE: - AES Ports- AES Gain
					AES Out 8 Invert R  cmdID= 38335 "
		::= { iqdbe02CmdEntry 38335 }


	iqdbe02AESGainAESOut8AESOut8LClip OBJECT-TYPE
		SYNTAX		RollCallString
		MAX-ACCESS		read-only
		STATUS			current
		DESCRIPTION
				"TYPE: - Display
				 PAGE: - AES Ports- AES Gain
					AES Out 8-L Clip  cmdID= 38534  format=   "
		::= { iqdbe02CmdEntry 38534 }


	iqdbe02AESGainAESOut8AESOut8RClip OBJECT-TYPE
		SYNTAX		RollCallString
		MAX-ACCESS		read-only
		STATUS			current
		DESCRIPTION
				"TYPE: - Display
				 PAGE: - AES Ports- AES Gain
					AES Out 8-R Clip  cmdID= 38535  format=   "
		::= { iqdbe02CmdEntry 38535 }


	iqdbe02AESOutAESOut1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 1
					Left  cmdID= 38200
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38200 }


	iqdbe02AESOutAESOut1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 1
					Right  cmdID= 38201
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38201 }


	iqdbe02AESOutAESOut1LinkLRSelection OBJECT-TYPE
		SYNTAX		INTEGER { disable(0), enable(1) }
		MAX-ACCESS		read-write
		STATUS			current
		DESCRIPTION
				"TYPE: - Checkbox
				 PAGE: - AES Ports- AES Out 1
					Link L+R Selection  cmdID= 38380 "
		::= { iqdbe02CmdEntry 38380 }


	iqdbe02AESOutAESOut2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 2
					Left  cmdID= 38202
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38202 }


	iqdbe02AESOutAESOut2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 2
					Right  cmdID= 38203
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38203 }


	iqdbe02AESOutAESOut2LinkLRSelection OBJECT-TYPE
		SYNTAX		INTEGER { disable(0), enable(1) }
		MAX-ACCESS		read-write
		STATUS			current
		DESCRIPTION
				"TYPE: - Checkbox
				 PAGE: - AES Ports- AES Out 2
					Link L+R Selection  cmdID= 38381 "
		::= { iqdbe02CmdEntry 38381 }


	iqdbe02AESOutAESOut3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 3
					Left  cmdID= 38204
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38204 }


	iqdbe02AESOutAESOut3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 3
					Right  cmdID= 38205
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38205 }


	iqdbe02AESOutAESOut3LinkLRSelection OBJECT-TYPE
		SYNTAX		INTEGER { disable(0), enable(1) }
		MAX-ACCESS		read-write
		STATUS			current
		DESCRIPTION
				"TYPE: - Checkbox
				 PAGE: - AES Ports- AES Out 3
					Link L+R Selection  cmdID= 38382 "
		::= { iqdbe02CmdEntry 38382 }


	iqdbe02AESOutAESOut4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 4
					Left  cmdID= 38206
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38206 }


	iqdbe02AESOutAESOut4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 4
					Right  cmdID= 38207
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38207 }


	iqdbe02AESOutAESOut4LinkLRSelection OBJECT-TYPE
		SYNTAX		INTEGER { disable(0), enable(1) }
		MAX-ACCESS		read-write
		STATUS			current
		DESCRIPTION
				"TYPE: - Checkbox
				 PAGE: - AES Ports- AES Out 4
					Link L+R Selection  cmdID= 38383 "
		::= { iqdbe02CmdEntry 38383 }


	iqdbe02AESOutAESOut5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 5
					Left  cmdID= 38208
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38208 }


	iqdbe02AESOutAESOut5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 5
					Right  cmdID= 38209
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38209 }


	iqdbe02AESOutAESOut5LinkLRSelection OBJECT-TYPE
		SYNTAX		INTEGER { disable(0), enable(1) }
		MAX-ACCESS		read-write
		STATUS			current
		DESCRIPTION
				"TYPE: - Checkbox
				 PAGE: - AES Ports- AES Out 5
					Link L+R Selection  cmdID= 38384 "
		::= { iqdbe02CmdEntry 38384 }


	iqdbe02AESOutAESOut6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 6
					Left  cmdID= 38210
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38210 }


	iqdbe02AESOutAESOut6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 6
					Right  cmdID= 38211
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38211 }


	iqdbe02AESOutAESOut6LinkLRSelection OBJECT-TYPE
		SYNTAX		INTEGER { disable(0), enable(1) }
		MAX-ACCESS		read-write
		STATUS			current
		DESCRIPTION
				"TYPE: - Checkbox
				 PAGE: - AES Ports- AES Out 6
					Link L+R Selection  cmdID= 38385 "
		::= { iqdbe02CmdEntry 38385 }


	iqdbe02AESOutAESOut7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 7
					Left  cmdID= 38212
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38212 }


	iqdbe02AESOutAESOut7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 7
					Right  cmdID= 38213
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38213 }


	iqdbe02AESOutAESOut7LinkLRSelection OBJECT-TYPE
		SYNTAX		INTEGER { disable(0), enable(1) }
		MAX-ACCESS		read-write
		STATUS			current
		DESCRIPTION
				"TYPE: - Checkbox
				 PAGE: - AES Ports- AES Out 7
					Link L+R Selection  cmdID= 38386 "
		::= { iqdbe02CmdEntry 38386 }


	iqdbe02AESOutAESOut8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 8
					Left  cmdID= 38214
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38214 }


	iqdbe02AESOutAESOut8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 8
					Right  cmdID= 38215
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38215 }


	iqdbe02AESOutAESOut8LinkLRSelection OBJECT-TYPE
		SYNTAX		INTEGER { disable(0), enable(1) }
		MAX-ACCESS		read-write
		STATUS			current
		DESCRIPTION
				"TYPE: - Checkbox
				 PAGE: - AES Ports- AES Out 8
					Link L+R Selection  cmdID= 38387 "
		::= { iqdbe02CmdEntry 38387 }


	iqdbe02AESOutMonitoropLeft OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- Monitor o/p
					Left  cmdID= 38641
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38641 }


	iqdbe02AESOutMonitoropRight OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- Monitor o/p
					Right  cmdID= 38642
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38642 }


	iqdbe02AESOutMonitoropLinkLRSelection OBJECT-TYPE
		SYNTAX		INTEGER { disable(0), enable(1) }
		MAX-ACCESS		read-write
		STATUS			current
		DESCRIPTION
				"TYPE: - Checkbox
				 PAGE: - AES Ports- Monitor o/p
					Link L+R Selection  cmdID= 38640 "
		::= { iqdbe02CmdEntry 38640 }


	iqdbe02AESOutAESPortNamesAESPort1Stereo OBJECT-TYPE
		SYNTAX		INTEGER { disable(0), enable(1) }
		MAX-ACCESS		read-write
		STATUS			current
		DESCRIPTION
				"TYPE: - Checkbox
				 PAGE: - AES Ports- AES Port Names
					AES Port 1 Stereo  cmdID= 38448 "
		::= { iqdbe02CmdEntry 38448 }


	iqdbe02AESOutAESPortNamesAESPort1L OBJECT-TYPE
		SYNTAX		RollCallString
		MAX-ACCESS		read-write
		STATUS			current
		DESCRIPTION
				"TYPE: - Editstring
				 PAGE: - AES Ports- AES Port Names
					AES Port 1-L  cmdID= 38496  "
		::= { iqdbe02CmdEntry 38496 }


	iqdbe02AESOutAESPortNamesAESPort1R OBJECT-TYPE
		SYNTAX		RollCallString
		MAX-ACCESS		read-write
		STATUS			current
		DESCRIPTION
				"TYPE: - Editstring
				 PAGE: - AES Ports- AES Port Names
					AES Port 1-R  cmdID= 38497  "
		::= { iqdbe02CmdEntry 38497 }


	iqdbe02AESOutAESPortNamesAESPort2Stereo OBJECT-TYPE
		SYNTAX		INTEGER { disable(0), enable(1) }
		MAX-ACCESS		read-write
		STATUS			current
		DESCRIPTION
				"TYPE: - Checkbox
				 PAGE: - AES Ports- AES Port Names
					AES Port 2 Stereo  cmdID= 38449 "
		::= { iqdbe02CmdEntry 38449 }


	iqdbe02AESOutAESPortNamesAESPort2L OBJECT-TYPE
		SYNTAX		RollCallString
		MAX-ACCESS		read-write
		STATUS			current
		DESCRIPTION
				"TYPE: - Editstring
				 PAGE: - AES Ports- AES Port Names
					AES Port 2-L  cmdID= 38498  "
		::= { iqdbe02CmdEntry 38498 }


	iqdbe02AESOutAESPortNamesAESPort2R OBJECT-TYPE
		SYNTAX		RollCallString
		MAX-ACCESS		read-write
		STATUS			current
		DESCRIPTION
				"TYPE: - Editstring
				 PAGE: - AES Ports- AES Port Names
					AES Port 2-R  cmdID= 38499  "
		::= { iqdbe02CmdEntry 38499 }


	iqdbe02AESOutAESPortNamesAESPort3Stereo OBJECT-TYPE
		SYNTAX		INTEGER { disable(0), enable(1) }
		MAX-ACCESS		read-write
		STATUS			current
		DESCRIPTION
				"TYPE: - Checkbox
				 PAGE: - AES Ports- AES Port Names
					AES Port 3 Stereo  cmdID= 38450 "
		::= { iqdbe02CmdEntry 38450 }


	iqdbe02AESOutAESPortNamesAESPort3L OBJECT-TYPE
		SYNTAX		RollCallString
		MAX-ACCESS		read-write
		STATUS			current
		DESCRIPTION
				"TYPE: - Editstring
				 PAGE: - AES Ports- AES Port Names
					AES Port 3-L  cmdID= 38500  "
		::= { iqdbe02CmdEntry 38500 }


	iqdbe02AESOutAESPortNamesAESPort3R OBJECT-TYPE
		SYNTAX		RollCallString
		MAX-ACCESS		read-write
		STATUS			current
		DESCRIPTION
				"TYPE: - Editstring
				 PAGE: - AES Ports- AES Port Names
					AES Port 3-R  cmdID= 38501  "
		::= { iqdbe02CmdEntry 38501 }


	iqdbe02AESOutAESPortNamesAESPort4Stereo OBJECT-TYPE
		SYNTAX		INTEGER { disable(0), enable(1) }
		MAX-ACCESS		read-write
		STATUS			current
		DESCRIPTION
				"TYPE: - Checkbox
				 PAGE: - AES Ports- AES Port Names
					AES Port 4 Stereo  cmdID= 38451 "
		::= { iqdbe02CmdEntry 38451 }


	iqdbe02AESOutAESPortNamesAESPort4L OBJECT-TYPE
		SYNTAX		RollCallString
		MAX-ACCESS		read-write
		STATUS			current
		DESCRIPTION
				"TYPE: - Editstring
				 PAGE: - AES Ports- AES Port Names
					AES Port 4-L  cmdID= 38502  "
		::= { iqdbe02CmdEntry 38502 }


	iqdbe02AESOutAESPortNamesAESPort4R OBJECT-TYPE
		SYNTAX		RollCallString
		MAX-ACCESS		read-write
		STATUS			current
		DESCRIPTION
				"TYPE: - Editstring
				 PAGE: - AES Ports- AES Port Names
					AES Port 4-R  cmdID= 38503  "
		::= { iqdbe02CmdEntry 38503 }


	iqdbe02AESOutAESPortNamesAESPort5Stereo OBJECT-TYPE
		SYNTAX		INTEGER { disable(0), enable(1) }
		MAX-ACCESS		read-write
		STATUS			current
		DESCRIPTION
				"TYPE: - Checkbox
				 PAGE: - AES Ports- AES Port Names
					AES Port 5 Stereo  cmdID= 38452 "
		::= { iqdbe02CmdEntry 38452 }


	iqdbe02AESOutAESPortNamesAESPort5L OBJECT-TYPE
		SYNTAX		RollCallString
		MAX-ACCESS		read-write
		STATUS			current
		DESCRIPTION
				"TYPE: - Editstring
				 PAGE: - AES Ports- AES Port Names
					AES Port 5-L  cmdID= 38504  "
		::= { iqdbe02CmdEntry 38504 }


	iqdbe02AESOutAESPortNamesAESPort5R OBJECT-TYPE
		SYNTAX		RollCallString
		MAX-ACCESS		read-write
		STATUS			current
		DESCRIPTION
				"TYPE: - Editstring
				 PAGE: - AES Ports- AES Port Names
					AES Port 5-R  cmdID= 38505  "
		::= { iqdbe02CmdEntry 38505 }


	iqdbe02AESOutAESPortNamesAESPort6Stereo OBJECT-TYPE
		SYNTAX		INTEGER { disable(0), enable(1) }
		MAX-ACCESS		read-write
		STATUS			current
		DESCRIPTION
				"TYPE: - Checkbox
				 PAGE: - AES Ports- AES Port Names
					AES Port 6 Stereo  cmdID= 38453 "
		::= { iqdbe02CmdEntry 38453 }


	iqdbe02AESOutAESPortNamesAESPort6L OBJECT-TYPE
		SYNTAX		RollCallString
		MAX-ACCESS		read-write
		STATUS			current
		DESCRIPTION
				"TYPE: - Editstring
				 PAGE: - AES Ports- AES Port Names
					AES Port 6-L  cmdID= 38506  "
		::= { iqdbe02CmdEntry 38506 }


	iqdbe02AESOutAESPortNamesAESPort6R OBJECT-TYPE
		SYNTAX		RollCallString
		MAX-ACCESS		read-write
		STATUS			current
		DESCRIPTION
				"TYPE: - Editstring
				 PAGE: - AES Ports- AES Port Names
					AES Port 6-R  cmdID= 38507  "
		::= { iqdbe02CmdEntry 38507 }


	iqdbe02AESOutAESPortNamesAESPort7Stereo OBJECT-TYPE
		SYNTAX		INTEGER { disable(0), enable(1) }
		MAX-ACCESS		read-write
		STATUS			current
		DESCRIPTION
				"TYPE: - Checkbox
				 PAGE: - AES Ports- AES Port Names
					AES Port 7 Stereo  cmdID= 38454 "
		::= { iqdbe02CmdEntry 38454 }


	iqdbe02AESOutAESPortNamesAESPort7L OBJECT-TYPE
		SYNTAX		RollCallString
		MAX-ACCESS		read-write
		STATUS			current
		DESCRIPTION
				"TYPE: - Editstring
				 PAGE: - AES Ports- AES Port Names
					AES Port 7-L  cmdID= 38508  "
		::= { iqdbe02CmdEntry 38508 }


	iqdbe02AESOutAESPortNamesAESPort7R OBJECT-TYPE
		SYNTAX		RollCallString
		MAX-ACCESS		read-write
		STATUS			current
		DESCRIPTION
				"TYPE: - Editstring
				 PAGE: - AES Ports- AES Port Names
					AES Port 7-R  cmdID= 38509  "
		::= { iqdbe02CmdEntry 38509 }


	iqdbe02AESOutAESPortNamesAESPort8Stereo OBJECT-TYPE
		SYNTAX		INTEGER { disable(0), enable(1) }
		MAX-ACCESS		read-write
		STATUS			current
		DESCRIPTION
				"TYPE: - Checkbox
				 PAGE: - AES Ports- AES Port Names
					AES Port 8 Stereo  cmdID= 38455 "
		::= { iqdbe02CmdEntry 38455 }


	iqdbe02AESOutAESPortNamesAESPort8L OBJECT-TYPE
		SYNTAX		RollCallString
		MAX-ACCESS		read-write
		STATUS			current
		DESCRIPTION
				"TYPE: - Editstring
				 PAGE: - AES Ports- AES Port Names
					AES Port 8-L  cmdID= 38510  "
		::= { iqdbe02CmdEntry 38510 }


	iqdbe02AESOutAESPortNamesAESPort8R OBJECT-TYPE
		SYNTAX		RollCallString
		MAX-ACCESS		read-write
		STATUS			current
		DESCRIPTION
				"TYPE: - Editstring
				 PAGE: - AES Ports- AES Port Names
					AES Port 8-R  cmdID= 38511  "
		::= { iqdbe02CmdEntry 38511 }


	iqdbe02AESBusAESDataModeInput1 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 1  cmdID= 38400
					PCM  value= 0
					Data  value= 1
					Mixed  value= 2  "
		::= { iqdbe02CmdEntry 38400 }


	iqdbe02AESBusAESDataModeInput2 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 2  cmdID= 38401
					PCM  value= 0
					Data  value= 1
					Mixed  value= 2  "
		::= { iqdbe02CmdEntry 38401 }


	iqdbe02AESBusAESDataModeInput3 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 3  cmdID= 38402
					PCM  value= 0
					Data  value= 1
					Mixed  value= 2  "
		::= { iqdbe02CmdEntry 38402 }


	iqdbe02AESBusAESDataModeInput4 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 4  cmdID= 38403
					PCM  value= 0
					Data  value= 1
					Mixed  value= 2  "
		::= { iqdbe02CmdEntry 38403 }


	iqdbe02AESBusAESDataModeInput5 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 5  cmdID= 38404
					PCM  value= 0
					Data  value= 1
					Mixed  value= 2  "
		::= { iqdbe02CmdEntry 38404 }


	iqdbe02AESBusAESDataModeInput6 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 6  cmdID= 38405
					PCM  value= 0
					Data  value= 1
					Mixed  value= 2  "
		::= { iqdbe02CmdEntry 38405 }


	iqdbe02AESBusAESDataModeInput7 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 7  cmdID= 38406
					PCM  value= 0
					Data  value= 1
					Mixed  value= 2  "
		::= { iqdbe02CmdEntry 38406 }


	iqdbe02AESBusAESDataModeInput8 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 8  cmdID= 38407
					PCM  value= 0
					Data  value= 1
					Mixed  value= 2  "
		::= { iqdbe02CmdEntry 38407 }


	iqdbe02AESBusAESBusNamesAESBus1Stereo OBJECT-TYPE
		SYNTAX		INTEGER { disable(0), enable(1) }
		MAX-ACCESS		read-write
		STATUS			current
		DESCRIPTION
				"TYPE: - Checkbox
				 PAGE: - AES Ports- AES Bus
					AES Bus 1 Stereo  cmdID= 38440 "
		::= { iqdbe02CmdEntry 38440 }


	iqdbe02AESBusAESBusNamesAESBus1 OBJECT-TYPE
		SYNTAX		RollCallString
		MAX-ACCESS		read-write
		STATUS			current
		DESCRIPTION
				"TYPE: - Editstring
				 PAGE: - AES Ports- AES Bus
					AES Bus 1  cmdID= 38480  "
		::= { iqdbe02CmdEntry 38480 }


	iqdbe02AESBusAESBusNamesAESBus1R OBJECT-TYPE
		SYNTAX		RollCallString
		MAX-ACCESS		read-write
		STATUS			current
		DESCRIPTION
				"TYPE: - Editstring
				 PAGE: - AES Ports- AES Bus
					AES Bus 1-R  cmdID= 38481  "
		::= { iqdbe02CmdEntry 38481 }


	iqdbe02AESBusAESBusNamesAESBus2Stereo OBJECT-TYPE
		SYNTAX		INTEGER { disable(0), enable(1) }
		MAX-ACCESS		read-write
		STATUS			current
		DESCRIPTION
				"TYPE: - Checkbox
				 PAGE: - AES Ports- AES Bus
					AES Bus 2 Stereo  cmdID= 38441 "
		::= { iqdbe02CmdEntry 38441 }


	iqdbe02AESBusAESBusNamesAESBus2 OBJECT-TYPE
		SYNTAX		RollCallString
		MAX-ACCESS		read-write
		STATUS			current
		DESCRIPTION
				"TYPE: - Editstring
				 PAGE: - AES Ports- AES Bus
					AES Bus 2  cmdID= 38482  "
		::= { iqdbe02CmdEntry 38482 }


	iqdbe02AESBusAESBusNamesAESBus2R OBJECT-TYPE
		SYNTAX		RollCallString
		MAX-ACCESS		read-write
		STATUS			current
		DESCRIPTION
				"TYPE: - Editstring
				 PAGE: - AES Ports- AES Bus
					AES Bus 2-R  cmdID= 38483  "
		::= { iqdbe02CmdEntry 38483 }


	iqdbe02AESBusAESBusNamesAESBus3Stereo OBJECT-TYPE
		SYNTAX		INTEGER { disable(0), enable(1) }
		MAX-ACCESS		read-write
		STATUS			current
		DESCRIPTION
				"TYPE: - Checkbox
				 PAGE: - AES Ports- AES Bus
					AES Bus 3 Stereo  cmdID= 38442 "
		::= { iqdbe02CmdEntry 38442 }


	iqdbe02AESBusAESBusNamesAESBus3 OBJECT-TYPE
		SYNTAX		RollCallString
		MAX-ACCESS		read-write
		STATUS			current
		DESCRIPTION
				"TYPE: - Editstring
				 PAGE: - AES Ports- AES Bus
					AES Bus 3  cmdID= 38484  "
		::= { iqdbe02CmdEntry 38484 }


	iqdbe02AESBusAESBusNamesAESBus3R OBJECT-TYPE
		SYNTAX		RollCallString
		MAX-ACCESS		read-write
		STATUS			current
		DESCRIPTION
				"TYPE: - Editstring
				 PAGE: - AES Ports- AES Bus
					AES Bus 3-R  cmdID= 38485  "
		::= { iqdbe02CmdEntry 38485 }


	iqdbe02AESBusAESBusNamesAESBus4Stereo OBJECT-TYPE
		SYNTAX		INTEGER { disable(0), enable(1) }
		MAX-ACCESS		read-write
		STATUS			current
		DESCRIPTION
				"TYPE: - Checkbox
				 PAGE: - AES Ports- AES Bus
					AES Bus 4 Stereo  cmdID= 38443 "
		::= { iqdbe02CmdEntry 38443 }


	iqdbe02AESBusAESBusNamesAESBus4 OBJECT-TYPE
		SYNTAX		RollCallString
		MAX-ACCESS		read-write
		STATUS			current
		DESCRIPTION
				"TYPE: - Editstring
				 PAGE: - AES Ports- AES Bus
					AES Bus 4  cmdID= 38486  "
		::= { iqdbe02CmdEntry 38486 }


	iqdbe02AESBusAESBusNamesAESBus4R OBJECT-TYPE
		SYNTAX		RollCallString
		MAX-ACCESS		read-write
		STATUS			current
		DESCRIPTION
				"TYPE: - Editstring
				 PAGE: - AES Ports- AES Bus
					AES Bus 4-R  cmdID= 38487  "
		::= { iqdbe02CmdEntry 38487 }


	iqdbe02AESBusAESBusNamesAESBus5Stereo OBJECT-TYPE
		SYNTAX		INTEGER { disable(0), enable(1) }
		MAX-ACCESS		read-write
		STATUS			current
		DESCRIPTION
				"TYPE: - Checkbox
				 PAGE: - AES Ports- AES Bus
					AES Bus 5 Stereo  cmdID= 38444 "
		::= { iqdbe02CmdEntry 38444 }


	iqdbe02AESBusAESBusNamesAESBus5 OBJECT-TYPE
		SYNTAX		RollCallString
		MAX-ACCESS		read-write
		STATUS			current
		DESCRIPTION
				"TYPE: - Editstring
				 PAGE: - AES Ports- AES Bus
					AES Bus 5  cmdID= 38488  "
		::= { iqdbe02CmdEntry 38488 }


	iqdbe02AESBusAESBusNamesAESBus5R OBJECT-TYPE
		SYNTAX		RollCallString
		MAX-ACCESS		read-write
		STATUS			current
		DESCRIPTION
				"TYPE: - Editstring
				 PAGE: - AES Ports- AES Bus
					AES Bus 5-R  cmdID= 38489  "
		::= { iqdbe02CmdEntry 38489 }


	iqdbe02AESBusAESBusNamesAESBus6Stereo OBJECT-TYPE
		SYNTAX		INTEGER { disable(0), enable(1) }
		MAX-ACCESS		read-write
		STATUS			current
		DESCRIPTION
				"TYPE: - Checkbox
				 PAGE: - AES Ports- AES Bus
					AES Bus 6 Stereo  cmdID= 38445 "
		::= { iqdbe02CmdEntry 38445 }


	iqdbe02AESBusAESBusNamesAESBus6 OBJECT-TYPE
		SYNTAX		RollCallString
		MAX-ACCESS		read-write
		STATUS			current
		DESCRIPTION
				"TYPE: - Editstring
				 PAGE: - AES Ports- AES Bus
					AES Bus 6  cmdID= 38490  "
		::= { iqdbe02CmdEntry 38490 }


	iqdbe02AESBusAESBusNamesAESBus6R OBJECT-TYPE
		SYNTAX		RollCallString
		MAX-ACCESS		read-write
		STATUS			current
		DESCRIPTION
				"TYPE: - Editstring
				 PAGE: - AES Ports- AES Bus
					AES Bus 6-R  cmdID= 38491  "
		::= { iqdbe02CmdEntry 38491 }


	iqdbe02AESBusAESBusNamesAESBus7Stereo OBJECT-TYPE
		SYNTAX		INTEGER { disable(0), enable(1) }
		MAX-ACCESS		read-write
		STATUS			current
		DESCRIPTION
				"TYPE: - Checkbox
				 PAGE: - AES Ports- AES Bus
					AES Bus 7 Stereo  cmdID= 38446 "
		::= { iqdbe02CmdEntry 38446 }


	iqdbe02AESBusAESBusNamesAESBus7 OBJECT-TYPE
		SYNTAX		RollCallString
		MAX-ACCESS		read-write
		STATUS			current
		DESCRIPTION
				"TYPE: - Editstring
				 PAGE: - AES Ports- AES Bus
					AES Bus 7  cmdID= 38492  "
		::= { iqdbe02CmdEntry 38492 }


	iqdbe02AESBusAESBusNamesAESBus7R OBJECT-TYPE
		SYNTAX		RollCallString
		MAX-ACCESS		read-write
		STATUS			current
		DESCRIPTION
				"TYPE: - Editstring
				 PAGE: - AES Ports- AES Bus
					AES Bus 7-R  cmdID= 38493  "
		::= { iqdbe02CmdEntry 38493 }


	iqdbe02AESBusAESBusNamesAESBus8Stereo OBJECT-TYPE
		SYNTAX		INTEGER { disable(0), enable(1) }
		MAX-ACCESS		read-write
		STATUS			current
		DESCRIPTION
				"TYPE: - Checkbox
				 PAGE: - AES Ports- AES Bus
					AES Bus 8 Stereo  cmdID= 38447 "
		::= { iqdbe02CmdEntry 38447 }


	iqdbe02AESBusAESBusNamesAESBus8 OBJECT-TYPE
		SYNTAX		RollCallString
		MAX-ACCESS		read-write
		STATUS			current
		DESCRIPTION
				"TYPE: - Editstring
				 PAGE: - AES Ports- AES Bus
					AES Bus 8  cmdID= 38494  "
		::= { iqdbe02CmdEntry 38494 }


	iqdbe02AESBusAESBusNamesAESBus8R OBJECT-TYPE
		SYNTAX		RollCallString
		MAX-ACCESS		read-write
		STATUS			current
		DESCRIPTION
				"TYPE: - Editstring
				 PAGE: - AES Ports- AES Bus
					AES Bus 8-R  cmdID= 38495  "
		::= { iqdbe02CmdEntry 38495 }


	iqdbe02AESBusAESBusRoutingSource1 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 1  cmdID= 38560
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38560 }


	iqdbe02AESBusAESBusRoutingSource2 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 2  cmdID= 38561
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38561 }


	iqdbe02AESBusAESBusRoutingSource3 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 3  cmdID= 38562
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38562 }


	iqdbe02AESBusAESBusRoutingSource4 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 4  cmdID= 38563
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38563 }


	iqdbe02AESBusAESBusRoutingSource5 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 5  cmdID= 38564
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38564 }


	iqdbe02AESBusAESBusRoutingSource6 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 6  cmdID= 38565
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38565 }


	iqdbe02AESBusAESBusRoutingSource7 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 7  cmdID= 38566
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38566 }


	iqdbe02AESBusAESBusRoutingSource8 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 8  cmdID= 38567
					AES Port 1  value= 1
					AES Port 2  value= 2
					AES Port 3  value= 3
					AES Port 4  value= 4
					AES Port 5  value= 5
					AES Port 6  value= 6
					AES Port 7  value= 7
					AES Port 8  value= 8  "
		::= { iqdbe02CmdEntry 38567 }


	iqdbe02AESPortsAESDirectionAESPort1Dir OBJECT-TYPE
		SYNTAX		INTEGER {
							val_Input(0),
							val_Output(1)
							}
		MAX-ACCESS		read-write
		STATUS			current
		DESCRIPTION
				"TYPE: - RadiobuttonList
				 PAGE: - AES Ports
					AES Port 1 Dir  cmdID= 38420
					Input  value= 0
					Output  value= 1  "
		::= { iqdbe02CmdEntry 38420 }


	iqdbe02AESPortsAESDirectionAESPort2Dir OBJECT-TYPE
		SYNTAX		INTEGER {
							val_Input(0),
							val_Output(1)
							}
		MAX-ACCESS		read-write
		STATUS			current
		DESCRIPTION
				"TYPE: - RadiobuttonList
				 PAGE: - AES Ports
					AES Port 2 Dir  cmdID= 38421
					Input  value= 0
					Output  value= 1  "
		::= { iqdbe02CmdEntry 38421 }


	iqdbe02AESPortsAESDirectionAESPort3Dir OBJECT-TYPE
		SYNTAX		INTEGER {
							val_Input(0),
							val_Output(1)
							}
		MAX-ACCESS		read-write
		STATUS			current
		DESCRIPTION
				"TYPE: - RadiobuttonList
				 PAGE: - AES Ports
					AES Port 3 Dir  cmdID= 38422
					Input  value= 0
					Output  value= 1  "
		::= { iqdbe02CmdEntry 38422 }


	iqdbe02AESPortsAESDirectionAESPort4Dir OBJECT-TYPE
		SYNTAX		INTEGER {
							val_Input(0),
							val_Output(1)
							}
		MAX-ACCESS		read-write
		STATUS			current
		DESCRIPTION
				"TYPE: - RadiobuttonList
				 PAGE: - AES Ports
					AES Port 4 Dir  cmdID= 38423
					Input  value= 0
					Output  value= 1  "
		::= { iqdbe02CmdEntry 38423 }


	iqdbe02AESPortsAESDirectionAESPort5Dir OBJECT-TYPE
		SYNTAX		INTEGER {
							val_Input(0),
							val_Output(1)
							}
		MAX-ACCESS		read-write
		STATUS			current
		DESCRIPTION
				"TYPE: - RadiobuttonList
				 PAGE: - AES Ports
					AES Port 5 Dir  cmdID= 38424
					Input  value= 0
					Output  value= 1  "
		::= { iqdbe02CmdEntry 38424 }


	iqdbe02AESPortsAESDirectionAESPort6Dir OBJECT-TYPE
		SYNTAX		INTEGER {
							val_Input(0),
							val_Output(1)
							}
		MAX-ACCESS		read-write
		STATUS			current
		DESCRIPTION
				"TYPE: - RadiobuttonList
				 PAGE: - AES Ports
					AES Port 6 Dir  cmdID= 38425
					Input  value= 0
					Output  value= 1  "
		::= { iqdbe02CmdEntry 38425 }


	iqdbe02AESPortsAESDirectionAESPort7Dir OBJECT-TYPE
		SYNTAX		INTEGER {
							val_Input(0),
							val_Output(1)
							}
		MAX-ACCESS		read-write
		STATUS			current
		DESCRIPTION
				"TYPE: - RadiobuttonList
				 PAGE: - AES Ports
					AES Port 7 Dir  cmdID= 38426
					Input  value= 0
					Output  value= 1  "
		::= { iqdbe02CmdEntry 38426 }


	iqdbe02AESPortsAESDirectionAESPort8Dir OBJECT-TYPE
		SYNTAX		INTEGER {
							val_Input(0),
							val_Output(1)
							}
		MAX-ACCESS		read-write
		STATUS			current
		DESCRIPTION
				"TYPE: - RadiobuttonList
				 PAGE: - AES Ports
					AES Port 8 Dir  cmdID= 38427
					Input  value= 0
					Output  value= 1  "
		::= { iqdbe02CmdEntry 38427 }


	iqdbe02AudioDolbyETimingSelAudioPair OBJECT-TYPE
		SYNTAX		INTEGER
		MAX-ACCESS		read-write
		STATUS			current
		DESCRIPTION
				"TYPE: - Number
					Sel Audio Pair  cmdID= 38650  min= 1  max= 8  step= 1  format= %0.0f  div_scale= 1
					Min = 1  Max = 8  Step = 1 "
		::= { iqdbe02CmdEntry 38650 }


	iqdbe02AudioDolbyETimingRelativeTiming OBJECT-TYPE
		SYNTAX		RollCallString
		MAX-ACCESS		read-only
		STATUS			current
		DESCRIPTION
				"TYPE: - Display
					Relative Timing  cmdID= 38653  format=   "
		::= { iqdbe02CmdEntry 38653 }


	iqdbe02AudioDolbyETimingStatus OBJECT-TYPE
		SYNTAX		RollCallString
		MAX-ACCESS		read-only
		STATUS			current
		DESCRIPTION
				"TYPE: - Display
					Status  cmdID= 38652  format=   "
		::= { iqdbe02CmdEntry 38652 }


	iqdbe02AudioDolbyETimingError OBJECT-TYPE
		SYNTAX		RollCallString
		MAX-ACCESS		read-only
		STATUS			current
		DESCRIPTION
				"TYPE: - Display
					Error  cmdID= 38654  format=   "
		::= { iqdbe02CmdEntry 38654 }


	iqdbe02DolbyETimingDolbyELineStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Standard  cmdID= 38655
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe02CmdEntry 38655 }


	iqdbe02DolbyETimingDolbyELineAutoLineNo OBJECT-TYPE
		SYNTAX		INTEGER
		MAX-ACCESS		read-write
		STATUS			current
		DESCRIPTION
				"TYPE: - Number
					Auto Line No.  cmdID= 38656  min= 1  max= 10000  step= 1  format= %0.0f  div_scale= 1
					Min = 1  Max = 10000  Step = 1 "
		::= { iqdbe02CmdEntry 38656 }


	iqdbe02DolbyELineUserDolbyELinePair1 OBJECT-TYPE
		SYNTAX		INTEGER {
							val_User_Line(1),
							val_Standard_Line(0)
							}
		MAX-ACCESS		read-write
		STATUS			current
		DESCRIPTION
				"TYPE: - RadiobuttonList
					Pair 1  cmdID= 38670
					User Line  value= 1
					Standard Line  value= 0  "
		::= { iqdbe02CmdEntry 38670 }


	iqdbe02DolbyELineUserDolbyELinePair2 OBJECT-TYPE
		SYNTAX		INTEGER {
							val_User_Line(1),
							val_Standard_Line(0)
							}
		MAX-ACCESS		read-write
		STATUS			current
		DESCRIPTION
				"TYPE: - RadiobuttonList
					Pair 2  cmdID= 38671
					User Line  value= 1
					Standard Line  value= 0  "
		::= { iqdbe02CmdEntry 38671 }


	iqdbe02DolbyELineUserDolbyELinePair3 OBJECT-TYPE
		SYNTAX		INTEGER {
							val_User_Line(1),
							val_Standard_Line(0)
							}
		MAX-ACCESS		read-write
		STATUS			current
		DESCRIPTION
				"TYPE: - RadiobuttonList
					Pair 3  cmdID= 38672
					User Line  value= 1
					Standard Line  value= 0  "
		::= { iqdbe02CmdEntry 38672 }


	iqdbe02DolbyELineUserDolbyELinePair4 OBJECT-TYPE
		SYNTAX		INTEGER {
							val_User_Line(1),
							val_Standard_Line(0)
							}
		MAX-ACCESS		read-write
		STATUS			current
		DESCRIPTION
				"TYPE: - RadiobuttonList
					Pair 4  cmdID= 38673
					User Line  value= 1
					Standard Line  value= 0  "
		::= { iqdbe02CmdEntry 38673 }


	iqdbe02DolbyELineUserDolbyELinePair5 OBJECT-TYPE
		SYNTAX		INTEGER {
							val_User_Line(1),
							val_Standard_Line(0)
							}
		MAX-ACCESS		read-write
		STATUS			current
		DESCRIPTION
				"TYPE: - RadiobuttonList
					Pair 5  cmdID= 38674
					User Line  value= 1
					Standard Line  value= 0  "
		::= { iqdbe02CmdEntry 38674 }


	iqdbe02DolbyELineUserDolbyELinePair6 OBJECT-TYPE
		SYNTAX		INTEGER {
							val_User_Line(1),
							val_Standard_Line(0)
							}
		MAX-ACCESS		read-write
		STATUS			current
		DESCRIPTION
				"TYPE: - RadiobuttonList
					Pair 6  cmdID= 38675
					User Line  value= 1
					Standard Line  value= 0  "
		::= { iqdbe02CmdEntry 38675 }


	iqdbe02DolbyELineUserDolbyELinePair7 OBJECT-TYPE
		SYNTAX		INTEGER {
							val_User_Line(1),
							val_Standard_Line(0)
							}
		MAX-ACCESS		read-write
		STATUS			current
		DESCRIPTION
				"TYPE: - RadiobuttonList
					Pair 7  cmdID= 38676
					User Line  value= 1
					Standard Line  value= 0  "
		::= { iqdbe02CmdEntry 38676 }


	iqdbe02DolbyELineUserDolbyELinePair8 OBJECT-TYPE
		SYNTAX		INTEGER {
							val_User_Line(1),
							val_Standard_Line(0)
							}
		MAX-ACCESS		read-write
		STATUS			current
		DESCRIPTION
				"TYPE: - RadiobuttonList
					Pair 8  cmdID= 38677
					User Line  value= 1
					Standard Line  value= 0  "
		::= { iqdbe02CmdEntry 38677 }


	iqdbe02InputChanAssignDolbyAA1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Dolby A
					A1  cmdID= 38900
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38900 }


	iqdbe02InputChanAssignDolbyAA2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Dolby A
					A2  cmdID= 38901
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38901 }


	iqdbe02InputChanAssignDolbyALinkLR OBJECT-TYPE
		SYNTAX		INTEGER { disable(0), enable(1) }
		MAX-ACCESS		read-write
		STATUS			current
		DESCRIPTION
				"TYPE: - Checkbox
				 PAGE: - Dolby Encoder- Dolby A
					Link L+R  cmdID= 38910 "
		::= { iqdbe02CmdEntry 38910 }


	iqdbe02InputChanAssignDolbyBB3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Dolby B
					B3  cmdID= 38902
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38902 }


	iqdbe02InputChanAssignDolbyBB4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Dolby B
					B4  cmdID= 38903
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38903 }


	iqdbe02InputChanAssignDolbyBLinkLR OBJECT-TYPE
		SYNTAX		INTEGER { disable(0), enable(1) }
		MAX-ACCESS		read-write
		STATUS			current
		DESCRIPTION
				"TYPE: - Checkbox
				 PAGE: - Dolby Encoder- Dolby B
					Link L+R  cmdID= 38911 "
		::= { iqdbe02CmdEntry 38911 }


	iqdbe02InputChanAssignDolbyCC5 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Dolby C
					C5  cmdID= 38904
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38904 }


	iqdbe02InputChanAssignDolbyCC6 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Dolby C
					C6  cmdID= 38905
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe02CmdEntry 38905 }


	iqdbe02InputChanAssignDolbyCLinkLR OBJECT-TYPE
		SYNTAX		INTEGER { disable(0), enable(1) }
		MAX-ACCESS		read-write
		STATUS			current
		DESCRIPTION
				"TYPE: - Checkbox
				 PAGE: - Dolby Encoder- Dolby C
					Link L+R  cmdID= 38912 "
		::= { iqdbe02CmdEntry 38912 }


	iqdbe02AudioDolbyEncoderEncodingMode OBJECT-TYPE
		SYNTAX		INTEGER {
							val_Dolby_D_Encoding(0),
							val_Pass_through(1)
							}
		MAX-ACCESS		read-write
		STATUS			current
		DESCRIPTION
				"TYPE: - RadiobuttonList
				 PAGE: - Dolby Encoder
					Encoding Mode  cmdID= 38920
					Dolby D Encoding  value= 0
					Pass-through  value= 1  "
		::= { iqdbe02CmdEntry 38920 }


	iqdbe02AudioDolbyEncoderDataRate OBJECT-TYPE
		SYNTAX		INTEGER {
							val_Auto384(0),
							val_Auto448(1),
							val_56_kbps(2),
							val_64_kbps(3),
							val_80_kbps(4),
							val_96_kbps(5),
							val_112_kbps(6),
							val_128_kbps(7),
							val_160_kbps(8),
							val_192_kbps(9),
							val_224_kbps(10),
							val_256_kbps(11),
							val_320_kbps(12),
							val_384_kbps(13),
							val_448_kbps(14),
							val_512_kbps(15),
							val_576_kbps(16),
							val_640_kbps(17)
							}
		MAX-ACCESS		read-write
		STATUS			current
		DESCRIPTION
				"TYPE: - RadiobuttonList
				 PAGE: - Dolby Encoder
					Data Rate  cmdID= 38925
					Auto384  value= 0
					Auto448  value= 1
					56 kbps  value= 2
					64 kbps  value= 3
					80 kbps  value= 4
					96 kbps  value= 5
					112 kbps  value= 6
					128 kbps  value= 7
					160 kbps  value= 8
					192 kbps  value= 9
					224 kbps  value= 10
					256 kbps  value= 11
					320 kbps  value= 12
					384 kbps  value= 13
					448 kbps  value= 14
					512 kbps  value= 15
					576 kbps  value= 16
					640 kbps  value= 17  "
		::= { iqdbe02CmdEntry 38925 }


	iqdbe02AudioDolbyEncoderReversionMode OBJECT-TYPE
		SYNTAX		INTEGER {
							val_Last_Used_valid(0),
							val_Internal(1)
							}
		MAX-ACCESS		read-write
		STATUS			current
		DESCRIPTION
				"TYPE: - RadiobuttonList
				 PAGE: - Dolby Encoder
					Reversion Mode  cmdID= 38924
					Last Used (valid)  value= 0
					Internal  value= 1  "
		::= { iqdbe02CmdEntry 38924 }


	iqdbe02AudioDolbyEncoderEncoderLatency OBJECT-TYPE
		SYNTAX		INTEGER
		MAX-ACCESS		read-write
		STATUS			current
		DESCRIPTION
				"TYPE: - Number
				 PAGE: - Dolby Encoder
					Encoder Latency  cmdID= 38927  min= 150  max= 300  step= 1  format= %0.0f ms  div_scale= 1
					Min = 150 ms  Max = 300 ms  Step = 1 ms "
		::= { iqdbe02CmdEntry 38927 }


	iqdbe02DolbyEncoderMetadataSourceMetadataSource OBJECT-TYPE
		SYNTAX		INTEGER {
							val_Internal(8),
							val_External_Program_1(0),
							val_External_Program_2(1),
							val_External_Program_3(2),
							val_External_Program_4(3),
							val_External_Program_5(4),
							val_External_Program_6(5),
							val_External_Program_7(6),
							val_External_Program_8(7)
							}
		MAX-ACCESS		read-write
		STATUS			current
		DESCRIPTION
				"TYPE: - RadiobuttonList
				 PAGE: - Dolby Encoder
					Metadata Source  cmdID= 38923
					Internal  value= 8
					External Program 1  value= 0
					External Program 2  value= 1
					External Program 3  value= 2
					External Program 4  value= 3
					External Program 5  value= 4
					External Program 6  value= 5
					External Program 7  value= 6
					External Program 8  value= 7  "
		::= { iqdbe02CmdEntry 38923 }


	iqdbe02DolbyEncoderMetadataSourceExternalProgConf OBJECT-TYPE
		SYNTAX		RollCallString
		MAX-ACCESS		read-only
		STATUS			current
		DESCRIPTION
				"TYPE: - Display
				 PAGE: - Dolby Encoder
					External Prog Conf  cmdID= 39040  format=   "
		::= { iqdbe02CmdEntry 39040 }


	iqdbe02DolbyEncoderMetadataSourceExtProgNamept1 OBJECT-TYPE
		SYNTAX		RollCallString
		MAX-ACCESS		read-only
		STATUS			current
		DESCRIPTION
				"TYPE: - Display
				 PAGE: - Dolby Encoder
					Ext Prog Name (pt1)  cmdID= 39041  format=   "
		::= { iqdbe02CmdEntry 39041 }


	iqdbe02DolbyEncoderMetadataSourceExtProgNamept2 OBJECT-TYPE
		SYNTAX		RollCallString
		MAX-ACCESS		read-only
		STATUS			current
		DESCRIPTION
				"TYPE: - Display
				 PAGE: - Dolby Encoder
					Ext Prog Name (pt2)  cmdID= 39042  format=   "
		::= { iqdbe02CmdEntry 39042 }


	iqdbe02DolbyEncoderInternalMetadataChannelMode OBJECT-TYPE
		SYNTAX		INTEGER {
							val_3_2_L_C_R_SL_SR(7),
							val_2_2_L_R_SL_SR(6),
							val_3_1_L_C_R_S(5),
							val_2_1_L_R_S(4),
							val_3_0_L_C_R(3),
							val_2_0_L_R(2),
							val_1_0_C(1)
							}
		MAX-ACCESS		read-write
		STATUS			current
		DESCRIPTION
				"TYPE: - RadiobuttonList
				 PAGE: - Dolby Encoder- Internal Metadata
					Channel Mode  cmdID= 38953
					3/2 (L C R SL SR)  value= 7
					2/2 (L R SL SR)  value= 6
					3/1 (L C R S)  value= 5
					2/1 (L R S)  value= 4
					3/0 (L C R)  value= 3
					2/0 (L R)  value= 2
					1/0 (C)  value= 1  "
		::= { iqdbe02CmdEntry 38953 }


	iqdbe02DolbyEncoderInternalMetadataInputAssignAB OBJECT-TYPE
		SYNTAX		RollCallString
		MAX-ACCESS		read-only
		STATUS			current
		DESCRIPTION
				"TYPE: - Display
				 PAGE: - Dolby Encoder- Internal Metadata
					Input Assign A-B  cmdID= 38963  format=   "
		::= { iqdbe02CmdEntry 38963 }


	iqdbe02DolbyEncoderInternalMetadataInputAssignC OBJECT-TYPE
		SYNTAX		RollCallString
		MAX-ACCESS		read-only
		STATUS			current
		DESCRIPTION
				"TYPE: - Display
				 PAGE: - Dolby Encoder- Internal Metadata
					Input Assign C  cmdID= 38964  format=   "
		::= { iqdbe02CmdEntry 38964 }


	iqdbe02DolbyEncoderInternalMetadataDialogueNorm OBJECT-TYPE
		SYNTAX		INTEGER
		MAX-ACCESS		read-write
		STATUS			current
		DESCRIPTION
				"TYPE: - Number
				 PAGE: - Dolby Encoder- Internal Metadata
					Dialogue Norm  cmdID= 38951  min= -31  max= -1  step= 1  format= %0.0f dB  div_scale= 1
					Min = -31 dB  Max = -1 dB  Step = 1 dB "
		::= { iqdbe02CmdEntry 38951 }


	iqdbe02DolbyEncoderInternalMetadataLFEChannel OBJECT-TYPE
		SYNTAX		INTEGER { disable(0), enable(1) }
		MAX-ACCESS		read-write
		STATUS			current
		DESCRIPTION
				"TYPE: - Checkbox
				 PAGE: - Dolby Encoder- Internal Metadata
					LFE Channel  cmdID= 38955 "
		::= { iqdbe02CmdEntry 38955 }


	iqdbe02DolbyEncoderInternalMetadataBitstreamMode OBJECT-TYPE
		SYNTAX		INTEGER {
							val_Complete_Main(0),
							val_Music_and_Effects(1),
							val_Visually_Impaired(2),
							val_Hearing_Impaired(3),
							val_Dialogue(4),
							val_Commentary(5),
							val_Emergency(6),
							val(7)
							}
		MAX-ACCESS		read-write
		STATUS			current
		DESCRIPTION
				"TYPE: - RadiobuttonList
				 PAGE: - Dolby Encoder- Internal Metadata
					Bitstream Mode  cmdID= 38952
					Complete Main  value= 0
					Music and Effects  value= 1
					Visually Impaired  value= 2
					Hearing Impaired  value= 3
					Dialogue  value= 4
					Commentary  value= 5
					Emergency  value= 6
					--  value= 7  "
		::= { iqdbe02CmdEntry 38952 }


	iqdbe02DolbyEncoderInternalMetadataRFMode OBJECT-TYPE
		SYNTAX		INTEGER {
							val_None(0),
							val_Film_Standard(1),
							val_Film_Light(2),
							val_Music_Standard(3),
							val_Music_Light(4),
							val_Speech(5)
							}
		MAX-ACCESS		read-write
		STATUS			current
		DESCRIPTION
				"TYPE: - RadiobuttonList
				 PAGE: - Dolby Encoder- Internal Metadata
					RF Mode  cmdID= 38954
					None  value= 0
					Film Standard  value= 1
					Film Light  value= 2
					Music Standard  value= 3
					Music Light  value= 4
					Speech  value= 5  "
		::= { iqdbe02CmdEntry 38954 }


	iqdbe02DolbyEncoderInternalMetadataLineMode OBJECT-TYPE
		SYNTAX		INTEGER {
							val_None(0),
							val_Film_Standard(1),
							val_Film_Light(2),
							val_Music_Standard(3),
							val_Music_Light(4),
							val_Speech(5)
							}
		MAX-ACCESS		read-write
		STATUS			current
		DESCRIPTION
				"TYPE: - RadiobuttonList
				 PAGE: - Dolby Encoder- Internal Metadata
					Line Mode  cmdID= 38956
					None  value= 0
					Film Standard  value= 1
					Film Light  value= 2
					Music Standard  value= 3
					Music Light  value= 4
					Speech  value= 5  "
		::= { iqdbe02CmdEntry 38956 }


	iqdbe02InternalMetadataAudioProdInfoExists OBJECT-TYPE
		SYNTAX		INTEGER { disable(0), enable(1) }
		MAX-ACCESS		read-write
		STATUS			current
		DESCRIPTION
				"TYPE: - Checkbox
				 PAGE: - Dolby Encoder- Internal Metadata
					Exists  cmdID= 38957 "
		::= { iqdbe02CmdEntry 38957 }


	iqdbe02InternalMetadataAudioProdInfoMixLevel OBJECT-TYPE
		SYNTAX		INTEGER
		MAX-ACCESS		read-write
		STATUS			current
		DESCRIPTION
				"TYPE: - Number
				 PAGE: - Dolby Encoder- Internal Metadata
					Mix Level  cmdID= 38958  min= 80  max= 111  step= 1  format= %0.0f dB  div_scale= 1
					Min = 80 dB  Max = 111 dB  Step = 1 dB "
		::= { iqdbe02CmdEntry 38958 }


	iqdbe02InternalMetadataAudioProdInfoRoomType OBJECT-TYPE
		SYNTAX		INTEGER {
							val_Not_Indicated(0),
							val_Large_Room(1),
							val_Small_Room(2)
							}
		MAX-ACCESS		read-write
		STATUS			current
		DESCRIPTION
				"TYPE: - RadiobuttonList
				 PAGE: - Dolby Encoder- Internal Metadata
					Room Type  cmdID= 38959
					Not Indicated  value= 0
					Large Room  value= 1
					Small Room  value= 2  "
		::= { iqdbe02CmdEntry 38959 }


	iqdbe02DolbyEncoderInternalMetadataSurroundMode OBJECT-TYPE
		SYNTAX		INTEGER {
							val_Not_Indicated(0),
							val_Not_Dolby_Surround(1),
							val_Dolby_Surround(2)
							}
		MAX-ACCESS		read-write
		STATUS			current
		DESCRIPTION
				"TYPE: - RadiobuttonList
				 PAGE: - Dolby Encoder- Internal Metadata
					Surround Mode  cmdID= 38960
					Not Indicated  value= 0
					Not Dolby Surround  value= 1
					Dolby Surround  value= 2  "
		::= { iqdbe02CmdEntry 38960 }


	iqdbe02DolbyEncoderInternalMetadataCenterMixLevel OBJECT-TYPE
		SYNTAX		INTEGER {
							val_0_707_3dB(0),
							val_0_596_4_5dB(1),
							val_0_500_6dB(2)
							}
		MAX-ACCESS		read-write
		STATUS			current
		DESCRIPTION
				"TYPE: - RadiobuttonList
				 PAGE: - Dolby Encoder- Internal Metadata
					Center Mix Level  cmdID= 38961
					0.707(-3dB)  value= 0
					0.596(-4.5dB)  value= 1
					0.500(-6dB)  value= 2  "
		::= { iqdbe02CmdEntry 38961 }


	iqdbe02DolbyEncoderInternalMetadataSurroundMixLevel OBJECT-TYPE
		SYNTAX		INTEGER {
							val_0_707_3dB(0),
							val_0_596_4_5dB(1),
							val_0_000_Inf_dB(2)
							}
		MAX-ACCESS		read-write
		STATUS			current
		DESCRIPTION
				"TYPE: - RadiobuttonList
				 PAGE: - Dolby Encoder- Internal Metadata
					Surround Mix Level  cmdID= 38962
					0.707(-3dB)  value= 0
					0.596(-4.5dB)  value= 1
					0.000(-Inf dB)  value= 2  "
		::= { iqdbe02CmdEntry 38962 }


	iqdbe02DolbyEncoderInternalMetadataCopyrightProtect OBJECT-TYPE
		SYNTAX		INTEGER { disable(0), enable(1) }
		MAX-ACCESS		read-write
		STATUS			current
		DESCRIPTION
				"TYPE: - Checkbox
				 PAGE: - Dolby Encoder- Internal Metadata
					Copyright Protect  cmdID= 38984 "
		::= { iqdbe02CmdEntry 38984 }


	iqdbe02InternalMetadataExtendedBSI1ExtBSI1Exists OBJECT-TYPE
		SYNTAX		INTEGER { disable(0), enable(1) }
		MAX-ACCESS		read-write
		STATUS			current
		DESCRIPTION
				"TYPE: - Checkbox
				 PAGE: - Dolby Encoder- Internal Metadata
					Ext BSI1 Exists  cmdID= 38965 "
		::= { iqdbe02CmdEntry 38965 }


	iqdbe02InternalMetadataExtendedBSI1StereoDownmixMode OBJECT-TYPE
		SYNTAX		INTEGER {
							val_Not_Indicated(0),
							val_LtRt_Prefered(1),
							val_LoRo_Prefered(2)
							}
		MAX-ACCESS		read-write
		STATUS			current
		DESCRIPTION
				"TYPE: - RadiobuttonList
				 PAGE: - Dolby Encoder- Internal Metadata
					Stereo Downmix Mode  cmdID= 38966
					Not Indicated  value= 0
					LtRt Prefered  value= 1
					LoRo Prefered  value= 2  "
		::= { iqdbe02CmdEntry 38966 }


	iqdbe02InternalMetadataExtendedBSI1LtRtCenterDownmix OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LtRt Center Downmix  cmdID= 38967
					+3.0 db  value= 0
					+1.5 dB  value= 1
					0.0 dB  value= 2
					-1.5 dB  value= 3
					-3.0 dB  value= 4
					-4.5 dB  value= 5
					-6.0 dB  value= 6
					-Inf dB  value= 7  "
		::= { iqdbe02CmdEntry 38967 }


	iqdbe02InternalMetadataExtendedBSI1LoRoCenterDownmix OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LoRo Center Downmix  cmdID= 38968
					+3.0 db  value= 0
					+1.5 dB  value= 1
					0.0 dB  value= 2
					-1.5 dB  value= 3
					-3.0 dB  value= 4
					-4.5 dB  value= 5
					-6.0 dB  value= 6
					-Inf dB  value= 7  "
		::= { iqdbe02CmdEntry 38968 }


	iqdbe02InternalMetadataExtendedBSI1LtRtSurroundDownm OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LtRt Surround Downm  cmdID= 38969
					+3.0 db  value= 0
					+1.5 dB  value= 1
					0.0 dB  value= 2
					-1.5 dB  value= 3
					-3.0 dB  value= 4
					-4.5 dB  value= 5
					-6.0 dB  value= 6
					-Inf dB  value= 7  "
		::= { iqdbe02CmdEntry 38969 }


	iqdbe02InternalMetadataExtendedBSI1LoRoSurroundDownm OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LoRo Surround Downm  cmdID= 38970
					+3.0 db  value= 0
					+1.5 dB  value= 1
					0.0 dB  value= 2
					-1.5 dB  value= 3
					-3.0 dB  value= 4
					-4.5 dB  value= 5
					-6.0 dB  value= 6
					-Inf dB  value= 7  "
		::= { iqdbe02CmdEntry 38970 }


	iqdbe02InternalMetadataExtendedBSI2ExtBSI2Exists OBJECT-TYPE
		SYNTAX		INTEGER { disable(0), enable(1) }
		MAX-ACCESS		read-write
		STATUS			current
		DESCRIPTION
				"TYPE: - Checkbox
				 PAGE: - Dolby Encoder- Internal Metadata
					Ext BSI2 Exists  cmdID= 38971 "
		::= { iqdbe02CmdEntry 38971 }


	iqdbe02InternalMetadataExtendedBSI2SurroundExMode OBJECT-TYPE
		SYNTAX		INTEGER {
							val_Not_Indicated(0),
							val_Not_Dolby_Surround(1),
							val_Dolby_Surround_Ex(2)
							}
		MAX-ACCESS		read-write
		STATUS			current
		DESCRIPTION
				"TYPE: - RadiobuttonList
				 PAGE: - Dolby Encoder- Internal Metadata
					Surround Ex Mode  cmdID= 38972
					Not Indicated  value= 0
					Not Dolby Surround   value= 1
					Dolby Surround Ex  value= 2  "
		::= { iqdbe02CmdEntry 38972 }


	iqdbe02InternalMetadataExtendedBSI2LowpassFilter OBJECT-TYPE
		SYNTAX		INTEGER { disable(0), enable(1) }
		MAX-ACCESS		read-write
		STATUS			current
		DESCRIPTION
				"TYPE: - Checkbox
				 PAGE: - Dolby Encoder- Internal Metadata
					Lowpass Filter  cmdID= 38973 "
		::= { iqdbe02CmdEntry 38973 }


	iqdbe02InternalMetadataExtendedBSI2LFEFilter OBJECT-TYPE
		SYNTAX		INTEGER { disable(0), enable(1) }
		MAX-ACCESS		read-write
		STATUS			current
		DESCRIPTION
				"TYPE: - Checkbox
				 PAGE: - Dolby Encoder- Internal Metadata
					LFE Filter  cmdID= 38974 "
		::= { iqdbe02CmdEntry 38974 }


	iqdbe02InternalMetadataExtendedBSI2SurrPhaseShiftFi OBJECT-TYPE
		SYNTAX		INTEGER { disable(0), enable(1) }
		MAX-ACCESS		read-write
		STATUS			current
		DESCRIPTION
				"TYPE: - Checkbox
				 PAGE: - Dolby Encoder- Internal Metadata
					Surr Phase Shift Fi  cmdID= 38975 "
		::= { iqdbe02CmdEntry 38975 }


	iqdbe02InternalMetadataExtendedBSI2Surr3dBAttenuator OBJECT-TYPE
		SYNTAX		INTEGER { disable(0), enable(1) }
		MAX-ACCESS		read-write
		STATUS			current
		DESCRIPTION
				"TYPE: - Checkbox
				 PAGE: - Dolby Encoder- Internal Metadata
					Surr 3dB Attenuator  cmdID= 38976 "
		::= { iqdbe02CmdEntry 38976 }


	iqdbe02DolbyEncoderInternalMetadataDolbyEncReset OBJECT-TYPE
		SYNTAX		INTEGER { noAction(0),val_Dolby_Enc_Reset(1) }
		MAX-ACCESS		read-write
		STATUS			current
		DESCRIPTION
				"TYPE: - Button
				 PAGE: - Dolby Encoder- Internal Metadata
					Dolby Enc Reset  cmdID= 39999  value= 1  "
		::= { iqdbe02CmdEntry 39999 }


	iqdbe02InternalMetadataPresetIntMD OBJECT-TYPE
		SYNTAX		INTEGER {
							val_Default(1),
							val_Stereo_Film(2),
							val_Stereo_Music(3),
							val_Surround_Film(4),
							val_Surround_Music(5),
							val_Copy_Ext_Prog_1(100),
							val_Copy_Ext_Prog_2(101),
							val_Copy_Ext_Prog_3(102),
							val_Copy_Ext_Prog_4(103),
							val_Copy_Ext_Prog_5(104),
							val_Copy_Ext_Prog_6(105),
							val_Copy_Ext_Prog_7(106),
							val_Copy_Ext_Prog_8(107)
							}
		MAX-ACCESS		read-write
		STATUS			current
		DESCRIPTION
				"TYPE: - RadiobuttonList
				 PAGE: - Dolby Encoder- Internal Metadata
					Defaults  cmdID= 38980
					Default  value= 1
					Stereo Film  value= 2
					Stereo Music  value= 3
					Surround Film  value= 4
					Surround Music  value= 5
					Copy Ext Prog 1  cmdID= 38980  value= 100
					Copy Ext Prog 2  cmdID= 38980  value= 101
					Copy Ext Prog 3  cmdID= 38980  value= 102
					Copy Ext Prog 4  cmdID= 38980  value= 103
					Copy Ext Prog 5  cmdID= 38980  value= 104
					Copy Ext Prog 6  cmdID= 38980  value= 105
					Copy Ext Prog 7  cmdID= 38980  value= 106
					Copy Ext Prog 8  cmdID= 38980  value= 107  "
		::= { iqdbe02CmdEntry 38980 }


	iqdbe02InternalMetadataUserPresetSelectUserPreset OBJECT-TYPE
		SYNTAX		INTEGER {
							val_User_Preset_1(0),
							val_User_Preset_2(1),
							val_User_Preset_3(2),
							val_User_Preset_4(3),
							val_User_Preset_5(4),
							val_User_Preset_6(5),
							val_User_Preset_7(6),
							val_User_Preset_8(7)
							}
		MAX-ACCESS		read-write
		STATUS			current
		DESCRIPTION
				"TYPE: - RadiobuttonList
				 PAGE: - Dolby Encoder- Internal Metadata
					Select User Preset  cmdID= 38981
					User Preset 1  value= 0
					User Preset 2  value= 1
					User Preset 3  value= 2
					User Preset 4  value= 3
					User Preset 5  value= 4
					User Preset 6  value= 5
					User Preset 7  value= 6
					User Preset 8  value= 7  "
		::= { iqdbe02CmdEntry 38981 }


	iqdbe02InternalMetadataUserPreset OBJECT-TYPE
		SYNTAX		INTEGER {
							val_Recall_User_Preset(1),
							val_Save_User_Preset(2)
							}
		MAX-ACCESS		read-write
		STATUS			current
		DESCRIPTION
				"TYPE: - Button
				 PAGE: - Dolby Encoder- Internal Metadata
					Recall User Preset  cmdID= 38982  value= 1
					Save User Preset  cmdID= 38982  value= 2  "
		::= { iqdbe02CmdEntry 38982 }


	iqdbe02InternalMetadataUserPresetUserPresetName OBJECT-TYPE
		SYNTAX		RollCallString
		MAX-ACCESS		read-write
		STATUS			current
		DESCRIPTION
				"TYPE: - Editstring
				 PAGE: - Dolby Encoder- Internal Metadata
					User Preset Name  cmdID= 38983  "
		::= { iqdbe02CmdEntry 38983 }


	iqdbe02DolbyEncoderOutputMetadataChannelMode OBJECT-TYPE
		SYNTAX		RollCallString
		MAX-ACCESS		read-only
		STATUS			current
		DESCRIPTION
				"TYPE: - Display
				 PAGE: - Dolby Encoder- Output Metadata
					Channel Mode  cmdID= 39002  format=   "
		::= { iqdbe02CmdEntry 39002 }


	iqdbe02DolbyEncoderOutputMetadataLFEChannel OBJECT-TYPE
		SYNTAX		RollCallString
		MAX-ACCESS		read-only
		STATUS			current
		DESCRIPTION
				"TYPE: - Display
				 PAGE: - Dolby Encoder- Output Metadata
					LFE Channel  cmdID= 39003  format=   "
		::= { iqdbe02CmdEntry 39003 }


	iqdbe02DolbyEncoderOutputMetadataDialogueNorm OBJECT-TYPE
		SYNTAX		RollCallString
		MAX-ACCESS		read-only
		STATUS			current
		DESCRIPTION
				"TYPE: - Display
				 PAGE: - Dolby Encoder- Output Metadata
					Dialogue Norm  cmdID= 39028  format=   "
		::= { iqdbe02CmdEntry 39028 }


	iqdbe02DolbyEncoderOutputMetadataBitstreamMode OBJECT-TYPE
		SYNTAX		RollCallString
		MAX-ACCESS		read-only
		STATUS			current
		DESCRIPTION
				"TYPE: - Display
				 PAGE: - Dolby Encoder- Output Metadata
					Bitstream Mode  cmdID= 39004  format=   "
		::= { iqdbe02CmdEntry 39004 }


	iqdbe02DolbyEncoderOutputMetadataRFMode OBJECT-TYPE
		SYNTAX		RollCallString
		MAX-ACCESS		read-only
		STATUS			current
		DESCRIPTION
				"TYPE: - Display
				 PAGE: - Dolby Encoder- Output Metadata
					RF Mode  cmdID= 39005  format=   "
		::= { iqdbe02CmdEntry 39005 }


	iqdbe02DolbyEncoderOutputMetadataLineMode OBJECT-TYPE
		SYNTAX		RollCallString
		MAX-ACCESS		read-only
		STATUS			current
		DESCRIPTION
				"TYPE: - Display
				 PAGE: - Dolby Encoder- Output Metadata
					Line Mode  cmdID= 39006  format=   "
		::= { iqdbe02CmdEntry 39006 }


	iqdbe02DolbyEncoderOutputMetadataCenterMixLevel OBJECT-TYPE
		SYNTAX		RollCallString
		MAX-ACCESS		read-only
		STATUS			current
		DESCRIPTION
				"TYPE: - Display
				 PAGE: - Dolby Encoder- Output Metadata
					Center Mix Level  cmdID= 39010  format=   "
		::= { iqdbe02CmdEntry 39010 }


	iqdbe02DolbyEncoderOutputMetadataSurroundMixLevel OBJECT-TYPE
		SYNTAX		RollCallString
		MAX-ACCESS		read-only
		STATUS			current
		DESCRIPTION
				"TYPE: - Display
				 PAGE: - Dolby Encoder- Output Metadata
					Surround Mix Level  cmdID= 39011  format=   "
		::= { iqdbe02CmdEntry 39011 }


	iqdbe02DolbyEncoderOutputMetadataSurrondMode OBJECT-TYPE
		SYNTAX		RollCallString
		MAX-ACCESS		read-only
		STATUS			current
		DESCRIPTION
				"TYPE: - Display
				 PAGE: - Dolby Encoder- Output Metadata
					Surrond Mode  cmdID= 39012  format=   "
		::= { iqdbe02CmdEntry 39012 }


	iqdbe02DolbyEncoderOutputMetadataCopyright OBJECT-TYPE
		SYNTAX		RollCallString
		MAX-ACCESS		read-only
		STATUS			current
		DESCRIPTION
				"TYPE: - Display
				 PAGE: - Dolby Encoder- Output Metadata
					Copyright  cmdID= 39029  format=   "
		::= { iqdbe02CmdEntry 39029 }


	iqdbe02OutputMetadataAudioProdInfoExists OBJECT-TYPE
		SYNTAX		RollCallString
		MAX-ACCESS		read-only
		STATUS			current
		DESCRIPTION
				"TYPE: - Display
				 PAGE: - Dolby Encoder- Output Metadata
					Exists  cmdID= 39007  format=   "
		::= { iqdbe02CmdEntry 39007 }


	iqdbe02OutputMetadataAudioProdInfoMixLevel OBJECT-TYPE
		SYNTAX		RollCallString
		MAX-ACCESS		read-only
		STATUS			current
		DESCRIPTION
				"TYPE: - Display
				 PAGE: - Dolby Encoder- Output Metadata
					Mix Level  cmdID= 39008  format=   "
		::= { iqdbe02CmdEntry 39008 }


	iqdbe02OutputMetadataAudioProdInfoRoomType OBJECT-TYPE
		SYNTAX		RollCallString
		MAX-ACCESS		read-only
		STATUS			current
		DESCRIPTION
				"TYPE: - Display
				 PAGE: - Dolby Encoder- Output Metadata
					Room Type  cmdID= 39009  format=   "
		::= { iqdbe02CmdEntry 39009 }


	iqdbe02OutputMetadataExtendedBSI1Exists OBJECT-TYPE
		SYNTAX		RollCallString
		MAX-ACCESS		read-only
		STATUS			current
		DESCRIPTION
				"TYPE: - Display
				 PAGE: - Dolby Encoder- Output Metadata
					Exists  cmdID= 39013  format=   "
		::= { iqdbe02CmdEntry 39013 }


	iqdbe02OutputMetadataExtendedBSI1StereoDownmixMode OBJECT-TYPE
		SYNTAX		RollCallString
		MAX-ACCESS		read-only
		STATUS			current
		DESCRIPTION
				"TYPE: - Display
				 PAGE: - Dolby Encoder- Output Metadata
					Stereo Downmix Mode  cmdID= 39014  format=   "
		::= { iqdbe02CmdEntry 39014 }


	iqdbe02OutputMetadataExtendedBSI1LtRtCenMixLevel OBJECT-TYPE
		SYNTAX		RollCallString
		MAX-ACCESS		read-only
		STATUS			current
		DESCRIPTION
				"TYPE: - Display
				 PAGE: - Dolby Encoder- Output Metadata
					LtRt Cen Mix Level  cmdID= 39015  format=   "
		::= { iqdbe02CmdEntry 39015 }


	iqdbe02OutputMetadataExtendedBSI1LtRtSurMixLevel OBJECT-TYPE
		SYNTAX		RollCallString
		MAX-ACCESS		read-only
		STATUS			current
		DESCRIPTION
				"TYPE: - Display
				 PAGE: - Dolby Encoder- Output Metadata
					LtRt Sur Mix Level  cmdID= 39016  format=   "
		::= { iqdbe02CmdEntry 39016 }


	iqdbe02OutputMetadataExtendedBSI1LoRoCenMixLevel OBJECT-TYPE
		SYNTAX		RollCallString
		MAX-ACCESS		read-only
		STATUS			current
		DESCRIPTION
				"TYPE: - Display
				 PAGE: - Dolby Encoder- Output Metadata
					LoRo Cen Mix Level  cmdID= 39017  format=   "
		::= { iqdbe02CmdEntry 39017 }


	iqdbe02OutputMetadataExtendedBSI1LoRoSurMixLevel OBJECT-TYPE
		SYNTAX		RollCallString
		MAX-ACCESS		read-only
		STATUS			current
		DESCRIPTION
				"TYPE: - Display
				 PAGE: - Dolby Encoder- Output Metadata
					LoRo Sur Mix Level  cmdID= 39018  format=   "
		::= { iqdbe02CmdEntry 39018 }


	iqdbe02OutputMetadataExtendedBSI2Exists OBJECT-TYPE
		SYNTAX		RollCallString
		MAX-ACCESS		read-only
		STATUS			current
		DESCRIPTION
				"TYPE: - Display
				 PAGE: - Dolby Encoder- Output Metadata
					Exists  cmdID= 39019  format=   "
		::= { iqdbe02CmdEntry 39019 }


	iqdbe02OutputMetadataExtendedBSI2SurExMode OBJECT-TYPE
		SYNTAX		RollCallString
		MAX-ACCESS		read-only
		STATUS			current
		DESCRIPTION
				"TYPE: - Display
				 PAGE: - Dolby Encoder- Output Metadata
					Sur Ex Mode  cmdID= 39020  format=   "
		::= { iqdbe02CmdEntry 39020 }


	iqdbe02OutputMetadataExtendedBSI2LowpassFilter OBJECT-TYPE
		SYNTAX		RollCallString
		MAX-ACCESS		read-only
		STATUS			current
		DESCRIPTION
				"TYPE: - Display
				 PAGE: - Dolby Encoder- Output Metadata
					Lowpass Filter  cmdID= 39021  format=   "
		::= { iqdbe02CmdEntry 39021 }


	iqdbe02OutputMetadataExtendedBSI2LFEFilter OBJECT-TYPE
		SYNTAX		RollCallString
		MAX-ACCESS		read-only
		STATUS			current
		DESCRIPTION
				"TYPE: - Display
				 PAGE: - Dolby Encoder- Output Metadata
					LFE Filter  cmdID= 39022  format=   "
		::= { iqdbe02CmdEntry 39022 }


	iqdbe02OutputMetadataExtendedBSI2SurPhshiftFilter OBJECT-TYPE
		SYNTAX		RollCallString
		MAX-ACCESS		read-only
		STATUS			current
		DESCRIPTION
				"TYPE: - Display
				 PAGE: - Dolby Encoder- Output Metadata
					Sur Ph shift Filter  cmdID= 39023  format=   "
		::= { iqdbe02CmdEntry 39023 }


	iqdbe02OutputMetadataExtendedBSI2Sur3dBAttenuator OBJECT-TYPE
		SYNTAX		RollCallString
		MAX-ACCESS		read-only
		STATUS			current
		DESCRIPTION
				"TYPE: - Display
				 PAGE: - Dolby Encoder- Output Metadata
					Sur 3dB Attenuator  cmdID= 39024  format=   "
		::= { iqdbe02CmdEntry 39024 }


	iqdbe02AudioDolbyEncoderFirmwareVersion OBJECT-TYPE
		SYNTAX		RollCallString
		MAX-ACCESS		read-only
		STATUS			current
		DESCRIPTION
				"TYPE: - Display
				 PAGE: - Dolby Encoder
					Firmware Version  cmdID= 38700  format=   "
		::= { iqdbe02CmdEntry 38700 }


	iqdbe02AudioDolbyEncoderBitstreamFormat OBJECT-TYPE
		SYNTAX		INTEGER {
							val_Dolby_D_32_bit(0),
							val_Dolby_D_16_bit_Ch1(1),
							val_Dolby_D_16_bit_Ch2(2)
							}
		MAX-ACCESS		read-write
		STATUS			current
		DESCRIPTION
				"TYPE: - RadiobuttonList
				 PAGE: - Dolby Encoder
					Bitstream Format  cmdID= 38926
					Dolby D 32-bit  value= 0
					Dolby D 16-bit Ch1  value= 1
					Dolby D 16-bit Ch2  value= 2  "
		::= { iqdbe02CmdEntry 38926 }


	iqdbe02AudioDolbyEncoderDDStreamNumber OBJECT-TYPE
		SYNTAX		INTEGER {
							val_Stream_0(0),
							val_Stream_1(1),
							val_Stream_2(2),
							val_Stream_3(3),
							val_Stream_4(4),
							val_Stream_5(5),
							val_Stream_6(6)
							}
		MAX-ACCESS		read-write
		STATUS			current
		DESCRIPTION
				"TYPE: - RadiobuttonList
				 PAGE: - Dolby Encoder
					DD Stream Number  cmdID= 38928
					Stream 0  value= 0
					Stream 1  value= 1
					Stream 2  value= 2
					Stream 3  value= 3
					Stream 4  value= 4
					Stream 5  value= 5
					Stream 6  value= 6  "
		::= { iqdbe02CmdEntry 38928 }


	iqdbe02AudioVidDelayInternalDelay OBJECT-TYPE
		SYNTAX		RollCallString
		MAX-ACCESS		read-only
		STATUS			current
		DESCRIPTION
				"TYPE: - Display
				 PAGE: - Vid. Delay
					Internal Delay  cmdID= 33025  format=   "
		::= { iqdbe02CmdEntry 33025 }


	iqdbe02AudioVidDelayDelayMode OBJECT-TYPE
		SYNTAX		INTEGER {
							val_Minimum_Audio(3),
							val_Frames(4),
							val_Manual_H_V(5),
							val_Manual_ms(6)
							}
		MAX-ACCESS		read-write
		STATUS			current
		DESCRIPTION
				"TYPE: - RadiobuttonList
				 PAGE: - Vid. Delay
					Delay Mode  cmdID= 33026
					Minimum Audio  value= 3
					Frames  value= 4
					Manual H/V  value= 5
					Manual ms  value= 6  "
		::= { iqdbe02CmdEntry 33026 }


	iqdbe02VidDelaySetDelayDelayFrames OBJECT-TYPE
		SYNTAX		INTEGER
		MAX-ACCESS		read-write
		STATUS			current
		DESCRIPTION
				"TYPE: - Number
				 PAGE: - Vid. Delay
					Delay Frames  cmdID= 33024  min= 0  max= 11  step= 1  format= %0.0f frames  div_scale= 1
					Min = 0 frames  Max = 11 frames  Step = 1 frames "
		::= { iqdbe02CmdEntry 33024 }


	iqdbe02VidDelaySetDelayVerticalTiming OBJECT-TYPE
		SYNTAX		INTEGER
		MAX-ACCESS		read-write
		STATUS			current
		DESCRIPTION
				"TYPE: - Number
				 PAGE: - Vid. Delay
					Vertical Timing  cmdID= 33022  min= -1500  max= 1500  step= 1  format= %0.0f lines  div_scale= 1
					Min = -1500 lines  Max = 1500 lines  Step = 1 lines "
		::= { iqdbe02CmdEntry 33022 }


	iqdbe02VidDelaySetDelayHorizontalTiming OBJECT-TYPE
		SYNTAX		INTEGER
		MAX-ACCESS		read-write
		STATUS			current
		DESCRIPTION
				"TYPE: - Number
				 PAGE: - Vid. Delay
					Horizontal Timing  cmdID= 33021  min= -3000  max= 3000  step= 1  format= %0.0f pixels  div_scale= 1
					Min = -3000 pixels  Max = 3000 pixels  Step = 1 pixels "
		::= { iqdbe02CmdEntry 33021 }


	iqdbe02VidDelaySetDelayDelayms OBJECT-TYPE
		SYNTAX		INTEGER
		MAX-ACCESS		read-write
		STATUS			current
		DESCRIPTION
				"TYPE: - Number
				 PAGE: - Vid. Delay
					Delay ms  cmdID= 33027  min= -48000  max= 48000  step= 5  format= %0.2f ms  div_scale= 100
					Min = -480.00 ms  Max = 480.00 ms  Step = 0.05 ms "
		::= { iqdbe02CmdEntry 33027 }


	iqdbe02UtilsPatternsPatternEnable OBJECT-TYPE
		SYNTAX		INTEGER { disable(0), enable(1) }
		MAX-ACCESS		read-write
		STATUS			current
		DESCRIPTION
				"TYPE: - Checkbox
				 PAGE: - Utils
					Pattern Enable  cmdID= 33038 "
		::= { iqdbe02CmdEntry 33038 }


	iqdbe02UtilsPatternsScrollPattern OBJECT-TYPE
		SYNTAX		INTEGER { disable(0), enable(1) }
		MAX-ACCESS		read-write
		STATUS			current
		DESCRIPTION
				"TYPE: - Checkbox
				 PAGE: - Utils
					Scroll Pattern  cmdID= 33040 "
		::= { iqdbe02CmdEntry 33040 }


	iqdbe02UtilsPatternsPatternType OBJECT-TYPE
		SYNTAX		INTEGER {
							val_100_Color_Bars(1),
							val_75_Color_Bars(2),
							val_SMPTE_Bars(3),
							val_Tartan_Bars(4),
							val_Pluge(5),
							val_Ramp(6),
							val_Sweep(7),
							val_Pulse_Bar(8),
							val_Burst(9),
							val_Black(10)
							}
		MAX-ACCESS		read-write
		STATUS			current
		DESCRIPTION
				"TYPE: - RadiobuttonList
				 PAGE: - Utils
					Pattern Type  cmdID= 33039
					100% Color Bars  value= 1
					75% Color Bars  value= 2
					SMPTE Bars  value= 3
					Tartan Bars  value= 4
					Pluge  value= 5
					Ramp  value= 6
					Sweep  value= 7
					Pulse & Bar  value= 8
					Burst  value= 9
					Black  value= 10  "
		::= { iqdbe02CmdEntry 33039 }


	iqdbe02AudioUtilsANCblankonMismat OBJECT-TYPE
		SYNTAX		INTEGER { disable(0), enable(1) }
		MAX-ACCESS		read-write
		STATUS			current
		DESCRIPTION
				"TYPE: - Checkbox
				 PAGE: - Utils
					ANC blank on Mismat  cmdID= 33036 "
		::= { iqdbe02CmdEntry 33036 }


	iqdbe02UtilsFreezeForceFreeze OBJECT-TYPE
		SYNTAX		INTEGER { disable(0), enable(1) }
		MAX-ACCESS		read-write
		STATUS			current
		DESCRIPTION
				"TYPE: - Checkbox
				 PAGE: - Utils
					Force Freeze  cmdID= 33032 "
		::= { iqdbe02CmdEntry 33032 }


	iqdbe02UtilsFreezeFreezeType OBJECT-TYPE
		SYNTAX		INTEGER {
							val_Frame(0),
							val_Field(1)
							}
		MAX-ACCESS		read-write
		STATUS			current
		DESCRIPTION
				"TYPE: - RadiobuttonList
				 PAGE: - Utils
					Freeze Type  cmdID= 33033
					Frame  value= 0
					Field  value= 1  "
		::= { iqdbe02CmdEntry 33033 }


	iqdbe02UtilsMonochrome OBJECT-TYPE
		SYNTAX		INTEGER { disable(0), enable(1) }
		MAX-ACCESS		read-write
		STATUS			current
		DESCRIPTION
				"TYPE: - Checkbox
				 PAGE: - Utils
					Monochrome  cmdID= 33034 "
		::= { iqdbe02CmdEntry 33034 }


	iqdbe02UtilsMonochromeMonochromeType OBJECT-TYPE
		SYNTAX		INTEGER {
							val_Y_only(0),
							val_C_only(1)
							}
		MAX-ACCESS		read-write
		STATUS			current
		DESCRIPTION
				"TYPE: - RadiobuttonList
				 PAGE: - Utils
					Monochrome Type  cmdID= 33035
					Y only  value= 0
					C only  value= 1  "
		::= { iqdbe02CmdEntry 33035 }


	iqdbe02UtilsVBIBlankingANCMode OBJECT-TYPE
		SYNTAX		INTEGER {
							val_Pass_Input_ANC(0),
							val_Blank_HANC(2),
							val_Blank_All_ANC(1)
							}
		MAX-ACCESS		read-write
		STATUS			current
		DESCRIPTION
				"TYPE: - RadiobuttonList
				 PAGE: - Utils
					ANC Mode  cmdID= 33037
					Pass Input ANC  value= 0
					Blank HANC  value= 2
					Blank All ANC  value= 1  "
		::= { iqdbe02CmdEntry 33037 }


	iqdbe02UtilsVBIBlankingStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Utils
					Standard  cmdID= 37200
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe02CmdEntry 37200 }


	iqdbe02UtilsVBIBlankingBlankAll OBJECT-TYPE
		SYNTAX		INTEGER { noAction(0),val_Blank_All(1) }
		MAX-ACCESS		read-write
		STATUS			current
		DESCRIPTION
				"TYPE: - Button
				 PAGE: - Utils
					Blank All  cmdID= 37201  value= 1  "
		::= { iqdbe02CmdEntry 37201 }


	iqdbe02UtilsVBIBlankingPassAll OBJECT-TYPE
		SYNTAX		INTEGER { noAction(0),val_Pass_All(1) }
		MAX-ACCESS		read-write
		STATUS			current
		DESCRIPTION
				"TYPE: - Button
				 PAGE: - Utils
					Pass All  cmdID= 37202  value= 1  "
		::= { iqdbe02CmdEntry 37202 }


	iqdbe02UtilsVBIBlankingBlank1 OBJECT-TYPE
		SYNTAX		INTEGER { disable(0), enable(1) }
		MAX-ACCESS		read-write
		STATUS			current
		DESCRIPTION
				"TYPE: - Checkbox
				 PAGE: - Utils
					Blank 1  cmdID= 37210 "
		::= { iqdbe02CmdEntry 37210 }


	iqdbe02UtilsVBIBlankingBlank2 OBJECT-TYPE
		SYNTAX		INTEGER { disable(0), enable(1) }
		MAX-ACCESS		read-write
		STATUS			current
		DESCRIPTION
				"TYPE: - Checkbox
				 PAGE: - Utils
					Blank 2  cmdID= 37211 "
		::= { iqdbe02CmdEntry 37211 }


	iqdbe02UtilsVBIBlankingBlank3 OBJECT-TYPE
		SYNTAX		INTEGER { disable(0), enable(1) }
		MAX-ACCESS		read-write
		STATUS			current
		DESCRIPTION
				"TYPE: - Checkbox
				 PAGE: - Utils
					Blank 3  cmdID= 37212 "
		::= { iqdbe02CmdEntry 37212 }


	iqdbe02UtilsVBIBlankingBlank4 OBJECT-TYPE
		SYNTAX		INTEGER { disable(0), enable(1) }
		MAX-ACCESS		read-write
		STATUS			current
		DESCRIPTION
				"TYPE: - Checkbox
				 PAGE: - Utils
					Blank 4  cmdID= 37213 "
		::= { iqdbe02CmdEntry 37213 }


	iqdbe02UtilsVBIBlankingBlank5 OBJECT-TYPE
		SYNTAX		INTEGER { disable(0), enable(1) }
		MAX-ACCESS		read-write
		STATUS			current
		DESCRIPTION
				"TYPE: - Checkbox
				 PAGE: - Utils
					Blank 5  cmdID= 37214 "
		::= { iqdbe02CmdEntry 37214 }


	iqdbe02UtilsVBIBlankingBlank6 OBJECT-TYPE
		SYNTAX		INTEGER { disable(0), enable(1) }
		MAX-ACCESS		read-write
		STATUS			current
		DESCRIPTION
				"TYPE: - Checkbox
				 PAGE: - Utils
					Blank 6  cmdID= 37215 "
		::= { iqdbe02CmdEntry 37215 }


	iqdbe02UtilsVBIBlankingBlank7 OBJECT-TYPE
		SYNTAX		INTEGER { disable(0), enable(1) }
		MAX-ACCESS		read-write
		STATUS			current
		DESCRIPTION
				"TYPE: - Checkbox
				 PAGE: - Utils
					Blank 7  cmdID= 37216 "
		::= { iqdbe02CmdEntry 37216 }


	iqdbe02UtilsVBIBlankingBlank8 OBJECT-TYPE
		SYNTAX		INTEGER { disable(0), enable(1) }
		MAX-ACCESS		read-write
		STATUS			current
		DESCRIPTION
				"TYPE: - Checkbox
				 PAGE: - Utils
					Blank 8  cmdID= 37217 "
		::= { iqdbe02CmdEntry 37217 }


	iqdbe02UtilsVBIBlankingBlank9 OBJECT-TYPE
		SYNTAX		INTEGER { disable(0), enable(1) }
		MAX-ACCESS		read-write
		STATUS			current
		DESCRIPTION
				"TYPE: - Checkbox
				 PAGE: - Utils
					Blank 9  cmdID= 37218 "
		::= { iqdbe02CmdEntry 37218 }


	iqdbe02UtilsVBIBlankingBlank10 OBJECT-TYPE
		SYNTAX		INTEGER { disable(0), enable(1) }
		MAX-ACCESS		read-write
		STATUS			current
		DESCRIPTION
				"TYPE: - Checkbox
				 PAGE: - Utils
					Blank 10  cmdID= 37219 "
		::= { iqdbe02CmdEntry 37219 }


	iqdbe02UtilsVBIBlankingBlank11 OBJECT-TYPE
		SYNTAX		INTEGER { disable(0), enable(1) }
		MAX-ACCESS		read-write
		STATUS			current
		DESCRIPTION
				"TYPE: - Checkbox
				 PAGE: - Utils
					Blank 11  cmdID= 37220 "
		::= { iqdbe02CmdEntry 37220 }


	iqdbe02UtilsVBIBlankingBlank12 OBJECT-TYPE
		SYNTAX		INTEGER { disable(0), enable(1) }
		MAX-ACCESS		read-write
		STATUS			current
		DESCRIPTION
				"TYPE: - Checkbox
				 PAGE: - Utils
					Blank 12  cmdID= 37221 "
		::= { iqdbe02CmdEntry 37221 }


	iqdbe02UtilsVBIBlankingBlank13 OBJECT-TYPE
		SYNTAX		INTEGER { disable(0), enable(1) }
		MAX-ACCESS		read-write
		STATUS			current
		DESCRIPTION
				"TYPE: - Checkbox
				 PAGE: - Utils
					Blank 13  cmdID= 37222 "
		::= { iqdbe02CmdEntry 37222 }


	iqdbe02UtilsVBIBlankingBlank14 OBJECT-TYPE
		SYNTAX		INTEGER { disable(0), enable(1) }
		MAX-ACCESS		read-write
		STATUS			current
		DESCRIPTION
				"TYPE: - Checkbox
				 PAGE: - Utils
					Blank 14  cmdID= 37223 "
		::= { iqdbe02CmdEntry 37223 }


	iqdbe02UtilsVBIBlankingBlank15 OBJECT-TYPE
		SYNTAX		INTEGER { disable(0), enable(1) }
		MAX-ACCESS		read-write
		STATUS			current
		DESCRIPTION
				"TYPE: - Checkbox
				 PAGE: - Utils
					Blank 15  cmdID= 37224 "
		::= { iqdbe02CmdEntry 37224 }


	iqdbe02UtilsVBIBlankingBlank16 OBJECT-TYPE
		SYNTAX		INTEGER { disable(0), enable(1) }
		MAX-ACCESS		read-write
		STATUS			current
		DESCRIPTION
				"TYPE: - Checkbox
				 PAGE: - Utils
					Blank 16  cmdID= 37225 "
		::= { iqdbe02CmdEntry 37225 }


	iqdbe02UtilsVBIBlankingBlank17 OBJECT-TYPE
		SYNTAX		INTEGER { disable(0), enable(1) }
		MAX-ACCESS		read-write
		STATUS			current
		DESCRIPTION
				"TYPE: - Checkbox
				 PAGE: - Utils
					Blank 17  cmdID= 37226 "
		::= { iqdbe02CmdEntry 37226 }


	iqdbe02UtilsVBIBlankingBlank18 OBJECT-TYPE
		SYNTAX		INTEGER { disable(0), enable(1) }
		MAX-ACCESS		read-write
		STATUS			current
		DESCRIPTION
				"TYPE: - Checkbox
				 PAGE: - Utils
					Blank 18  cmdID= 37227 "
		::= { iqdbe02CmdEntry 37227 }


	iqdbe02UtilsVBIBlankingBlank19 OBJECT-TYPE
		SYNTAX		INTEGER { disable(0), enable(1) }
		MAX-ACCESS		read-write
		STATUS			current
		DESCRIPTION
				"TYPE: - Checkbox
				 PAGE: - Utils
					Blank 19  cmdID= 37228 "
		::= { iqdbe02CmdEntry 37228 }


	iqdbe02UtilsVBIBlankingBlank20 OBJECT-TYPE
		SYNTAX		INTEGER { disable(0), enable(1) }
		MAX-ACCESS		read-write
		STATUS			current
		DESCRIPTION
				"TYPE: - Checkbox
				 PAGE: - Utils
					Blank 20  cmdID= 37229 "
		::= { iqdbe02CmdEntry 37229 }


	iqdbe02UtilsVBIBlankingBlank21 OBJECT-TYPE
		SYNTAX		INTEGER { disable(0), enable(1) }
		MAX-ACCESS		read-write
		STATUS			current
		DESCRIPTION
				"TYPE: - Checkbox
				 PAGE: - Utils
					Blank 21  cmdID= 37230 "
		::= { iqdbe02CmdEntry 37230 }


	iqdbe02UtilsVBIBlankingBlank22 OBJECT-TYPE
		SYNTAX		INTEGER { disable(0), enable(1) }
		MAX-ACCESS		read-write
		STATUS			current
		DESCRIPTION
				"TYPE: - Checkbox
				 PAGE: - Utils
					Blank 22  cmdID= 37231 "
		::= { iqdbe02CmdEntry 37231 }


	iqdbe02UtilsVBIBlankingBlank23 OBJECT-TYPE
		SYNTAX		INTEGER { disable(0), enable(1) }
		MAX-ACCESS		read-write
		STATUS			current
		DESCRIPTION
				"TYPE: - Checkbox
				 PAGE: - Utils
					Blank 23  cmdID= 37232 "
		::= { iqdbe02CmdEntry 37232 }


	iqdbe02UtilsVBIBlankingBlank24 OBJECT-TYPE
		SYNTAX		INTEGER { disable(0), enable(1) }
		MAX-ACCESS		read-write
		STATUS			current
		DESCRIPTION
				"TYPE: - Checkbox
				 PAGE: - Utils
					Blank 24  cmdID= 37233 "
		::= { iqdbe02CmdEntry 37233 }


	iqdbe02UtilsVBIBlankingBlank25 OBJECT-TYPE
		SYNTAX		INTEGER { disable(0), enable(1) }
		MAX-ACCESS		read-write
		STATUS			current
		DESCRIPTION
				"TYPE: - Checkbox
				 PAGE: - Utils
					Blank 25  cmdID= 37234 "
		::= { iqdbe02CmdEntry 37234 }


	iqdbe02UtilsVBIBlankingBlank26 OBJECT-TYPE
		SYNTAX		INTEGER { disable(0), enable(1) }
		MAX-ACCESS		read-write
		STATUS			current
		DESCRIPTION
				"TYPE: - Checkbox
				 PAGE: - Utils
					Blank 26  cmdID= 37235 "
		::= { iqdbe02CmdEntry 37235 }


	iqdbe02UtilsVBIBlankingBlank27 OBJECT-TYPE
		SYNTAX		INTEGER { disable(0), enable(1) }
		MAX-ACCESS		read-write
		STATUS			current
		DESCRIPTION
				"TYPE: - Checkbox
				 PAGE: - Utils
					Blank 27  cmdID= 37236 "
		::= { iqdbe02CmdEntry 37236 }


	iqdbe02UtilsVBIBlankingBlank28 OBJECT-TYPE
		SYNTAX		INTEGER { disable(0), enable(1) }
		MAX-ACCESS		read-write
		STATUS			current
		DESCRIPTION
				"TYPE: - Checkbox
				 PAGE: - Utils
					Blank 28  cmdID= 37237 "
		::= { iqdbe02CmdEntry 37237 }


	iqdbe02UtilsVBIBlankingBlank29 OBJECT-TYPE
		SYNTAX		INTEGER { disable(0), enable(1) }
		MAX-ACCESS		read-write
		STATUS			current
		DESCRIPTION
				"TYPE: - Checkbox
				 PAGE: - Utils
					Blank 29  cmdID= 37238 "
		::= { iqdbe02CmdEntry 37238 }


	iqdbe02UtilsVBIBlankingBlank30 OBJECT-TYPE
		SYNTAX		INTEGER { disable(0), enable(1) }
		MAX-ACCESS		read-write
		STATUS			current
		DESCRIPTION
				"TYPE: - Checkbox
				 PAGE: - Utils
					Blank 30  cmdID= 37239 "
		::= { iqdbe02CmdEntry 37239 }


	iqdbe02UtilsVBIBlankingBlank31 OBJECT-TYPE
		SYNTAX		INTEGER { disable(0), enable(1) }
		MAX-ACCESS		read-write
		STATUS			current
		DESCRIPTION
				"TYPE: - Checkbox
				 PAGE: - Utils
					Blank 31  cmdID= 37240 "
		::= { iqdbe02CmdEntry 37240 }


	iqdbe02UtilsVBIBlankingBlank32 OBJECT-TYPE
		SYNTAX		INTEGER { disable(0), enable(1) }
		MAX-ACCESS		read-write
		STATUS			current
		DESCRIPTION
				"TYPE: - Checkbox
				 PAGE: - Utils
					Blank 32  cmdID= 37241 "
		::= { iqdbe02CmdEntry 37241 }


	iqdbe02UtilsVBIBlankingBlank33 OBJECT-TYPE
		SYNTAX		INTEGER { disable(0), enable(1) }
		MAX-ACCESS		read-write
		STATUS			current
		DESCRIPTION
				"TYPE: - Checkbox
				 PAGE: - Utils
					Blank 33  cmdID= 37242 "
		::= { iqdbe02CmdEntry 37242 }


	iqdbe02UtilsVBIBlankingBlank34 OBJECT-TYPE
		SYNTAX		INTEGER { disable(0), enable(1) }
		MAX-ACCESS		read-write
		STATUS			current
		DESCRIPTION
				"TYPE: - Checkbox
				 PAGE: - Utils
					Blank 34  cmdID= 37243 "
		::= { iqdbe02CmdEntry 37243 }


	iqdbe02RecallMemory OBJECT-TYPE
		SYNTAX		INTEGER {
							val_None_Selected(0),
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Recall Memory  cmdID= 37100
					None Selected  value= 0
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqdbe02CmdEntry 37100 }


	iqdbe02SelMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqdbe02CmdEntry 37101 }


	iqdbe02SaveMemory OBJECT-TYPE
		SYNTAX		INTEGER { noAction(0),val_Save_Memory(1) }
		MAX-ACCESS		read-write
		STATUS			current
		DESCRIPTION
				"TYPE: - Button
				 PAGE: - Memories
					Save Memory  cmdID= 37102  value= 1  "
		::= { iqdbe02CmdEntry 37102 }


	iqdbe02ClearMemory OBJECT-TYPE
		SYNTAX		INTEGER { noAction(0),val_Clear_Memory(1) }
		MAX-ACCESS		read-write
		STATUS			current
		DESCRIPTION
				"TYPE: - Button
				 PAGE: - Memories
					Clear Memory  cmdID= 37105  value= 1  "
		::= { iqdbe02CmdEntry 37105 }


	iqdbe02MemoryNameChangeName OBJECT-TYPE
		SYNTAX		RollCallString
		MAX-ACCESS		read-write
		STATUS			current
		DESCRIPTION
				"TYPE: - Editstring
				 PAGE: - Memories
					Change Name  cmdID= 37103  "
		::= { iqdbe02CmdEntry 37103 }


	iqdbe02MemoryNameLastUserMemory OBJECT-TYPE
		SYNTAX		RollCallString
		MAX-ACCESS		read-only
		STATUS			current
		DESCRIPTION
				"TYPE: - Display
				 PAGE: - Memories
					Last User Memory  cmdID= 37104  format=   "
		::= { iqdbe02CmdEntry 37104 }


	iqdbe02MemoryName1 OBJECT-TYPE
		SYNTAX		RollCallString
		MAX-ACCESS		read-only
		STATUS			current
		DESCRIPTION
				"TYPE: - Display
				 PAGE: - Memories
					Memory Name1  cmdID= 37106  format=   "
		::= { iqdbe02CmdEntry 37106 }


	iqdbe02MemoryName2 OBJECT-TYPE
		SYNTAX		RollCallString
		MAX-ACCESS		read-only
		STATUS			current
		DESCRIPTION
				"TYPE: - Display
				 PAGE: - Memories
					Memory Name2  cmdID= 37107  format=   "
		::= { iqdbe02CmdEntry 37107 }


	iqdbe02MemoryName3 OBJECT-TYPE
		SYNTAX		RollCallString
		MAX-ACCESS		read-only
		STATUS			current
		DESCRIPTION
				"TYPE: - Display
				 PAGE: - Memories
					Memory Name3  cmdID= 37108  format=   "
		::= { iqdbe02CmdEntry 37108 }


	iqdbe02MemoryName4 OBJECT-TYPE
		SYNTAX		RollCallString
		MAX-ACCESS		read-only
		STATUS			current
		DESCRIPTION
				"TYPE: - Display
				 PAGE: - Memories
					Memory Name4  cmdID= 37109  format=   "
		::= { iqdbe02CmdEntry 37109 }


	iqdbe02MemoryName5 OBJECT-TYPE
		SYNTAX		RollCallString
		MAX-ACCESS		read-only
		STATUS			current
		DESCRIPTION
				"TYPE: - Display
				 PAGE: - Memories
					Memory Name5  cmdID= 37110  format=   "
		::= { iqdbe02CmdEntry 37110 }


	iqdbe02MemoryName6 OBJECT-TYPE
		SYNTAX		RollCallString
		MAX-ACCESS		read-only
		STATUS			current
		DESCRIPTION
				"TYPE: - Display
				 PAGE: - Memories
					Memory Name6  cmdID= 37111  format=   "
		::= { iqdbe02CmdEntry 37111 }


	iqdbe02MemoryName7 OBJECT-TYPE
		SYNTAX		RollCallString
		MAX-ACCESS		read-only
		STATUS			current
		DESCRIPTION
				"TYPE: - Display
				 PAGE: - Memories
					Memory Name7  cmdID= 37112  format=   "
		::= { iqdbe02CmdEntry 37112 }


	iqdbe02MemoryName8 OBJECT-TYPE
		SYNTAX		RollCallString
		MAX-ACCESS		read-only
		STATUS			current
		DESCRIPTION
				"TYPE: - Display
				 PAGE: - Memories
					Memory Name8  cmdID= 37113  format=   "
		::= { iqdbe02CmdEntry 37113 }


	iqdbe02MemoryName9 OBJECT-TYPE
		SYNTAX		RollCallString
		MAX-ACCESS		read-only
		STATUS			current
		DESCRIPTION
				"TYPE: - Display
				 PAGE: - Memories
					Memory Name9  cmdID= 37114  format=   "
		::= { iqdbe02CmdEntry 37114 }


	iqdbe02MemoryName10 OBJECT-TYPE
		SYNTAX		RollCallString
		MAX-ACCESS		read-only
		STATUS			current
		DESCRIPTION
				"TYPE: - Display
				 PAGE: - Memories
					Memory Name10  cmdID= 37115  format=   "
		::= { iqdbe02CmdEntry 37115 }


	iqdbe02MemoryName11 OBJECT-TYPE
		SYNTAX		RollCallString
		MAX-ACCESS		read-only
		STATUS			current
		DESCRIPTION
				"TYPE: - Display
				 PAGE: - Memories
					Memory Name11  cmdID= 37116  format=   "
		::= { iqdbe02CmdEntry 37116 }


	iqdbe02MemoryName12 OBJECT-TYPE
		SYNTAX		RollCallString
		MAX-ACCESS		read-only
		STATUS			current
		DESCRIPTION
				"TYPE: - Display
				 PAGE: - Memories
					Memory Name12  cmdID= 37117  format=   "
		::= { iqdbe02CmdEntry 37117 }


	iqdbe02MemoryName13 OBJECT-TYPE
		SYNTAX		RollCallString
		MAX-ACCESS		read-only
		STATUS			current
		DESCRIPTION
				"TYPE: - Display
				 PAGE: - Memories
					Memory Name13  cmdID= 37118  format=   "
		::= { iqdbe02CmdEntry 37118 }


	iqdbe02MemoryName14 OBJECT-TYPE
		SYNTAX		RollCallString
		MAX-ACCESS		read-only
		STATUS			current
		DESCRIPTION
				"TYPE: - Display
				 PAGE: - Memories
					Memory Name14  cmdID= 37119  format=   "
		::= { iqdbe02CmdEntry 37119 }


	iqdbe02MemoryName15 OBJECT-TYPE
		SYNTAX		RollCallString
		MAX-ACCESS		read-only
		STATUS			current
		DESCRIPTION
				"TYPE: - Display
				 PAGE: - Memories
					Memory Name15  cmdID= 37120  format=   "
		::= { iqdbe02CmdEntry 37120 }


	iqdbe02MemoryName16 OBJECT-TYPE
		SYNTAX		RollCallString
		MAX-ACCESS		read-only
		STATUS			current
		DESCRIPTION
				"TYPE: - Display
				 PAGE: - Memories
					Memory Name16  cmdID= 37121  format=   "
		::= { iqdbe02CmdEntry 37121 }


	iqdbe02LoggingVideoLoggingLogInput1Type OBJECT-TYPE
		SYNTAX		INTEGER { disable(0), enable(1) }
		MAX-ACCESS		read-write
		STATUS			current
		DESCRIPTION
				"TYPE: - Checkbox
				 PAGE: - RollCall- Logging
					Log Input 1 Type  cmdID= 35017 "
		::= { iqdbe02CmdEntry 35017 }


	iqdbe02LoggingVideoLoggingInput1Type OBJECT-TYPE
		SYNTAX		RollCallString
		MAX-ACCESS		read-only
		STATUS			current
		DESCRIPTION
				"TYPE: - Display
				 PAGE: - RollCall- Logging
					Input 1 Type=  cmdID= 36017  format=   "
		::= { iqdbe02CmdEntry 36017 }


	iqdbe02LoggingVideoLoggingLogInput1Status OBJECT-TYPE
		SYNTAX		INTEGER { disable(0), enable(1) }
		MAX-ACCESS		read-write
		STATUS			current
		DESCRIPTION
				"TYPE: - Checkbox
				 PAGE: - RollCall- Logging
					Log Input 1 Status  cmdID= 35005 "
		::= { iqdbe02CmdEntry 35005 }


	iqdbe02LoggingVideoLoggingInput1Status OBJECT-TYPE
		SYNTAX		RollCallString
		MAX-ACCESS		read-only
		STATUS			current
		DESCRIPTION
				"TYPE: - Display
				 PAGE: - RollCall- Logging
					Input 1 Status=  cmdID= 36005  format=   "
		::= { iqdbe02CmdEntry 36005 }


	iqdbe02LoggingVideoLoggingLogInput1Std OBJECT-TYPE
		SYNTAX		INTEGER { disable(0), enable(1) }
		MAX-ACCESS		read-write
		STATUS			current
		DESCRIPTION
				"TYPE: - Checkbox
				 PAGE: - RollCall- Logging
					Log Input 1 Std.  cmdID= 35016 "
		::= { iqdbe02CmdEntry 35016 }


	iqdbe02LoggingVideoLoggingInput1Std OBJECT-TYPE
		SYNTAX		RollCallString
		MAX-ACCESS		read-only
		STATUS			current
		DESCRIPTION
				"TYPE: - Display
				 PAGE: - RollCall- Logging
					Input 1 Std.=  cmdID= 36016  format=   "
		::= { iqdbe02CmdEntry 36016 }


	iqdbe02LoggingVideoLoggingLogInput1Errors OBJECT-TYPE
		SYNTAX		INTEGER { disable(0), enable(1) }
		MAX-ACCESS		read-write
		STATUS			current
		DESCRIPTION
				"TYPE: - Checkbox
				 PAGE: - RollCall- Logging
					Log Input 1 Errors  cmdID= 35002 "
		::= { iqdbe02CmdEntry 35002 }


	iqdbe02LoggingVideoLoggingInput1Errors OBJECT-TYPE
		SYNTAX		RollCallString
		MAX-ACCESS		read-only
		STATUS			current
		DESCRIPTION
				"TYPE: - Display
				 PAGE: - RollCall- Logging
					Input 1 Errors=  cmdID= 36002  format=   "
		::= { iqdbe02CmdEntry 36002 }


	iqdbe02LoggingVideoLoggingLogInput1ErrSecs OBJECT-TYPE
		SYNTAX		INTEGER { disable(0), enable(1) }
		MAX-ACCESS		read-write
		STATUS			current
		DESCRIPTION
				"TYPE: - Checkbox
				 PAGE: - RollCall- Logging
					Log Input 1 ErrSecs  cmdID= 35003 "
		::= { iqdbe02CmdEntry 35003 }


	iqdbe02LoggingVideoLoggingInput1ErrSecs OBJECT-TYPE
		SYNTAX		RollCallString
		MAX-ACCESS		read-only
		STATUS			current
		DESCRIPTION
				"TYPE: - Display
				 PAGE: - RollCall- Logging
					Input 1 ErrSecs=  cmdID= 36003  format=   "
		::= { iqdbe02CmdEntry 36003 }


	iqdbe02LoggingVideoLoggingLogInput1ANCErr OBJECT-TYPE
		SYNTAX		INTEGER { disable(0), enable(1) }
		MAX-ACCESS		read-write
		STATUS			current
		DESCRIPTION
				"TYPE: - Checkbox
				 PAGE: - RollCall- Logging
					Log Input 1 ANC Err  cmdID= 35000 "
		::= { iqdbe02CmdEntry 35000 }


	iqdbe02LoggingVideoLoggingInput1ANCErrors OBJECT-TYPE
		SYNTAX		RollCallString
		MAX-ACCESS		read-only
		STATUS			current
		DESCRIPTION
				"TYPE: - Display
				 PAGE: - RollCall- Logging
					Input 1 ANC Errors=  cmdID= 36000  format=   "
		::= { iqdbe02CmdEntry 36000 }


	iqdbe02LoggingVideoLoggingLogInput1ANCErrSec OBJECT-TYPE
		SYNTAX		INTEGER { disable(0), enable(1) }
		MAX-ACCESS		read-write
		STATUS			current
		DESCRIPTION
				"TYPE: - Checkbox
				 PAGE: - RollCall- Logging
					Log Input 1 ANC Err  cmdID= 35001 "
		::= { iqdbe02CmdEntry 35001 }


	iqdbe02LoggingVideoLoggingInput1ANCErrSecs OBJECT-TYPE
		SYNTAX		RollCallString
		MAX-ACCESS		read-only
		STATUS			current
		DESCRIPTION
				"TYPE: - Display
				 PAGE: - RollCall- Logging
					Input 1 ANC ErrSecs  cmdID= 36001  format=   "
		::= { iqdbe02CmdEntry 36001 }


	iqdbe02LoggingVideoLoggingLogOutputState OBJECT-TYPE
		SYNTAX		INTEGER { disable(0), enable(1) }
		MAX-ACCESS		read-write
		STATUS			current
		DESCRIPTION
				"TYPE: - Checkbox
				 PAGE: - RollCall- Logging
					Log Output State  cmdID= 35941 "
		::= { iqdbe02CmdEntry 35941 }


	iqdbe02LoggingVideoLoggingOutputState OBJECT-TYPE
		SYNTAX		RollCallString
		MAX-ACCESS		read-only
		STATUS			current
		DESCRIPTION
				"TYPE: - Display
				 PAGE: - RollCall- Logging
					Output State=  cmdID= 36941  format=   "
		::= { iqdbe02CmdEntry 36941 }


	iqdbe02LoggingVideoLoggingLogOutputType OBJECT-TYPE
		SYNTAX		INTEGER { disable(0), enable(1) }
		MAX-ACCESS		read-write
		STATUS			current
		DESCRIPTION
				"TYPE: - Checkbox
				 PAGE: - RollCall- Logging
					Log Output Type  cmdID= 35942 "
		::= { iqdbe02CmdEntry 35942 }


	iqdbe02LoggingVideoLoggingOutputType OBJECT-TYPE
		SYNTAX		RollCallString
		MAX-ACCESS		read-only
		STATUS			current
		DESCRIPTION
				"TYPE: - Display
				 PAGE: - RollCall- Logging
					Output Type=  cmdID= 36942  format=   "
		::= { iqdbe02CmdEntry 36942 }


	iqdbe02LoggingVideoLoggingLogOutputStandard OBJECT-TYPE
		SYNTAX		INTEGER { disable(0), enable(1) }
		MAX-ACCESS		read-write
		STATUS			current
		DESCRIPTION
				"TYPE: - Checkbox
				 PAGE: - RollCall- Logging
					Log Output Standard  cmdID= 35940 "
		::= { iqdbe02CmdEntry 35940 }


	iqdbe02LoggingVideoLoggingOutputStandard OBJECT-TYPE
		SYNTAX		RollCallString
		MAX-ACCESS		read-only
		STATUS			current
		DESCRIPTION
				"TYPE: - Display
				 PAGE: - RollCall- Logging
					Output Standard=  cmdID= 36940  format=   "
		::= { iqdbe02CmdEntry 36940 }


	iqdbe02LoggingVideoLoggingLogoutputANCstat OBJECT-TYPE
		SYNTAX		INTEGER { disable(0), enable(1) }
		MAX-ACCESS		read-write
		STATUS			current
		DESCRIPTION
				"TYPE: - Checkbox
				 PAGE: - RollCall- Logging
					Log output ANC stat  cmdID= 35946 "
		::= { iqdbe02CmdEntry 35946 }


	iqdbe02LoggingVideoLoggingOutputANCstate OBJECT-TYPE
		SYNTAX		RollCallString
		MAX-ACCESS		read-only
		STATUS			current
		DESCRIPTION
				"TYPE: - Display
				 PAGE: - RollCall- Logging
					Output ANC state=  cmdID= 36946  format=   "
		::= { iqdbe02CmdEntry 36946 }


	iqdbe02LoggingEmbAudLoggingLogInp1Emb1stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 stat  cmdID= 35006 "
		::= { iqdbe02CmdEntry 35006 }


	iqdbe02LoggingEmbAudLoggingInp1Emb1state OBJECT-TYPE
		SYNTAX		RollCallString
		MAX-ACCESS		read-only
		STATUS			current
		DESCRIPTION
				"TYPE: - Display
				 PAGE: - RollCall- Logging- Emb.Aud Logging
					Inp1 Emb.1 state=  cmdID= 36006  format=   "
		::= { iqdbe02CmdEntry 36006 }


	iqdbe02LoggingEmbAudLoggingLogInp1Emb2stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 stat  cmdID= 35007 "
		::= { iqdbe02CmdEntry 35007 }


	iqdbe02LoggingEmbAudLoggingInp1Emb2state OBJECT-TYPE
		SYNTAX		RollCallString
		MAX-ACCESS		read-only
		STATUS			current
		DESCRIPTION
				"TYPE: - Display
				 PAGE: - RollCall- Logging- Emb.Aud Logging
					Inp1 Emb.2 state=  cmdID= 36007  format=   "
		::= { iqdbe02CmdEntry 36007 }


	iqdbe02LoggingEmbAudLoggingLogInp1Emb3stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 stat  cmdID= 35008 "
		::= { iqdbe02CmdEntry 35008 }


	iqdbe02LoggingEmbAudLoggingInp1Emb3state OBJECT-TYPE
		SYNTAX		RollCallString
		MAX-ACCESS		read-only
		STATUS			current
		DESCRIPTION
				"TYPE: - Display
				 PAGE: - RollCall- Logging- Emb.Aud Logging
					Inp1 Emb.3 state=  cmdID= 36008  format=   "
		::= { iqdbe02CmdEntry 36008 }


	iqdbe02LoggingEmbAudLoggingLogInp1Emb4stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 stat  cmdID= 35009 "
		::= { iqdbe02CmdEntry 35009 }


	iqdbe02LoggingEmbAudLoggingInp1Emb4state OBJECT-TYPE
		SYNTAX		RollCallString
		MAX-ACCESS		read-only
		STATUS			current
		DESCRIPTION
				"TYPE: - Display
				 PAGE: - RollCall- Logging- Emb.Aud Logging
					Inp1 Emb.4 state=  cmdID= 36009  format=   "
		::= { iqdbe02CmdEntry 36009 }


	iqdbe02LoggingEmbAudLoggingLogInp1Emb5stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 stat  cmdID= 35010 "
		::= { iqdbe02CmdEntry 35010 }


	iqdbe02LoggingEmbAudLoggingInp1Emb5state OBJECT-TYPE
		SYNTAX		RollCallString
		MAX-ACCESS		read-only
		STATUS			current
		DESCRIPTION
				"TYPE: - Display
				 PAGE: - RollCall- Logging- Emb.Aud Logging
					Inp1 Emb.5 state=  cmdID= 36010  format=   "
		::= { iqdbe02CmdEntry 36010 }


	iqdbe02LoggingEmbAudLoggingLogInp1Emb6stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 stat  cmdID= 35011 "
		::= { iqdbe02CmdEntry 35011 }


	iqdbe02LoggingEmbAudLoggingInp1Emb6state OBJECT-TYPE
		SYNTAX		RollCallString
		MAX-ACCESS		read-only
		STATUS			current
		DESCRIPTION
				"TYPE: - Display
				 PAGE: - RollCall- Logging- Emb.Aud Logging
					Inp1 Emb.6 state=  cmdID= 36011  format=   "
		::= { iqdbe02CmdEntry 36011 }


	iqdbe02LoggingEmbAudLoggingLogInp1Emb7stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 stat  cmdID= 35012 "
		::= { iqdbe02CmdEntry 35012 }


	iqdbe02LoggingEmbAudLoggingInp1Emb7state OBJECT-TYPE
		SYNTAX		RollCallString
		MAX-ACCESS		read-only
		STATUS			current
		DESCRIPTION
				"TYPE: - Display
				 PAGE: - RollCall- Logging- Emb.Aud Logging
					Inp1 Emb.7 state=  cmdID= 36012  format=   "
		::= { iqdbe02CmdEntry 36012 }


	iqdbe02LoggingEmbAudLoggingLogInp1Emb8stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 stat  cmdID= 35013 "
		::= { iqdbe02CmdEntry 35013 }


	iqdbe02LoggingEmbAudLoggingInp1Emb8state OBJECT-TYPE
		SYNTAX		RollCallString
		MAX-ACCESS		read-only
		STATUS			current
		DESCRIPTION
				"TYPE: - Display
				 PAGE: - RollCall- Logging- Emb.Aud Logging
					Inp1 Emb.8 state=  cmdID= 36013  format=   "
		::= { iqdbe02CmdEntry 36013 }


	iqdbe02LoggingEmbAudLoggingLogInp1Emb1type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 type  cmdID= 35018 "
		::= { iqdbe02CmdEntry 35018 }


	iqdbe02LoggingEmbAudLoggingInp1Emb1type OBJECT-TYPE
		SYNTAX		RollCallString
		MAX-ACCESS		read-only
		STATUS			current
		DESCRIPTION
				"TYPE: - Display
				 PAGE: - RollCall- Logging- Emb.Aud Logging
					Inp1 Emb.1 type=  cmdID= 36018  format=   "
		::= { iqdbe02CmdEntry 36018 }


	iqdbe02LoggingEmbAudLoggingLogInp1Emb2type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 type  cmdID= 35019 "
		::= { iqdbe02CmdEntry 35019 }


	iqdbe02LoggingEmbAudLoggingInp1Emb2type OBJECT-TYPE
		SYNTAX		RollCallString
		MAX-ACCESS		read-only
		STATUS			current
		DESCRIPTION
				"TYPE: - Display
				 PAGE: - RollCall- Logging- Emb.Aud Logging
					Inp1 Emb.2 type=  cmdID= 36019  format=   "
		::= { iqdbe02CmdEntry 36019 }


	iqdbe02LoggingEmbAudLoggingLogInp1Emb3type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 type  cmdID= 35020 "
		::= { iqdbe02CmdEntry 35020 }


	iqdbe02LoggingEmbAudLoggingInp1Emb3type OBJECT-TYPE
		SYNTAX		RollCallString
		MAX-ACCESS		read-only
		STATUS			current
		DESCRIPTION
				"TYPE: - Display
				 PAGE: - RollCall- Logging- Emb.Aud Logging
					Inp1 Emb.3 type=  cmdID= 36020  format=   "
		::= { iqdbe02CmdEntry 36020 }


	iqdbe02LoggingEmbAudLoggingLogInp1Emb4type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 type  cmdID= 35021 "
		::= { iqdbe02CmdEntry 35021 }


	iqdbe02LoggingEmbAudLoggingInp1Emb4type OBJECT-TYPE
		SYNTAX		RollCallString
		MAX-ACCESS		read-only
		STATUS			current
		DESCRIPTION
				"TYPE: - Display
				 PAGE: - RollCall- Logging- Emb.Aud Logging
					Inp1 Emb.4 type=  cmdID= 36021  format=   "
		::= { iqdbe02CmdEntry 36021 }


	iqdbe02LoggingEmbAudLoggingLogInp1Emb5type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 type  cmdID= 35022 "
		::= { iqdbe02CmdEntry 35022 }


	iqdbe02LoggingEmbAudLoggingInp1Emb5type OBJECT-TYPE
		SYNTAX		RollCallString
		MAX-ACCESS		read-only
		STATUS			current
		DESCRIPTION
				"TYPE: - Display
				 PAGE: - RollCall- Logging- Emb.Aud Logging
					Inp1 Emb.5 type=  cmdID= 36022  format=   "
		::= { iqdbe02CmdEntry 36022 }


	iqdbe02LoggingEmbAudLoggingLogInp1Emb6type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 type  cmdID= 35023 "
		::= { iqdbe02CmdEntry 35023 }


	iqdbe02LoggingEmbAudLoggingInp1Emb6type OBJECT-TYPE
		SYNTAX		RollCallString
		MAX-ACCESS		read-only
		STATUS			current
		DESCRIPTION
				"TYPE: - Display
				 PAGE: - RollCall- Logging- Emb.Aud Logging
					Inp1 Emb.6 type=  cmdID= 36023  format=   "
		::= { iqdbe02CmdEntry 36023 }


	iqdbe02LoggingEmbAudLoggingLogInp1Emb7type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 type  cmdID= 35024 "
		::= { iqdbe02CmdEntry 35024 }


	iqdbe02LoggingEmbAudLoggingInp1Emb7type OBJECT-TYPE
		SYNTAX		RollCallString
		MAX-ACCESS		read-only
		STATUS			current
		DESCRIPTION
				"TYPE: - Display
				 PAGE: - RollCall- Logging- Emb.Aud Logging
					Inp1 Emb.7 type=  cmdID= 36024  format=   "
		::= { iqdbe02CmdEntry 36024 }


	iqdbe02LoggingEmbAudLoggingLogInp1Emb8type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 type  cmdID= 35025 "
		::= { iqdbe02CmdEntry 35025 }


	iqdbe02LoggingEmbAudLoggingInp1Emb8type OBJECT-TYPE
		SYNTAX		RollCallString
		MAX-ACCESS		read-only
		STATUS			current
		DESCRIPTION
				"TYPE: - Display
				 PAGE: - RollCall- Logging- Emb.Aud Logging
					Inp1 Emb.8 type=  cmdID= 36025  format=   "
		::= { iqdbe02CmdEntry 36025 }


	iqdbe02LoggingOPAudLoggingLogOutEmb1state OBJECT-TYPE
		SYNTAX		INTEGER { disable(0), enable(1) }
		MAX-ACCESS		read-write
		STATUS			current
		DESCRIPTION
				"TYPE: - Checkbox
				 PAGE: - RollCall- Logging
					Log Out Emb.1 state  cmdID= 35920 "
		::= { iqdbe02CmdEntry 35920 }


	iqdbe02LoggingOPAudLoggingOutEmb1state OBJECT-TYPE
		SYNTAX		RollCallString
		MAX-ACCESS		read-only
		STATUS			current
		DESCRIPTION
				"TYPE: - Display
				 PAGE: - RollCall- Logging
					Out Emb.1 state=  cmdID= 36920  format=   "
		::= { iqdbe02CmdEntry 36920 }


	iqdbe02LoggingOPAudLoggingLogOutEmb2state OBJECT-TYPE
		SYNTAX		INTEGER { disable(0), enable(1) }
		MAX-ACCESS		read-write
		STATUS			current
		DESCRIPTION
				"TYPE: - Checkbox
				 PAGE: - RollCall- Logging
					Log Out Emb.2 state  cmdID= 35921 "
		::= { iqdbe02CmdEntry 35921 }


	iqdbe02LoggingOPAudLoggingOutEmb2state OBJECT-TYPE
		SYNTAX		RollCallString
		MAX-ACCESS		read-only
		STATUS			current
		DESCRIPTION
				"TYPE: - Display
				 PAGE: - RollCall- Logging
					Out Emb.2 state=  cmdID= 36921  format=   "
		::= { iqdbe02CmdEntry 36921 }


	iqdbe02LoggingOPAudLoggingLogOutEmb3state OBJECT-TYPE
		SYNTAX		INTEGER { disable(0), enable(1) }
		MAX-ACCESS		read-write
		STATUS			current
		DESCRIPTION
				"TYPE: - Checkbox
				 PAGE: - RollCall- Logging
					Log Out Emb.3 state  cmdID= 35922 "
		::= { iqdbe02CmdEntry 35922 }


	iqdbe02LoggingOPAudLoggingOutEmb3state OBJECT-TYPE
		SYNTAX		RollCallString
		MAX-ACCESS		read-only
		STATUS			current
		DESCRIPTION
				"TYPE: - Display
				 PAGE: - RollCall- Logging
					Out Emb.3 state=  cmdID= 36922  format=   "
		::= { iqdbe02CmdEntry 36922 }


	iqdbe02LoggingOPAudLoggingLogOutEmb4state OBJECT-TYPE
		SYNTAX		INTEGER { disable(0), enable(1) }
		MAX-ACCESS		read-write
		STATUS			current
		DESCRIPTION
				"TYPE: - Checkbox
				 PAGE: - RollCall- Logging
					Log Out Emb.4 state  cmdID= 35923 "
		::= { iqdbe02CmdEntry 35923 }


	iqdbe02LoggingOPAudLoggingOutEmb4state OBJECT-TYPE
		SYNTAX		RollCallString
		MAX-ACCESS		read-only
		STATUS			current
		DESCRIPTION
				"TYPE: - Display
				 PAGE: - RollCall- Logging
					Out Emb.4 state=  cmdID= 36923  format=   "
		::= { iqdbe02CmdEntry 36923 }


	iqdbe02LoggingOPAudLoggingLogOutEmb5state OBJECT-TYPE
		SYNTAX		INTEGER { disable(0), enable(1) }
		MAX-ACCESS		read-write
		STATUS			current
		DESCRIPTION
				"TYPE: - Checkbox
				 PAGE: - RollCall- Logging
					Log Out Emb.5 state  cmdID= 35924 "
		::= { iqdbe02CmdEntry 35924 }


	iqdbe02LoggingOPAudLoggingOutEmb5state OBJECT-TYPE
		SYNTAX		RollCallString
		MAX-ACCESS		read-only
		STATUS			current
		DESCRIPTION
				"TYPE: - Display
				 PAGE: - RollCall- Logging
					Out Emb.5 state=  cmdID= 36924  format=   "
		::= { iqdbe02CmdEntry 36924 }


	iqdbe02LoggingOPAudLoggingLogOutEmb6state OBJECT-TYPE
		SYNTAX		INTEGER { disable(0), enable(1) }
		MAX-ACCESS		read-write
		STATUS			current
		DESCRIPTION
				"TYPE: - Checkbox
				 PAGE: - RollCall- Logging
					Log Out Emb.6 state  cmdID= 35925 "
		::= { iqdbe02CmdEntry 35925 }


	iqdbe02LoggingOPAudLoggingOutEmb6state OBJECT-TYPE
		SYNTAX		RollCallString
		MAX-ACCESS		read-only
		STATUS			current
		DESCRIPTION
				"TYPE: - Display
				 PAGE: - RollCall- Logging
					Out Emb.6 state=  cmdID= 36925  format=   "
		::= { iqdbe02CmdEntry 36925 }


	iqdbe02LoggingOPAudLoggingLogOutEmb7state OBJECT-TYPE
		SYNTAX		INTEGER { disable(0), enable(1) }
		MAX-ACCESS		read-write
		STATUS			current
		DESCRIPTION
				"TYPE: - Checkbox
				 PAGE: - RollCall- Logging
					Log Out Emb.7 state  cmdID= 35926 "
		::= { iqdbe02CmdEntry 35926 }


	iqdbe02LoggingOPAudLoggingOutEmb7state OBJECT-TYPE
		SYNTAX		RollCallString
		MAX-ACCESS		read-only
		STATUS			current
		DESCRIPTION
				"TYPE: - Display
				 PAGE: - RollCall- Logging
					Out Emb.7 state=  cmdID= 36926  format=   "
		::= { iqdbe02CmdEntry 36926 }


	iqdbe02LoggingOPAudLoggingLogOutEmb8state OBJECT-TYPE
		SYNTAX		INTEGER { disable(0), enable(1) }
		MAX-ACCESS		read-write
		STATUS			current
		DESCRIPTION
				"TYPE: - Checkbox
				 PAGE: - RollCall- Logging
					Log Out Emb.8 state  cmdID= 35927 "
		::= { iqdbe02CmdEntry 35927 }


	iqdbe02LoggingOPAudLoggingOutEmb8state OBJECT-TYPE
		SYNTAX		RollCallString
		MAX-ACCESS		read-only
		STATUS			current
		DESCRIPTION
				"TYPE: - Display
				 PAGE: - RollCall- Logging
					Out Emb.8 state=  cmdID= 36927  format=   "
		::= { iqdbe02CmdEntry 36927 }


	iqdbe02LoggingOPAudLoggingLogOutEmb1type OBJECT-TYPE
		SYNTAX		INTEGER { disable(0), enable(1) }
		MAX-ACCESS		read-write
		STATUS			current
		DESCRIPTION
				"TYPE: - Checkbox
				 PAGE: - RollCall- Logging
					Log Out Emb.1 type  cmdID= 35930 "
		::= { iqdbe02CmdEntry 35930 }


	iqdbe02LoggingOPAudLoggingOutEmb1type OBJECT-TYPE
		SYNTAX		RollCallString
		MAX-ACCESS		read-only
		STATUS			current
		DESCRIPTION
				"TYPE: - Display
				 PAGE: - RollCall- Logging
					Out Emb.1 type=  cmdID= 36930  format=   "
		::= { iqdbe02CmdEntry 36930 }


	iqdbe02LoggingOPAudLoggingLogOutEmb2type OBJECT-TYPE
		SYNTAX		INTEGER { disable(0), enable(1) }
		MAX-ACCESS		read-write
		STATUS			current
		DESCRIPTION
				"TYPE: - Checkbox
				 PAGE: - RollCall- Logging
					Log Out Emb.2 type  cmdID= 35931 "
		::= { iqdbe02CmdEntry 35931 }


	iqdbe02LoggingOPAudLoggingOutEmb2type OBJECT-TYPE
		SYNTAX		RollCallString
		MAX-ACCESS		read-only
		STATUS			current
		DESCRIPTION
				"TYPE: - Display
				 PAGE: - RollCall- Logging
					Out Emb.2 type=  cmdID= 36931  format=   "
		::= { iqdbe02CmdEntry 36931 }


	iqdbe02LoggingOPAudLoggingLogOutEmb3type OBJECT-TYPE
		SYNTAX		INTEGER { disable(0), enable(1) }
		MAX-ACCESS		read-write
		STATUS			current
		DESCRIPTION
				"TYPE: - Checkbox
				 PAGE: - RollCall- Logging
					Log Out Emb.3 type  cmdID= 35932 "
		::= { iqdbe02CmdEntry 35932 }


	iqdbe02LoggingOPAudLoggingOutEmb3type OBJECT-TYPE
		SYNTAX		RollCallString
		MAX-ACCESS		read-only
		STATUS			current
		DESCRIPTION
				"TYPE: - Display
				 PAGE: - RollCall- Logging
					Out Emb.3 type=  cmdID= 36932  format=   "
		::= { iqdbe02CmdEntry 36932 }


	iqdbe02LoggingOPAudLoggingLogOutEmb4type OBJECT-TYPE
		SYNTAX		INTEGER { disable(0), enable(1) }
		MAX-ACCESS		read-write
		STATUS			current
		DESCRIPTION
				"TYPE: - Checkbox
				 PAGE: - RollCall- Logging
					Log Out Emb.4 type  cmdID= 35933 "
		::= { iqdbe02CmdEntry 35933 }


	iqdbe02LoggingOPAudLoggingOutEmb4type OBJECT-TYPE
		SYNTAX		RollCallString
		MAX-ACCESS		read-only
		STATUS			current
		DESCRIPTION
				"TYPE: - Display
				 PAGE: - RollCall- Logging
					Out Emb.4 type=  cmdID= 36933  format=   "
		::= { iqdbe02CmdEntry 36933 }


	iqdbe02LoggingOPAudLoggingLogOutEmb5type OBJECT-TYPE
		SYNTAX		INTEGER { disable(0), enable(1) }
		MAX-ACCESS		read-write
		STATUS			current
		DESCRIPTION
				"TYPE: - Checkbox
				 PAGE: - RollCall- Logging
					Log Out Emb.5 type  cmdID= 35934 "
		::= { iqdbe02CmdEntry 35934 }


	iqdbe02LoggingOPAudLoggingOutEmb5type OBJECT-TYPE
		SYNTAX		RollCallString
		MAX-ACCESS		read-only
		STATUS			current
		DESCRIPTION
				"TYPE: - Display
				 PAGE: - RollCall- Logging
					Out Emb.5 type=  cmdID= 36934  format=   "
		::= { iqdbe02CmdEntry 36934 }


	iqdbe02LoggingOPAudLoggingLogOutEmb6type OBJECT-TYPE
		SYNTAX		INTEGER { disable(0), enable(1) }
		MAX-ACCESS		read-write
		STATUS			current
		DESCRIPTION
				"TYPE: - Checkbox
				 PAGE: - RollCall- Logging
					Log Out Emb.6 type  cmdID= 35935 "
		::= { iqdbe02CmdEntry 35935 }


	iqdbe02LoggingOPAudLoggingOutEmb6type OBJECT-TYPE
		SYNTAX		RollCallString
		MAX-ACCESS		read-only
		STATUS			current
		DESCRIPTION
				"TYPE: - Display
				 PAGE: - RollCall- Logging
					Out Emb.6 type=  cmdID= 36935  format=   "
		::= { iqdbe02CmdEntry 36935 }


	iqdbe02LoggingOPAudLoggingLogOutEmb7type OBJECT-TYPE
		SYNTAX		INTEGER { disable(0), enable(1) }
		MAX-ACCESS		read-write
		STATUS			current
		DESCRIPTION
				"TYPE: - Checkbox
				 PAGE: - RollCall- Logging
					Log Out Emb.7 type  cmdID= 35936 "
		::= { iqdbe02CmdEntry 35936 }


	iqdbe02LoggingOPAudLoggingOutEmb7type OBJECT-TYPE
		SYNTAX		RollCallString
		MAX-ACCESS		read-only
		STATUS			current
		DESCRIPTION
				"TYPE: - Display
				 PAGE: - RollCall- Logging
					Out Emb.7 type=  cmdID= 36936  format=   "
		::= { iqdbe02CmdEntry 36936 }


	iqdbe02LoggingOPAudLoggingLogOutEmb8type OBJECT-TYPE
		SYNTAX		INTEGER { disable(0), enable(1) }
		MAX-ACCESS		read-write
		STATUS			current
		DESCRIPTION
				"TYPE: - Checkbox
				 PAGE: - RollCall- Logging
					Log Out Emb.8 type  cmdID= 35937 "
		::= { iqdbe02CmdEntry 35937 }


	iqdbe02LoggingOPAudLoggingOutEmb8type OBJECT-TYPE
		SYNTAX		RollCallString
		MAX-ACCESS		read-only
		STATUS			current
		DESCRIPTION
				"TYPE: - Display
				 PAGE: - RollCall- Logging
					Out Emb.8 type=  cmdID= 36937  format=   "
		::= { iqdbe02CmdEntry 36937 }


	iqdbe02LoggingOPAudLevelLoggiLogOutEmb1LLev OBJECT-TYPE
		SYNTAX		INTEGER { disable(0), enable(1) }
		MAX-ACCESS		read-write
		STATUS			current
		DESCRIPTION
				"TYPE: - Checkbox
				 PAGE: - RollCall- Logging
					Log Out Emb.1-L Lev  cmdID= 35900 "
		::= { iqdbe02CmdEntry 35900 }


	iqdbe02LoggingOPAudLevelLoggiOutEmb1LLevel OBJECT-TYPE
		SYNTAX		RollCallString
		MAX-ACCESS		read-only
		STATUS			current
		DESCRIPTION
				"TYPE: - Display
				 PAGE: - RollCall- Logging
					Out Emb.1-L Level=  cmdID= 36900  format=   "
		::= { iqdbe02CmdEntry 36900 }


	iqdbe02LoggingOPAudLevelLoggiLogOutEmb1RLev OBJECT-TYPE
		SYNTAX		INTEGER { disable(0), enable(1) }
		MAX-ACCESS		read-write
		STATUS			current
		DESCRIPTION
				"TYPE: - Checkbox
				 PAGE: - RollCall- Logging
					Log Out Emb.1-R Lev  cmdID= 35901 "
		::= { iqdbe02CmdEntry 35901 }


	iqdbe02LoggingOPAudLevelLoggiOutEmb1RLevel OBJECT-TYPE
		SYNTAX		RollCallString
		MAX-ACCESS		read-only
		STATUS			current
		DESCRIPTION
				"TYPE: - Display
				 PAGE: - RollCall- Logging
					Out Emb.1-R Level=  cmdID= 36901  format=   "
		::= { iqdbe02CmdEntry 36901 }


	iqdbe02LoggingOPAudLevelLoggiLogOutEmb2LLev OBJECT-TYPE
		SYNTAX		INTEGER { disable(0), enable(1) }
		MAX-ACCESS		read-write
		STATUS			current
		DESCRIPTION
				"TYPE: - Checkbox
				 PAGE: - RollCall- Logging
					Log Out Emb.2-L Lev  cmdID= 35902 "
		::= { iqdbe02CmdEntry 35902 }


	iqdbe02LoggingOPAudLevelLoggiOutEmb2LLevel OBJECT-TYPE
		SYNTAX		RollCallString
		MAX-ACCESS		read-only
		STATUS			current
		DESCRIPTION
				"TYPE: - Display
				 PAGE: - RollCall- Logging
					Out Emb.2-L Level=  cmdID= 36902  format=   "
		::= { iqdbe02CmdEntry 36902 }


	iqdbe02LoggingOPAudLevelLoggiLogOutEmb2RLev OBJECT-TYPE
		SYNTAX		INTEGER { disable(0), enable(1) }
		MAX-ACCESS		read-write
		STATUS			current
		DESCRIPTION
				"TYPE: - Checkbox
				 PAGE: - RollCall- Logging
					Log Out Emb.2-R Lev  cmdID= 35903 "
		::= { iqdbe02CmdEntry 35903 }


	iqdbe02LoggingOPAudLevelLoggiOutEmb2RLevel OBJECT-TYPE
		SYNTAX		RollCallString
		MAX-ACCESS		read-only
		STATUS			current
		DESCRIPTION
				"TYPE: - Display
				 PAGE: - RollCall- Logging
					Out Emb.2-R Level=  cmdID= 36903  format=   "
		::= { iqdbe02CmdEntry 36903 }


	iqdbe02LoggingOPAudLevelLoggiLogOutEmb3LLev OBJECT-TYPE
		SYNTAX		INTEGER { disable(0), enable(1) }
		MAX-ACCESS		read-write
		STATUS			current
		DESCRIPTION
				"TYPE: - Checkbox
				 PAGE: - RollCall- Logging
					Log Out Emb.3-L Lev  cmdID= 35904 "
		::= { iqdbe02CmdEntry 35904 }


	iqdbe02LoggingOPAudLevelLoggiOutEmb3LLevel OBJECT-TYPE
		SYNTAX		RollCallString
		MAX-ACCESS		read-only
		STATUS			current
		DESCRIPTION
				"TYPE: - Display
				 PAGE: - RollCall- Logging
					Out Emb.3-L Level=  cmdID= 36904  format=   "
		::= { iqdbe02CmdEntry 36904 }


	iqdbe02LoggingOPAudLevelLoggiLogOutEmb3RLev OBJECT-TYPE
		SYNTAX		INTEGER { disable(0), enable(1) }
		MAX-ACCESS		read-write
		STATUS			current
		DESCRIPTION
				"TYPE: - Checkbox
				 PAGE: - RollCall- Logging
					Log Out Emb.3-R Lev  cmdID= 35905 "
		::= { iqdbe02CmdEntry 35905 }


	iqdbe02LoggingOPAudLevelLoggiOutEmb3RLevel OBJECT-TYPE
		SYNTAX		RollCallString
		MAX-ACCESS		read-only
		STATUS			current
		DESCRIPTION
				"TYPE: - Display
				 PAGE: - RollCall- Logging
					Out Emb.3-R Level=  cmdID= 36905  format=   "
		::= { iqdbe02CmdEntry 36905 }


	iqdbe02LoggingOPAudLevelLoggiLogOutEmb4LLev OBJECT-TYPE
		SYNTAX		INTEGER { disable(0), enable(1) }
		MAX-ACCESS		read-write
		STATUS			current
		DESCRIPTION
				"TYPE: - Checkbox
				 PAGE: - RollCall- Logging
					Log Out Emb.4-L Lev  cmdID= 35906 "
		::= { iqdbe02CmdEntry 35906 }


	iqdbe02LoggingOPAudLevelLoggiOutEmb4LLevel OBJECT-TYPE
		SYNTAX		RollCallString
		MAX-ACCESS		read-only
		STATUS			current
		DESCRIPTION
				"TYPE: - Display
				 PAGE: - RollCall- Logging
					Out Emb.4-L Level=  cmdID= 36906  format=   "
		::= { iqdbe02CmdEntry 36906 }


	iqdbe02LoggingOPAudLevelLoggiLogOutEmb4RLev OBJECT-TYPE
		SYNTAX		INTEGER { disable(0), enable(1) }
		MAX-ACCESS		read-write
		STATUS			current
		DESCRIPTION
				"TYPE: - Checkbox
				 PAGE: - RollCall- Logging
					Log Out Emb.4-R Lev  cmdID= 35907 "
		::= { iqdbe02CmdEntry 35907 }


	iqdbe02LoggingOPAudLevelLoggiOutEmb4RLevel OBJECT-TYPE
		SYNTAX		RollCallString
		MAX-ACCESS		read-only
		STATUS			current
		DESCRIPTION
				"TYPE: - Display
				 PAGE: - RollCall- Logging
					Out Emb.4-R Level=  cmdID= 36907  format=   "
		::= { iqdbe02CmdEntry 36907 }


	iqdbe02LoggingOPAudLevelLoggiLogOutEmb5LLev OBJECT-TYPE
		SYNTAX		INTEGER { disable(0), enable(1) }
		MAX-ACCESS		read-write
		STATUS			current
		DESCRIPTION
				"TYPE: - Checkbox
				 PAGE: - RollCall- Logging
					Log Out Emb.5-L Lev  cmdID= 35908 "
		::= { iqdbe02CmdEntry 35908 }


	iqdbe02LoggingOPAudLevelLoggiOutEmb5LLevel OBJECT-TYPE
		SYNTAX		RollCallString
		MAX-ACCESS		read-only
		STATUS			current
		DESCRIPTION
				"TYPE: - Display
				 PAGE: - RollCall- Logging
					Out Emb.5-L Level=  cmdID= 36908  format=   "
		::= { iqdbe02CmdEntry 36908 }


	iqdbe02LoggingOPAudLevelLoggiLogOutEmb5RLev OBJECT-TYPE
		SYNTAX		INTEGER { disable(0), enable(1) }
		MAX-ACCESS		read-write
		STATUS			current
		DESCRIPTION
				"TYPE: - Checkbox
				 PAGE: - RollCall- Logging
					Log Out Emb.5-R Lev  cmdID= 35909 "
		::= { iqdbe02CmdEntry 35909 }


	iqdbe02LoggingOPAudLevelLoggiOutEmb5RLevel OBJECT-TYPE
		SYNTAX		RollCallString
		MAX-ACCESS		read-only
		STATUS			current
		DESCRIPTION
				"TYPE: - Display
				 PAGE: - RollCall- Logging
					Out Emb.5-R Level=  cmdID= 36909  format=   "
		::= { iqdbe02CmdEntry 36909 }


	iqdbe02LoggingOPAudLevelLoggiLogOutEmb6LLev OBJECT-TYPE
		SYNTAX		INTEGER { disable(0), enable(1) }
		MAX-ACCESS		read-write
		STATUS			current
		DESCRIPTION
				"TYPE: - Checkbox
				 PAGE: - RollCall- Logging
					Log Out Emb.6-L Lev  cmdID= 35910 "
		::= { iqdbe02CmdEntry 35910 }


	iqdbe02LoggingOPAudLevelLoggiOutEmb6LLevel OBJECT-TYPE
		SYNTAX		RollCallString
		MAX-ACCESS		read-only
		STATUS			current
		DESCRIPTION
				"TYPE: - Display
				 PAGE: - RollCall- Logging
					Out Emb.6-L Level=  cmdID= 36910  format=   "
		::= { iqdbe02CmdEntry 36910 }


	iqdbe02LoggingOPAudLevelLoggiLogOutEmb6RLev OBJECT-TYPE
		SYNTAX		INTEGER { disable(0), enable(1) }
		MAX-ACCESS		read-write
		STATUS			current
		DESCRIPTION
				"TYPE: - Checkbox
				 PAGE: - RollCall- Logging
					Log Out Emb.6-R Lev  cmdID= 35911 "
		::= { iqdbe02CmdEntry 35911 }


	iqdbe02LoggingOPAudLevelLoggiOutEmb6RLevel OBJECT-TYPE
		SYNTAX		RollCallString
		MAX-ACCESS		read-only
		STATUS			current
		DESCRIPTION
				"TYPE: - Display
				 PAGE: - RollCall- Logging
					Out Emb.6-R Level=  cmdID= 36911  format=   "
		::= { iqdbe02CmdEntry 36911 }


	iqdbe02LoggingOPAudLevelLoggiLogOutEmb7LLev OBJECT-TYPE
		SYNTAX		INTEGER { disable(0), enable(1) }
		MAX-ACCESS		read-write
		STATUS			current
		DESCRIPTION
				"TYPE: - Checkbox
				 PAGE: - RollCall- Logging
					Log Out Emb.7-L Lev  cmdID= 35912 "
		::= { iqdbe02CmdEntry 35912 }


	iqdbe02LoggingOPAudLevelLoggiOutEmb7LLevel OBJECT-TYPE
		SYNTAX		RollCallString
		MAX-ACCESS		read-only
		STATUS			current
		DESCRIPTION
				"TYPE: - Display
				 PAGE: - RollCall- Logging
					Out Emb.7-L Level=  cmdID= 36912  format=   "
		::= { iqdbe02CmdEntry 36912 }


	iqdbe02LoggingOPAudLevelLoggiLogOutEmb7RLev OBJECT-TYPE
		SYNTAX		INTEGER { disable(0), enable(1) }
		MAX-ACCESS		read-write
		STATUS			current
		DESCRIPTION
				"TYPE: - Checkbox
				 PAGE: - RollCall- Logging
					Log Out Emb.7-R Lev  cmdID= 35913 "
		::= { iqdbe02CmdEntry 35913 }


	iqdbe02LoggingOPAudLevelLoggiOutEmb7RLevel OBJECT-TYPE
		SYNTAX		RollCallString
		MAX-ACCESS		read-only
		STATUS			current
		DESCRIPTION
				"TYPE: - Display
				 PAGE: - RollCall- Logging
					Out Emb.7-R Level=  cmdID= 36913  format=   "
		::= { iqdbe02CmdEntry 36913 }


	iqdbe02LoggingOPAudLevelLoggiLogOutEmb8LLev OBJECT-TYPE
		SYNTAX		INTEGER { disable(0), enable(1) }
		MAX-ACCESS		read-write
		STATUS			current
		DESCRIPTION
				"TYPE: - Checkbox
				 PAGE: - RollCall- Logging
					Log Out Emb.8-L Lev  cmdID= 35914 "
		::= { iqdbe02CmdEntry 35914 }


	iqdbe02LoggingOPAudLevelLoggiOutEmb8LLevel OBJECT-TYPE
		SYNTAX		RollCallString
		MAX-ACCESS		read-only
		STATUS			current
		DESCRIPTION
				"TYPE: - Display
				 PAGE: - RollCall- Logging
					Out Emb.8-L Level=  cmdID= 36914  format=   "
		::= { iqdbe02CmdEntry 36914 }


	iqdbe02LoggingOPAudLevelLoggiLogOutEmb8RLev OBJECT-TYPE
		SYNTAX		INTEGER { disable(0), enable(1) }
		MAX-ACCESS		read-write
		STATUS			current
		DESCRIPTION
				"TYPE: - Checkbox
				 PAGE: - RollCall- Logging
					Log Out Emb.8-R Lev  cmdID= 35915 "
		::= { iqdbe02CmdEntry 35915 }


	iqdbe02LoggingOPAudLevelLoggiOutEmb8RLevel OBJECT-TYPE
		SYNTAX		RollCallString
		MAX-ACCESS		read-only
		STATUS			current
		DESCRIPTION
				"TYPE: - Display
				 PAGE: - RollCall- Logging
					Out Emb.8-R Level=  cmdID= 36915  format=   "
		::= { iqdbe02CmdEntry 36915 }


	iqdbe02LoggingOPDolbyELoggingLogEmbDolbyE1 OBJECT-TYPE
		SYNTAX		INTEGER { disable(0), enable(1) }
		MAX-ACCESS		read-write
		STATUS			current
		DESCRIPTION
				"TYPE: - Checkbox
				 PAGE: - RollCall- Logging
					Log Emb DolbyE 1  cmdID= 35950 "
		::= { iqdbe02CmdEntry 35950 }


	iqdbe02LoggingOPDolbyELoggingEmbDolbyE1 OBJECT-TYPE
		SYNTAX		RollCallString
		MAX-ACCESS		read-only
		STATUS			current
		DESCRIPTION
				"TYPE: - Display
				 PAGE: - RollCall- Logging
					Emb DolbyE 1=  cmdID= 36950  format=   "
		::= { iqdbe02CmdEntry 36950 }


	iqdbe02LoggingOPDolbyELoggingLogEmbDolbyE2 OBJECT-TYPE
		SYNTAX		INTEGER { disable(0), enable(1) }
		MAX-ACCESS		read-write
		STATUS			current
		DESCRIPTION
				"TYPE: - Checkbox
				 PAGE: - RollCall- Logging
					Log Emb DolbyE 2  cmdID= 35951 "
		::= { iqdbe02CmdEntry 35951 }


	iqdbe02LoggingOPDolbyELoggingEmbDolbyE2 OBJECT-TYPE
		SYNTAX		RollCallString
		MAX-ACCESS		read-only
		STATUS			current
		DESCRIPTION
				"TYPE: - Display
				 PAGE: - RollCall- Logging
					Emb DolbyE 2=  cmdID= 36951  format=   "
		::= { iqdbe02CmdEntry 36951 }


	iqdbe02LoggingOPDolbyELoggingLogEmbDolbyE3 OBJECT-TYPE
		SYNTAX		INTEGER { disable(0), enable(1) }
		MAX-ACCESS		read-write
		STATUS			current
		DESCRIPTION
				"TYPE: - Checkbox
				 PAGE: - RollCall- Logging
					Log Emb DolbyE 3  cmdID= 35952 "
		::= { iqdbe02CmdEntry 35952 }


	iqdbe02LoggingOPDolbyELoggingEmbDolbyE3 OBJECT-TYPE
		SYNTAX		RollCallString
		MAX-ACCESS		read-only
		STATUS			current
		DESCRIPTION
				"TYPE: - Display
				 PAGE: - RollCall- Logging
					Emb DolbyE 3=  cmdID= 36952  format=   "
		::= { iqdbe02CmdEntry 36952 }


	iqdbe02LoggingOPDolbyELoggingLogEmbDolbyE4 OBJECT-TYPE
		SYNTAX		INTEGER { disable(0), enable(1) }
		MAX-ACCESS		read-write
		STATUS			current
		DESCRIPTION
				"TYPE: - Checkbox
				 PAGE: - RollCall- Logging
					Log Emb DolbyE 4  cmdID= 35953 "
		::= { iqdbe02CmdEntry 35953 }


	iqdbe02LoggingOPDolbyELoggingEmbDolbyE4 OBJECT-TYPE
		SYNTAX		RollCallString
		MAX-ACCESS		read-only
		STATUS			current
		DESCRIPTION
				"TYPE: - Display
				 PAGE: - RollCall- Logging
					Emb DolbyE 4=  cmdID= 36953  format=   "
		::= { iqdbe02CmdEntry 36953 }


	iqdbe02LoggingOPDolbyELoggingLogEmbDolbyE5 OBJECT-TYPE
		SYNTAX		INTEGER { disable(0), enable(1) }
		MAX-ACCESS		read-write
		STATUS			current
		DESCRIPTION
				"TYPE: - Checkbox
				 PAGE: - RollCall- Logging
					Log Emb DolbyE 5  cmdID= 35954 "
		::= { iqdbe02CmdEntry 35954 }


	iqdbe02LoggingOPDolbyELoggingEmbDolbyE5 OBJECT-TYPE
		SYNTAX		RollCallString
		MAX-ACCESS		read-only
		STATUS			current
		DESCRIPTION
				"TYPE: - Display
				 PAGE: - RollCall- Logging
					Emb DolbyE 5=  cmdID= 36954  format=   "
		::= { iqdbe02CmdEntry 36954 }


	iqdbe02LoggingOPDolbyELoggingLogEmbDolbyE6 OBJECT-TYPE
		SYNTAX		INTEGER { disable(0), enable(1) }
		MAX-ACCESS		read-write
		STATUS			current
		DESCRIPTION
				"TYPE: - Checkbox
				 PAGE: - RollCall- Logging
					Log Emb DolbyE 6  cmdID= 35955 "
		::= { iqdbe02CmdEntry 35955 }


	iqdbe02LoggingOPDolbyELoggingEmbDolbyE6 OBJECT-TYPE
		SYNTAX		RollCallString
		MAX-ACCESS		read-only
		STATUS			current
		DESCRIPTION
				"TYPE: - Display
				 PAGE: - RollCall- Logging
					Emb DolbyE 6=  cmdID= 36955  format=   "
		::= { iqdbe02CmdEntry 36955 }


	iqdbe02LoggingOPDolbyELoggingLogEmbDolbyE7 OBJECT-TYPE
		SYNTAX		INTEGER { disable(0), enable(1) }
		MAX-ACCESS		read-write
		STATUS			current
		DESCRIPTION
				"TYPE: - Checkbox
				 PAGE: - RollCall- Logging
					Log Emb DolbyE 7  cmdID= 35956 "
		::= { iqdbe02CmdEntry 35956 }


	iqdbe02LoggingOPDolbyELoggingEmbDolbyE7 OBJECT-TYPE
		SYNTAX		RollCallString
		MAX-ACCESS		read-only
		STATUS			current
		DESCRIPTION
				"TYPE: - Display
				 PAGE: - RollCall- Logging
					Emb DolbyE 7=  cmdID= 36956  format=   "
		::= { iqdbe02CmdEntry 36956 }


	iqdbe02LoggingOPDolbyELoggingLogEmbDolbyE8 OBJECT-TYPE
		SYNTAX		INTEGER { disable(0), enable(1) }
		MAX-ACCESS		read-write
		STATUS			current
		DESCRIPTION
				"TYPE: - Checkbox
				 PAGE: - RollCall- Logging
					Log Emb DolbyE 8  cmdID= 35957 "
		::= { iqdbe02CmdEntry 35957 }


	iqdbe02LoggingOPDolbyELoggingEmbDolbyE8 OBJECT-TYPE
		SYNTAX		RollCallString
		MAX-ACCESS		read-only
		STATUS			current
		DESCRIPTION
				"TYPE: - Display
				 PAGE: - RollCall- Logging
					Emb DolbyE 8=  cmdID= 36957  format=   "
		::= { iqdbe02CmdEntry 36957 }


	iqdbe02LoggingAESInputLoggingLogAESInput1sta OBJECT-TYPE
		SYNTAX		INTEGER { disable(0), enable(1) }
		MAX-ACCESS		read-write
		STATUS			current
		DESCRIPTION
				"TYPE: - Checkbox
				 PAGE: - RollCall- Logging
					Log AES Input 1 sta  cmdID= 35600 "
		::= { iqdbe02CmdEntry 35600 }


	iqdbe02LoggingAESInputLoggingAESInput1state OBJECT-TYPE
		SYNTAX		RollCallString
		MAX-ACCESS		read-only
		STATUS			current
		DESCRIPTION
				"TYPE: - Display
				 PAGE: - RollCall- Logging
					AES Input 1 state=  cmdID= 36600  format=   "
		::= { iqdbe02CmdEntry 36600 }


	iqdbe02LoggingAESInputLoggingLogAESInput2sta OBJECT-TYPE
		SYNTAX		INTEGER { disable(0), enable(1) }
		MAX-ACCESS		read-write
		STATUS			current
		DESCRIPTION
				"TYPE: - Checkbox
				 PAGE: - RollCall- Logging
					Log AES Input 2 sta  cmdID= 35601 "
		::= { iqdbe02CmdEntry 35601 }


	iqdbe02LoggingAESInputLoggingAESInput2state OBJECT-TYPE
		SYNTAX		RollCallString
		MAX-ACCESS		read-only
		STATUS			current
		DESCRIPTION
				"TYPE: - Display
				 PAGE: - RollCall- Logging
					AES Input 2 state=  cmdID= 36601  format=   "
		::= { iqdbe02CmdEntry 36601 }


	iqdbe02LoggingAESInputLoggingLogAESInput3sta OBJECT-TYPE
		SYNTAX		INTEGER { disable(0), enable(1) }
		MAX-ACCESS		read-write
		STATUS			current
		DESCRIPTION
				"TYPE: - Checkbox
				 PAGE: - RollCall- Logging
					Log AES Input 3 sta  cmdID= 35602 "
		::= { iqdbe02CmdEntry 35602 }


	iqdbe02LoggingAESInputLoggingAESInput3state OBJECT-TYPE
		SYNTAX		RollCallString
		MAX-ACCESS		read-only
		STATUS			current
		DESCRIPTION
				"TYPE: - Display
				 PAGE: - RollCall- Logging
					AES Input 3 state=  cmdID= 36602  format=   "
		::= { iqdbe02CmdEntry 36602 }


	iqdbe02LoggingAESInputLoggingLogAESInput4sta OBJECT-TYPE
		SYNTAX		INTEGER { disable(0), enable(1) }
		MAX-ACCESS		read-write
		STATUS			current
		DESCRIPTION
				"TYPE: - Checkbox
				 PAGE: - RollCall- Logging
					Log AES Input 4 sta  cmdID= 35603 "
		::= { iqdbe02CmdEntry 35603 }


	iqdbe02LoggingAESInputLoggingAESInput4state OBJECT-TYPE
		SYNTAX		RollCallString
		MAX-ACCESS		read-only
		STATUS			current
		DESCRIPTION
				"TYPE: - Display
				 PAGE: - RollCall- Logging
					AES Input 4 state=  cmdID= 36603  format=   "
		::= { iqdbe02CmdEntry 36603 }


	iqdbe02LoggingAESInputLoggingLogAESInput5sta OBJECT-TYPE
		SYNTAX		INTEGER { disable(0), enable(1) }
		MAX-ACCESS		read-write
		STATUS			current
		DESCRIPTION
				"TYPE: - Checkbox
				 PAGE: - RollCall- Logging
					Log AES Input 5 sta  cmdID= 35604 "
		::= { iqdbe02CmdEntry 35604 }


	iqdbe02LoggingAESInputLoggingAESInput5state OBJECT-TYPE
		SYNTAX		RollCallString
		MAX-ACCESS		read-only
		STATUS			current
		DESCRIPTION
				"TYPE: - Display
				 PAGE: - RollCall- Logging
					AES Input 5 state=  cmdID= 36604  format=   "
		::= { iqdbe02CmdEntry 36604 }


	iqdbe02LoggingAESInputLoggingLogAESInput6sta OBJECT-TYPE
		SYNTAX		INTEGER { disable(0), enable(1) }
		MAX-ACCESS		read-write
		STATUS			current
		DESCRIPTION
				"TYPE: - Checkbox
				 PAGE: - RollCall- Logging
					Log AES Input 6 sta  cmdID= 35605 "
		::= { iqdbe02CmdEntry 35605 }


	iqdbe02LoggingAESInputLoggingAESInput6state OBJECT-TYPE
		SYNTAX		RollCallString
		MAX-ACCESS		read-only
		STATUS			current
		DESCRIPTION
				"TYPE: - Display
				 PAGE: - RollCall- Logging
					AES Input 6 state=  cmdID= 36605  format=   "
		::= { iqdbe02CmdEntry 36605 }


	iqdbe02LoggingAESInputLoggingLogAESInput7sta OBJECT-TYPE
		SYNTAX		INTEGER { disable(0), enable(1) }
		MAX-ACCESS		read-write
		STATUS			current
		DESCRIPTION
				"TYPE: - Checkbox
				 PAGE: - RollCall- Logging
					Log AES Input 7 sta  cmdID= 35606 "
		::= { iqdbe02CmdEntry 35606 }


	iqdbe02LoggingAESInputLoggingAESInput7state OBJECT-TYPE
		SYNTAX		RollCallString
		MAX-ACCESS		read-only
		STATUS			current
		DESCRIPTION
				"TYPE: - Display
				 PAGE: - RollCall- Logging
					AES Input 7 state=  cmdID= 36606  format=   "
		::= { iqdbe02CmdEntry 36606 }


	iqdbe02LoggingAESInputLoggingLogAESInput8sta OBJECT-TYPE
		SYNTAX		INTEGER { disable(0), enable(1) }
		MAX-ACCESS		read-write
		STATUS			current
		DESCRIPTION
				"TYPE: - Checkbox
				 PAGE: - RollCall- Logging
					Log AES Input 8 sta  cmdID= 35607 "
		::= { iqdbe02CmdEntry 35607 }


	iqdbe02LoggingAESInputLoggingAESInput8state OBJECT-TYPE
		SYNTAX		RollCallString
		MAX-ACCESS		read-only
		STATUS			current
		DESCRIPTION
				"TYPE: - Display
				 PAGE: - RollCall- Logging
					AES Input 8 state=  cmdID= 36607  format=   "
		::= { iqdbe02CmdEntry 36607 }


	iqdbe02LoggingAESInputLoggingLogAESInput1typ OBJECT-TYPE
		SYNTAX		INTEGER { disable(0), enable(1) }
		MAX-ACCESS		read-write
		STATUS			current
		DESCRIPTION
				"TYPE: - Checkbox
				 PAGE: - RollCall- Logging
					Log AES Input 1 typ  cmdID= 35640 "
		::= { iqdbe02CmdEntry 35640 }


	iqdbe02LoggingAESInputLoggingAESInput1type OBJECT-TYPE
		SYNTAX		RollCallString
		MAX-ACCESS		read-only
		STATUS			current
		DESCRIPTION
				"TYPE: - Display
				 PAGE: - RollCall- Logging
					AES Input 1 type=  cmdID= 36640  format=   "
		::= { iqdbe02CmdEntry 36640 }


	iqdbe02LoggingAESInputLoggingLogAESInput2typ OBJECT-TYPE
		SYNTAX		INTEGER { disable(0), enable(1) }
		MAX-ACCESS		read-write
		STATUS			current
		DESCRIPTION
				"TYPE: - Checkbox
				 PAGE: - RollCall- Logging
					Log AES Input 2 typ  cmdID= 35641 "
		::= { iqdbe02CmdEntry 35641 }


	iqdbe02LoggingAESInputLoggingAESInput2type OBJECT-TYPE
		SYNTAX		RollCallString
		MAX-ACCESS		read-only
		STATUS			current
		DESCRIPTION
				"TYPE: - Display
				 PAGE: - RollCall- Logging
					AES Input 2 type=  cmdID= 36641  format=   "
		::= { iqdbe02CmdEntry 36641 }


	iqdbe02LoggingAESInputLoggingLogAESInput3typ OBJECT-TYPE
		SYNTAX		INTEGER { disable(0), enable(1) }
		MAX-ACCESS		read-write
		STATUS			current
		DESCRIPTION
				"TYPE: - Checkbox
				 PAGE: - RollCall- Logging
					Log AES Input 3 typ  cmdID= 35642 "
		::= { iqdbe02CmdEntry 35642 }


	iqdbe02LoggingAESInputLoggingAESInput3type OBJECT-TYPE
		SYNTAX		RollCallString
		MAX-ACCESS		read-only
		STATUS			current
		DESCRIPTION
				"TYPE: - Display
				 PAGE: - RollCall- Logging
					AES Input 3 type=  cmdID= 36642  format=   "
		::= { iqdbe02CmdEntry 36642 }


	iqdbe02LoggingAESInputLoggingLogAESInput4typ OBJECT-TYPE
		SYNTAX		INTEGER { disable(0), enable(1) }
		MAX-ACCESS		read-write
		STATUS			current
		DESCRIPTION
				"TYPE: - Checkbox
				 PAGE: - RollCall- Logging
					Log AES Input 4 typ  cmdID= 35643 "
		::= { iqdbe02CmdEntry 35643 }


	iqdbe02LoggingAESInputLoggingAESInput4type OBJECT-TYPE
		SYNTAX		RollCallString
		MAX-ACCESS		read-only
		STATUS			current
		DESCRIPTION
				"TYPE: - Display
				 PAGE: - RollCall- Logging
					AES Input 4 type=  cmdID= 36643  format=   "
		::= { iqdbe02CmdEntry 36643 }


	iqdbe02LoggingAESInputLoggingLogAESInput5typ OBJECT-TYPE
		SYNTAX		INTEGER { disable(0), enable(1) }
		MAX-ACCESS		read-write
		STATUS			current
		DESCRIPTION
				"TYPE: - Checkbox
				 PAGE: - RollCall- Logging
					Log AES Input 5 typ  cmdID= 35644 "
		::= { iqdbe02CmdEntry 35644 }


	iqdbe02LoggingAESInputLoggingAESInput5type OBJECT-TYPE
		SYNTAX		RollCallString
		MAX-ACCESS		read-only
		STATUS			current
		DESCRIPTION
				"TYPE: - Display
				 PAGE: - RollCall- Logging
					AES Input 5 type=  cmdID= 36644  format=   "
		::= { iqdbe02CmdEntry 36644 }


	iqdbe02LoggingAESInputLoggingLogAESInput6typ OBJECT-TYPE
		SYNTAX		INTEGER { disable(0), enable(1) }
		MAX-ACCESS		read-write
		STATUS			current
		DESCRIPTION
				"TYPE: - Checkbox
				 PAGE: - RollCall- Logging
					Log AES Input 6 typ  cmdID= 35645 "
		::= { iqdbe02CmdEntry 35645 }


	iqdbe02LoggingAESInputLoggingAESInput6type OBJECT-TYPE
		SYNTAX		RollCallString
		MAX-ACCESS		read-only
		STATUS			current
		DESCRIPTION
				"TYPE: - Display
				 PAGE: - RollCall- Logging
					AES Input 6 type=  cmdID= 36645  format=   "
		::= { iqdbe02CmdEntry 36645 }


	iqdbe02LoggingAESInputLoggingLogAESInput7typ OBJECT-TYPE
		SYNTAX		INTEGER { disable(0), enable(1) }
		MAX-ACCESS		read-write
		STATUS			current
		DESCRIPTION
				"TYPE: - Checkbox
				 PAGE: - RollCall- Logging
					Log AES Input 7 typ  cmdID= 35646 "
		::= { iqdbe02CmdEntry 35646 }


	iqdbe02LoggingAESInputLoggingAESInput7type OBJECT-TYPE
		SYNTAX		RollCallString
		MAX-ACCESS		read-only
		STATUS			current
		DESCRIPTION
				"TYPE: - Display
				 PAGE: - RollCall- Logging
					AES Input 7 type=  cmdID= 36646  format=   "
		::= { iqdbe02CmdEntry 36646 }


	iqdbe02LoggingAESInputLoggingLogAESInput8typ OBJECT-TYPE
		SYNTAX		INTEGER { disable(0), enable(1) }
		MAX-ACCESS		read-write
		STATUS			current
		DESCRIPTION
				"TYPE: - Checkbox
				 PAGE: - RollCall- Logging
					Log AES Input 8 typ  cmdID= 35647 "
		::= { iqdbe02CmdEntry 35647 }


	iqdbe02LoggingAESInputLoggingAESInput8type OBJECT-TYPE
		SYNTAX		RollCallString
		MAX-ACCESS		read-only
		STATUS			current
		DESCRIPTION
				"TYPE: - Display
				 PAGE: - RollCall- Logging
					AES Input 8 type=  cmdID= 36647  format=   "
		::= { iqdbe02CmdEntry 36647 }


	iqdbe02LoggingAESOutputLoggingLogAESOutput1st OBJECT-TYPE
		SYNTAX		INTEGER { disable(0), enable(1) }
		MAX-ACCESS		read-write
		STATUS			current
		DESCRIPTION
				"TYPE: - Checkbox
				 PAGE: - RollCall- Logging
					Log AES Output 1 st  cmdID= 35620 "
		::= { iqdbe02CmdEntry 35620 }


	iqdbe02LoggingAESOutputLoggingAESOutput1state OBJECT-TYPE
		SYNTAX		RollCallString
		MAX-ACCESS		read-only
		STATUS			current
		DESCRIPTION
				"TYPE: - Display
				 PAGE: - RollCall- Logging
					AES Output 1 state=  cmdID= 36620  format=   "
		::= { iqdbe02CmdEntry 36620 }


	iqdbe02LoggingAESOutputLoggingLogAESOutput2st OBJECT-TYPE
		SYNTAX		INTEGER { disable(0), enable(1) }
		MAX-ACCESS		read-write
		STATUS			current
		DESCRIPTION
				"TYPE: - Checkbox
				 PAGE: - RollCall- Logging
					Log AES Output 2 st  cmdID= 35621 "
		::= { iqdbe02CmdEntry 35621 }


	iqdbe02LoggingAESOutputLoggingAESOutput2state OBJECT-TYPE
		SYNTAX		RollCallString
		MAX-ACCESS		read-only
		STATUS			current
		DESCRIPTION
				"TYPE: - Display
				 PAGE: - RollCall- Logging
					AES Output 2 state=  cmdID= 36621  format=   "
		::= { iqdbe02CmdEntry 36621 }


	iqdbe02LoggingAESOutputLoggingLogAESOutput3st OBJECT-TYPE
		SYNTAX		INTEGER { disable(0), enable(1) }
		MAX-ACCESS		read-write
		STATUS			current
		DESCRIPTION
				"TYPE: - Checkbox
				 PAGE: - RollCall- Logging
					Log AES Output 3 st  cmdID= 35622 "
		::= { iqdbe02CmdEntry 35622 }


	iqdbe02LoggingAESOutputLoggingAESOutput3state OBJECT-TYPE
		SYNTAX		RollCallString
		MAX-ACCESS		read-only
		STATUS			current
		DESCRIPTION
				"TYPE: - Display
				 PAGE: - RollCall- Logging
					AES Output 3 state=  cmdID= 36622  format=   "
		::= { iqdbe02CmdEntry 36622 }


	iqdbe02LoggingAESOutputLoggingLogAESOutput4st OBJECT-TYPE
		SYNTAX		INTEGER { disable(0), enable(1) }
		MAX-ACCESS		read-write
		STATUS			current
		DESCRIPTION
				"TYPE: - Checkbox
				 PAGE: - RollCall- Logging
					Log AES Output 4 st  cmdID= 35623 "
		::= { iqdbe02CmdEntry 35623 }


	iqdbe02LoggingAESOutputLoggingAESOutput4state OBJECT-TYPE
		SYNTAX		RollCallString
		MAX-ACCESS		read-only
		STATUS			current
		DESCRIPTION
				"TYPE: - Display
				 PAGE: - RollCall- Logging
					AES Output 4 state=  cmdID= 36623  format=   "
		::= { iqdbe02CmdEntry 36623 }


	iqdbe02LoggingAESOutputLoggingLogAESOutput5st OBJECT-TYPE
		SYNTAX		INTEGER { disable(0), enable(1) }
		MAX-ACCESS		read-write
		STATUS			current
		DESCRIPTION
				"TYPE: - Checkbox
				 PAGE: - RollCall- Logging
					Log AES Output 5 st  cmdID= 35624 "
		::= { iqdbe02CmdEntry 35624 }


	iqdbe02LoggingAESOutputLoggingAESOutput5state OBJECT-TYPE
		SYNTAX		RollCallString
		MAX-ACCESS		read-only
		STATUS			current
		DESCRIPTION
				"TYPE: - Display
				 PAGE: - RollCall- Logging
					AES Output 5 state=  cmdID= 36624  format=   "
		::= { iqdbe02CmdEntry 36624 }


	iqdbe02LoggingAESOutputLoggingLogAESOutput6st OBJECT-TYPE
		SYNTAX		INTEGER { disable(0), enable(1) }
		MAX-ACCESS		read-write
		STATUS			current
		DESCRIPTION
				"TYPE: - Checkbox
				 PAGE: - RollCall- Logging
					Log AES Output 6 st  cmdID= 35625 "
		::= { iqdbe02CmdEntry 35625 }


	iqdbe02LoggingAESOutputLoggingAESOutput6state OBJECT-TYPE
		SYNTAX		RollCallString
		MAX-ACCESS		read-only
		STATUS			current
		DESCRIPTION
				"TYPE: - Display
				 PAGE: - RollCall- Logging
					AES Output 6 state=  cmdID= 36625  format=   "
		::= { iqdbe02CmdEntry 36625 }


	iqdbe02LoggingAESOutputLoggingLogAESOutput7st OBJECT-TYPE
		SYNTAX		INTEGER { disable(0), enable(1) }
		MAX-ACCESS		read-write
		STATUS			current
		DESCRIPTION
				"TYPE: - Checkbox
				 PAGE: - RollCall- Logging
					Log AES Output 7 st  cmdID= 35626 "
		::= { iqdbe02CmdEntry 35626 }


	iqdbe02LoggingAESOutputLoggingAESOutput7state OBJECT-TYPE
		SYNTAX		RollCallString
		MAX-ACCESS		read-only
		STATUS			current
		DESCRIPTION
				"TYPE: - Display
				 PAGE: - RollCall- Logging
					AES Output 7 state=  cmdID= 36626  format=   "
		::= { iqdbe02CmdEntry 36626 }


	iqdbe02LoggingAESOutputLoggingLogAESOutput8st OBJECT-TYPE
		SYNTAX		INTEGER { disable(0), enable(1) }
		MAX-ACCESS		read-write
		STATUS			current
		DESCRIPTION
				"TYPE: - Checkbox
				 PAGE: - RollCall- Logging
					Log AES Output 8 st  cmdID= 35627 "
		::= { iqdbe02CmdEntry 35627 }


	iqdbe02LoggingAESOutputLoggingAESOutput8state OBJECT-TYPE
		SYNTAX		RollCallString
		MAX-ACCESS		read-only
		STATUS			current
		DESCRIPTION
				"TYPE: - Display
				 PAGE: - RollCall- Logging
					AES Output 8 state=  cmdID= 36627  format=   "
		::= { iqdbe02CmdEntry 36627 }


	iqdbe02LoggingAESOutputLoggingLogAESOutput1ty OBJECT-TYPE
		SYNTAX		INTEGER { disable(0), enable(1) }
		MAX-ACCESS		read-write
		STATUS			current
		DESCRIPTION
				"TYPE: - Checkbox
				 PAGE: - RollCall- Logging
					Log AES Output 1 ty  cmdID= 35660 "
		::= { iqdbe02CmdEntry 35660 }


	iqdbe02LoggingAESOutputLoggingAESOutput1type OBJECT-TYPE
		SYNTAX		RollCallString
		MAX-ACCESS		read-only
		STATUS			current
		DESCRIPTION
				"TYPE: - Display
				 PAGE: - RollCall- Logging
					AES Output 1 type=  cmdID= 36660  format=   "
		::= { iqdbe02CmdEntry 36660 }


	iqdbe02LoggingAESOutputLoggingLogAESOutput2ty OBJECT-TYPE
		SYNTAX		INTEGER { disable(0), enable(1) }
		MAX-ACCESS		read-write
		STATUS			current
		DESCRIPTION
				"TYPE: - Checkbox
				 PAGE: - RollCall- Logging
					Log AES Output 2 ty  cmdID= 35661 "
		::= { iqdbe02CmdEntry 35661 }


	iqdbe02LoggingAESOutputLoggingAESOutput2type OBJECT-TYPE
		SYNTAX		RollCallString
		MAX-ACCESS		read-only
		STATUS			current
		DESCRIPTION
				"TYPE: - Display
				 PAGE: - RollCall- Logging
					AES Output 2 type=  cmdID= 36661  format=   "
		::= { iqdbe02CmdEntry 36661 }


	iqdbe02LoggingAESOutputLoggingLogAESOutput3ty OBJECT-TYPE
		SYNTAX		INTEGER { disable(0), enable(1) }
		MAX-ACCESS		read-write
		STATUS			current
		DESCRIPTION
				"TYPE: - Checkbox
				 PAGE: - RollCall- Logging
					Log AES Output 3 ty  cmdID= 35662 "
		::= { iqdbe02CmdEntry 35662 }


	iqdbe02LoggingAESOutputLoggingAESOutput3type OBJECT-TYPE
		SYNTAX		RollCallString
		MAX-ACCESS		read-only
		STATUS			current
		DESCRIPTION
				"TYPE: - Display
				 PAGE: - RollCall- Logging
					AES Output 3 type=  cmdID= 36662  format=   "
		::= { iqdbe02CmdEntry 36662 }


	iqdbe02LoggingAESOutputLoggingLogAESOutput4ty OBJECT-TYPE
		SYNTAX		INTEGER { disable(0), enable(1) }
		MAX-ACCESS		read-write
		STATUS			current
		DESCRIPTION
				"TYPE: - Checkbox
				 PAGE: - RollCall- Logging
					Log AES Output 4 ty  cmdID= 35663 "
		::= { iqdbe02CmdEntry 35663 }


	iqdbe02LoggingAESOutputLoggingAESOutput4type OBJECT-TYPE
		SYNTAX		RollCallString
		MAX-ACCESS		read-only
		STATUS			current
		DESCRIPTION
				"TYPE: - Display
				 PAGE: - RollCall- Logging
					AES Output 4 type=  cmdID= 36663  format=   "
		::= { iqdbe02CmdEntry 36663 }


	iqdbe02LoggingAESOutputLoggingLogAESOutput5ty OBJECT-TYPE
		SYNTAX		INTEGER { disable(0), enable(1) }
		MAX-ACCESS		read-write
		STATUS			current
		DESCRIPTION
				"TYPE: - Checkbox
				 PAGE: - RollCall- Logging
					Log AES Output 5 ty  cmdID= 35664 "
		::= { iqdbe02CmdEntry 35664 }


	iqdbe02LoggingAESOutputLoggingAESOutput5type OBJECT-TYPE
		SYNTAX		RollCallString
		MAX-ACCESS		read-only
		STATUS			current
		DESCRIPTION
				"TYPE: - Display
				 PAGE: - RollCall- Logging
					AES Output 5 type=  cmdID= 36664  format=   "
		::= { iqdbe02CmdEntry 36664 }


	iqdbe02LoggingAESOutputLoggingLogAESOutput6ty OBJECT-TYPE
		SYNTAX		INTEGER { disable(0), enable(1) }
		MAX-ACCESS		read-write
		STATUS			current
		DESCRIPTION
				"TYPE: - Checkbox
				 PAGE: - RollCall- Logging
					Log AES Output 6 ty  cmdID= 35665 "
		::= { iqdbe02CmdEntry 35665 }


	iqdbe02LoggingAESOutputLoggingAESOutput6type OBJECT-TYPE
		SYNTAX		RollCallString
		MAX-ACCESS		read-only
		STATUS			current
		DESCRIPTION
				"TYPE: - Display
				 PAGE: - RollCall- Logging
					AES Output 6 type=  cmdID= 36665  format=   "
		::= { iqdbe02CmdEntry 36665 }


	iqdbe02LoggingAESOutputLoggingLogAESOutput7ty OBJECT-TYPE
		SYNTAX		INTEGER { disable(0), enable(1) }
		MAX-ACCESS		read-write
		STATUS			current
		DESCRIPTION
				"TYPE: - Checkbox
				 PAGE: - RollCall- Logging
					Log AES Output 7 ty  cmdID= 35666 "
		::= { iqdbe02CmdEntry 35666 }


	iqdbe02LoggingAESOutputLoggingAESOutput7type OBJECT-TYPE
		SYNTAX		RollCallString
		MAX-ACCESS		read-only
		STATUS			current
		DESCRIPTION
				"TYPE: - Display
				 PAGE: - RollCall- Logging
					AES Output 7 type=  cmdID= 36666  format=   "
		::= { iqdbe02CmdEntry 36666 }


	iqdbe02LoggingAESOutputLoggingLogAESOutput8ty OBJECT-TYPE
		SYNTAX		INTEGER { disable(0), enable(1) }
		MAX-ACCESS		read-write
		STATUS			current
		DESCRIPTION
				"TYPE: - Checkbox
				 PAGE: - RollCall- Logging
					Log AES Output 8 ty  cmdID= 35667 "
		::= { iqdbe02CmdEntry 35667 }


	iqdbe02LoggingAESOutputLoggingAESOutput8type OBJECT-TYPE
		SYNTAX		RollCallString
		MAX-ACCESS		read-only
		STATUS			current
		DESCRIPTION
				"TYPE: - Display
				 PAGE: - RollCall- Logging
					AES Output 8 type=  cmdID= 36667  format=   "
		::= { iqdbe02CmdEntry 36667 }


	iqdbe02LoggingDolbyEncoderLogChannelMode OBJECT-TYPE
		SYNTAX		INTEGER { disable(0), enable(1) }
		MAX-ACCESS		read-write
		STATUS			current
		DESCRIPTION
				"TYPE: - Checkbox
				 PAGE: - RollCall- Logging- Dolby Encoder
					Log Channel Mode  cmdID= 35810 "
		::= { iqdbe02CmdEntry 35810 }


	iqdbe02LoggingDolbyEncoderChannelMode OBJECT-TYPE
		SYNTAX		RollCallString
		MAX-ACCESS		read-only
		STATUS			current
		DESCRIPTION
				"TYPE: - Display
				 PAGE: - RollCall- Logging- Dolby Encoder
					Channel Mode=  cmdID= 36810  format=   "
		::= { iqdbe02CmdEntry 36810 }


	iqdbe02LoggingDolbyEncoderLogSource OBJECT-TYPE
		SYNTAX		INTEGER { disable(0), enable(1) }
		MAX-ACCESS		read-write
		STATUS			current
		DESCRIPTION
				"TYPE: - Checkbox
				 PAGE: - RollCall- Logging- Dolby Encoder
					Log Source  cmdID= 35801 "
		::= { iqdbe02CmdEntry 35801 }


	iqdbe02LoggingDolbyEncoderSource OBJECT-TYPE
		SYNTAX		RollCallString
		MAX-ACCESS		read-only
		STATUS			current
		DESCRIPTION
				"TYPE: - Display
				 PAGE: - RollCall- Logging- Dolby Encoder
					Source=  cmdID= 36801  format=   "
		::= { iqdbe02CmdEntry 36801 }


	iqdbe02LoggingDolbyEncoderLogStatus OBJECT-TYPE
		SYNTAX		INTEGER { disable(0), enable(1) }
		MAX-ACCESS		read-write
		STATUS			current
		DESCRIPTION
				"TYPE: - Checkbox
				 PAGE: - RollCall- Logging- Dolby Encoder
					Log Status  cmdID= 35802 "
		::= { iqdbe02CmdEntry 35802 }


	iqdbe02LoggingDolbyEncoderStatus OBJECT-TYPE
		SYNTAX		RollCallString
		MAX-ACCESS		read-only
		STATUS			current
		DESCRIPTION
				"TYPE: - Display
				 PAGE: - RollCall- Logging- Dolby Encoder
					Status=  cmdID= 36802  format=   "
		::= { iqdbe02CmdEntry 36802 }


	iqdbe02LoggingDolbyEncoderLogAC3 OBJECT-TYPE
		SYNTAX		INTEGER { disable(0), enable(1) }
		MAX-ACCESS		read-write
		STATUS			current
		DESCRIPTION
				"TYPE: - Checkbox
				 PAGE: - RollCall- Logging- Dolby Encoder
					Log AC_3  cmdID= 35803 "
		::= { iqdbe02CmdEntry 35803 }


	iqdbe02LoggingDolbyEncoderAC3 OBJECT-TYPE
		SYNTAX		RollCallString
		MAX-ACCESS		read-only
		STATUS			current
		DESCRIPTION
				"TYPE: - Display
				 PAGE: - RollCall- Logging- Dolby Encoder
					AC_3=  cmdID= 36803  format=   "
		::= { iqdbe02CmdEntry 36803 }


	iqdbe02LoggingDolbyEncoderLogExBSI OBJECT-TYPE
		SYNTAX		INTEGER { disable(0), enable(1) }
		MAX-ACCESS		read-write
		STATUS			current
		DESCRIPTION
				"TYPE: - Checkbox
				 PAGE: - RollCall- Logging- Dolby Encoder
					Log Ex BSI  cmdID= 35804 "
		::= { iqdbe02CmdEntry 35804 }


	iqdbe02LoggingDolbyEncoderExBSI OBJECT-TYPE
		SYNTAX		RollCallString
		MAX-ACCESS		read-only
		STATUS			current
		DESCRIPTION
				"TYPE: - Display
				 PAGE: - RollCall- Logging- Dolby Encoder
					Ex BSI=  cmdID= 36804  format=   "
		::= { iqdbe02CmdEntry 36804 }


	iqdbe02LoggingDolbyEncoderLogDataRate OBJECT-TYPE
		SYNTAX		INTEGER { disable(0), enable(1) }
		MAX-ACCESS		read-write
		STATUS			current
		DESCRIPTION
				"TYPE: - Checkbox
				 PAGE: - RollCall- Logging- Dolby Encoder
					Log Data Rate  cmdID= 35811 "
		::= { iqdbe02CmdEntry 35811 }


	iqdbe02LoggingDolbyEncoderDataRate OBJECT-TYPE
		SYNTAX		RollCallString
		MAX-ACCESS		read-only
		STATUS			current
		DESCRIPTION
				"TYPE: - Display
				 PAGE: - RollCall- Logging- Dolby Encoder
					Data Rate=  cmdID= 36811  format=   "
		::= { iqdbe02CmdEntry 36811 }


	iqdbe02LoggingMiscLoggingLogSerialNo OBJECT-TYPE
		SYNTAX		INTEGER { disable(0), enable(1) }
		MAX-ACCESS		read-write
		STATUS			current
		DESCRIPTION
				"TYPE: - Checkbox
				 PAGE: - RollCall- Logging
					Log Serial No.  cmdID= 35015 "
		::= { iqdbe02CmdEntry 35015 }


	iqdbe02LoggingMiscLoggingSerialNo OBJECT-TYPE
		SYNTAX		RollCallString
		MAX-ACCESS		read-only
		STATUS			current
		DESCRIPTION
				"TYPE: - Display
				 PAGE: - RollCall- Logging
					Serial No.=  cmdID= 36015  format=   "
		::= { iqdbe02CmdEntry 36015 }


	iqdbe02LoggingMiscLoggingLogOSVersion OBJECT-TYPE
		SYNTAX		INTEGER { disable(0), enable(1) }
		MAX-ACCESS		read-write
		STATUS			current
		DESCRIPTION
				"TYPE: - Checkbox
				 PAGE: - RollCall- Logging
					Log OS Version  cmdID= 35993 "
		::= { iqdbe02CmdEntry 35993 }


	iqdbe02LoggingMiscLoggingOSVersion OBJECT-TYPE
		SYNTAX		RollCallString
		MAX-ACCESS		read-only
		STATUS			current
		DESCRIPTION
				"TYPE: - Display
				 PAGE: - RollCall- Logging
					OS Version=  cmdID= 36993  format=   "
		::= { iqdbe02CmdEntry 36993 }


	iqdbe02LoggingMiscLoggingLogBuildNo OBJECT-TYPE
		SYNTAX		INTEGER { disable(0), enable(1) }
		MAX-ACCESS		read-write
		STATUS			current
		DESCRIPTION
				"TYPE: - Checkbox
				 PAGE: - RollCall- Logging
					Log Build No.  cmdID= 35990 "
		::= { iqdbe02CmdEntry 35990 }


	iqdbe02LoggingMiscLoggingBuildNo OBJECT-TYPE
		SYNTAX		RollCallString
		MAX-ACCESS		read-only
		STATUS			current
		DESCRIPTION
				"TYPE: - Display
				 PAGE: - RollCall- Logging
					Build No.=  cmdID= 36990  format=   "
		::= { iqdbe02CmdEntry 36990 }


	iqdbe02LoggingMiscLoggingLogHardwareVer OBJECT-TYPE
		SYNTAX		INTEGER { disable(0), enable(1) }
		MAX-ACCESS		read-write
		STATUS			current
		DESCRIPTION
				"TYPE: - Checkbox
				 PAGE: - RollCall- Logging
					Log Hardware Ver.  cmdID= 35992 "
		::= { iqdbe02CmdEntry 35992 }


	iqdbe02LoggingMiscLoggingHardwareVer OBJECT-TYPE
		SYNTAX		RollCallString
		MAX-ACCESS		read-only
		STATUS			current
		DESCRIPTION
				"TYPE: - Display
				 PAGE: - RollCall- Logging
					Hardware Ver.=  cmdID= 36992  format=   "
		::= { iqdbe02CmdEntry 36992 }


	iqdbe02LoggingMiscLoggingLogFirmwareVer OBJECT-TYPE
		SYNTAX		INTEGER { disable(0), enable(1) }
		MAX-ACCESS		read-write
		STATUS			current
		DESCRIPTION
				"TYPE: - Checkbox
				 PAGE: - RollCall- Logging
					Log Firmware Ver.  cmdID= 35991 "
		::= { iqdbe02CmdEntry 35991 }


	iqdbe02LoggingMiscLoggingFirmwareVer OBJECT-TYPE
		SYNTAX		RollCallString
		MAX-ACCESS		read-only
		STATUS			current
		DESCRIPTION
				"TYPE: - Display
				 PAGE: - RollCall- Logging
					Firmware Ver.=  cmdID= 36991  format=   "
		::= { iqdbe02CmdEntry 36991 }


	iqdbe02LoggingMiscLoggingLogUpTime OBJECT-TYPE
		SYNTAX		INTEGER { disable(0), enable(1) }
		MAX-ACCESS		read-write
		STATUS			current
		DESCRIPTION
				"TYPE: - Checkbox
				 PAGE: - RollCall- Logging
					Log Up Time  cmdID= 35994 "
		::= { iqdbe02CmdEntry 35994 }


	iqdbe02LoggingMiscLoggingUpTime OBJECT-TYPE
		SYNTAX		RollCallString
		MAX-ACCESS		read-only
		STATUS			current
		DESCRIPTION
				"TYPE: - Display
				 PAGE: - RollCall- Logging
					Up Time=  cmdID= 36994  format=   "
		::= { iqdbe02CmdEntry 36994 }


	iqdbe02RollCallRollTrackDisableAll OBJECT-TYPE
		SYNTAX		INTEGER { disable(0), enable(1) }
		MAX-ACCESS		read-write
		STATUS			current
		DESCRIPTION
				"TYPE: - Checkbox
				 PAGE: - RollCall
					Disable All  cmdID= 36104 "
		::= { iqdbe02CmdEntry 36104 }


	iqdbe02RollCallRollTrackIndex OBJECT-TYPE
		SYNTAX		INTEGER
		MAX-ACCESS		read-write
		STATUS			current
		DESCRIPTION
				"TYPE: - BarGraph
				 PAGE: - RollCall
					Index  cmdID= 36100  min= 1  max= 16   step= 1  format= %0.0f  div_scale= 1
					Min = 1  Max = 16  Step = 1 "
		::= { iqdbe02CmdEntry 36100 }


	iqdbe02RollCallRollTrackSource OBJECT-TYPE
		SYNTAX		INTEGER {
							val_Unused(-1),
							val_Video_Delay(0),
							val_Input_Present(1),
							val_Input_Loss(2),
							val_O_p_Freeze(3),
							val_O_p_UnFreeze(4),
							val_Output_1080(53),
							val_Output_720(54),
							val_Output_576_625(55),
							val_Output_480_525(56),
							val_Disembed_1_Data(5),
							val_Disembed_1_Pcm(6),
							val_Disembed_1_Lost(7),
							val_Disembed_2_Data(8),
							val_Disembed_2_Pcm(9),
							val_Disembed_2_Lost(10),
							val_Disembed_3_Data(11),
							val_Disembed_3_Pcm(12),
							val_Disembed_3_Lost(13),
							val_Disembed_4_Data(14),
							val_Disembed_4_Pcm(15),
							val_Disembed_4_Lost(16),
							val_Disembed_5_Data(17),
							val_Disembed_5_Pcm(18),
							val_Disembed_5_Lost(19),
							val_Disembed_6_Data(20),
							val_Disembed_6_Pcm(21),
							val_Disembed_6_Lost(22),
							val_Disembed_7_Data(23),
							val_Disembed_7_Pcm(24),
							val_Disembed_7_Lost(25),
							val_Disembed_8_Data(26),
							val_Disembed_8_Pcm(27),
							val_Disembed_8_Lost(28),
							val_AES_1_Data(29),
							val_AES_1_Pcm(30),
							val_AES_1_Lost(31),
							val_AES_2_Data(32),
							val_AES_2_Pcm(33),
							val_AES_2_Lost(34),
							val_AES_3_Data(35),
							val_AES_3_Pcm(36),
							val_AES_3_Lost(37),
							val_AES_4_Data(38),
							val_AES_4_Pcm(39),
							val_AES_4_Lost(40),
							val_AES_5_Data(41),
							val_AES_5_Pcm(42),
							val_AES_5_Lost(43),
							val_AES_6_Data(44),
							val_AES_6_Pcm(45),
							val_AES_6_Lost(46),
							val_AES_7_Data(47),
							val_AES_7_Pcm(48),
							val_AES_7_Lost(49)
							}
		MAX-ACCESS		read-write
		STATUS			current
		DESCRIPTION
				"TYPE: - RadiobuttonList
				 PAGE: - RollCall
					Source  cmdID= 36101
					Unused  value= -1
					Video Delay  value= 0
					Input Present  value= 1
					Input Loss  value= 2
					O/p Freeze  value= 3
					O/p UnFreeze  value= 4
					Output:1080  value= 53
					Output:720  value= 54
					Output:576(625)  value= 55
					Output:480(525)  value= 56
					Disembed 1 Data  value= 5
					Disembed 1 Pcm  value= 6
					Disembed 1 Lost  value= 7
					Disembed 2 Data  value= 8
					Disembed 2 Pcm  value= 9
					Disembed 2 Lost  value= 10
					Disembed 3 Data  value= 11
					Disembed 3 Pcm  value= 12
					Disembed 3 Lost  value= 13
					Disembed 4 Data  value= 14
					Disembed 4 Pcm  value= 15
					Disembed 4 Lost  value= 16
					Disembed 5 Data  value= 17
					Disembed 5 Pcm  value= 18
					Disembed 5 Lost  value= 19
					Disembed 6 Data  value= 20
					Disembed 6 Pcm  value= 21
					Disembed 6 Lost  value= 22
					Disembed 7 Data  value= 23
					Disembed 7 Pcm  value= 24
					Disembed 7 Lost  value= 25
					Disembed 8 Data  value= 26
					Disembed 8 Pcm  value= 27
					Disembed 8 Lost  value= 28
					AES 1 Data  value= 29
					AES 1 Pcm  value= 30
					AES 1 Lost  value= 31
					AES 2 Data  value= 32
					AES 2 Pcm  value= 33
					AES 2 Lost  value= 34
					AES 3 Data  value= 35
					AES 3 Pcm  value= 36
					AES 3 Lost  value= 37
					AES 4 Data  value= 38
					AES 4 Pcm  value= 39
					AES 4 Lost  value= 40
					AES 5 Data  value= 41
					AES 5 Pcm  value= 42
					AES 5 Lost  value= 43
					AES 6 Data  value= 44
					AES 6 Pcm  value= 45
					AES 6 Lost  value= 46
					AES 7 Data  value= 47
					AES 7 Pcm  value= 48
					AES 7 Lost  value= 49  "
		::= { iqdbe02CmdEntry 36101 }


	iqdbe02RollCallRollTrackAddress OBJECT-TYPE
		SYNTAX		RollCallString
		MAX-ACCESS		read-write
		STATUS			current
		DESCRIPTION
				"TYPE: - Editstring
				 PAGE: - RollCall
					Address  cmdID= 36102  "
		::= { iqdbe02CmdEntry 36102 }


	iqdbe02RollCallRollTrackCommand OBJECT-TYPE
		SYNTAX		RollCallString
		MAX-ACCESS		read-write
		STATUS			current
		DESCRIPTION
				"TYPE: - Editstring
				 PAGE: - RollCall
					Command  cmdID= 36103  "
		::= { iqdbe02CmdEntry 36103 }


	iqdbe02RollCallRollTrackStatus OBJECT-TYPE
		SYNTAX		RollCallString
		MAX-ACCESS		read-only
		STATUS			current
		DESCRIPTION
				"TYPE: - Display
				 PAGE: - RollCall
					Status  cmdID= 36105  format=   "
		::= { iqdbe02CmdEntry 36105 }


	iqdbe02RollCallRollTrackSending OBJECT-TYPE
		SYNTAX		RollCallString
		MAX-ACCESS		read-only
		STATUS			current
		DESCRIPTION
				"TYPE: - Display
				 PAGE: - RollCall
					Sending  cmdID= 36106  format=   "
		::= { iqdbe02CmdEntry 36106 }


	iqdbe02AudioSetupUnitStatusDisplay OBJECT-TYPE
		SYNTAX		INTEGER {
							val_Video_Status(0),
							val_Audio_Status(1),
							val_Dolby_Enc_Status(2),
							val_Dolby_Enc_Metadata(3)
							}
		MAX-ACCESS		read-write
		STATUS			current
		DESCRIPTION
				"TYPE: - RadiobuttonList
					Unit Status Display  cmdID= 32773
					Video Status  value= 0
					Audio Status  value= 1
					Dolby Enc Status  value= 2
					Dolby Enc Metadata  value= 3  "
		::= { iqdbe02CmdEntry 32773 }


	iqdbe02AudioSetupProduct OBJECT-TYPE
		SYNTAX		RollCallString
		MAX-ACCESS		read-only
		STATUS			current
		DESCRIPTION
				"TYPE: - Display
					Product  cmdID= 32771  format=   "
		::= { iqdbe02CmdEntry 32771 }


	iqdbe02AudioSetupRelease OBJECT-TYPE
		SYNTAX		RollCallString
		MAX-ACCESS		read-only
		STATUS			current
		DESCRIPTION
				"TYPE: - Display
					Release  cmdID= 2  format=   "
		::= { iqdbe02CmdEntry 2 }


	iqdbe02AudioSetupBuild OBJECT-TYPE
		SYNTAX		RollCallString
		MAX-ACCESS		read-only
		STATUS			current
		DESCRIPTION
				"TYPE: - Display
					Build  cmdID= 5  format=   "
		::= { iqdbe02CmdEntry 5 }


	iqdbe02AudioSetupKOS OBJECT-TYPE
		SYNTAX		RollCallString
		MAX-ACCESS		read-only
		STATUS			current
		DESCRIPTION
				"TYPE: - Display
					KOS  cmdID= 32772  format=   "
		::= { iqdbe02CmdEntry 32772 }


	iqdbe02AudioSetupSerialNo OBJECT-TYPE
		SYNTAX		RollCallString
		MAX-ACCESS		read-only
		STATUS			current
		DESCRIPTION
				"TYPE: - Display
					Serial No.  cmdID= 1  format=   "
		::= { iqdbe02CmdEntry 1 }


	iqdbe02AudioSetupFirmware OBJECT-TYPE
		SYNTAX		RollCallString
		MAX-ACCESS		read-only
		STATUS			current
		DESCRIPTION
				"TYPE: - Display
					Firmware  cmdID= 32769  format=   "
		::= { iqdbe02CmdEntry 32769 }


	iqdbe02AudioSetupPCB OBJECT-TYPE
		SYNTAX		RollCallString
		MAX-ACCESS		read-only
		STATUS			current
		DESCRIPTION
				"TYPE: - Display
					PCB  cmdID= 32770  format=   "
		::= { iqdbe02CmdEntry 32770 }


	iqdbe02AudioSetupFactoryDefault OBJECT-TYPE
		SYNTAX		INTEGER { noAction(0),val_Factory_Default(1) }
		MAX-ACCESS		read-write
		STATUS			current
		DESCRIPTION
				"TYPE: - Button
					Factory Default  cmdID= 37002  value= 1  "
		::= { iqdbe02CmdEntry 37002 }


	iqdbe02AudioSetupRestart OBJECT-TYPE
		SYNTAX		INTEGER { noAction(0),val_Restart(1) }
		MAX-ACCESS		read-write
		STATUS			current
		DESCRIPTION
				"TYPE: - Button
					Restart  cmdID= 4  value= 1  "
		::= { iqdbe02CmdEntry 4 }


	iqdbe02AudioSetupDefaultSettings OBJECT-TYPE
		SYNTAX		INTEGER { noAction(0),val_Default_Settings(1) }
		MAX-ACCESS		read-write
		STATUS			current
		DESCRIPTION
				"TYPE: - Button
					Default Settings  cmdID= 37001  value= 1  "
		::= { iqdbe02CmdEntry 37001 }


	iqdbe02AudioSetupSerialNumber OBJECT-TYPE
		SYNTAX		RollCallString
		MAX-ACCESS		read-write
		STATUS			current
		DESCRIPTION
				"TYPE: - Editstring
					Serial Number  cmdID= 32774  "
		::= { iqdbe02CmdEntry 32774 }


	iqdbe02AudioSetupBoardID OBJECT-TYPE
		SYNTAX		INTEGER {
							val_IQDBE02(564),
							val_IQDBE03(565)
							}
		MAX-ACCESS		read-write
		STATUS			current
		DESCRIPTION
				"TYPE: - RadiobuttonList
					BoardID  cmdID= 32776
					IQDBE02  value= 564
					IQDBE03  value= 565  "
		::= { iqdbe02CmdEntry 32776 }


	iqdbe02AudioSetupSaveID OBJECT-TYPE
		SYNTAX		INTEGER { noAction(0),val_Save_ID(1) }
		MAX-ACCESS		read-write
		STATUS			current
		DESCRIPTION
				"TYPE: - Button
					Save ID  cmdID= 32775  value= 1  "
		::= { iqdbe02CmdEntry 32775 }


	iqdbe02AudioEngineerEngineerPassword OBJECT-TYPE
		SYNTAX		RollCallString
		MAX-ACCESS		read-write
		STATUS			current
		DESCRIPTION
				"TYPE: - Editstring
				 PAGE: - Engineer
					Engineer Password  cmdID= 34011  "
		::= { iqdbe02CmdEntry 34011 }


	iqdbe02AudioEngineerShowEngineer OBJECT-TYPE
		SYNTAX		INTEGER { disable(0), enable(1) }
		MAX-ACCESS		read-write
		STATUS			current
		DESCRIPTION
				"TYPE: - Checkbox
				 PAGE: - Engineer
					Show Engineer  cmdID= 34012 "
		::= { iqdbe02CmdEntry 34012 }


	iqdbe02EngineerPageOptions1 OBJECT-TYPE
		SYNTAX		INTEGER { disable(0), enable(1) }
		MAX-ACCESS		read-write
		STATUS			current
		DESCRIPTION
				"TYPE: - Checkbox
				 PAGE: - Engineer
					$S1  cmdID= 34014 "
		::= { iqdbe02CmdEntry 34014 }


	iqdbe02EngineerPageOptions2 OBJECT-TYPE
		SYNTAX		INTEGER { disable(0), enable(1) }
		MAX-ACCESS		read-write
		STATUS			current
		DESCRIPTION
				"TYPE: - Checkbox
				 PAGE: - Engineer
					$S1  cmdID= 34015 "
		::= { iqdbe02CmdEntry 34015 }


	iqdbe02EngineerPageOptions3  OBJECT-TYPE
		SYNTAX		INTEGER { disable(0), enable(1) }
		MAX-ACCESS		read-write
		STATUS			current
		DESCRIPTION
				"TYPE: - Checkbox
				 PAGE: - Engineer
					$S1  cmdID= 34016 "
		::= { iqdbe02CmdEntry 34016 }


	iqdbe02EngineerEngineerPageUndoChanges OBJECT-TYPE
		SYNTAX		INTEGER { noAction(0),val_Undo_Changes(1) }
		MAX-ACCESS		read-write
		STATUS			current
		DESCRIPTION
				"TYPE: - Button
				 PAGE: - Engineer
					Undo Changes  cmdID= 34013  value= 1  "
		::= { iqdbe02CmdEntry 34013 }


	iqdbe02EngineerEngineerPageLineNumber OBJECT-TYPE
		SYNTAX		RollCallString
		MAX-ACCESS		read-only
		STATUS			current
		DESCRIPTION
				"TYPE: - Display
				 PAGE: - Engineer
					Line Number  cmdID= 38651  format=   "
		::= { iqdbe02CmdEntry 38651 }


	iqdbe02EngineerEngineerPageSampleNumber OBJECT-TYPE
		SYNTAX		RollCallString
		MAX-ACCESS		read-only
		STATUS			current
		DESCRIPTION
				"TYPE: - Display
				 PAGE: - Engineer
					Sample Number  cmdID= 38657  format=   "
		::= { iqdbe02CmdEntry 38657 }


	iqdbe02EngineerEngineerPageDolbyModuleUpdate OBJECT-TYPE
		SYNTAX		INTEGER {
							val_Disabled_Update(0),
							val_Enable_Ext_Ser_Upd(1),
							val_Start_Internal_Upd(2)
							}
		MAX-ACCESS		read-write
		STATUS			current
		DESCRIPTION
				"TYPE: - RadiobuttonList
				 PAGE: - Engineer
					Dolby Module Update  cmdID= 39998
					Disabled Update  value= 0
					Enable Ext Ser Upd  value= 1
					Start Internal Upd  value= 2  "
		::= { iqdbe02CmdEntry 39998 }


	iqdbe02EngineerPaAutoalignEmbeddedInputs OBJECT-TYPE
		SYNTAX		INTEGER { disable(0), enable(1) }
		MAX-ACCESS		read-write
		STATUS			current
		DESCRIPTION
				"TYPE: - Checkbox
				 PAGE: - Engineer
					Embedded Inputs  cmdID= 34060 "
		::= { iqdbe02CmdEntry 34060 }


	iqdbe02EngineerPaAutoalignAESInputs OBJECT-TYPE
		SYNTAX		INTEGER { disable(0), enable(1) }
		MAX-ACCESS		read-write
		STATUS			current
		DESCRIPTION
				"TYPE: - Checkbox
				 PAGE: - Engineer
					AES Inputs  cmdID= 34061 "
		::= { iqdbe02CmdEntry 34061 }


	iqdbe02MenuAudioShowEngineer2 OBJECT-TYPE
		SYNTAX		INTEGER { disable(0), enable(1) }
		MAX-ACCESS		read-write
		STATUS			current
		DESCRIPTION
				"TYPE: - Checkbox
					Show Engineer2  cmdID= 34050 "
		::= { iqdbe02CmdEntry 34050 }


	iqdbe02MenuAudioUseEmbDelayFbac OBJECT-TYPE
		SYNTAX		INTEGER { disable(0), enable(1) }
		MAX-ACCESS		read-write
		STATUS			current
		DESCRIPTION
				"TYPE: - Checkbox
					Use Emb Delay F/bac  cmdID= 34049 "
		::= { iqdbe02CmdEntry 34049 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S35034500
--				:
-- Comments		: Serial Number or module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:34:00
--				:
-- Comments		: Uptime in formated date-time string
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number or current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 2001420336
--				:
-- Comments		: String of current Software build number
--
---------------------------------------------------------------------------------------------------
-- Header		: INFORMATION1
--
-- MIB ref		: swCardEventLogSlotXX       .12.73.78.70.79.82.77.65.84.73.79.78.49
-- absolute OID	: 1.3.6.1.4.1.7995.2.6.1.1.XX.12.73.78.70.79.82.77.65.84.73.79.78.49
-- Vary			: YES
--
-- Value(s)		: D Encode Text A
--				:
-- Comments		: User configurable text string
--
---------------------------------------------------------------------------------------------------
-- Header		: INFORMATION2
--
-- MIB ref		: swCardEventLogSlotXX       .12.73.78.70.79.82.77.65.84.73.79.78.50
-- absolute OID	: 1.3.6.1.4.1.7995.2.6.1.1.XX.12.73.78.70.79.82.77.65.84.73.79.78.50
-- Vary			: YES
--
-- Value(s)		: D Encode Text B
--				:
-- Comments		: User configurable text string
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD / SD SDI
--				:
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2010-04-22T14:05:57Z
--				:
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				:
-- Comments		: Time String of last control modification
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: HD / SD SDI
--				:
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: BLACK
--				: PATTERN
--				: MONO
--				: FROZEN
--				: OK
--				: FAIL
-- Comments		:
--
---------------------------------------------------------------------------------------------------
-- Header		: AES_INPUT_1_TYPE
--
-- MIB ref		: swCardEventLogSlotXX       .16.65.69.83.95.73.78.80.85.84.95.49.95.84.89.80.69
-- absolute OID	: 1.3.6.1.4.1.7995.2.6.1.1.XX.16.65.69.83.95.73.78.80.85.84.95.49.95.84.89.80.69
-- Vary			: YES
--
-- Value(s)		: Unknown
--				: NONPCM
--              : PCM
--              : WARN: No Input
-- Comments		:
--
---------------------------------------------------------------------------------------------------
-- Header		: AES_INPUT_2_TYPE
--
-- MIB ref		: swCardEventLogSlotXX       .16.65.69.83.95.73.78.80.85.84.95.50.95.84.89.80.69
-- absolute OID	: 1.3.6.1.4.1.7995.2.6.1.1.XX.16.65.69.83.95.73.78.80.85.84.95.50.95.84.89.80.69
-- Vary			: YES
--
-- Value(s)		: Unknown
--				: NONPCM
--              : PCM
--              : WARN: No Input
-- Comments		:
--
---------------------------------------------------------------------------------------------------
-- Header		: AES_INPUT_3_TYPE
--
-- MIB ref		: swCardEventLogSlotXX       .16.65.69.83.95.73.78.80.85.84.95.51.95.84.89.80.69
-- absolute OID	: 1.3.6.1.4.1.7995.2.6.1.1.XX.16.65.69.83.95.73.78.80.85.84.95.51.95.84.89.80.69
-- Vary			: YES
--
-- Value(s)		: Unknown
--				: NONPCM
--              : PCM
--              : WARN: No Input
-- Comments		:
--
---------------------------------------------------------------------------------------------------
-- Header		: AES_INPUT_4_TYPE
--
-- MIB ref		: swCardEventLogSlotXX       .16.65.69.83.95.73.78.80.85.84.95.52.95.84.89.80.69
-- absolute OID	: 1.3.6.1.4.1.7995.2.6.1.1.XX.16.65.69.83.95.73.78.80.85.84.95.52.95.84.89.80.69
-- Vary			: YES
--
-- Value(s)		: Unknown
--				: NONPCM
--              : PCM
--              : WARN: No Input
-- Comments		:
--
---------------------------------------------------------------------------------------------------
-- Header		: AES_INPUT_5_TYPE
--
-- MIB ref		: swCardEventLogSlotXX       .16.65.69.83.95.73.78.80.85.84.95.53.95.84.89.80.69
-- absolute OID	: 1.3.6.1.4.1.7995.2.6.1.1.XX.16.65.69.83.95.73.78.80.85.84.95.53.95.84.89.80.69
-- Vary			: YES
--
-- Value(s)		: Unknown
--				: NONPCM
--              : PCM
--              : WARN: No Input
-- Comments		:
--
---------------------------------------------------------------------------------------------------
-- Header		: AES_INPUT_6_TYPE
--
-- MIB ref		: swCardEventLogSlotXX       .16.65.69.83.95.73.78.80.85.84.95.54.95.84.89.80.69
-- absolute OID	: 1.3.6.1.4.1.7995.2.6.1.1.XX.16.65.69.83.95.73.78.80.85.84.95.54.95.84.89.80.69
-- Vary			: YES
--
-- Value(s)		: Unknown
--				: NONPCM
--              : PCM
--              : WARN: No Input
-- Comments		:
--
---------------------------------------------------------------------------------------------------
-- Header		: AES_INPUT_7_TYPE
--
-- MIB ref		: swCardEventLogSlotXX       .16.65.69.83.95.73.78.80.85.84.95.55.95.84.89.80.69
-- absolute OID	: 1.3.6.1.4.1.7995.2.6.1.1.XX.16.65.69.83.95.73.78.80.85.84.95.55.95.84.89.80.69
-- Vary			: YES
--
-- Value(s)		: Unknown
--				: NONPCM
--              : PCM
--              : WARN: No Input
-- Comments		:
--
---------------------------------------------------------------------------------------------------
-- Header		: AES_INPUT_8_TYPE
--
-- MIB ref		: swCardEventLogSlotXX       .16.65.69.83.95.73.78.80.85.84.95.56.95.84.89.80.69
-- absolute OID	: 1.3.6.1.4.1.7995.2.6.1.1.XX.16.65.69.83.95.73.78.80.85.84.95.56.95.84.89.80.69
-- Vary			: YES
--
-- Value(s)		: Unknown
--				: NONPCM
--              : PCM
--              : WARN: No Input
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 2.158
--				:
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RDAUD1B.004
--				:
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: NONE
--              : WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
-- Vary			: YES
--
-- Value(s)		: LOST
--				: FAIL:Lost
--              : OK
--              : Unknown
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
-- Vary			: YES
--
-- Value(s)		: LOST
--				: FAIL:Lost
--              : OK
--              : Unknown
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
-- Vary			: YES
--
-- Value(s)		: LOST
--				: FAIL:Lost
--              : OK
--              : Unknown
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
-- Vary			: YES
--
-- Value(s)		: LOST
--				: FAIL:Lost
--              : OK
--              : Unknown
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
-- Vary			: YES
--
-- Value(s)		: LOST
--				: FAIL:Lost
--              : OK
--              : Unknown
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
-- Vary			: YES
--
-- Value(s)		: LOST
--				: FAIL:Lost
--              : OK
--              : Unknown
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
-- Vary			: YES
--
-- Value(s)		: LOST
--				: FAIL:Lost
--              : OK
--              : Unknown
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
-- Vary			: YES
--
-- Value(s)		: LOST
--				: FAIL:Lost
--              : OK
--              : Unknown
-- Comments		:
--
---------------------------------------------------------------------------------------------------
-- Header		: AES_OUTPUT_1_TYPE
--
-- MIB ref		: swCardEventLogSlotXX       .17.65.69.83.95.79.85.84.80.85.84.95.49.95.84.89.80.69
-- absolute OID	: 1.3.6.1.4.1.7995.2.6.1.1.XX.17.65.69.83.95.79.85.84.80.85.84.95.49.95.84.89.80.69
-- Vary			: YES
--
-- Value(s)		: Unknown
--				: PCM
--              : NONPCM
--              : WARN: No Input
-- Comments		:
--
---------------------------------------------------------------------------------------------------
-- Header		: AES_OUTPUT_2_TYPE
--
-- MIB ref		: swCardEventLogSlotXX       .17.65.69.83.95.79.85.84.80.85.84.95.50.95.84.89.80.69
-- absolute OID	: 1.3.6.1.4.1.7995.2.6.1.1.XX.17.65.69.83.95.79.85.84.80.85.84.95.50.95.84.89.80.69
-- Vary			: YES
--
-- Value(s)		: Unknown
--				: PCM
--              : NONPCM
--              : WARN: No Input
-- Comments		:
--
---------------------------------------------------------------------------------------------------
-- Header		: AES_OUTPUT_3_TYPE
--
-- MIB ref		: swCardEventLogSlotXX       .17.65.69.83.95.79.85.84.80.85.84.95.51.95.84.89.80.69
-- absolute OID	: 1.3.6.1.4.1.7995.2.6.1.1.XX.17.65.69.83.95.79.85.84.80.85.84.95.51.95.84.89.80.69
-- Vary			: YES
--
-- Value(s)		: Unknown
--				: PCM
--              : NONPCM
--              : WARN: No Input
-- Comments		:
--
---------------------------------------------------------------------------------------------------
-- Header		: AES_OUTPUT_4_TYPE
--
-- MIB ref		: swCardEventLogSlotXX       .17.65.69.83.95.79.85.84.80.85.84.95.52.95.84.89.80.69
-- absolute OID	: 1.3.6.1.4.1.7995.2.6.1.1.XX.17.65.69.83.95.79.85.84.80.85.84.95.52.95.84.89.80.69
-- Vary			: YES
--
-- Value(s)		: Unknown
--				: PCM
--              : NONPCM
--              : WARN: No Input
-- Comments		:
--
---------------------------------------------------------------------------------------------------
-- Header		: AES_OUTPUT_5_TYPE
--
-- MIB ref		: swCardEventLogSlotXX       .17.65.69.83.95.79.85.84.80.85.84.95.53.95.84.89.80.69
-- absolute OID	: 1.3.6.1.4.1.7995.2.6.1.1.XX.17.65.69.83.95.79.85.84.80.85.84.95.53.95.84.89.80.69
-- Vary			: YES
--
-- Value(s)		: Unknown
--				: PCM
--              : NONPCM
--              : WARN: No Input
-- Comments		:
--
---------------------------------------------------------------------------------------------------
-- Header		: AES_OUTPUT_6_TYPE
--
-- MIB ref		: swCardEventLogSlotXX       .17.65.69.83.95.79.85.84.80.85.84.95.54.95.84.89.80.69
-- absolute OID	: 1.3.6.1.4.1.7995.2.6.1.1.XX.17.65.69.83.95.79.85.84.80.85.84.95.54.95.84.89.80.69
-- Vary			: YES
--
-- Value(s)		: Unknown
--				: PCM
--              : NONPCM
--              : WARN: No Input
-- Comments		:
--
---------------------------------------------------------------------------------------------------
-- Header		: AES_OUTPUT_7_TYPE
--
-- MIB ref		: swCardEventLogSlotXX       .17.65.69.83.95.79.85.84.80.85.84.95.55.95.84.89.80.69
-- absolute OID	: 1.3.6.1.4.1.7995.2.6.1.1.XX.17.65.69.83.95.79.85.84.80.85.84.95.55.95.84.89.80.69
-- Vary			: YES
--
-- Value(s)		: Unknown
--				: PCM
--              : NONPCM
--              : WARN: No Input
-- Comments		:
--
---------------------------------------------------------------------------------------------------
-- Header		: AES_OUTPUT_8_TYPE
--
-- MIB ref		: swCardEventLogSlotXX       .17.65.69.83.95.79.85.84.80.85.84.95.56.95.84.89.80.69
-- absolute OID	: 1.3.6.1.4.1.7995.2.6.1.1.XX.17.65.69.83.95.79.85.84.80.85.84.95.56.95.84.89.80.69
-- Vary			: YES
--
-- Value(s)		: Unknown
--				: PCM
--              : NONPCM
--              : WARN: No Input
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_OUTPUT_1_STATE
--
-- MIB ref		: swCardEventLogSlotXX       .18.65.69.83.95.79.85.84.80.85.84.95.49.95.83.84.65.84.69
-- absolute OID	: 1.3.6.1.4.1.7995.2.6.1.1.XX.18.65.69.83.95.79.85.84.80.85.84.95.49.95.83.84.65.84.69
-- Vary			: YES
--
-- Value(s)		: WARN:Off
-- Value(s)		: LOST
--				: FAIL:Lost
--              : OK
--              : Unknown
-- Comments		:
--
---------------------------------------------------------------------------------------------------
-- Header		: AES_OUTPUT_2_STATE
--
-- MIB ref		: swCardEventLogSlotXX       .18.65.69.83.95.79.85.84.80.85.84.95.50.95.83.84.65.84.69
-- absolute OID	: 1.3.6.1.4.1.7995.2.6.1.1.XX.18.65.69.83.95.79.85.84.80.85.84.95.50.95.83.84.65.84.69
-- Vary			: YES
--
-- Value(s)		: WARN:Off
-- Value(s)		: LOST
--				: FAIL:Lost
--              : OK
--              : Unknown
-- Comments		:
--
---------------------------------------------------------------------------------------------------
-- Header		: AES_OUTPUT_3_STATE
--
-- MIB ref		: swCardEventLogSlotXX       .18.65.69.83.95.79.85.84.80.85.84.95.51.95.83.84.65.84.69
-- absolute OID	: 1.3.6.1.4.1.7995.2.6.1.1.XX.18.65.69.83.95.79.85.84.80.85.84.95.51.95.83.84.65.84.69
-- Vary			: YES
--
-- Value(s)		: WARN:Off
-- Value(s)		: LOST
--				: FAIL:Lost
--              : OK
--              : Unknown
-- Comments		:
--
---------------------------------------------------------------------------------------------------
-- Header		: AES_OUTPUT_4_STATE
--
-- MIB ref		: swCardEventLogSlotXX       .18.65.69.83.95.79.85.84.80.85.84.95.52.95.83.84.65.84.69
-- absolute OID	: 1.3.6.1.4.1.7995.2.6.1.1.XX.18.65.69.83.95.79.85.84.80.85.84.95.52.95.83.84.65.84.69
-- Vary			: YES
--
-- Value(s)		: WARN:Off
-- Value(s)		: LOST
--				: FAIL:Lost
--              : OK
--              : Unknown
-- Comments		:
--
---------------------------------------------------------------------------------------------------
-- Header		: AES_OUTPUT_5_STATE
--
-- MIB ref		: swCardEventLogSlotXX       .18.65.69.83.95.79.85.84.80.85.84.95.53.95.83.84.65.84.69
-- absolute OID	: 1.3.6.1.4.1.7995.2.6.1.1.XX.18.65.69.83.95.79.85.84.80.85.84.95.53.95.83.84.65.84.69
-- Vary			: YES
--
-- Value(s)		: WARN:Off
-- Value(s)		: LOST
--				: FAIL:Lost
--              : OK
--              : Unknown
-- Comments		:
--
---------------------------------------------------------------------------------------------------
-- Header		: AES_OUTPUT_6_STATE
--
-- MIB ref		: swCardEventLogSlotXX       .18.65.69.83.95.79.85.84.80.85.84.95.54.95.83.84.65.84.69
-- absolute OID	: 1.3.6.1.4.1.7995.2.6.1.1.XX.18.65.69.83.95.79.85.84.80.85.84.95.54.95.83.84.65.84.69
-- Vary			: YES
--
-- Value(s)		: WARN:Off
-- Value(s)		: LOST
--				: FAIL:Lost
--              : OK
--              : Unknown
-- Comments		:
--
---------------------------------------------------------------------------------------------------
-- Header		: AES_OUTPUT_7_STATE
--
-- MIB ref		: swCardEventLogSlotXX       .18.65.69.83.95.79.85.84.80.85.84.95.55.95.83.84.65.84.69
-- absolute OID	: 1.3.6.1.4.1.7995.2.6.1.1.XX.18.65.69.83.95.79.85.84.80.85.84.95.55.95.83.84.65.84.69
-- Vary			: YES
--
-- Value(s)		: WARN:Off
-- Value(s)		: LOST
--				: FAIL:Lost
--              : OK
--              : Unknown
-- Comments		:
--
---------------------------------------------------------------------------------------------------
-- Header		: AES_OUTPUT_8_STATE
--
-- MIB ref		: swCardEventLogSlotXX       .18.65.69.83.95.79.85.84.80.85.84.95.56.95.83.84.65.84.69
-- absolute OID	: 1.3.6.1.4.1.7995.2.6.1.1.XX.18.65.69.83.95.79.85.84.80.85.84.95.56.95.83.84.65.84.69
-- Vary			: YES
--
-- Value(s)		: Warn:Off
-- Value(s)		: LOST
--				: FAIL:Lost
--              : OK
--              : Unknown
-- Comments		:
--
---------------------------------------------------------------------------------------------------
-- Header		: DOLBY_ENCODER_AC_3
--
-- MIB ref		: swCardEventLogSlotXX       .18.68.79.76.66.89.95.69.78.67.79.68.69.82.95.65.67.95.51
-- absolute OID	: 1.3.6.1.4.1.7995.2.6.1.1.XX.18.68.79.76.66.89.95.69.78.67.79.68.69.82.95.65.67.95.51
-- Vary			: YES
--
-- Value(s)     :No
--              :Yes
--              :-
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				:
-- Comments		: Number of error seconds
--
---------------------------------------------------------------------------------------------------
-- Header		: OUTPUT_1_ANC_STATE
--
-- MIB ref		: swCardEventLogSlotXX       .18.79.85.84.80.85.84.95.49.95.65.78.67.95.83.84.65.84.69
-- absolute OID	: 1.3.6.1.4.1.7995.2.6.1.1.XX.18.79.85.84.80.85.84.95.49.95.65.78.67.95.83.84.65.84.69
-- Vary			: YES
--
-- Value(s)		: OK
--				: ANC FULL
-- Comments		:
--
---------------------------------------------------------------------------------------------------
-- Header		: DOLBY_ENCODER_EX_BSI
--
-- MIB ref		: swCardEventLogSlotXX       .20.68.79.76.66.89.95.69.78.67.79.68.69.82.95.69.88.95.66.83.73
-- absolute OID	: 1.3.6.1.4.1.7995.2.6.1.1.XX.20.68.79.76.66.89.95.69.78.67.79.68.69.82.95.69.88.95.66.83.73
-- Vary			: YES
--
-- Value(s)     : No
--              : Yes
--              : -
-- Comments		:
--
---------------------------------------------------------------------------------------------------
-- Header		: DOLBY_ENCODER_SOURCE
--
-- MIB ref		: swCardEventLogSlotXX       .20.68.79.76.66.89.95.69.78.67.79.68.69.82.95.83.79.85.82.67.69
-- absolute OID	: 1.3.6.1.4.1.7995.2.6.1.1.XX.20.68.79.76.66.89.95.69.78.67.79.68.69.82.95.83.79.85.82.67.69
-- Vary			: YES
--
-- Value(s)     : Internal
--              : External
--              : Last Valid
--              : Internal:Rev
--              : External:Rev
--              : Last Valid:Rev
--              : -
-- Comments		:
--
---------------------------------------------------------------------------------------------------
-- Header		: DOLBY_ENCODER_STATUS
--
-- MIB ref		: swCardEventLogSlotXX       .20.68.79.76.66.89.95.69.78.67.79.68.69.82.95.83.84.65.84.85.83
-- absolute OID	: 1.3.6.1.4.1.7995.2.6.1.1.XX.20.68.79.76.66.89.95.69.78.67.79.68.69.82.95.83.84.65.84.85.83
-- Vary			: YES
--
-- Value(s)     : Encoder Active
--              : Encoder Stopped
--              : Pass Mode
--              : -
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: NONE
--              : WARN
-- Comments		:
--
---------------------------------------------------------------------------------------------------
-- Header		: DOLBY_ENCODER_CHAN_MODE
--
-- MIB ref		: swCardEventLogSlotXX       .23.68.79.76.66.89.95.69.78.67.79.68.69.82.95.67.72.65.78.95.77.79.68.69
-- absolute OID	: 1.3.6.1.4.1.7995.2.6.1.1.XX.23.68.79.76.66.89.95.69.78.67.79.68.69.82.95.67.72.65.78.95.77.79.68.69
-- Vary			: YES
--
-- Value(s)     : 1/0
--              : 2/0
--              : 3/0
--              : 2/1
--              : 3/1
--              : 2/2
--              : 3/2
--              : 3/0L
--              : 2/1L
--              : 3/1L
--              : 2/2L
--              : 3/2L
-- Comments		:
--
---------------------------------------------------------------------------------------------------
-- Header		: DOLBY_ENCODER_DATA_RATE
--
-- MIB ref		: swCardEventLogSlotXX       .23.68.79.76.66.89.95.69.78.67.79.68.69.82.95.68.65.84.65.95.82.65.84.69
-- absolute OID	: 1.3.6.1.4.1.7995.2.6.1.1.XX.23.68.79.76.66.89.95.69.78.67.79.68.69.82.95.68.65.84.65.95.82.65.84.69
-- Vary			: YES
--
-- Value(s      : Auto384
--              : Auto448
--              : 56 kbps
--              : 64 kbps
--              : 80 kbps
--              : 96 kbps
--              : 112 kbps
--              : 128 kbps
--              : 160 kbps
--              : 192 kbps
--              : 224 kbps
--              : 256 kbps
--              : 320 kbps
--              : 384 kbps
--              : 448 kbps
--              : 512 kbps
--              : 576 kbps
--              : 640 kbps
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				:
-- Comments		: Number of error seconds
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_2_DOLBY
--
-- MIB ref		: swCardEventLogSlotXX       .31.79.85.84.80.85.84.95.49.95.69.77.66.69.68.68.69.68.95.65.85.68.73.79.95.50.95.68.79.76.66.89
-- absolute OID	: 1.3.6.1.4.1.7995.2.6.1.1.XX.31.79.85.84.80.85.84.95.49.95.69.77.66.69.68.68.69.68.95.65.85.68.73.79.95.50.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_3_DOLBY
--
-- MIB ref		: swCardEventLogSlotXX       .31.79.85.84.80.85.84.95.49.95.69.77.66.69.68.68.69.68.95.65.85.68.73.79.95.51.95.68.79.76.66.89
-- absolute OID	: 1.3.6.1.4.1.7995.2.6.1.1.XX.31.79.85.84.80.85.84.95.49.95.69.77.66.69.68.68.69.68.95.65.85.68.73.79.95.51.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_4_DOLBY
--
-- MIB ref		: swCardEventLogSlotXX       .31.79.85.84.80.85.84.95.49.95.69.77.66.69.68.68.69.68.95.65.85.68.73.79.95.52.95.68.79.76.66.89
-- absolute OID	: 1.3.6.1.4.1.7995.2.6.1.1.XX.31.79.85.84.80.85.84.95.49.95.69.77.66.69.68.68.69.68.95.65.85.68.73.79.95.52.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_5_DOLBY
--
-- MIB ref		: swCardEventLogSlotXX       .31.79.85.84.80.85.84.95.49.95.69.77.66.69.68.68.69.68.95.65.85.68.73.79.95.53.95.68.79.76.66.89
-- absolute OID	: 1.3.6.1.4.1.7995.2.6.1.1.XX.31.79.85.84.80.85.84.95.49.95.69.77.66.69.68.68.69.68.95.65.85.68.73.79.95.53.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_6_DOLBY
--
-- MIB ref		: swCardEventLogSlotXX       .31.79.85.84.80.85.84.95.49.95.69.77.66.69.68.68.69.68.95.65.85.68.73.79.95.54.95.68.79.76.66.89
-- absolute OID	: 1.3.6.1.4.1.7995.2.6.1.1.XX.31.79.85.84.80.85.84.95.49.95.69.77.66.69.68.68.69.68.95.65.85.68.73.79.95.54.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_7_DOLBY
--
-- MIB ref		: swCardEventLogSlotXX       .31.79.85.84.80.85.84.95.49.95.69.77.66.69.68.68.69.68.95.65.85.68.73.79.95.55.95.68.79.76.66.89
-- absolute OID	: 1.3.6.1.4.1.7995.2.6.1.1.XX.31.79.85.84.80.85.84.95.49.95.69.77.66.69.68.68.69.68.95.65.85.68.73.79.95.55.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_8_DOLBY
--
-- MIB ref		: swCardEventLogSlotXX       .31.79.85.84.80.85.84.95.49.95.69.77.66.69.68.68.69.68.95.65.85.68.73.79.95.56.95.68.79.76.66.89
-- absolute OID	: 1.3.6.1.4.1.7995.2.6.1.1.XX.31.79.85.84.80.85.84.95.49.95.69.77.66.69.68.68.69.68.95.65.85.68.73.79.95.56.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
-- Vary			: YES
--
-- Value(s)		: OK
--				: WARN:Silent
--              : WARN:Quiet
--              : WARN:Loud
--              : WARN:Overflow
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
-- Vary			: YES
--
-- Value(s)		: OK
--				: WARN:Silent
--              : WARN:Quiet
--              : WARN:Loud
--              : WARN:Overflow
-- Comments		:
--
---------------------------------------------------------------------------------------------------
