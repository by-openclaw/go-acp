-- ************************************************************************************
--       Source File:Original_SNELL-IQDMX32-CMD-MIB.mib
--    Logging Source:dmx32logging.csv
--            Author:jonathanriches
--              Date:19/08/2011
--              Time:16:34
--
-- Copyright (c) 2010 Snell Ltd
-- All rights reserved.
--
-- Snell&Wilcox Card:IQDMX32
--        Module Id#:533
--       Command Set:10
--          Filename:SNELL-IQDMX32-CMD-MIB.mib
--            Author:J Riches
--              Date:19/08/2011
--              Time:15:41
--
-- Copyright (c) 2005 Snell & Wilcox Ltd
-- All rights reserved.
--
-- ************************************************************************************

SNELL-IQDMX32-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMX32,
    moduleIQDMX32MIB
        FROM SNELL-WILCOX-PRODUCT-REG;

 moduleIQDMX32CmdMi MODULE-IDENTITY
    LAST-UPDATED "1108191541Z"
    ORGANIZATION "Snell & Wilcox Ltd"
    CONTACT-INFO
        "Primary Author:J Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMX32MIB 1 }




--********************************************************************************
--*
--*  Snell Wilcox Card:
--*  command set:
--*  list commands/menus:
--*
--******************************************************************************
	iqdmx32CmdTable OBJECT-TYPE
		SYNTAX			SEQUENCE OF Iqdmx32CmdEntry
		MAX-ACCESS		not-accessible
		STATUS			current
		DESCRIPTION
				"Note the instance of this table is relected in the command set Version"
		::= { moduleIQDMX32 1 }

	iqdmx32CmdEntry OBJECT-TYPE
		SYNTAX		Iqdmx32CmdEntry
		MAX-ACCESS		not-accessible
		STATUS			current
		DESCRIPTION
				"Entry in command table."
		INDEX	{ iqdmx32SlotIndex }
		::= { iqdmx32CmdTable 1 }

	Iqdmx32CmdEntry ::=
		SEQUENCE {
			iqdmx32SlotIndex
				Unsigned32,
			iqdmx32Video1ValidInputFormats62525i
				INTEGER,
			iqdmx32Video1ValidInputFormats52529i
				INTEGER,
			iqdmx32Video1ValidInputFormats72050p
				INTEGER,
			iqdmx32Video1ValidInputFormats72059p
				INTEGER,
			iqdmx32Video1ValidInputFormats108025i
				INTEGER,
			iqdmx32Video1ValidInputFormats108029i
				INTEGER,
			iqdmx32Video1ValidInputFormats108050pA
				INTEGER,
			iqdmx32Video1ValidInputFormats108059pA
				INTEGER,
			iqdmx32Video1ValidInputFormats108050pB
				INTEGER,
			iqdmx32Video1ValidInputFormats108059pB
				INTEGER,
			iqdmx32Channel1Video1DefaultFormat
				INTEGER,
			iqdmx32Channel1Video1DefaultOutput
				INTEGER,
			iqdmx32Video1VideoProcampProcAmpEnable
				INTEGER,
			iqdmx32Video1VideoProcampBlackLevel
				INTEGER,
			iqdmx32Video1VideoProcampHueAdjust
				INTEGER,
			iqdmx32Video1VideoProcampMasterVideoGain
				INTEGER,
			iqdmx32Video1VideoProcampYGain
				INTEGER,
			iqdmx32Video1VideoProcampCbCrGain
				INTEGER,
			iqdmx32Video1VideoProcampYCTiming
				INTEGER,
			iqdmx32Video1VideoProcampPictureposition
				INTEGER,
			iqdmx32Video1VideoProcampModalIndex
				INTEGER,
			iqdmx32Video1VideoProcampYCTimingnm
				INTEGER,
			iqdmx32Video1VideoProcampPicturepositionnm
				INTEGER,
			iqdmx32Video1BlankingBlankVANC
				INTEGER,
			iqdmx32Blanking625BlankLinesLine23ch1
				INTEGER,
			iqdmx32Blanking625BlankLinesLine336ch1
				INTEGER,
			iqdmx32Blanking525BlankLinesLine21ch1
				INTEGER,
			iqdmx32Blanking525BlankLinesLine22ch1
				INTEGER,
			iqdmx32Blanking525BlankLinesLine283ch1
				INTEGER,
			iqdmx32Blanking525BlankLinesLine284ch1
				INTEGER,
			iqdmx32Video1BlankingBlankHANC
				INTEGER,
			iqdmx32Video1Caption
				INTEGER,
			iqdmx32Video1CaptionEditCaption
				RollCallString,
			iqdmx32Channel1Video1Pattern
				INTEGER,
			iqdmx32Video1Freeze
				INTEGER,
			iqdmx32Video1FreezeManualFreeze
				INTEGER,
			iqdmx32EmbeddersEmbedder1Enablech1
				INTEGER,
			iqdmx32EmbeddersEmbedder1SourceLNonPCMPair1
				INTEGER,
			iqdmx32EmbeddersEmbedder1SourceRPair1
				INTEGER,
			iqdmx32EmbeddersEmbedder1MutePair1
				INTEGER,
			iqdmx32EmbeddersEmbedder1MuteonVbitPair1
				INTEGER,
			iqdmx32EmbeddersEmbedder1InvertLPair1
				INTEGER,
			iqdmx32EmbeddersEmbedder1InvertRPair1
				INTEGER,
			iqdmx32EmbeddersEmbedder1GainLPair1
				INTEGER,
			iqdmx32EmbeddersEmbedder1GainRPair1
				INTEGER,
			iqdmx32EmbeddersEmbedder1PairModePair1
				INTEGER,
			iqdmx32EmbeddersEmbedder1SourceLNonPCMPair2
				INTEGER,
			iqdmx32EmbeddersEmbedder1SourceRPair2
				INTEGER,
			iqdmx32EmbeddersEmbedder1MutePair2
				INTEGER,
			iqdmx32EmbeddersEmbedder1MuteonVbitPair2
				INTEGER,
			iqdmx32EmbeddersEmbedder1InvertLPair2
				INTEGER,
			iqdmx32EmbeddersEmbedder1InvertRPair2
				INTEGER,
			iqdmx32EmbeddersEmbedder1GainLPair2
				INTEGER,
			iqdmx32EmbeddersEmbedder1GainRPair2
				INTEGER,
			iqdmx32EmbeddersEmbedder1PairModePair2
				INTEGER,
			iqdmx32EmbeddersEmbedder1NonModalIndexPair2
				INTEGER,
			iqdmx32EmbeddersEmbedder1NonModalGainPair2
				INTEGER,
			iqdmx32EmbeddersEmbedder1NonModalIndexPair2
				INTEGER,
			iqdmx32EmbeddersEmbedder1NonModalGainPair2
				INTEGER,
			iqdmx32EmbeddersEmbedder2EnablePair2
				INTEGER,
			iqdmx32EmbeddersEmbedder2SourceLNonPCMPair1
				INTEGER,
			iqdmx32EmbeddersEmbedder2SourceRPair1
				INTEGER,
			iqdmx32EmbeddersEmbedder2MutePair1
				INTEGER,
			iqdmx32EmbeddersEmbedder2MuteonVbitPair1
				INTEGER,
			iqdmx32EmbeddersEmbedder2InvertLPair1
				INTEGER,
			iqdmx32EmbeddersEmbedder2InvertRPair1
				INTEGER,
			iqdmx32EmbeddersEmbedder2GainLPair1
				INTEGER,
			iqdmx32EmbeddersEmbedder2GainRPair1
				INTEGER,
			iqdmx32EmbeddersEmbedder2PairModePair1
				INTEGER,
			iqdmx32EmbeddersEmbedder2SourceLNonPCMPair2
				INTEGER,
			iqdmx32EmbeddersEmbedder2SourceRPair2
				INTEGER,
			iqdmx32EmbeddersEmbedder2MutePair2
				INTEGER,
			iqdmx32EmbeddersEmbedder2MuteonVbitPair2
				INTEGER,
			iqdmx32EmbeddersEmbedder2InvertLPair2
				INTEGER,
			iqdmx32EmbeddersEmbedder2InvertRPair2
				INTEGER,
			iqdmx32EmbeddersEmbedder2GainLPair2
				INTEGER,
			iqdmx32EmbeddersEmbedder2GainRPair2
				INTEGER,
			iqdmx32EmbeddersEmbedder2PairModePair2
				INTEGER,
			iqdmx32EmbeddersEmbedder3EnablePair2
				INTEGER,
			iqdmx32EmbeddersEmbedder3SourceLNonPCMPair1
				INTEGER,
			iqdmx32EmbeddersEmbedder3SourceRPair1
				INTEGER,
			iqdmx32EmbeddersEmbedder3MutePair1
				INTEGER,
			iqdmx32EmbeddersEmbedder3MuteonVbitPair1
				INTEGER,
			iqdmx32EmbeddersEmbedder3InvertLPair1
				INTEGER,
			iqdmx32EmbeddersEmbedder3InvertRPair1
				INTEGER,
			iqdmx32EmbeddersEmbedder3GainLPair1
				INTEGER,
			iqdmx32EmbeddersEmbedder3GainRPair1
				INTEGER,
			iqdmx32EmbeddersEmbedder3PairModePair1
				INTEGER,
			iqdmx32EmbeddersEmbedder3SourceLNonPCMPair2
				INTEGER,
			iqdmx32EmbeddersEmbedder3SourceRPair2
				INTEGER,
			iqdmx32EmbeddersEmbedder3MutePair2
				INTEGER,
			iqdmx32EmbeddersEmbedder3MuteonVbitPair2
				INTEGER,
			iqdmx32EmbeddersEmbedder3InvertLPair2
				INTEGER,
			iqdmx32EmbeddersEmbedder3InvertRPair2
				INTEGER,
			iqdmx32EmbeddersEmbedder3GainLPair2
				INTEGER,
			iqdmx32EmbeddersEmbedder3GainRPair2
				INTEGER,
			iqdmx32EmbeddersEmbedder3PairModePair2
				INTEGER,
			iqdmx32EmbeddersEmbedder4EnablePair2
				INTEGER,
			iqdmx32EmbeddersEmbedder4SourceLNonPCMPair1
				INTEGER,
			iqdmx32EmbeddersEmbedder4SourceRPair1
				INTEGER,
			iqdmx32EmbeddersEmbedder4MutePair1
				INTEGER,
			iqdmx32EmbeddersEmbedder4MuteonVbitPair1
				INTEGER,
			iqdmx32EmbeddersEmbedder4InvertLPair1
				INTEGER,
			iqdmx32EmbeddersEmbedder4InvertRPair1
				INTEGER,
			iqdmx32EmbeddersEmbedder4GainLPair1
				INTEGER,
			iqdmx32EmbeddersEmbedder4GainRPair1
				INTEGER,
			iqdmx32EmbeddersEmbedder4PairModePair1
				INTEGER,
			iqdmx32EmbeddersEmbedder4SourceLNonPCMPair2
				INTEGER,
			iqdmx32EmbeddersEmbedder4SourceRPair2
				INTEGER,
			iqdmx32EmbeddersEmbedder4MutePair2
				INTEGER,
			iqdmx32EmbeddersEmbedder4MuteonVbitPair2
				INTEGER,
			iqdmx32EmbeddersEmbedder4InvertLPair2
				INTEGER,
			iqdmx32EmbeddersEmbedder4InvertRPair2
				INTEGER,
			iqdmx32EmbeddersEmbedder4GainLPair2
				INTEGER,
			iqdmx32EmbeddersEmbedder4GainRPair2
				INTEGER,
			iqdmx32EmbeddersEmbedder4PairModePair2
				INTEGER,
			iqdmx32AESOutAESOut1SourceLNonPCM
				INTEGER,
			iqdmx32AESOutAESOut1SourceR
				INTEGER,
			iqdmx32AESOutAESOut1Mute
				INTEGER,
			iqdmx32AESOutAESOut1MuteonVbit
				INTEGER,
			iqdmx32AESOutAESOut1InvertL
				INTEGER,
			iqdmx32AESOutAESOut1InvertR
				INTEGER,
			iqdmx32AESOutAESOut1GainL
				INTEGER,
			iqdmx32AESOutAESOut1GainR
				INTEGER,
			iqdmx32AESOutAESOut1PairMode
				INTEGER,
			iqdmx32AESOutAESOut2SourceLNonPCM
				INTEGER,
			iqdmx32AESOutAESOut2SourceR
				INTEGER,
			iqdmx32AESOutAESOut2Mute
				INTEGER,
			iqdmx32AESOutAESOut2MuteonVbit
				INTEGER,
			iqdmx32AESOutAESOut2InvertL
				INTEGER,
			iqdmx32AESOutAESOut2InvertR
				INTEGER,
			iqdmx32AESOutAESOut2GainL
				INTEGER,
			iqdmx32AESOutAESOut2GainR
				INTEGER,
			iqdmx32AESOutAESOut2PairMode
				INTEGER,
			iqdmx32AESOutAESOut3SourceLNonPCM
				INTEGER,
			iqdmx32AESOutAESOut3SourceR
				INTEGER,
			iqdmx32AESOutAESOut3Mute
				INTEGER,
			iqdmx32AESOutAESOut3MuteonVbit
				INTEGER,
			iqdmx32AESOutAESOut3InvertL
				INTEGER,
			iqdmx32AESOutAESOut3InvertR
				INTEGER,
			iqdmx32AESOutAESOut3GainL
				INTEGER,
			iqdmx32AESOutAESOut3GainR
				INTEGER,
			iqdmx32AESOutAESOut3PairMode
				INTEGER,
			iqdmx32AESOutAESOut4SourceLNonPCM
				INTEGER,
			iqdmx32AESOutAESOut4SourceR
				INTEGER,
			iqdmx32AESOutAESOut4Mute
				INTEGER,
			iqdmx32AESOutAESOut4MuteonVbit
				INTEGER,
			iqdmx32AESOutAESOut4InvertL
				INTEGER,
			iqdmx32AESOutAESOut4InvertR
				INTEGER,
			iqdmx32AESOutAESOut4GainL
				INTEGER,
			iqdmx32AESOutAESOut4GainR
				INTEGER,
			iqdmx32AESOutAESOut4PairMode
				INTEGER,
			iqdmx32AudioDelayDelaysVideoDelayCh1
				INTEGER,
			iqdmx32AudioDelayDelaysManualDelayCh1
				INTEGER,
			iqdmx32AudioDelayDelaysCoarseDelayCh1
				INTEGER,
			iqdmx32AudioDelayDelaysFineDelayCh1
				INTEGER,
			iqdmx32AudioDelayDelayStatusTotalDelayCh1
				RollCallString,
			iqdmx32AudioDelayDelayStatusVideoDelayCh1
				RollCallString,
			iqdmx32AudioDelayDelayStatusManualDelayCh1
				RollCallString,
			iqdmx32Audio1ToneFrequency
				INTEGER,
			iqdmx32Audio1ToneChannelident
				INTEGER,
			iqdmx32Audio1AudioMonitorSilenceLevel
				INTEGER,
			iqdmx32Audio1AudioMonitorOverloadLevel
				INTEGER,
			iqdmx32Audio1AudioMonitorWarningTimer
				INTEGER,
			iqdmx32Channel1VideoDelay1FreerunFrequency
				INTEGER,
			iqdmx32Channel1VideoDelay1VideoHdelay
				INTEGER,
			iqdmx32Channel1VideoDelay1VideoVdelay
				INTEGER,
			iqdmx32Channel1VideoDelay1VideoFdelay
				INTEGER,
			iqdmx32Channel1VideoDelay1Genlocksaveindex
				INTEGER,
			iqdmx32Channel1VideoDelay1VideoHdelaysave
				INTEGER,
			iqdmx32Channel1VideoDelay1VideoVdelaysave
				INTEGER,
			iqdmx32Video2ValidInputFormats62525i
				INTEGER,
			iqdmx32Video2ValidInputFormats52529i
				INTEGER,
			iqdmx32Video2ValidInputFormats72050p
				INTEGER,
			iqdmx32Video2ValidInputFormats72059p
				INTEGER,
			iqdmx32Video2ValidInputFormats108025i
				INTEGER,
			iqdmx32Video2ValidInputFormats108029i
				INTEGER,
			iqdmx32Video2ValidInputFormats108050pA
				INTEGER,
			iqdmx32Video2ValidInputFormats108059pA
				INTEGER,
			iqdmx32Video2ValidInputFormats108050pB
				INTEGER,
			iqdmx32Video2ValidInputFormats108059pB
				INTEGER,
			iqdmx32Channel2Video2DefaultFormat
				INTEGER,
			iqdmx32Channel2Video2DefaultOutput
				INTEGER,
			iqdmx32Video2VideoProcampProcAmpEnable
				INTEGER,
			iqdmx32Video2VideoProcampBlackLevel
				INTEGER,
			iqdmx32Video2VideoProcampHueAdjust
				INTEGER,
			iqdmx32Video2VideoProcampMasterVideoGain
				INTEGER,
			iqdmx32Video2VideoProcampYGain
				INTEGER,
			iqdmx32Video2VideoProcampCbCrGain
				INTEGER,
			iqdmx32Video2VideoProcampYCTiming
				INTEGER,
			iqdmx32Video2VideoProcampPictureposition
				INTEGER,
			iqdmx32Video2VideoProcampModalIndex
				INTEGER,
			iqdmx32Video2VideoProcampYCTimingnm
				INTEGER,
			iqdmx32Video2VideoProcampPicturepositionnm
				INTEGER,
			iqdmx32Video2BlankingBlankVANC
				INTEGER,
			iqdmx32Blanking625BlankLinesLine23ch2
				INTEGER,
			iqdmx32Blanking625BlankLinesLine336ch2
				INTEGER,
			iqdmx32Blanking525BlankLinesLine21ch2
				INTEGER,
			iqdmx32Blanking525BlankLinesLine22ch2
				INTEGER,
			iqdmx32Blanking525BlankLinesLine283ch2
				INTEGER,
			iqdmx32Blanking525BlankLinesLine284ch2
				INTEGER,
			iqdmx32Video2BlankingBlankHANC
				INTEGER,
			iqdmx32Video2Caption
				INTEGER,
			iqdmx32Video2CaptionEditCaption
				RollCallString,
			iqdmx32Channel2Video2Pattern
				INTEGER,
			iqdmx32Video2Freeze
				INTEGER,
			iqdmx32Video2FreezeManualFreeze
				INTEGER,
			iqdmx32EmbeddersEmbedder1Enablech2
				INTEGER,
			iqdmx32EmbeddersEmbedder1SourceLNonPCMPair1
				INTEGER,
			iqdmx32EmbeddersEmbedder1SourceRPair1
				INTEGER,
			iqdmx32EmbeddersEmbedder1MutePair1
				INTEGER,
			iqdmx32EmbeddersEmbedder1MuteonVbitPair1
				INTEGER,
			iqdmx32EmbeddersEmbedder1InvertLPair1
				INTEGER,
			iqdmx32EmbeddersEmbedder1InvertRPair1
				INTEGER,
			iqdmx32EmbeddersEmbedder1GainLPair1
				INTEGER,
			iqdmx32EmbeddersEmbedder1GainRPair1
				INTEGER,
			iqdmx32EmbeddersEmbedder1PairModePair1
				INTEGER,
			iqdmx32EmbeddersEmbedder1SourceLNonPCMPair2
				INTEGER,
			iqdmx32EmbeddersEmbedder1SourceRPair2
				INTEGER,
			iqdmx32EmbeddersEmbedder1MutePair2
				INTEGER,
			iqdmx32EmbeddersEmbedder1MuteonVbitPair2
				INTEGER,
			iqdmx32EmbeddersEmbedder1InvertLPair2
				INTEGER,
			iqdmx32EmbeddersEmbedder1InvertRPair2
				INTEGER,
			iqdmx32EmbeddersEmbedder1GainLPair2
				INTEGER,
			iqdmx32EmbeddersEmbedder1GainRPair2
				INTEGER,
			iqdmx32EmbeddersEmbedder1PairModePair2
				INTEGER,
			iqdmx32EmbeddersEmbedder2EnablePair2
				INTEGER,
			iqdmx32EmbeddersEmbedder2SourceLNonPCMPair1
				INTEGER,
			iqdmx32EmbeddersEmbedder2SourceRPair1
				INTEGER,
			iqdmx32EmbeddersEmbedder2MutePair1
				INTEGER,
			iqdmx32EmbeddersEmbedder2MuteonVbitPair1
				INTEGER,
			iqdmx32EmbeddersEmbedder2InvertLPair1
				INTEGER,
			iqdmx32EmbeddersEmbedder2InvertRPair1
				INTEGER,
			iqdmx32EmbeddersEmbedder2GainLPair1
				INTEGER,
			iqdmx32EmbeddersEmbedder2GainRPair1
				INTEGER,
			iqdmx32EmbeddersEmbedder2PairModePair1
				INTEGER,
			iqdmx32EmbeddersEmbedder2SourceLNonPCMPair2
				INTEGER,
			iqdmx32EmbeddersEmbedder2SourceRPair2
				INTEGER,
			iqdmx32EmbeddersEmbedder2MutePair2
				INTEGER,
			iqdmx32EmbeddersEmbedder2MuteonVbitPair2
				INTEGER,
			iqdmx32EmbeddersEmbedder2InvertLPair2
				INTEGER,
			iqdmx32EmbeddersEmbedder2InvertRPair2
				INTEGER,
			iqdmx32EmbeddersEmbedder2GainLPair2
				INTEGER,
			iqdmx32EmbeddersEmbedder2GainRPair2
				INTEGER,
			iqdmx32EmbeddersEmbedder2PairModePair2
				INTEGER,
			iqdmx32EmbeddersEmbedder3EnablePair2
				INTEGER,
			iqdmx32EmbeddersEmbedder3SourceLNonPCMPair1
				INTEGER,
			iqdmx32EmbeddersEmbedder3SourceRPair1
				INTEGER,
			iqdmx32EmbeddersEmbedder3MutePair1
				INTEGER,
			iqdmx32EmbeddersEmbedder3MuteonVbitPair1
				INTEGER,
			iqdmx32EmbeddersEmbedder3InvertLPair1
				INTEGER,
			iqdmx32EmbeddersEmbedder3InvertRPair1
				INTEGER,
			iqdmx32EmbeddersEmbedder3GainLPair1
				INTEGER,
			iqdmx32EmbeddersEmbedder3GainRPair1
				INTEGER,
			iqdmx32EmbeddersEmbedder3PairModePair1
				INTEGER,
			iqdmx32EmbeddersEmbedder3SourceLNonPCMPair2
				INTEGER,
			iqdmx32EmbeddersEmbedder3SourceRPair2
				INTEGER,
			iqdmx32EmbeddersEmbedder3MutePair2
				INTEGER,
			iqdmx32EmbeddersEmbedder3MuteonVbitPair2
				INTEGER,
			iqdmx32EmbeddersEmbedder3InvertLPair2
				INTEGER,
			iqdmx32EmbeddersEmbedder3InvertRPair2
				INTEGER,
			iqdmx32EmbeddersEmbedder3GainLPair2
				INTEGER,
			iqdmx32EmbeddersEmbedder3GainRPair2
				INTEGER,
			iqdmx32EmbeddersEmbedder3PairModePair2
				INTEGER,
			iqdmx32EmbeddersEmbedder4EnablePair2
				INTEGER,
			iqdmx32EmbeddersEmbedder4SourceLNonPCMPair1
				INTEGER,
			iqdmx32EmbeddersEmbedder4SourceRPair1
				INTEGER,
			iqdmx32EmbeddersEmbedder4MutePair1
				INTEGER,
			iqdmx32EmbeddersEmbedder4MuteonVbitPair1
				INTEGER,
			iqdmx32EmbeddersEmbedder4InvertLPair1
				INTEGER,
			iqdmx32EmbeddersEmbedder4InvertRPair1
				INTEGER,
			iqdmx32EmbeddersEmbedder4GainLPair1
				INTEGER,
			iqdmx32EmbeddersEmbedder4GainRPair1
				INTEGER,
			iqdmx32EmbeddersEmbedder4PairModePair1
				INTEGER,
			iqdmx32EmbeddersEmbedder4SourceLNonPCMPair2
				INTEGER,
			iqdmx32EmbeddersEmbedder4SourceRPair2
				INTEGER,
			iqdmx32EmbeddersEmbedder4MutePair2
				INTEGER,
			iqdmx32EmbeddersEmbedder4MuteonVbitPair2
				INTEGER,
			iqdmx32EmbeddersEmbedder4InvertLPair2
				INTEGER,
			iqdmx32EmbeddersEmbedder4InvertRPair2
				INTEGER,
			iqdmx32EmbeddersEmbedder4GainLPair2
				INTEGER,
			iqdmx32EmbeddersEmbedder4GainRPair2
				INTEGER,
			iqdmx32EmbeddersEmbedder4PairModePair2
				INTEGER,
			iqdmx32AESOutAESOut5SourceLNonPCM
				INTEGER,
			iqdmx32AESOutAESOut5SourceR
				INTEGER,
			iqdmx32AESOutAESOut5Mute
				INTEGER,
			iqdmx32AESOutAESOut5MuteonVbit
				INTEGER,
			iqdmx32AESOutAESOut5InvertL
				INTEGER,
			iqdmx32AESOutAESOut5InvertR
				INTEGER,
			iqdmx32AESOutAESOut5GainL
				INTEGER,
			iqdmx32AESOutAESOut5GainR
				INTEGER,
			iqdmx32AESOutAESOut5PairMode
				INTEGER,
			iqdmx32AESOutAESOut6SourceLNonPCM
				INTEGER,
			iqdmx32AESOutAESOut6SourceR
				INTEGER,
			iqdmx32AESOutAESOut6Mute
				INTEGER,
			iqdmx32AESOutAESOut6MuteonVbit
				INTEGER,
			iqdmx32AESOutAESOut6InvertL
				INTEGER,
			iqdmx32AESOutAESOut6InvertR
				INTEGER,
			iqdmx32AESOutAESOut6GainL
				INTEGER,
			iqdmx32AESOutAESOut6GainR
				INTEGER,
			iqdmx32AESOutAESOut6PairMode
				INTEGER,
			iqdmx32AESOutAESOut7SourceLNonPCM
				INTEGER,
			iqdmx32AESOutAESOut7SourceR
				INTEGER,
			iqdmx32AESOutAESOut7Mute
				INTEGER,
			iqdmx32AESOutAESOut7MuteonVbit
				INTEGER,
			iqdmx32AESOutAESOut7InvertL
				INTEGER,
			iqdmx32AESOutAESOut7InvertR
				INTEGER,
			iqdmx32AESOutAESOut7GainL
				INTEGER,
			iqdmx32AESOutAESOut7GainR
				INTEGER,
			iqdmx32AESOutAESOut7PairMode
				INTEGER,
			iqdmx32AESOutAESOut8SourceLNonPCM
				INTEGER,
			iqdmx32AESOutAESOut8SourceR
				INTEGER,
			iqdmx32AESOutAESOut8Mute
				INTEGER,
			iqdmx32AESOutAESOut8MuteonVbit
				INTEGER,
			iqdmx32AESOutAESOut8InvertL
				INTEGER,
			iqdmx32AESOutAESOut8InvertR
				INTEGER,
			iqdmx32AESOutAESOut8GainL
				INTEGER,
			iqdmx32AESOutAESOut8GainR
				INTEGER,
			iqdmx32AESOutAESOut8PairMode
				INTEGER,
			iqdmx32AudioDelayDelaysVideoDelayCh2
				INTEGER,
			iqdmx32AudioDelayDelaysManualDelayCh2
				INTEGER,
			iqdmx32AudioDelayDelaysCoarseDelayCh2
				INTEGER,
			iqdmx32AudioDelayDelaysFineDelayCh2
				INTEGER,
			iqdmx32AudioDelayDelayStatusTotalDelayCh2
				RollCallString,
			iqdmx32AudioDelayDelayStatusVideoDelayCh2
				RollCallString,
			iqdmx32AudioDelayDelayStatusManualDelayCh2
				RollCallString,
			iqdmx32Audio2ToneFrequency
				INTEGER,
			iqdmx32Audio2ToneChannelident
				INTEGER,
			iqdmx32Audio2AudioMonitorSilenceLevel
				INTEGER,
			iqdmx32Audio2AudioMonitorOverloadLevel
				INTEGER,
			iqdmx32Audio2AudioMonitorWarningTimer
				INTEGER,
			iqdmx32Channel2VideoDelay2FreerunFrequency
				INTEGER,
			iqdmx32Channel2VideoDelay2VideoHdelay
				INTEGER,
			iqdmx32Channel2VideoDelay2VideoVdelay
				INTEGER,
			iqdmx32Channel2VideoDelay2VideoFdelay
				INTEGER,
			iqdmx32CommonMemoriesSelMemory
				INTEGER,
			iqdmx32CommonMemoriesSetMemName
				RollCallString,
			iqdmx32CommonMemoriesRecallMemory
				INTEGER,
			iqdmx32CommonMemoriesSaveMemory
				INTEGER,
			iqdmx32CommonMemoriesLastUserMemory
				RollCallString,
			iqdmx32CommonMemoriesClearMemory
				INTEGER,
			iqdmx32MemoriesMemoryNamesMemory1Name
				RollCallString,
			iqdmx32MemoriesMemoryNamesMemory2Name
				RollCallString,
			iqdmx32MemoriesMemoryNamesMemory3Name
				RollCallString,
			iqdmx32MemoriesMemoryNamesMemory4Name
				RollCallString,
			iqdmx32MemoriesMemoryNamesMemory5Name
				RollCallString,
			iqdmx32MemoriesMemoryNamesMemory6Name
				RollCallString,
			iqdmx32MemoriesMemoryNamesMemory7Name
				RollCallString,
			iqdmx32MemoriesMemoryNamesMemory8Name
				RollCallString,
			iqdmx32MemoriesMemoryNamesMemory9Name
				RollCallString,
			iqdmx32MemoriesMemoryNamesMemory10Name
				RollCallString,
			iqdmx32MemoriesMemoryNamesMemory11Name
				RollCallString,
			iqdmx32MemoriesMemoryNamesMemory12Name
				RollCallString,
			iqdmx32MemoriesMemoryNamesMemory13Name
				RollCallString,
			iqdmx32MemoriesMemoryNamesMemory14Name
				RollCallString,
			iqdmx32MemoriesMemoryNamesMemory15Name
				RollCallString,
			iqdmx32MemoriesMemoryNamesMemory16Name
				RollCallString,
			iqdmx32SetupLoggingUptime
				INTEGER,
			iqdmx32SetupLoggingUptimeLog
				RollCallString,
			iqdmx32SetupLoggingOSVersion
				INTEGER,
			iqdmx32SetupLoggingOSVersionLog
				RollCallString,
			iqdmx32SetupLoggingHardwareVersion
				INTEGER,
			iqdmx32SetupLoggingHardwareVersionLog
				RollCallString,
			iqdmx32SetupLoggingBuildNumber
				INTEGER,
			iqdmx32SetupLoggingBuildNumberLog
				RollCallString,
			iqdmx32SetupLoggingSerialNumber
				INTEGER,
			iqdmx32SetupLoggingSerialNumberLog
				RollCallString,
			iqdmx32SetupLoggingLicensedOptions
				INTEGER,
			iqdmx32SetupLoggingLicensedOptionsLog
				RollCallString,
			iqdmx32SetupLoggingFirmwareVersion
				INTEGER,
			iqdmx32SetupLoggingFirmwareVersionLog
				RollCallString,
			iqdmx32SetupLoggingRearid
				INTEGER,
			iqdmx32SetupLoggingRearidLog
				RollCallString,
			iqdmx32SetupLoggingRearstatus
				INTEGER,
			iqdmx32SetupLoggingRearstatusLog
				RollCallString,
			iqdmx32SetupLoggingSlotwidth
				INTEGER,
			iqdmx32SetupLoggingSlotwidthLog
				RollCallString,
			iqdmx32SetupLoggingSlotStart
				INTEGER,
			iqdmx32SetupLoggingSlotStartLog
				RollCallString,
			iqdmx32SetupLoggingInput1
				INTEGER,
			iqdmx32SetupLoggingInput1Log
				RollCallString,
			iqdmx32SetupLoggingInput1Standard
				INTEGER,
			iqdmx32SetupLoggingInput1StandardLog
				RollCallString,
			iqdmx32SetupLoggingInput1Type
				INTEGER,
			iqdmx32SetupLoggingInput1TypeLog
				RollCallString,
			iqdmx32SetupLoggingInput1Ident
				INTEGER,
			iqdmx32SetupLoggingInput1IdentLog
				RollCallString,
			iqdmx32SetupLoggingIn1SDIERRS
				INTEGER,
			iqdmx32SetupLoggingIn1SDIERRSLog
				RollCallString,
			iqdmx32SetupLoggingIn1SDIANCERRS
				INTEGER,
			iqdmx32SetupLoggingIn1SDIANCERRSLog
				RollCallString,
			iqdmx32SetupLoggingInput1Audio1
				INTEGER,
			iqdmx32SetupLoggingInput1Audio1Log
				RollCallString,
			iqdmx32SetupLoggingInput1Audio2
				INTEGER,
			iqdmx32SetupLoggingInput1Audio2Log
				RollCallString,
			iqdmx32SetupLoggingInput1Audio3
				INTEGER,
			iqdmx32SetupLoggingInput1Audio3Log
				RollCallString,
			iqdmx32SetupLoggingInput1Audio4
				INTEGER,
			iqdmx32SetupLoggingInput1Audio4Log
				RollCallString,
			iqdmx32SetupLoggingInput1Audio5
				INTEGER,
			iqdmx32SetupLoggingInput1Audio5Log
				RollCallString,
			iqdmx32SetupLoggingInput1Audio6
				INTEGER,
			iqdmx32SetupLoggingInput1Audio6Log
				RollCallString,
			iqdmx32SetupLoggingInput1Audio7
				INTEGER,
			iqdmx32SetupLoggingInput1Audio7Log
				RollCallString,
			iqdmx32SetupLoggingInput1Audio8
				INTEGER,
			iqdmx32SetupLoggingInput1Audio8Log
				RollCallString,
			iqdmx32SetupLoggingOutput1Type
				INTEGER,
			iqdmx32SetupLoggingOutput1TypeLog
				RollCallString,
			iqdmx32SetupLoggingOutput1State
				INTEGER,
			iqdmx32SetupLoggingOutput1StateLog
				RollCallString,
			iqdmx32SetupLoggingOutput1Std
				INTEGER,
			iqdmx32SetupLoggingOutput1StdLog
				RollCallString,
			iqdmx32SetupLoggingOutput1Caption
				INTEGER,
			iqdmx32SetupLoggingOutput1CaptionLog
				RollCallString,
			iqdmx32SetupLoggingInput2
				INTEGER,
			iqdmx32SetupLoggingInput2Log
				RollCallString,
			iqdmx32SetupLoggingInput2Standard
				INTEGER,
			iqdmx32SetupLoggingInput2StandardLog
				RollCallString,
			iqdmx32SetupLoggingInput2Type
				INTEGER,
			iqdmx32SetupLoggingInput2TypeLog
				RollCallString,
			iqdmx32SetupLoggingInput2Ident
				INTEGER,
			iqdmx32SetupLoggingInput2IdentLog
				RollCallString,
			iqdmx32SetupLoggingIn2SDIERRS
				INTEGER,
			iqdmx32SetupLoggingIn2SDIERRSLog
				RollCallString,
			iqdmx32SetupLoggingIn2SDIANCERRS
				INTEGER,
			iqdmx32SetupLoggingIn2SDIANCERRSLog
				RollCallString,
			iqdmx32SetupLoggingInput2Audio1
				INTEGER,
			iqdmx32SetupLoggingInput2Audio1Log
				RollCallString,
			iqdmx32SetupLoggingInput2Audio2
				INTEGER,
			iqdmx32SetupLoggingInput2Audio2Log
				RollCallString,
			iqdmx32SetupLoggingInput2Audio3
				INTEGER,
			iqdmx32SetupLoggingInput2Audio3Log
				RollCallString,
			iqdmx32SetupLoggingInput2Audio4
				INTEGER,
			iqdmx32SetupLoggingInput2Audio4Log
				RollCallString,
			iqdmx32SetupLoggingInput2Audio5
				INTEGER,
			iqdmx32SetupLoggingInput2Audio5Log
				RollCallString,
			iqdmx32SetupLoggingInput2Audio6
				INTEGER,
			iqdmx32SetupLoggingInput2Audio6Log
				RollCallString,
			iqdmx32SetupLoggingInput2Audio7
				INTEGER,
			iqdmx32SetupLoggingInput2Audio7Log
				RollCallString,
			iqdmx32SetupLoggingInput2Audio8
				INTEGER,
			iqdmx32SetupLoggingInput2Audio8Log
				RollCallString,
			iqdmx32SetupLoggingOutput2Type
				INTEGER,
			iqdmx32SetupLoggingOutput2TypeLog
				RollCallString,
			iqdmx32SetupLoggingOutput2State
				INTEGER,
			iqdmx32SetupLoggingOutput2StateLog
				RollCallString,
			iqdmx32SetupLoggingOutput2Std
				INTEGER,
			iqdmx32SetupLoggingOutput2StdLog
				RollCallString,
			iqdmx32SetupLoggingOutput2Caption
				INTEGER,
			iqdmx32SetupLoggingOutput2CaptionLog
				RollCallString,
			iqdmx32SetupLoggingop1embed11
				INTEGER,
			iqdmx32SetupLoggingop1embed11Log
				RollCallString,
			iqdmx32SetupLoggingop1embed12
				INTEGER,
			iqdmx32SetupLoggingop1embed12Log
				RollCallString,
			iqdmx32SetupLoggingop1embed21
				INTEGER,
			iqdmx32SetupLoggingop1embed21Log
				RollCallString,
			iqdmx32SetupLoggingop1embed22
				INTEGER,
			iqdmx32SetupLoggingop1embed22Log
				RollCallString,
			iqdmx32SetupLoggingop1embed31
				INTEGER,
			iqdmx32SetupLoggingop1embed31Log
				RollCallString,
			iqdmx32SetupLoggingop1embed32
				INTEGER,
			iqdmx32SetupLoggingop1embed32Log
				RollCallString,
			iqdmx32SetupLoggingop1embed41
				INTEGER,
			iqdmx32SetupLoggingop1embed41Log
				RollCallString,
			iqdmx32SetupLoggingop1embed42
				INTEGER,
			iqdmx32SetupLoggingop1embed42Log
				RollCallString,
			iqdmx32SetupLoggingop1embed51
				INTEGER,
			iqdmx32SetupLoggingop1embed51Log
				RollCallString,
			iqdmx32SetupLoggingop1embed52
				INTEGER,
			iqdmx32SetupLoggingop1embed52Log
				RollCallString,
			iqdmx32SetupLoggingop1embed61
				INTEGER,
			iqdmx32SetupLoggingop1embed61Log
				RollCallString,
			iqdmx32SetupLoggingop1embed62
				INTEGER,
			iqdmx32SetupLoggingop1embed62Log
				RollCallString,
			iqdmx32SetupLoggingop1embed71
				INTEGER,
			iqdmx32SetupLoggingop1embed71Log
				RollCallString,
			iqdmx32SetupLoggingop1embed72
				INTEGER,
			iqdmx32SetupLoggingop1embed72Log
				RollCallString,
			iqdmx32SetupLoggingop1embed81
				INTEGER,
			iqdmx32SetupLoggingop1embed81Log
				RollCallString,
			iqdmx32SetupLoggingop1embed82
				INTEGER,
			iqdmx32SetupLoggingop1embed82Log
				RollCallString,
			iqdmx32SetupLoggingop1aes11
				INTEGER,
			iqdmx32SetupLoggingop1aes11Log
				RollCallString,
			iqdmx32SetupLoggingop1aes12
				INTEGER,
			iqdmx32SetupLoggingop1aes12Log
				RollCallString,
			iqdmx32SetupLoggingop1aes21
				INTEGER,
			iqdmx32SetupLoggingop1aes21Log
				RollCallString,
			iqdmx32SetupLoggingop1aes22
				INTEGER,
			iqdmx32SetupLoggingop1aes22Log
				RollCallString,
			iqdmx32SetupLoggingop1aes31
				INTEGER,
			iqdmx32SetupLoggingop1aes31Log
				RollCallString,
			iqdmx32SetupLoggingop1aes32
				INTEGER,
			iqdmx32SetupLoggingop1aes32Log
				RollCallString,
			iqdmx32SetupLoggingop1aes41
				INTEGER,
			iqdmx32SetupLoggingop1aes41Log
				RollCallString,
			iqdmx32SetupLoggingop1aes42
				INTEGER,
			iqdmx32SetupLoggingop1aes42Log
				RollCallString,
			iqdmx32SetupLoggingop2embed11
				INTEGER,
			iqdmx32SetupLoggingop2embed11Log
				RollCallString,
			iqdmx32SetupLoggingop2embed12
				INTEGER,
			iqdmx32SetupLoggingop2embed12Log
				RollCallString,
			iqdmx32SetupLoggingop2embed21
				INTEGER,
			iqdmx32SetupLoggingop2embed21Log
				RollCallString,
			iqdmx32SetupLoggingop2embed22
				INTEGER,
			iqdmx32SetupLoggingop2embed22Log
				RollCallString,
			iqdmx32SetupLoggingop2embed31
				INTEGER,
			iqdmx32SetupLoggingop2embed31Log
				RollCallString,
			iqdmx32SetupLoggingop2embed32
				INTEGER,
			iqdmx32SetupLoggingop2embed32Log
				RollCallString,
			iqdmx32SetupLoggingop2embed41
				INTEGER,
			iqdmx32SetupLoggingop2embed41Log
				RollCallString,
			iqdmx32SetupLoggingop2embed42
				INTEGER,
			iqdmx32SetupLoggingop2embed42Log
				RollCallString,
			iqdmx32SetupLoggingop2embed51
				INTEGER,
			iqdmx32SetupLoggingop2embed51Log
				RollCallString,
			iqdmx32SetupLoggingop2embed52
				INTEGER,
			iqdmx32SetupLoggingop2embed52Log
				RollCallString,
			iqdmx32SetupLoggingop2embed61
				INTEGER,
			iqdmx32SetupLoggingop2embed61Log
				RollCallString,
			iqdmx32SetupLoggingop2embed62
				INTEGER,
			iqdmx32SetupLoggingop2embed62Log
				RollCallString,
			iqdmx32SetupLoggingop2embed71
				INTEGER,
			iqdmx32SetupLoggingop2embed71Log
				RollCallString,
			iqdmx32SetupLoggingop2embed72
				INTEGER,
			iqdmx32SetupLoggingop2embed72Log
				RollCallString,
			iqdmx32SetupLoggingop2embed81
				INTEGER,
			iqdmx32SetupLoggingop2embed81Log
				RollCallString,
			iqdmx32SetupLoggingop2embed82
				INTEGER,
			iqdmx32SetupLoggingop2embed82Log
				RollCallString,
			iqdmx32SetupLoggingop2aes11
				INTEGER,
			iqdmx32SetupLoggingop2aes11Log
				RollCallString,
			iqdmx32SetupLoggingop2aes12
				INTEGER,
			iqdmx32SetupLoggingop2aes12Log
				RollCallString,
			iqdmx32SetupLoggingop2aes21
				INTEGER,
			iqdmx32SetupLoggingop2aes21Log
				RollCallString,
			iqdmx32SetupLoggingop2aes22
				INTEGER,
			iqdmx32SetupLoggingop2aes22Log
				RollCallString,
			iqdmx32SetupLoggingop2aes31
				INTEGER,
			iqdmx32SetupLoggingop2aes31Log
				RollCallString,
			iqdmx32SetupLoggingop2aes32
				INTEGER,
			iqdmx32SetupLoggingop2aes32Log
				RollCallString,
			iqdmx32SetupLoggingop2aes41
				INTEGER,
			iqdmx32SetupLoggingop2aes41Log
				RollCallString,
			iqdmx32SetupLoggingop2aes42
				INTEGER,
			iqdmx32SetupLoggingop2aes42Log
				RollCallString,
			iqdmx32SetupRollTracksRollTrackIndex
				INTEGER,
			iqdmx32SetupRollTracksRollTrackSource
				INTEGER,
			iqdmx32SetupRollTracksRollTrackDisable
				INTEGER,
			iqdmx32SetupRollTracksRollTrackAddress
				RollCallString,
			iqdmx32SetupRollTracksRollTrackCommand
				RollCallString,
			iqdmx32SetupRollTracksRollTrackSending
				RollCallString,
			iqdmx32SetupRollTracksRollTrackStatus
				RollCallString,
			iqdmx32SetupRollTracksRollTrackIndexSave
				INTEGER,
			iqdmx32SetupRollTracksRollTrackSourceSave
				INTEGER,
			iqdmx32SetupRollTracksRollTrackAddressSave
				RollCallString,
			iqdmx32SetupRollTracksRollTrackCommandSave
				RollCallString,
			iqdmx32CommonStatusStatusDisplay
				INTEGER,
			iqdmx32CommonStatusProduct
				RollCallString,
			iqdmx32CommonStatusSoftwareVersion
				RollCallString,
			iqdmx32CommonStatusSerialNo
				RollCallString,
			iqdmx32CommonStatusFactoryDefaults
				INTEGER,
			iqdmx32CommonStatusDefaultSetting
				INTEGER,
			iqdmx32CommonStatusRestart
				INTEGER,
			iqdmx32CommonStatusBuild
				RollCallString,
			iqdmx32CommonStatusPCB
				RollCallString,
			iqdmx32CommonStatusKOSVersion
				RollCallString,
			iqdmx32CommonStatusFirmwareVersion
				RollCallString,
			iqdmx32CommonStatusUpTime
				RollCallString
		}

	iqdmx32SlotIndex OBJECT-TYPE
		SYNTAX		Unsigned32
		MAX-ACCESS		not-accessible
		STATUS			current
		DESCRIPTION
				"The unique Index value for each slot.  Its value
					ranges between 1 and the value of slotNumber."
        ::= { iqdmx32CmdEntry 99999 }


	iqdmx32Video1ValidInputFormats62525i OBJECT-TYPE
		SYNTAX		INTEGER { disable(0), enable(1) }
		MAX-ACCESS		read-write
		STATUS			current
		DESCRIPTION
				"TYPE: - Checkbox
				 PAGE: - Channel 1- Video 1
					625/25i  cmdID= 5202 "
		::= { iqdmx32CmdEntry 5202 }


	iqdmx32Video1ValidInputFormats52529i OBJECT-TYPE
		SYNTAX		INTEGER { disable(0), enable(1) }
		MAX-ACCESS		read-write
		STATUS			current
		DESCRIPTION
				"TYPE: - Checkbox
				 PAGE: - Channel 1- Video 1
					525/29i  cmdID= 5203 "
		::= { iqdmx32CmdEntry 5203 }


	iqdmx32Video1ValidInputFormats72050p OBJECT-TYPE
		SYNTAX		INTEGER { disable(0), enable(1) }
		MAX-ACCESS		read-write
		STATUS			current
		DESCRIPTION
				"TYPE: - Checkbox
				 PAGE: - Channel 1- Video 1
					720/50p  cmdID= 5209 "
		::= { iqdmx32CmdEntry 5209 }


	iqdmx32Video1ValidInputFormats72059p OBJECT-TYPE
		SYNTAX		INTEGER { disable(0), enable(1) }
		MAX-ACCESS		read-write
		STATUS			current
		DESCRIPTION
				"TYPE: - Checkbox
				 PAGE: - Channel 1- Video 1
					720/59p  cmdID= 5210 "
		::= { iqdmx32CmdEntry 5210 }


	iqdmx32Video1ValidInputFormats108025i OBJECT-TYPE
		SYNTAX		INTEGER { disable(0), enable(1) }
		MAX-ACCESS		read-write
		STATUS			current
		DESCRIPTION
				"TYPE: - Checkbox
				 PAGE: - Channel 1- Video 1
					1080/25i  cmdID= 5217 "
		::= { iqdmx32CmdEntry 5217 }


	iqdmx32Video1ValidInputFormats108029i OBJECT-TYPE
		SYNTAX		INTEGER { disable(0), enable(1) }
		MAX-ACCESS		read-write
		STATUS			current
		DESCRIPTION
				"TYPE: - Checkbox
				 PAGE: - Channel 1- Video 1
					1080/29i  cmdID= 5218 "
		::= { iqdmx32CmdEntry 5218 }


	iqdmx32Video1ValidInputFormats108050pA OBJECT-TYPE
		SYNTAX		INTEGER { disable(0), enable(1) }
		MAX-ACCESS		read-write
		STATUS			current
		DESCRIPTION
				"TYPE: - Checkbox
				 PAGE: - Channel 1- Video 1
					1080/50p-A  cmdID= 5222 "
		::= { iqdmx32CmdEntry 5222 }


	iqdmx32Video1ValidInputFormats108059pA OBJECT-TYPE
		SYNTAX		INTEGER { disable(0), enable(1) }
		MAX-ACCESS		read-write
		STATUS			current
		DESCRIPTION
				"TYPE: - Checkbox
				 PAGE: - Channel 1- Video 1
					1080/59p-A  cmdID= 5223 "
		::= { iqdmx32CmdEntry 5223 }


	iqdmx32Video1ValidInputFormats108050pB OBJECT-TYPE
		SYNTAX		INTEGER { disable(0), enable(1) }
		MAX-ACCESS		read-write
		STATUS			current
		DESCRIPTION
				"TYPE: - Checkbox
				 PAGE: - Channel 1- Video 1
					1080/50p-B  cmdID= 5225 "
		::= { iqdmx32CmdEntry 5225 }


	iqdmx32Video1ValidInputFormats108059pB OBJECT-TYPE
		SYNTAX		INTEGER { disable(0), enable(1) }
		MAX-ACCESS		read-write
		STATUS			current
		DESCRIPTION
				"TYPE: - Checkbox
				 PAGE: - Channel 1- Video 1
					1080/59p-B  cmdID= 5226 "
		::= { iqdmx32CmdEntry 5226 }


	iqdmx32Channel1Video1DefaultFormat OBJECT-TYPE
		SYNTAX		INTEGER {
							val-Last-Known-Good(1),
							val-625-25i(2),
							val-525-29i(3),
							val-720-50p(9),
							val-720-59p(10),
							val-1080-25i(17),
							val-1080-29i(18),
							val-1080-50p-A(22),
							val-1080-59p-A(23),
							val-1080-50p-B(25),
							val-1080-59p-B(26)
							}
		MAX-ACCESS		read-write
		STATUS			current
		DESCRIPTION
				"TYPE: - RadiobuttonList
				 PAGE: - Channel 1- Video 1
					Default Format  cmdID= 5136 
					Last Known Good  value= 1  
					625/25i  value= 2  
					525/29i  value= 3  
					720/50p  value= 9  
					720/59p  value= 10  
					1080/25i  value= 17  
					1080/29i  value= 18  
					1080/50p-A  value= 22  
					1080/59p-A  value= 23  
					1080/50p-B  value= 25  
					1080/59p-B  value= 26  "
		::= { iqdmx32CmdEntry 5136 }


	iqdmx32Channel1Video1DefaultOutput OBJECT-TYPE
		SYNTAX		INTEGER {
							val-Black(0),
							val-Freeze(1),
							val-Pattern(2)
							}
		MAX-ACCESS		read-write
		STATUS			current
		DESCRIPTION
				"TYPE: - RadiobuttonList
				 PAGE: - Channel 1- Video 1
					Default Output  cmdID= 2623 
					Black  value= 0  
					Freeze  value= 1  
					Pattern  value= 2  "
		::= { iqdmx32CmdEntry 2623 }


	iqdmx32Video1VideoProcampProcAmpEnable OBJECT-TYPE
		SYNTAX		INTEGER { disable(0), enable(1) }
		MAX-ACCESS		read-write
		STATUS			current
		DESCRIPTION
				"TYPE: - Checkbox
				 PAGE: - Channel 1- Video 1
					ProcAmp Enable  cmdID= 2864 "
		::= { iqdmx32CmdEntry 2864 }


	iqdmx32Video1VideoProcampBlackLevel OBJECT-TYPE
		SYNTAX		INTEGER
		MAX-ACCESS		read-write
		STATUS			current
		DESCRIPTION
				"TYPE: - Number
				 PAGE: - Channel 1- Video 1
					Black Level  cmdID= 2708  min= -1000  max= 1000  step= 8  format= %3.1fmV  div_scale= 10 
					Min = -100.0mV  Max = 100.0mV  Step = 0.8mV "
		::= { iqdmx32CmdEntry 2708 }


	iqdmx32Video1VideoProcampHueAdjust OBJECT-TYPE
		SYNTAX		INTEGER
		MAX-ACCESS		read-write
		STATUS			current
		DESCRIPTION
				"TYPE: - Number
				 PAGE: - Channel 1- Video 1
					Hue Adjust  cmdID= 3622  min= -180  max= 180  step= 1  format= %1.0fdeg  div_scale= 1 
					Min = -180deg  Max = 180deg  Step = 1deg "
		::= { iqdmx32CmdEntry 3622 }


	iqdmx32Video1VideoProcampMasterVideoGain OBJECT-TYPE
		SYNTAX		INTEGER
		MAX-ACCESS		read-write
		STATUS			current
		DESCRIPTION
				"TYPE: - Number
				 PAGE: - Channel 1- Video 1
					Master Video Gain  cmdID= 3780  min= -60  max= 60  step= 1  format= %0.1fdB  div_scale= 10 
					Min = -6.0dB  Max = 6.0dB  Step = 0.1dB "
		::= { iqdmx32CmdEntry 3780 }


	iqdmx32Video1VideoProcampYGain OBJECT-TYPE
		SYNTAX		INTEGER
		MAX-ACCESS		read-write
		STATUS			current
		DESCRIPTION
				"TYPE: - Number
				 PAGE: - Channel 1- Video 1
					Y Gain  cmdID= 2707  min= -60  max= 60  step= 1  format= %0.1fdB  div_scale= 10 
					Min = -6.0dB  Max = 6.0dB  Step = 0.1dB "
		::= { iqdmx32CmdEntry 2707 }


	iqdmx32Video1VideoProcampCbCrGain OBJECT-TYPE
		SYNTAX		INTEGER
		MAX-ACCESS		read-write
		STATUS			current
		DESCRIPTION
				"TYPE: - Number
				 PAGE: - Channel 1- Video 1
					Cb/Cr Gain  cmdID= 2706  min= -60  max= 60  step= 1  format= %0.1fdB  div_scale= 10 
					Min = -6.0dB  Max = 6.0dB  Step = 0.1dB "
		::= { iqdmx32CmdEntry 2706 }


	iqdmx32Video1VideoProcampYCTiming OBJECT-TYPE
		SYNTAX		INTEGER
		MAX-ACCESS		read-write
		STATUS			current
		DESCRIPTION
				"TYPE: - Number
				 PAGE: - Channel 1- Video 1
					Y/C Timing  cmdID= 2924  min= -8  max= 8  step= 2  format= %1.0f pixels  div_scale= 1 
					Min = -8 pixels  Max = 8 pixels  Step = 2 pixels "
		::= { iqdmx32CmdEntry 2924 }


	iqdmx32Video1VideoProcampPictureposition OBJECT-TYPE
		SYNTAX		INTEGER
		MAX-ACCESS		read-write
		STATUS			current
		DESCRIPTION
				"TYPE: - Number
				 PAGE: - Channel 1- Video 1
					Picture position  cmdID= 2709  min= -8  max= 8  step= 2  format= %1.0f pixels  div_scale= 1 
					Min = -8 pixels  Max = 8 pixels  Step = 2 pixels "
		::= { iqdmx32CmdEntry 2709 }


	iqdmx32Video1VideoProcampModalIndex OBJECT-TYPE
		SYNTAX		INTEGER
		MAX-ACCESS		read-write
		STATUS			current
		DESCRIPTION
				"TYPE: - Number
				 PAGE: - Channel 1- Video 1
					Modal Index  cmdID= 5006  min= 0  max= 1  step= 1  format= %1.0f  div_scale= 1 
					Min = 0  Max = 1  Step = 1 "
		::= { iqdmx32CmdEntry 5006 }


	iqdmx32Video1VideoProcampYCTimingnm OBJECT-TYPE
		SYNTAX		INTEGER
		MAX-ACCESS		read-write
		STATUS			current
		DESCRIPTION
				"TYPE: - Number
				 PAGE: - Channel 1- Video 1
					Y/C Timing nm  cmdID= 5008  min= -16  max= 16  step= 2  format= %1.0f pixels  div_scale= 1 
					Min = -16 pixels  Max = 16 pixels  Step = 2 pixels "
		::= { iqdmx32CmdEntry 5008 }


	iqdmx32Video1VideoProcampPicturepositionnm OBJECT-TYPE
		SYNTAX		INTEGER
		MAX-ACCESS		read-write
		STATUS			current
		DESCRIPTION
				"TYPE: - Number
				 PAGE: - Channel 1- Video 1
					Picture position nm  cmdID= 5007  min= -16  max= 16  step= 2  format= %1.0f pixels  div_scale= 1 
					Min = -16 pixels  Max = 16 pixels  Step = 2 pixels "
		::= { iqdmx32CmdEntry 5007 }


	iqdmx32Video1BlankingBlankVANC OBJECT-TYPE
		SYNTAX		INTEGER { disable(0), enable(1) }
		MAX-ACCESS		read-write
		STATUS			current
		DESCRIPTION
				"TYPE: - Checkbox
				 PAGE: - Channel 1- Video 1
					Blank VANC  cmdID= 3949 "
		::= { iqdmx32CmdEntry 3949 }


	iqdmx32Blanking625BlankLinesLine23ch1 OBJECT-TYPE
		SYNTAX		INTEGER { disable(0), enable(1) }
		MAX-ACCESS		read-write
		STATUS			current
		DESCRIPTION
				"TYPE: - Checkbox
				 PAGE: - Channel 1- Video 1
					Line 23  cmdID= 3951 "
		::= { iqdmx32CmdEntry 3951 }


	iqdmx32Blanking625BlankLinesLine336ch1 OBJECT-TYPE
		SYNTAX		INTEGER { disable(0), enable(1) }
		MAX-ACCESS		read-write
		STATUS			current
		DESCRIPTION
				"TYPE: - Checkbox
				 PAGE: - Channel 1- Video 1
					Line 336  cmdID= 3952 "
		::= { iqdmx32CmdEntry 3952 }


	iqdmx32Blanking525BlankLinesLine21ch1 OBJECT-TYPE
		SYNTAX		INTEGER { disable(0), enable(1) }
		MAX-ACCESS		read-write
		STATUS			current
		DESCRIPTION
				"TYPE: - Checkbox
				 PAGE: - Channel 1- Video 1
					Line 21  cmdID= 3953 "
		::= { iqdmx32CmdEntry 3953 }


	iqdmx32Blanking525BlankLinesLine22ch1 OBJECT-TYPE
		SYNTAX		INTEGER { disable(0), enable(1) }
		MAX-ACCESS		read-write
		STATUS			current
		DESCRIPTION
				"TYPE: - Checkbox
				 PAGE: - Channel 1- Video 1
					Line 22  cmdID= 3955 "
		::= { iqdmx32CmdEntry 3955 }


	iqdmx32Blanking525BlankLinesLine283ch1 OBJECT-TYPE
		SYNTAX		INTEGER { disable(0), enable(1) }
		MAX-ACCESS		read-write
		STATUS			current
		DESCRIPTION
				"TYPE: - Checkbox
				 PAGE: - Channel 1- Video 1
					Line 283  cmdID= 3954 "
		::= { iqdmx32CmdEntry 3954 }


	iqdmx32Blanking525BlankLinesLine284ch1 OBJECT-TYPE
		SYNTAX		INTEGER { disable(0), enable(1) }
		MAX-ACCESS		read-write
		STATUS			current
		DESCRIPTION
				"TYPE: - Checkbox
				 PAGE: - Channel 1- Video 1
					Line 284  cmdID= 3956 "
		::= { iqdmx32CmdEntry 3956 }


	iqdmx32Video1BlankingBlankHANC OBJECT-TYPE
		SYNTAX		INTEGER { disable(0), enable(1) }
		MAX-ACCESS		read-write
		STATUS			current
		DESCRIPTION
				"TYPE: - Checkbox
				 PAGE: - Channel 1- Video 1
					Blank HANC  cmdID= 3947 "
		::= { iqdmx32CmdEntry 3947 }


	iqdmx32Video1Caption OBJECT-TYPE
		SYNTAX		INTEGER {
							val-Off(0),
							val-On(1)
							}
		MAX-ACCESS		read-write
		STATUS			current
		DESCRIPTION
				"TYPE: - Button
				 PAGE: - Channel 1- Video 1
					Off  cmdID= 1037  value= 0  
					On  cmdID= 1037  value= 1  "
		::= { iqdmx32CmdEntry 1037 }


	iqdmx32Video1CaptionEditCaption OBJECT-TYPE
		SYNTAX		RollCallString
		MAX-ACCESS		read-write
		STATUS			current
		DESCRIPTION
				"TYPE: - Editstring
				 PAGE: - Channel 1- Video 1
					Edit Caption  cmdID= 1041  "
		::= { iqdmx32CmdEntry 1041 }


	iqdmx32Channel1Video1Pattern OBJECT-TYPE
		SYNTAX		INTEGER {
							val-Off(0),
							val-Black(1),
							val-Bars(2)
							}
		MAX-ACCESS		read-write
		STATUS			current
		DESCRIPTION
				"TYPE: - RadiobuttonList
				 PAGE: - Channel 1- Video 1
					Pattern  cmdID= 2624 
					Off  value= 0  
					Black  value= 1  
					Bars  value= 2  "
		::= { iqdmx32CmdEntry 2624 }


	iqdmx32Video1Freeze OBJECT-TYPE
		SYNTAX		INTEGER {
							val-Field(0),
							val-Frame(1)
							}
		MAX-ACCESS		read-write
		STATUS			current
		DESCRIPTION
				"TYPE: - Button
				 PAGE: - Channel 1- Video 1
					Field  cmdID= 5023  value= 0  
					Frame  cmdID= 5023  value= 1  "
		::= { iqdmx32CmdEntry 5023 }


	iqdmx32Video1FreezeManualFreeze OBJECT-TYPE
		SYNTAX		INTEGER { disable(0), enable(1) }
		MAX-ACCESS		read-write
		STATUS			current
		DESCRIPTION
				"TYPE: - Checkbox
				 PAGE: - Channel 1- Video 1
					Manual Freeze  cmdID= 5022 "
		::= { iqdmx32CmdEntry 5022 }


	iqdmx32EmbeddersEmbedder1Enablech1 OBJECT-TYPE
		SYNTAX		INTEGER { disable(0), enable(1) }
		MAX-ACCESS		read-write
		STATUS			current
		DESCRIPTION
				"TYPE: - Checkbox
				 PAGE: - Channel 1- Audio 1- Embedders- Embedder 1
					Enable  cmdID= 5066 "
		::= { iqdmx32CmdEntry 5066 }


	iqdmx32EmbeddersEmbedder1SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 1
					Source L / Non-PCM  cmdID= 5034 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5034 }


	iqdmx32EmbeddersEmbedder1SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 1
					Source R  cmdID= 5035 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5035 }


	iqdmx32EmbeddersEmbedder1MutePair1 OBJECT-TYPE
		SYNTAX		INTEGER { disable(0), enable(1) }
		MAX-ACCESS		read-write
		STATUS			current
		DESCRIPTION
				"TYPE: - Checkbox
				 PAGE: - Channel 1- Audio 1- Embedders- Embedder 1
					Mute  cmdID= 3240 "
		::= { iqdmx32CmdEntry 3240 }


	iqdmx32EmbeddersEmbedder1MuteonVbitPair1 OBJECT-TYPE
		SYNTAX		INTEGER { disable(0), enable(1) }
		MAX-ACCESS		read-write
		STATUS			current
		DESCRIPTION
				"TYPE: - Checkbox
				 PAGE: - Channel 1- Audio 1- Embedders- Embedder 1
					Mute on V bit  cmdID= 3272 "
		::= { iqdmx32CmdEntry 3272 }


	iqdmx32EmbeddersEmbedder1InvertLPair1 OBJECT-TYPE
		SYNTAX		INTEGER { disable(0), enable(1) }
		MAX-ACCESS		read-write
		STATUS			current
		DESCRIPTION
				"TYPE: - Checkbox
				 PAGE: - Channel 1- Audio 1- Embedders- Embedder 1
					Invert L  cmdID= 3160 "
		::= { iqdmx32CmdEntry 3160 }


	iqdmx32EmbeddersEmbedder1InvertRPair1 OBJECT-TYPE
		SYNTAX		INTEGER { disable(0), enable(1) }
		MAX-ACCESS		read-write
		STATUS			current
		DESCRIPTION
				"TYPE: - Checkbox
				 PAGE: - Channel 1- Audio 1- Embedders- Embedder 1
					Invert R  cmdID= 3161 "
		::= { iqdmx32CmdEntry 3161 }


	iqdmx32EmbeddersEmbedder1GainLPair1 OBJECT-TYPE
		SYNTAX		INTEGER
		MAX-ACCESS		read-write
		STATUS			current
		DESCRIPTION
				"TYPE: - Number
				 PAGE: - Channel 1- Audio 1- Embedders- Embedder 1
					Gain L  cmdID= 3080  min= -720  max= 120  step= 1  format= %0.1fdB  div_scale= 10 
					Min = -72.0dB  Max = 12.0dB  Step = 0.1dB "
		::= { iqdmx32CmdEntry 3080 }


	iqdmx32EmbeddersEmbedder1GainRPair1 OBJECT-TYPE
		SYNTAX		INTEGER
		MAX-ACCESS		read-write
		STATUS			current
		DESCRIPTION
				"TYPE: - Number
				 PAGE: - Channel 1- Audio 1- Embedders- Embedder 1
					Gain R  cmdID= 3081  min= -720  max= 120  step= 1  format= %0.1fdB  div_scale= 10 
					Min = -72.0dB  Max = 12.0dB  Step = 0.1dB "
		::= { iqdmx32CmdEntry 3081 }


	iqdmx32EmbeddersEmbedder1PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 1
					Pair Mode  cmdID= 3930 
					2 Channel PCM  value= 0  
					Stereo PCM  value= 1  
					nonPCM  value= 2  "
		::= { iqdmx32CmdEntry 3930 }


	iqdmx32EmbeddersEmbedder1SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 1
					Source L / Non-PCM  cmdID= 5036 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5036 }


	iqdmx32EmbeddersEmbedder1SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 1
					Source R  cmdID= 5037 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5037 }


	iqdmx32EmbeddersEmbedder1MutePair2 OBJECT-TYPE
		SYNTAX		INTEGER { disable(0), enable(1) }
		MAX-ACCESS		read-write
		STATUS			current
		DESCRIPTION
				"TYPE: - Checkbox
				 PAGE: - Channel 1- Audio 1- Embedders- Embedder 1
					Mute  cmdID= 3241 "
		::= { iqdmx32CmdEntry 3241 }


	iqdmx32EmbeddersEmbedder1MuteonVbitPair2 OBJECT-TYPE
		SYNTAX		INTEGER { disable(0), enable(1) }
		MAX-ACCESS		read-write
		STATUS			current
		DESCRIPTION
				"TYPE: - Checkbox
				 PAGE: - Channel 1- Audio 1- Embedders- Embedder 1
					Mute on V bit  cmdID= 3273 "
		::= { iqdmx32CmdEntry 3273 }


	iqdmx32EmbeddersEmbedder1InvertLPair2 OBJECT-TYPE
		SYNTAX		INTEGER { disable(0), enable(1) }
		MAX-ACCESS		read-write
		STATUS			current
		DESCRIPTION
				"TYPE: - Checkbox
				 PAGE: - Channel 1- Audio 1- Embedders- Embedder 1
					Invert L  cmdID= 3162 "
		::= { iqdmx32CmdEntry 3162 }


	iqdmx32EmbeddersEmbedder1InvertRPair2 OBJECT-TYPE
		SYNTAX		INTEGER { disable(0), enable(1) }
		MAX-ACCESS		read-write
		STATUS			current
		DESCRIPTION
				"TYPE: - Checkbox
				 PAGE: - Channel 1- Audio 1- Embedders- Embedder 1
					Invert R  cmdID= 3163 "
		::= { iqdmx32CmdEntry 3163 }


	iqdmx32EmbeddersEmbedder1GainLPair2 OBJECT-TYPE
		SYNTAX		INTEGER
		MAX-ACCESS		read-write
		STATUS			current
		DESCRIPTION
				"TYPE: - Number
				 PAGE: - Channel 1- Audio 1- Embedders- Embedder 1
					Gain L  cmdID= 3082  min= -720  max= 120  step= 1  format= %0.1fdB  div_scale= 10 
					Min = -72.0dB  Max = 12.0dB  Step = 0.1dB "
		::= { iqdmx32CmdEntry 3082 }


	iqdmx32EmbeddersEmbedder1GainRPair2 OBJECT-TYPE
		SYNTAX		INTEGER
		MAX-ACCESS		read-write
		STATUS			current
		DESCRIPTION
				"TYPE: - Number
				 PAGE: - Channel 1- Audio 1- Embedders- Embedder 1
					Gain R  cmdID= 3083  min= -720  max= 120  step= 1  format= %0.1fdB  div_scale= 10 
					Min = -72.0dB  Max = 12.0dB  Step = 0.1dB "
		::= { iqdmx32CmdEntry 3083 }


	iqdmx32EmbeddersEmbedder1PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 1
					Pair Mode  cmdID= 3931 
					2 Channel PCM  value= 0  
					Stereo PCM  value= 1  
					nonPCM  value= 2  "
		::= { iqdmx32CmdEntry 3931 }


	iqdmx32EmbeddersEmbedder1NonModalIndexPair2 OBJECT-TYPE
		SYNTAX		INTEGER
		MAX-ACCESS		read-write
		STATUS			current
		DESCRIPTION
				"TYPE: - Number
				 PAGE: - Channel 1- Audio 1- Embedders- Embedder 1
					NonModal Index  cmdID= 5338  min= 0  max= 31  step= 1  format=   div_scale= 1 
					Min =   Max =   Step =  "
		::= { iqdmx32CmdEntry 5338 }


	iqdmx32EmbeddersEmbedder1NonModalGainPair2 OBJECT-TYPE
		SYNTAX		INTEGER
		MAX-ACCESS		read-write
		STATUS			current
		DESCRIPTION
				"TYPE: - Number
				 PAGE: - Channel 1- Audio 1- Embedders- Embedder 1
					NonModal Gain  cmdID= 5339  min= -720  max= 120  step= 1  format=   div_scale= 10 
					Min =   Max =   Step =  "
		::= { iqdmx32CmdEntry 5339 }


	iqdmx32EmbeddersEmbedder1NonModalIndexPair2 OBJECT-TYPE
		SYNTAX		INTEGER
		MAX-ACCESS		read-write
		STATUS			current
		DESCRIPTION
				"TYPE: - Number
				 PAGE: - Channel 1- Audio 1- Embedders- Embedder 1
					NonModal Index  cmdID= 5340  min= 0  max= 15  step= 1  format=   div_scale= 1 
					Min =   Max =   Step =  "
		::= { iqdmx32CmdEntry 5340 }


	iqdmx32EmbeddersEmbedder1NonModalGainPair2 OBJECT-TYPE
		SYNTAX		INTEGER
		MAX-ACCESS		read-write
		STATUS			current
		DESCRIPTION
				"TYPE: - Number
				 PAGE: - Channel 1- Audio 1- Embedders- Embedder 1
					NonModal Gain  cmdID= 5341  min= -720  max= 120  step= 1  format=   div_scale= 10 
					Min =   Max =   Step =  "
		::= { iqdmx32CmdEntry 5341 }


	iqdmx32EmbeddersEmbedder2EnablePair2 OBJECT-TYPE
		SYNTAX		INTEGER { disable(0), enable(1) }
		MAX-ACCESS		read-write
		STATUS			current
		DESCRIPTION
				"TYPE: - Checkbox
				 PAGE: - Channel 1- Audio 1- Embedders- Embedder 2
					Enable  cmdID= 5067 "
		::= { iqdmx32CmdEntry 5067 }


	iqdmx32EmbeddersEmbedder2SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 2
					Source L / Non-PCM  cmdID= 5038 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5038 }


	iqdmx32EmbeddersEmbedder2SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 2
					Source R  cmdID= 5039 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5039 }


	iqdmx32EmbeddersEmbedder2MutePair1 OBJECT-TYPE
		SYNTAX		INTEGER { disable(0), enable(1) }
		MAX-ACCESS		read-write
		STATUS			current
		DESCRIPTION
				"TYPE: - Checkbox
				 PAGE: - Channel 1- Audio 1- Embedders- Embedder 2
					Mute  cmdID= 3242 "
		::= { iqdmx32CmdEntry 3242 }


	iqdmx32EmbeddersEmbedder2MuteonVbitPair1 OBJECT-TYPE
		SYNTAX		INTEGER { disable(0), enable(1) }
		MAX-ACCESS		read-write
		STATUS			current
		DESCRIPTION
				"TYPE: - Checkbox
				 PAGE: - Channel 1- Audio 1- Embedders- Embedder 2
					Mute on V bit  cmdID= 3274 "
		::= { iqdmx32CmdEntry 3274 }


	iqdmx32EmbeddersEmbedder2InvertLPair1 OBJECT-TYPE
		SYNTAX		INTEGER { disable(0), enable(1) }
		MAX-ACCESS		read-write
		STATUS			current
		DESCRIPTION
				"TYPE: - Checkbox
				 PAGE: - Channel 1- Audio 1- Embedders- Embedder 2
					Invert L  cmdID= 3164 "
		::= { iqdmx32CmdEntry 3164 }


	iqdmx32EmbeddersEmbedder2InvertRPair1 OBJECT-TYPE
		SYNTAX		INTEGER { disable(0), enable(1) }
		MAX-ACCESS		read-write
		STATUS			current
		DESCRIPTION
				"TYPE: - Checkbox
				 PAGE: - Channel 1- Audio 1- Embedders- Embedder 2
					Invert R  cmdID= 3165 "
		::= { iqdmx32CmdEntry 3165 }


	iqdmx32EmbeddersEmbedder2GainLPair1 OBJECT-TYPE
		SYNTAX		INTEGER
		MAX-ACCESS		read-write
		STATUS			current
		DESCRIPTION
				"TYPE: - Number
				 PAGE: - Channel 1- Audio 1- Embedders- Embedder 2
					Gain L  cmdID= 3084  min= -720  max= 120  step= 1  format= %0.1fdB  div_scale= 10 
					Min = -72.0dB  Max = 12.0dB  Step = 0.1dB "
		::= { iqdmx32CmdEntry 3084 }


	iqdmx32EmbeddersEmbedder2GainRPair1 OBJECT-TYPE
		SYNTAX		INTEGER
		MAX-ACCESS		read-write
		STATUS			current
		DESCRIPTION
				"TYPE: - Number
				 PAGE: - Channel 1- Audio 1- Embedders- Embedder 2
					Gain R  cmdID= 3085  min= -720  max= 120  step= 1  format= %0.1fdB  div_scale= 10 
					Min = -72.0dB  Max = 12.0dB  Step = 0.1dB "
		::= { iqdmx32CmdEntry 3085 }


	iqdmx32EmbeddersEmbedder2PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 2
					Pair Mode  cmdID= 3932 
					2 Channel PCM  value= 0  
					Stereo PCM  value= 1  
					nonPCM  value= 2  "
		::= { iqdmx32CmdEntry 3932 }


	iqdmx32EmbeddersEmbedder2SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 2
					Source L / Non-PCM  cmdID= 5040 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5040 }


	iqdmx32EmbeddersEmbedder2SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 2
					Source R  cmdID= 5041 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5041 }


	iqdmx32EmbeddersEmbedder2MutePair2 OBJECT-TYPE
		SYNTAX		INTEGER { disable(0), enable(1) }
		MAX-ACCESS		read-write
		STATUS			current
		DESCRIPTION
				"TYPE: - Checkbox
				 PAGE: - Channel 1- Audio 1- Embedders- Embedder 2
					Mute  cmdID= 3243 "
		::= { iqdmx32CmdEntry 3243 }


	iqdmx32EmbeddersEmbedder2MuteonVbitPair2 OBJECT-TYPE
		SYNTAX		INTEGER { disable(0), enable(1) }
		MAX-ACCESS		read-write
		STATUS			current
		DESCRIPTION
				"TYPE: - Checkbox
				 PAGE: - Channel 1- Audio 1- Embedders- Embedder 2
					Mute on V bit  cmdID= 3275 "
		::= { iqdmx32CmdEntry 3275 }


	iqdmx32EmbeddersEmbedder2InvertLPair2 OBJECT-TYPE
		SYNTAX		INTEGER { disable(0), enable(1) }
		MAX-ACCESS		read-write
		STATUS			current
		DESCRIPTION
				"TYPE: - Checkbox
				 PAGE: - Channel 1- Audio 1- Embedders- Embedder 2
					Invert L  cmdID= 3166 "
		::= { iqdmx32CmdEntry 3166 }


	iqdmx32EmbeddersEmbedder2InvertRPair2 OBJECT-TYPE
		SYNTAX		INTEGER { disable(0), enable(1) }
		MAX-ACCESS		read-write
		STATUS			current
		DESCRIPTION
				"TYPE: - Checkbox
				 PAGE: - Channel 1- Audio 1- Embedders- Embedder 2
					Invert R  cmdID= 3167 "
		::= { iqdmx32CmdEntry 3167 }


	iqdmx32EmbeddersEmbedder2GainLPair2 OBJECT-TYPE
		SYNTAX		INTEGER
		MAX-ACCESS		read-write
		STATUS			current
		DESCRIPTION
				"TYPE: - Number
				 PAGE: - Channel 1- Audio 1- Embedders- Embedder 2
					Gain L  cmdID= 3086  min= -720  max= 120  step= 1  format= %0.1fdB  div_scale= 10 
					Min = -72.0dB  Max = 12.0dB  Step = 0.1dB "
		::= { iqdmx32CmdEntry 3086 }


	iqdmx32EmbeddersEmbedder2GainRPair2 OBJECT-TYPE
		SYNTAX		INTEGER
		MAX-ACCESS		read-write
		STATUS			current
		DESCRIPTION
				"TYPE: - Number
				 PAGE: - Channel 1- Audio 1- Embedders- Embedder 2
					Gain R  cmdID= 3087  min= -720  max= 120  step= 1  format= %0.1fdB  div_scale= 10 
					Min = -72.0dB  Max = 12.0dB  Step = 0.1dB "
		::= { iqdmx32CmdEntry 3087 }


	iqdmx32EmbeddersEmbedder2PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 2
					Pair Mode  cmdID= 3933 
					2 Channel PCM  value= 0  
					Stereo PCM  value= 1  
					nonPCM  value= 2  "
		::= { iqdmx32CmdEntry 3933 }


	iqdmx32EmbeddersEmbedder3EnablePair2 OBJECT-TYPE
		SYNTAX		INTEGER { disable(0), enable(1) }
		MAX-ACCESS		read-write
		STATUS			current
		DESCRIPTION
				"TYPE: - Checkbox
				 PAGE: - Channel 1- Audio 1- Embedders- Embedder 3
					Enable  cmdID= 5068 "
		::= { iqdmx32CmdEntry 5068 }


	iqdmx32EmbeddersEmbedder3SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 3
					Source L / Non-PCM  cmdID= 5042 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5042 }


	iqdmx32EmbeddersEmbedder3SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 3
					Source R  cmdID= 5043 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5043 }


	iqdmx32EmbeddersEmbedder3MutePair1 OBJECT-TYPE
		SYNTAX		INTEGER { disable(0), enable(1) }
		MAX-ACCESS		read-write
		STATUS			current
		DESCRIPTION
				"TYPE: - Checkbox
				 PAGE: - Channel 1- Audio 1- Embedders- Embedder 3
					Mute  cmdID= 3244 "
		::= { iqdmx32CmdEntry 3244 }


	iqdmx32EmbeddersEmbedder3MuteonVbitPair1 OBJECT-TYPE
		SYNTAX		INTEGER { disable(0), enable(1) }
		MAX-ACCESS		read-write
		STATUS			current
		DESCRIPTION
				"TYPE: - Checkbox
				 PAGE: - Channel 1- Audio 1- Embedders- Embedder 3
					Mute on V bit  cmdID= 3276 "
		::= { iqdmx32CmdEntry 3276 }


	iqdmx32EmbeddersEmbedder3InvertLPair1 OBJECT-TYPE
		SYNTAX		INTEGER { disable(0), enable(1) }
		MAX-ACCESS		read-write
		STATUS			current
		DESCRIPTION
				"TYPE: - Checkbox
				 PAGE: - Channel 1- Audio 1- Embedders- Embedder 3
					Invert L  cmdID= 3168 "
		::= { iqdmx32CmdEntry 3168 }


	iqdmx32EmbeddersEmbedder3InvertRPair1 OBJECT-TYPE
		SYNTAX		INTEGER { disable(0), enable(1) }
		MAX-ACCESS		read-write
		STATUS			current
		DESCRIPTION
				"TYPE: - Checkbox
				 PAGE: - Channel 1- Audio 1- Embedders- Embedder 3
					Invert R  cmdID= 3169 "
		::= { iqdmx32CmdEntry 3169 }


	iqdmx32EmbeddersEmbedder3GainLPair1 OBJECT-TYPE
		SYNTAX		INTEGER
		MAX-ACCESS		read-write
		STATUS			current
		DESCRIPTION
				"TYPE: - Number
				 PAGE: - Channel 1- Audio 1- Embedders- Embedder 3
					Gain L  cmdID= 3088  min= -720  max= 120  step= 1  format= %0.1fdB  div_scale= 10 
					Min = -72.0dB  Max = 12.0dB  Step = 0.1dB "
		::= { iqdmx32CmdEntry 3088 }


	iqdmx32EmbeddersEmbedder3GainRPair1 OBJECT-TYPE
		SYNTAX		INTEGER
		MAX-ACCESS		read-write
		STATUS			current
		DESCRIPTION
				"TYPE: - Number
				 PAGE: - Channel 1- Audio 1- Embedders- Embedder 3
					Gain R  cmdID= 3089  min= -720  max= 120  step= 1  format= %0.1fdB  div_scale= 10 
					Min = -72.0dB  Max = 12.0dB  Step = 0.1dB "
		::= { iqdmx32CmdEntry 3089 }


	iqdmx32EmbeddersEmbedder3PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 3
					Pair Mode  cmdID= 3934 
					2 Channel PCM  value= 0  
					Stereo PCM  value= 1  
					nonPCM  value= 2  "
		::= { iqdmx32CmdEntry 3934 }


	iqdmx32EmbeddersEmbedder3SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 3
					Source L / Non-PCM  cmdID= 5044 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5044 }


	iqdmx32EmbeddersEmbedder3SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 3
					Source R  cmdID= 5045 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5045 }


	iqdmx32EmbeddersEmbedder3MutePair2 OBJECT-TYPE
		SYNTAX		INTEGER { disable(0), enable(1) }
		MAX-ACCESS		read-write
		STATUS			current
		DESCRIPTION
				"TYPE: - Checkbox
				 PAGE: - Channel 1- Audio 1- Embedders- Embedder 3
					Mute  cmdID= 3245 "
		::= { iqdmx32CmdEntry 3245 }


	iqdmx32EmbeddersEmbedder3MuteonVbitPair2 OBJECT-TYPE
		SYNTAX		INTEGER { disable(0), enable(1) }
		MAX-ACCESS		read-write
		STATUS			current
		DESCRIPTION
				"TYPE: - Checkbox
				 PAGE: - Channel 1- Audio 1- Embedders- Embedder 3
					Mute on V bit  cmdID= 3277 "
		::= { iqdmx32CmdEntry 3277 }


	iqdmx32EmbeddersEmbedder3InvertLPair2 OBJECT-TYPE
		SYNTAX		INTEGER { disable(0), enable(1) }
		MAX-ACCESS		read-write
		STATUS			current
		DESCRIPTION
				"TYPE: - Checkbox
				 PAGE: - Channel 1- Audio 1- Embedders- Embedder 3
					Invert L  cmdID= 3170 "
		::= { iqdmx32CmdEntry 3170 }


	iqdmx32EmbeddersEmbedder3InvertRPair2 OBJECT-TYPE
		SYNTAX		INTEGER { disable(0), enable(1) }
		MAX-ACCESS		read-write
		STATUS			current
		DESCRIPTION
				"TYPE: - Checkbox
				 PAGE: - Channel 1- Audio 1- Embedders- Embedder 3
					Invert R  cmdID= 3171 "
		::= { iqdmx32CmdEntry 3171 }


	iqdmx32EmbeddersEmbedder3GainLPair2 OBJECT-TYPE
		SYNTAX		INTEGER
		MAX-ACCESS		read-write
		STATUS			current
		DESCRIPTION
				"TYPE: - Number
				 PAGE: - Channel 1- Audio 1- Embedders- Embedder 3
					Gain L  cmdID= 3090  min= -720  max= 120  step= 1  format= %0.1fdB  div_scale= 10 
					Min = -72.0dB  Max = 12.0dB  Step = 0.1dB "
		::= { iqdmx32CmdEntry 3090 }


	iqdmx32EmbeddersEmbedder3GainRPair2 OBJECT-TYPE
		SYNTAX		INTEGER
		MAX-ACCESS		read-write
		STATUS			current
		DESCRIPTION
				"TYPE: - Number
				 PAGE: - Channel 1- Audio 1- Embedders- Embedder 3
					Gain R  cmdID= 3091  min= -720  max= 120  step= 1  format= %0.1fdB  div_scale= 10 
					Min = -72.0dB  Max = 12.0dB  Step = 0.1dB "
		::= { iqdmx32CmdEntry 3091 }


	iqdmx32EmbeddersEmbedder3PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 3
					Pair Mode  cmdID= 3935 
					2 Channel PCM  value= 0  
					Stereo PCM  value= 1  
					nonPCM  value= 2  "
		::= { iqdmx32CmdEntry 3935 }


	iqdmx32EmbeddersEmbedder4EnablePair2 OBJECT-TYPE
		SYNTAX		INTEGER { disable(0), enable(1) }
		MAX-ACCESS		read-write
		STATUS			current
		DESCRIPTION
				"TYPE: - Checkbox
				 PAGE: - Channel 1- Audio 1- Embedders- Embedder 4
					Enable  cmdID= 5069 "
		::= { iqdmx32CmdEntry 5069 }


	iqdmx32EmbeddersEmbedder4SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 4
					Source L / Non-PCM  cmdID= 5046 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5046 }


	iqdmx32EmbeddersEmbedder4SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 4
					Source R  cmdID= 5047 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5047 }


	iqdmx32EmbeddersEmbedder4MutePair1 OBJECT-TYPE
		SYNTAX		INTEGER { disable(0), enable(1) }
		MAX-ACCESS		read-write
		STATUS			current
		DESCRIPTION
				"TYPE: - Checkbox
				 PAGE: - Channel 1- Audio 1- Embedders- Embedder 4
					Mute  cmdID= 3246 "
		::= { iqdmx32CmdEntry 3246 }


	iqdmx32EmbeddersEmbedder4MuteonVbitPair1 OBJECT-TYPE
		SYNTAX		INTEGER { disable(0), enable(1) }
		MAX-ACCESS		read-write
		STATUS			current
		DESCRIPTION
				"TYPE: - Checkbox
				 PAGE: - Channel 1- Audio 1- Embedders- Embedder 4
					Mute on V bit  cmdID= 3278 "
		::= { iqdmx32CmdEntry 3278 }


	iqdmx32EmbeddersEmbedder4InvertLPair1 OBJECT-TYPE
		SYNTAX		INTEGER { disable(0), enable(1) }
		MAX-ACCESS		read-write
		STATUS			current
		DESCRIPTION
				"TYPE: - Checkbox
				 PAGE: - Channel 1- Audio 1- Embedders- Embedder 4
					Invert L  cmdID= 3172 "
		::= { iqdmx32CmdEntry 3172 }


	iqdmx32EmbeddersEmbedder4InvertRPair1 OBJECT-TYPE
		SYNTAX		INTEGER { disable(0), enable(1) }
		MAX-ACCESS		read-write
		STATUS			current
		DESCRIPTION
				"TYPE: - Checkbox
				 PAGE: - Channel 1- Audio 1- Embedders- Embedder 4
					Invert R  cmdID= 3173 "
		::= { iqdmx32CmdEntry 3173 }


	iqdmx32EmbeddersEmbedder4GainLPair1 OBJECT-TYPE
		SYNTAX		INTEGER
		MAX-ACCESS		read-write
		STATUS			current
		DESCRIPTION
				"TYPE: - Number
				 PAGE: - Channel 1- Audio 1- Embedders- Embedder 4
					Gain L  cmdID= 3092  min= -720  max= 120  step= 1  format= %0.1fdB  div_scale= 10 
					Min = -72.0dB  Max = 12.0dB  Step = 0.1dB "
		::= { iqdmx32CmdEntry 3092 }


	iqdmx32EmbeddersEmbedder4GainRPair1 OBJECT-TYPE
		SYNTAX		INTEGER
		MAX-ACCESS		read-write
		STATUS			current
		DESCRIPTION
				"TYPE: - Number
				 PAGE: - Channel 1- Audio 1- Embedders- Embedder 4
					Gain R  cmdID= 3093  min= -720  max= 120  step= 1  format= %0.1fdB  div_scale= 10 
					Min = -72.0dB  Max = 12.0dB  Step = 0.1dB "
		::= { iqdmx32CmdEntry 3093 }


	iqdmx32EmbeddersEmbedder4PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 4
					Pair Mode  cmdID= 3936 
					2 Channel PCM  value= 0  
					Stereo PCM  value= 1  
					nonPCM  value= 2  "
		::= { iqdmx32CmdEntry 3936 }


	iqdmx32EmbeddersEmbedder4SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 1- Audio 1- Embedders- Embedder 4
					Source L / Non-PCM  cmdID= 5048 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5048 }


	iqdmx32EmbeddersEmbedder4SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 1- Audio 1- Embedders- Embedder 4
					Source R  cmdID= 5049 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5049 }


	iqdmx32EmbeddersEmbedder4MutePair2 OBJECT-TYPE
		SYNTAX		INTEGER { disable(0), enable(1) }
		MAX-ACCESS		read-write
		STATUS			current
		DESCRIPTION
				"TYPE: - Checkbox
				 PAGE: - Channel 1- Audio 1- Embedders- Embedder 4
					Mute  cmdID= 3247 "
		::= { iqdmx32CmdEntry 3247 }


	iqdmx32EmbeddersEmbedder4MuteonVbitPair2 OBJECT-TYPE
		SYNTAX		INTEGER { disable(0), enable(1) }
		MAX-ACCESS		read-write
		STATUS			current
		DESCRIPTION
				"TYPE: - Checkbox
				 PAGE: - Channel 1- Audio 1- Embedders- Embedder 4
					Mute on V bit  cmdID= 3279 "
		::= { iqdmx32CmdEntry 3279 }


	iqdmx32EmbeddersEmbedder4InvertLPair2 OBJECT-TYPE
		SYNTAX		INTEGER { disable(0), enable(1) }
		MAX-ACCESS		read-write
		STATUS			current
		DESCRIPTION
				"TYPE: - Checkbox
				 PAGE: - Channel 1- Audio 1- Embedders- Embedder 4
					Invert L  cmdID= 3174 "
		::= { iqdmx32CmdEntry 3174 }


	iqdmx32EmbeddersEmbedder4InvertRPair2 OBJECT-TYPE
		SYNTAX		INTEGER { disable(0), enable(1) }
		MAX-ACCESS		read-write
		STATUS			current
		DESCRIPTION
				"TYPE: - Checkbox
				 PAGE: - Channel 1- Audio 1- Embedders- Embedder 4
					Invert R  cmdID= 3175 "
		::= { iqdmx32CmdEntry 3175 }


	iqdmx32EmbeddersEmbedder4GainLPair2 OBJECT-TYPE
		SYNTAX		INTEGER
		MAX-ACCESS		read-write
		STATUS			current
		DESCRIPTION
				"TYPE: - Number
				 PAGE: - Channel 1- Audio 1- Embedders- Embedder 4
					Gain L  cmdID= 3094  min= -720  max= 120  step= 1  format= %0.1fdB  div_scale= 10 
					Min = -72.0dB  Max = 12.0dB  Step = 0.1dB "
		::= { iqdmx32CmdEntry 3094 }


	iqdmx32EmbeddersEmbedder4GainRPair2 OBJECT-TYPE
		SYNTAX		INTEGER
		MAX-ACCESS		read-write
		STATUS			current
		DESCRIPTION
				"TYPE: - Number
				 PAGE: - Channel 1- Audio 1- Embedders- Embedder 4
					Gain R  cmdID= 3095  min= -720  max= 120  step= 1  format= %0.1fdB  div_scale= 10 
					Min = -72.0dB  Max = 12.0dB  Step = 0.1dB "
		::= { iqdmx32CmdEntry 3095 }


	iqdmx32EmbeddersEmbedder4PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- Embedders- Embedder 4
					Pair Mode  cmdID= 3937 
					2 Channel PCM  value= 0  
					Stereo PCM  value= 1  
					nonPCM  value= 2  "
		::= { iqdmx32CmdEntry 3937 }


	iqdmx32AESOutAESOut1SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 1- Audio 1- AES Out- AES Out 1
					Source L / Non-PCM  cmdID= 5096 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5096 }


	iqdmx32AESOutAESOut1SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 1- Audio 1- AES Out- AES Out 1
					Source R  cmdID= 5097 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5097 }


	iqdmx32AESOutAESOut1Mute OBJECT-TYPE
		SYNTAX		INTEGER { disable(0), enable(1) }
		MAX-ACCESS		read-write
		STATUS			current
		DESCRIPTION
				"TYPE: - Checkbox
				 PAGE: - Channel 1- Audio 1- AES Out- AES Out 1
					Mute  cmdID= 3256 "
		::= { iqdmx32CmdEntry 3256 }


	iqdmx32AESOutAESOut1MuteonVbit OBJECT-TYPE
		SYNTAX		INTEGER { disable(0), enable(1) }
		MAX-ACCESS		read-write
		STATUS			current
		DESCRIPTION
				"TYPE: - Checkbox
				 PAGE: - Channel 1- Audio 1- AES Out- AES Out 1
					Mute on V bit  cmdID= 3288 "
		::= { iqdmx32CmdEntry 3288 }


	iqdmx32AESOutAESOut1InvertL OBJECT-TYPE
		SYNTAX		INTEGER { disable(0), enable(1) }
		MAX-ACCESS		read-write
		STATUS			current
		DESCRIPTION
				"TYPE: - Checkbox
				 PAGE: - Channel 1- Audio 1- AES Out- AES Out 1
					Invert L  cmdID= 3192 "
		::= { iqdmx32CmdEntry 3192 }


	iqdmx32AESOutAESOut1InvertR OBJECT-TYPE
		SYNTAX		INTEGER { disable(0), enable(1) }
		MAX-ACCESS		read-write
		STATUS			current
		DESCRIPTION
				"TYPE: - Checkbox
				 PAGE: - Channel 1- Audio 1- AES Out- AES Out 1
					Invert R  cmdID= 3193 "
		::= { iqdmx32CmdEntry 3193 }


	iqdmx32AESOutAESOut1GainL OBJECT-TYPE
		SYNTAX		INTEGER
		MAX-ACCESS		read-write
		STATUS			current
		DESCRIPTION
				"TYPE: - Number
				 PAGE: - Channel 1- Audio 1- AES Out- AES Out 1
					Gain L  cmdID= 3112  min= -720  max= 120  step= 1  format= %0.1fdB  div_scale= 10 
					Min = -72.0dB  Max = 12.0dB  Step = 0.1dB "
		::= { iqdmx32CmdEntry 3112 }


	iqdmx32AESOutAESOut1GainR OBJECT-TYPE
		SYNTAX		INTEGER
		MAX-ACCESS		read-write
		STATUS			current
		DESCRIPTION
				"TYPE: - Number
				 PAGE: - Channel 1- Audio 1- AES Out- AES Out 1
					Gain R  cmdID= 3113  min= -720  max= 120  step= 1  format= %0.1fdB  div_scale= 10 
					Min = -72.0dB  Max = 12.0dB  Step = 0.1dB "
		::= { iqdmx32CmdEntry 3113 }


	iqdmx32AESOutAESOut1PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- AES Out- AES Out 1
					Pair Mode  cmdID= 5112 
					2 Channel PCM  value= 0  
					Stereo PCM  value= 1  
					nonPCM  value= 2  "
		::= { iqdmx32CmdEntry 5112 }


	iqdmx32AESOutAESOut2SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 1- Audio 1- AES Out- AES Out 2
					Source L / Non-PCM  cmdID= 5098 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5098 }


	iqdmx32AESOutAESOut2SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 1- Audio 1- AES Out- AES Out 2
					Source R  cmdID= 5099 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5099 }


	iqdmx32AESOutAESOut2Mute OBJECT-TYPE
		SYNTAX		INTEGER { disable(0), enable(1) }
		MAX-ACCESS		read-write
		STATUS			current
		DESCRIPTION
				"TYPE: - Checkbox
				 PAGE: - Channel 1- Audio 1- AES Out- AES Out 2
					Mute  cmdID= 3257 "
		::= { iqdmx32CmdEntry 3257 }


	iqdmx32AESOutAESOut2MuteonVbit OBJECT-TYPE
		SYNTAX		INTEGER { disable(0), enable(1) }
		MAX-ACCESS		read-write
		STATUS			current
		DESCRIPTION
				"TYPE: - Checkbox
				 PAGE: - Channel 1- Audio 1- AES Out- AES Out 2
					Mute on V bit  cmdID= 3289 "
		::= { iqdmx32CmdEntry 3289 }


	iqdmx32AESOutAESOut2InvertL OBJECT-TYPE
		SYNTAX		INTEGER { disable(0), enable(1) }
		MAX-ACCESS		read-write
		STATUS			current
		DESCRIPTION
				"TYPE: - Checkbox
				 PAGE: - Channel 1- Audio 1- AES Out- AES Out 2
					Invert L  cmdID= 3194 "
		::= { iqdmx32CmdEntry 3194 }


	iqdmx32AESOutAESOut2InvertR OBJECT-TYPE
		SYNTAX		INTEGER { disable(0), enable(1) }
		MAX-ACCESS		read-write
		STATUS			current
		DESCRIPTION
				"TYPE: - Checkbox
				 PAGE: - Channel 1- Audio 1- AES Out- AES Out 2
					Invert R  cmdID= 3195 "
		::= { iqdmx32CmdEntry 3195 }


	iqdmx32AESOutAESOut2GainL OBJECT-TYPE
		SYNTAX		INTEGER
		MAX-ACCESS		read-write
		STATUS			current
		DESCRIPTION
				"TYPE: - Number
				 PAGE: - Channel 1- Audio 1- AES Out- AES Out 2
					Gain L  cmdID= 3114  min= -720  max= 120  step= 1  format= %0.1fdB  div_scale= 10 
					Min = -72.0dB  Max = 12.0dB  Step = 0.1dB "
		::= { iqdmx32CmdEntry 3114 }


	iqdmx32AESOutAESOut2GainR OBJECT-TYPE
		SYNTAX		INTEGER
		MAX-ACCESS		read-write
		STATUS			current
		DESCRIPTION
				"TYPE: - Number
				 PAGE: - Channel 1- Audio 1- AES Out- AES Out 2
					Gain R  cmdID= 3115  min= -720  max= 120  step= 1  format= %0.1fdB  div_scale= 10 
					Min = -72.0dB  Max = 12.0dB  Step = 0.1dB "
		::= { iqdmx32CmdEntry 3115 }


	iqdmx32AESOutAESOut2PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- AES Out- AES Out 2
					Pair Mode  cmdID= 5113 
					2 Channel PCM  value= 0  
					Stereo PCM  value= 1  
					nonPCM  value= 2  "
		::= { iqdmx32CmdEntry 5113 }


	iqdmx32AESOutAESOut3SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 1- Audio 1- AES Out- AES Out 3
					Source L / Non-PCM  cmdID= 5100 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5100 }


	iqdmx32AESOutAESOut3SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 1- Audio 1- AES Out- AES Out 3
					Source R  cmdID= 5101 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5101 }


	iqdmx32AESOutAESOut3Mute OBJECT-TYPE
		SYNTAX		INTEGER { disable(0), enable(1) }
		MAX-ACCESS		read-write
		STATUS			current
		DESCRIPTION
				"TYPE: - Checkbox
				 PAGE: - Channel 1- Audio 1- AES Out- AES Out 3
					Mute  cmdID= 3258 "
		::= { iqdmx32CmdEntry 3258 }


	iqdmx32AESOutAESOut3MuteonVbit OBJECT-TYPE
		SYNTAX		INTEGER { disable(0), enable(1) }
		MAX-ACCESS		read-write
		STATUS			current
		DESCRIPTION
				"TYPE: - Checkbox
				 PAGE: - Channel 1- Audio 1- AES Out- AES Out 3
					Mute on V bit  cmdID= 3290 "
		::= { iqdmx32CmdEntry 3290 }


	iqdmx32AESOutAESOut3InvertL OBJECT-TYPE
		SYNTAX		INTEGER { disable(0), enable(1) }
		MAX-ACCESS		read-write
		STATUS			current
		DESCRIPTION
				"TYPE: - Checkbox
				 PAGE: - Channel 1- Audio 1- AES Out- AES Out 3
					Invert L  cmdID= 3196 "
		::= { iqdmx32CmdEntry 3196 }


	iqdmx32AESOutAESOut3InvertR OBJECT-TYPE
		SYNTAX		INTEGER { disable(0), enable(1) }
		MAX-ACCESS		read-write
		STATUS			current
		DESCRIPTION
				"TYPE: - Checkbox
				 PAGE: - Channel 1- Audio 1- AES Out- AES Out 3
					Invert R  cmdID= 3197 "
		::= { iqdmx32CmdEntry 3197 }


	iqdmx32AESOutAESOut3GainL OBJECT-TYPE
		SYNTAX		INTEGER
		MAX-ACCESS		read-write
		STATUS			current
		DESCRIPTION
				"TYPE: - Number
				 PAGE: - Channel 1- Audio 1- AES Out- AES Out 3
					Gain L  cmdID= 3116  min= -720  max= 120  step= 1  format= %0.1fdB  div_scale= 10 
					Min = -72.0dB  Max = 12.0dB  Step = 0.1dB "
		::= { iqdmx32CmdEntry 3116 }


	iqdmx32AESOutAESOut3GainR OBJECT-TYPE
		SYNTAX		INTEGER
		MAX-ACCESS		read-write
		STATUS			current
		DESCRIPTION
				"TYPE: - Number
				 PAGE: - Channel 1- Audio 1- AES Out- AES Out 3
					Gain R  cmdID= 3117  min= -720  max= 120  step= 1  format= %0.1fdB  div_scale= 10 
					Min = -72.0dB  Max = 12.0dB  Step = 0.1dB "
		::= { iqdmx32CmdEntry 3117 }


	iqdmx32AESOutAESOut3PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- AES Out- AES Out 3
					Pair Mode  cmdID= 5114 
					2 Channel PCM  value= 0  
					Stereo PCM  value= 1  
					nonPCM  value= 2  "
		::= { iqdmx32CmdEntry 5114 }


	iqdmx32AESOutAESOut4SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 1- Audio 1- AES Out- AES Out 4
					Source L / Non-PCM  cmdID= 5102 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5102 }


	iqdmx32AESOutAESOut4SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 1- Audio 1- AES Out- AES Out 4
					Source R  cmdID= 5103 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5103 }


	iqdmx32AESOutAESOut4Mute OBJECT-TYPE
		SYNTAX		INTEGER { disable(0), enable(1) }
		MAX-ACCESS		read-write
		STATUS			current
		DESCRIPTION
				"TYPE: - Checkbox
				 PAGE: - Channel 1- Audio 1- AES Out- AES Out 4
					Mute  cmdID= 3259 "
		::= { iqdmx32CmdEntry 3259 }


	iqdmx32AESOutAESOut4MuteonVbit OBJECT-TYPE
		SYNTAX		INTEGER { disable(0), enable(1) }
		MAX-ACCESS		read-write
		STATUS			current
		DESCRIPTION
				"TYPE: - Checkbox
				 PAGE: - Channel 1- Audio 1- AES Out- AES Out 4
					Mute on V bit  cmdID= 3291 "
		::= { iqdmx32CmdEntry 3291 }


	iqdmx32AESOutAESOut4InvertL OBJECT-TYPE
		SYNTAX		INTEGER { disable(0), enable(1) }
		MAX-ACCESS		read-write
		STATUS			current
		DESCRIPTION
				"TYPE: - Checkbox
				 PAGE: - Channel 1- Audio 1- AES Out- AES Out 4
					Invert L  cmdID= 3198 "
		::= { iqdmx32CmdEntry 3198 }


	iqdmx32AESOutAESOut4InvertR OBJECT-TYPE
		SYNTAX		INTEGER { disable(0), enable(1) }
		MAX-ACCESS		read-write
		STATUS			current
		DESCRIPTION
				"TYPE: - Checkbox
				 PAGE: - Channel 1- Audio 1- AES Out- AES Out 4
					Invert R  cmdID= 3199 "
		::= { iqdmx32CmdEntry 3199 }


	iqdmx32AESOutAESOut4GainL OBJECT-TYPE
		SYNTAX		INTEGER
		MAX-ACCESS		read-write
		STATUS			current
		DESCRIPTION
				"TYPE: - Number
				 PAGE: - Channel 1- Audio 1- AES Out- AES Out 4
					Gain L  cmdID= 3118  min= -720  max= 120  step= 1  format= %0.1fdB  div_scale= 10 
					Min = -72.0dB  Max = 12.0dB  Step = 0.1dB "
		::= { iqdmx32CmdEntry 3118 }


	iqdmx32AESOutAESOut4GainR OBJECT-TYPE
		SYNTAX		INTEGER
		MAX-ACCESS		read-write
		STATUS			current
		DESCRIPTION
				"TYPE: - Number
				 PAGE: - Channel 1- Audio 1- AES Out- AES Out 4
					Gain R  cmdID= 3119  min= -720  max= 120  step= 1  format= %0.1fdB  div_scale= 10 
					Min = -72.0dB  Max = 12.0dB  Step = 0.1dB "
		::= { iqdmx32CmdEntry 3119 }


	iqdmx32AESOutAESOut4PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 1- Audio 1- AES Out- AES Out 4
					Pair Mode  cmdID= 5115 
					2 Channel PCM  value= 0  
					Stereo PCM  value= 1  
					nonPCM  value= 2  "
		::= { iqdmx32CmdEntry 5115 }


	iqdmx32AudioDelayDelaysVideoDelayCh1 OBJECT-TYPE
		SYNTAX		INTEGER { disable(0), enable(1) }
		MAX-ACCESS		read-write
		STATUS			current
		DESCRIPTION
				"TYPE: - Checkbox
				 PAGE: - Channel 1- Audio 1
					Video Delay  cmdID= 5078 "
		::= { iqdmx32CmdEntry 5078 }


	iqdmx32AudioDelayDelaysManualDelayCh1 OBJECT-TYPE
		SYNTAX		INTEGER { disable(0), enable(1) }
		MAX-ACCESS		read-write
		STATUS			current
		DESCRIPTION
				"TYPE: - Checkbox
				 PAGE: - Channel 1- Audio 1
					Manual Delay  cmdID= 5079 "
		::= { iqdmx32CmdEntry 5079 }


	iqdmx32AudioDelayDelaysCoarseDelayCh1 OBJECT-TYPE
		SYNTAX		INTEGER
		MAX-ACCESS		read-write
		STATUS			current
		DESCRIPTION
				"TYPE: - Number
				 PAGE: - Channel 1- Audio 1
					Coarse Delay  cmdID= 5075  min= 0  max= 1750  step= 5  format= %5.3fs  div_scale= 1000 
					Min = 0.000s  Max = 1.750s  Step = 0.005s "
		::= { iqdmx32CmdEntry 5075 }


	iqdmx32AudioDelayDelaysFineDelayCh1 OBJECT-TYPE
		SYNTAX		INTEGER
		MAX-ACCESS		read-write
		STATUS			current
		DESCRIPTION
				"TYPE: - Number
				 PAGE: - Channel 1- Audio 1
					Fine Delay  cmdID= 5077  min= -2500  max= 2500  step= 5  format= %0.1fms  div_scale= 10 
					Min = -250.0ms  Max = 250.0ms  Step = 0.5ms "
		::= { iqdmx32CmdEntry 5077 }


	iqdmx32AudioDelayDelayStatusTotalDelayCh1 OBJECT-TYPE
		SYNTAX		RollCallString
		MAX-ACCESS		read-only
		STATUS			current
		DESCRIPTION
				"TYPE: - Display
				 PAGE: - Channel 1- Audio 1
					Total Delay  cmdID= 5084  format=   "
		::= { iqdmx32CmdEntry 5084 }


	iqdmx32AudioDelayDelayStatusVideoDelayCh1 OBJECT-TYPE
		SYNTAX		RollCallString
		MAX-ACCESS		read-only
		STATUS			current
		DESCRIPTION
				"TYPE: - Display
				 PAGE: - Channel 1- Audio 1
					Video Delay  cmdID= 5074  format=   "
		::= { iqdmx32CmdEntry 5074 }


	iqdmx32AudioDelayDelayStatusManualDelayCh1 OBJECT-TYPE
		SYNTAX		RollCallString
		MAX-ACCESS		read-only
		STATUS			current
		DESCRIPTION
				"TYPE: - Display
				 PAGE: - Channel 1- Audio 1
					Manual Delay  cmdID= 5076  format=   "
		::= { iqdmx32CmdEntry 5076 }


	iqdmx32Audio1ToneFrequency OBJECT-TYPE
		SYNTAX		INTEGER
		MAX-ACCESS		read-write
		STATUS			current
		DESCRIPTION
				"TYPE: - Number
				 PAGE: - Channel 1- Audio 1
					Frequency  cmdID= 2487  min= 100  max= 10000  step= 100  format= %5.0fHz  div_scale= 1 
					Min =   100Hz  Max = 10000Hz  Step =   100Hz "
		::= { iqdmx32CmdEntry 2487 }


	iqdmx32Audio1ToneChannelident OBJECT-TYPE
		SYNTAX		INTEGER { disable(0), enable(1) }
		MAX-ACCESS		read-write
		STATUS			current
		DESCRIPTION
				"TYPE: - Checkbox
				 PAGE: - Channel 1- Audio 1
					Channel ident  cmdID= 5030 "
		::= { iqdmx32CmdEntry 5030 }


	iqdmx32Audio1AudioMonitorSilenceLevel OBJECT-TYPE
		SYNTAX		INTEGER
		MAX-ACCESS		read-write
		STATUS			current
		DESCRIPTION
				"TYPE: - Number
				 PAGE: - Channel 1- Audio 1
					Silence Level  cmdID= 3061  min= -80  max= 0  step= 1  format= %1.0f dB  div_scale= 1 
					Min = -80 dB  Max = 0 dB  Step = 1 dB "
		::= { iqdmx32CmdEntry 3061 }


	iqdmx32Audio1AudioMonitorOverloadLevel OBJECT-TYPE
		SYNTAX		INTEGER
		MAX-ACCESS		read-write
		STATUS			current
		DESCRIPTION
				"TYPE: - Number
				 PAGE: - Channel 1- Audio 1
					Overload Level  cmdID= 3064  min= -80  max= 0  step= 1  format= %1.0f dB  div_scale= 1 
					Min = -80 dB  Max = 0 dB  Step = 1 dB "
		::= { iqdmx32CmdEntry 3064 }


	iqdmx32Audio1AudioMonitorWarningTimer OBJECT-TYPE
		SYNTAX		INTEGER
		MAX-ACCESS		read-write
		STATUS			current
		DESCRIPTION
				"TYPE: - Number
				 PAGE: - Channel 1- Audio 1
					Warning Timer  cmdID= 3065  min= 1  max= 20  step= 1  format= %1.0f sec  div_scale= 1 
					Min = 1 sec  Max = 20 sec  Step = 1 sec "
		::= { iqdmx32CmdEntry 3065 }


	iqdmx32Channel1VideoDelay1FreerunFrequency OBJECT-TYPE
		SYNTAX		INTEGER
		MAX-ACCESS		read-write
		STATUS			current
		DESCRIPTION
				"TYPE: - Number
				 PAGE: - Channel 1
					Freerun Frequency  cmdID= 5336  min= -200  max= 200  step= 1  format= %.0f  div_scale= 1 
					Min = -200  Max = 200  Step = 1 "
		::= { iqdmx32CmdEntry 5336 }


	iqdmx32Channel1VideoDelay1VideoHdelay OBJECT-TYPE
		SYNTAX		INTEGER
		MAX-ACCESS		read-write
		STATUS			current
		DESCRIPTION
				"TYPE: - Number
				 PAGE: - Channel 1
					Video H delay  cmdID= 3794  min= 0  max= 2640  step= 1  format= %.0f pixels  div_scale= 1 
					Min = 0 pixels  Max = 2640 pixels  Step = 1 pixels "
		::= { iqdmx32CmdEntry 3794 }


	iqdmx32Channel1VideoDelay1VideoVdelay OBJECT-TYPE
		SYNTAX		INTEGER
		MAX-ACCESS		read-write
		STATUS			current
		DESCRIPTION
				"TYPE: - Number
				 PAGE: - Channel 1
					Video V delay  cmdID= 3795  min= 0  max= 1125  step= 1  format= %.0f lines  div_scale= 1 
					Min = 0 lines  Max = 1125 lines  Step = 1 lines "
		::= { iqdmx32CmdEntry 3795 }


	iqdmx32Channel1VideoDelay1VideoFdelay OBJECT-TYPE
		SYNTAX		INTEGER
		MAX-ACCESS		read-write
		STATUS			current
		DESCRIPTION
				"TYPE: - Number
				 PAGE: - Channel 1
					Video F delay  cmdID= 3796  min= 0  max= 3  step= 1  format= %.0f frames  div_scale= 1 
					Min = 0 frames  Max = 3 frames  Step = 1 frames "
		::= { iqdmx32CmdEntry 3796 }


	iqdmx32Channel1VideoDelay1Genlocksaveindex OBJECT-TYPE
		SYNTAX		INTEGER
		MAX-ACCESS		read-write
		STATUS			current
		DESCRIPTION
				"TYPE: - Number
				 PAGE: - Channel 1
					Genlock save index  cmdID= 3991  min= 0  max= 21  step= 1  format= %.0f  div_scale= 1 
					Min = 0  Max = 21  Step = 1 "
		::= { iqdmx32CmdEntry 3991 }


	iqdmx32Channel1VideoDelay1VideoHdelaysave OBJECT-TYPE
		SYNTAX		INTEGER
		MAX-ACCESS		read-write
		STATUS			current
		DESCRIPTION
				"TYPE: - Number
				 PAGE: - Channel 1
					Video H delay save  cmdID= 3994  min= 0  max= 2640  step= 1  format= %.0f pixels  div_scale= 1 
					Min = 0 pixels  Max = 2640 pixels  Step = 1 pixels "
		::= { iqdmx32CmdEntry 3994 }


	iqdmx32Channel1VideoDelay1VideoVdelaysave OBJECT-TYPE
		SYNTAX		INTEGER
		MAX-ACCESS		read-write
		STATUS			current
		DESCRIPTION
				"TYPE: - Number
				 PAGE: - Channel 1
					Video V delay save  cmdID= 3995  min= 0  max= 1125  step= 1  format= %.0f lines  div_scale= 1 
					Min = 0 lines  Max = 1125 lines  Step = 1 lines "
		::= { iqdmx32CmdEntry 3995 }


	iqdmx32Video2ValidInputFormats62525i OBJECT-TYPE
		SYNTAX		INTEGER { disable(0), enable(1) }
		MAX-ACCESS		read-write
		STATUS			current
		DESCRIPTION
				"TYPE: - Checkbox
				 PAGE: - Channel 2- Video 2
					625/25i  cmdID= 5252 "
		::= { iqdmx32CmdEntry 5252 }


	iqdmx32Video2ValidInputFormats52529i OBJECT-TYPE
		SYNTAX		INTEGER { disable(0), enable(1) }
		MAX-ACCESS		read-write
		STATUS			current
		DESCRIPTION
				"TYPE: - Checkbox
				 PAGE: - Channel 2- Video 2
					525/29i  cmdID= 5253 "
		::= { iqdmx32CmdEntry 5253 }


	iqdmx32Video2ValidInputFormats72050p OBJECT-TYPE
		SYNTAX		INTEGER { disable(0), enable(1) }
		MAX-ACCESS		read-write
		STATUS			current
		DESCRIPTION
				"TYPE: - Checkbox
				 PAGE: - Channel 2- Video 2
					720/50p  cmdID= 5259 "
		::= { iqdmx32CmdEntry 5259 }


	iqdmx32Video2ValidInputFormats72059p OBJECT-TYPE
		SYNTAX		INTEGER { disable(0), enable(1) }
		MAX-ACCESS		read-write
		STATUS			current
		DESCRIPTION
				"TYPE: - Checkbox
				 PAGE: - Channel 2- Video 2
					720/59p  cmdID= 5260 "
		::= { iqdmx32CmdEntry 5260 }


	iqdmx32Video2ValidInputFormats108025i OBJECT-TYPE
		SYNTAX		INTEGER { disable(0), enable(1) }
		MAX-ACCESS		read-write
		STATUS			current
		DESCRIPTION
				"TYPE: - Checkbox
				 PAGE: - Channel 2- Video 2
					1080/25i  cmdID= 5267 "
		::= { iqdmx32CmdEntry 5267 }


	iqdmx32Video2ValidInputFormats108029i OBJECT-TYPE
		SYNTAX		INTEGER { disable(0), enable(1) }
		MAX-ACCESS		read-write
		STATUS			current
		DESCRIPTION
				"TYPE: - Checkbox
				 PAGE: - Channel 2- Video 2
					1080/29i  cmdID= 5268 "
		::= { iqdmx32CmdEntry 5268 }


	iqdmx32Video2ValidInputFormats108050pA OBJECT-TYPE
		SYNTAX		INTEGER { disable(0), enable(1) }
		MAX-ACCESS		read-write
		STATUS			current
		DESCRIPTION
				"TYPE: - Checkbox
				 PAGE: - Channel 2- Video 2
					1080/50p-A  cmdID= 5272 "
		::= { iqdmx32CmdEntry 5272 }


	iqdmx32Video2ValidInputFormats108059pA OBJECT-TYPE
		SYNTAX		INTEGER { disable(0), enable(1) }
		MAX-ACCESS		read-write
		STATUS			current
		DESCRIPTION
				"TYPE: - Checkbox
				 PAGE: - Channel 2- Video 2
					1080/59p-A  cmdID= 5273 "
		::= { iqdmx32CmdEntry 5273 }


	iqdmx32Video2ValidInputFormats108050pB OBJECT-TYPE
		SYNTAX		INTEGER { disable(0), enable(1) }
		MAX-ACCESS		read-write
		STATUS			current
		DESCRIPTION
				"TYPE: - Checkbox
				 PAGE: - Channel 2- Video 2
					1080/50p-B  cmdID= 5275 "
		::= { iqdmx32CmdEntry 5275 }


	iqdmx32Video2ValidInputFormats108059pB OBJECT-TYPE
		SYNTAX		INTEGER { disable(0), enable(1) }
		MAX-ACCESS		read-write
		STATUS			current
		DESCRIPTION
				"TYPE: - Checkbox
				 PAGE: - Channel 2- Video 2
					1080/59p-B  cmdID= 5276 "
		::= { iqdmx32CmdEntry 5276 }


	iqdmx32Channel2Video2DefaultFormat OBJECT-TYPE
		SYNTAX		INTEGER {
							val-Last-Known-Good(1),
							val-625-25i(2),
							val-525-29i(3),
							val-720-50p(9),
							val-720-59p(10),
							val-1080-25i(17),
							val-1080-29i(18),
							val-1080-50p-A(22),
							val-1080-59p-A(23),
							val-1080-50p-B(25),
							val-1080-59p-B(26)
							}
		MAX-ACCESS		read-write
		STATUS			current
		DESCRIPTION
				"TYPE: - RadiobuttonList
				 PAGE: - Channel 2- Video 2
					Default Format  cmdID= 5137 
					Last Known Good  value= 1  
					625/25i  value= 2  
					525/29i  value= 3  
					720/50p  value= 9  
					720/59p  value= 10  
					1080/25i  value= 17  
					1080/29i  value= 18  
					1080/50p-A  value= 22  
					1080/59p-A  value= 23  
					1080/50p-B  value= 25  
					1080/59p-B  value= 26  "
		::= { iqdmx32CmdEntry 5137 }


	iqdmx32Channel2Video2DefaultOutput OBJECT-TYPE
		SYNTAX		INTEGER {
							val-Black(0),
							val-Freeze(1),
							val-Pattern(2)
							}
		MAX-ACCESS		read-write
		STATUS			current
		DESCRIPTION
				"TYPE: - RadiobuttonList
				 PAGE: - Channel 2- Video 2
					Default Output  cmdID= 2628 
					Black  value= 0  
					Freeze  value= 1  
					Pattern  value= 2  "
		::= { iqdmx32CmdEntry 2628 }


	iqdmx32Video2VideoProcampProcAmpEnable OBJECT-TYPE
		SYNTAX		INTEGER { disable(0), enable(1) }
		MAX-ACCESS		read-write
		STATUS			current
		DESCRIPTION
				"TYPE: - Checkbox
				 PAGE: - Channel 2- Video 2
					ProcAmp Enable  cmdID= 2865 "
		::= { iqdmx32CmdEntry 2865 }


	iqdmx32Video2VideoProcampBlackLevel OBJECT-TYPE
		SYNTAX		INTEGER
		MAX-ACCESS		read-write
		STATUS			current
		DESCRIPTION
				"TYPE: - Number
				 PAGE: - Channel 2- Video 2
					Black Level  cmdID= 2712  min= -1000  max= 1000  step= 8  format= %3.1fmV  div_scale= 10 
					Min = -100.0mV  Max = 100.0mV  Step = 0.8mV "
		::= { iqdmx32CmdEntry 2712 }


	iqdmx32Video2VideoProcampHueAdjust OBJECT-TYPE
		SYNTAX		INTEGER
		MAX-ACCESS		read-write
		STATUS			current
		DESCRIPTION
				"TYPE: - Number
				 PAGE: - Channel 2- Video 2
					Hue Adjust  cmdID= 3630  min= -180  max= 180  step= 1  format= %1.0fdeg  div_scale= 1 
					Min = -180deg  Max = 180deg  Step = 1deg "
		::= { iqdmx32CmdEntry 3630 }


	iqdmx32Video2VideoProcampMasterVideoGain OBJECT-TYPE
		SYNTAX		INTEGER
		MAX-ACCESS		read-write
		STATUS			current
		DESCRIPTION
				"TYPE: - Number
				 PAGE: - Channel 2- Video 2
					Master Video Gain  cmdID= 3788  min= -60  max= 60  step= 1  format= %0.1fdB  div_scale= 10 
					Min = -6.0dB  Max = 6.0dB  Step = 0.1dB "
		::= { iqdmx32CmdEntry 3788 }


	iqdmx32Video2VideoProcampYGain OBJECT-TYPE
		SYNTAX		INTEGER
		MAX-ACCESS		read-write
		STATUS			current
		DESCRIPTION
				"TYPE: - Number
				 PAGE: - Channel 2- Video 2
					Y Gain  cmdID= 2711  min= -60  max= 60  step= 1  format= %0.1fdB  div_scale= 10 
					Min = -6.0dB  Max = 6.0dB  Step = 0.1dB "
		::= { iqdmx32CmdEntry 2711 }


	iqdmx32Video2VideoProcampCbCrGain OBJECT-TYPE
		SYNTAX		INTEGER
		MAX-ACCESS		read-write
		STATUS			current
		DESCRIPTION
				"TYPE: - Number
				 PAGE: - Channel 2- Video 2
					Cb/Cr Gain  cmdID= 2710  min= -60  max= 60  step= 1  format= %0.1fdB  div_scale= 10 
					Min = -6.0dB  Max = 6.0dB  Step = 0.1dB "
		::= { iqdmx32CmdEntry 2710 }


	iqdmx32Video2VideoProcampYCTiming OBJECT-TYPE
		SYNTAX		INTEGER
		MAX-ACCESS		read-write
		STATUS			current
		DESCRIPTION
				"TYPE: - Number
				 PAGE: - Channel 2- Video 2
					Y/C Timing  cmdID= 2925  min= -8  max= 8  step= 2  format= %1.0f pixels  div_scale= 1 
					Min = -8 pixels  Max = 8 pixels  Step = 2 pixels "
		::= { iqdmx32CmdEntry 2925 }


	iqdmx32Video2VideoProcampPictureposition OBJECT-TYPE
		SYNTAX		INTEGER
		MAX-ACCESS		read-write
		STATUS			current
		DESCRIPTION
				"TYPE: - Number
				 PAGE: - Channel 2- Video 2
					Picture position  cmdID= 2713  min= -8  max= 8  step= 2  format= %1.0f pixels  div_scale= 1 
					Min = -8 pixels  Max = 8 pixels  Step = 2 pixels "
		::= { iqdmx32CmdEntry 2713 }


	iqdmx32Video2VideoProcampModalIndex OBJECT-TYPE
		SYNTAX		INTEGER
		MAX-ACCESS		read-write
		STATUS			current
		DESCRIPTION
				"TYPE: - Number
				 PAGE: - Channel 2- Video 2
					Modal Index  cmdID= 5009  min= 0  max= 1  step= 1  format= %1.0f  div_scale= 1 
					Min = 0  Max = 1  Step = 1 "
		::= { iqdmx32CmdEntry 5009 }


	iqdmx32Video2VideoProcampYCTimingnm OBJECT-TYPE
		SYNTAX		INTEGER
		MAX-ACCESS		read-write
		STATUS			current
		DESCRIPTION
				"TYPE: - Number
				 PAGE: - Channel 2- Video 2
					Y/C Timing nm  cmdID= 5011  min= -16  max= 16  step= 2  format= %1.0f pixels  div_scale= 1 
					Min = -16 pixels  Max = 16 pixels  Step = 2 pixels "
		::= { iqdmx32CmdEntry 5011 }


	iqdmx32Video2VideoProcampPicturepositionnm OBJECT-TYPE
		SYNTAX		INTEGER
		MAX-ACCESS		read-write
		STATUS			current
		DESCRIPTION
				"TYPE: - Number
				 PAGE: - Channel 2- Video 2
					Picture position nm  cmdID= 5010  min= -16  max= 16  step= 2  format= %1.0f pixels  div_scale= 1 
					Min = -16 pixels  Max = 16 pixels  Step = 2 pixels "
		::= { iqdmx32CmdEntry 5010 }


	iqdmx32Video2BlankingBlankVANC OBJECT-TYPE
		SYNTAX		INTEGER { disable(0), enable(1) }
		MAX-ACCESS		read-write
		STATUS			current
		DESCRIPTION
				"TYPE: - Checkbox
				 PAGE: - Channel 2- Video 2
					Blank VANC  cmdID= 3950 "
		::= { iqdmx32CmdEntry 3950 }


	iqdmx32Blanking625BlankLinesLine23ch2 OBJECT-TYPE
		SYNTAX		INTEGER { disable(0), enable(1) }
		MAX-ACCESS		read-write
		STATUS			current
		DESCRIPTION
				"TYPE: - Checkbox
				 PAGE: - Channel 2- Video 2
					Line 23  cmdID= 3971 "
		::= { iqdmx32CmdEntry 3971 }


	iqdmx32Blanking625BlankLinesLine336ch2 OBJECT-TYPE
		SYNTAX		INTEGER { disable(0), enable(1) }
		MAX-ACCESS		read-write
		STATUS			current
		DESCRIPTION
				"TYPE: - Checkbox
				 PAGE: - Channel 2- Video 2
					Line 336  cmdID= 3972 "
		::= { iqdmx32CmdEntry 3972 }


	iqdmx32Blanking525BlankLinesLine21ch2 OBJECT-TYPE
		SYNTAX		INTEGER { disable(0), enable(1) }
		MAX-ACCESS		read-write
		STATUS			current
		DESCRIPTION
				"TYPE: - Checkbox
				 PAGE: - Channel 2- Video 2
					Line 21  cmdID= 3973 "
		::= { iqdmx32CmdEntry 3973 }


	iqdmx32Blanking525BlankLinesLine22ch2 OBJECT-TYPE
		SYNTAX		INTEGER { disable(0), enable(1) }
		MAX-ACCESS		read-write
		STATUS			current
		DESCRIPTION
				"TYPE: - Checkbox
				 PAGE: - Channel 2- Video 2
					Line 22  cmdID= 3975 "
		::= { iqdmx32CmdEntry 3975 }


	iqdmx32Blanking525BlankLinesLine283ch2 OBJECT-TYPE
		SYNTAX		INTEGER { disable(0), enable(1) }
		MAX-ACCESS		read-write
		STATUS			current
		DESCRIPTION
				"TYPE: - Checkbox
				 PAGE: - Channel 2- Video 2
					Line 283  cmdID= 3974 "
		::= { iqdmx32CmdEntry 3974 }


	iqdmx32Blanking525BlankLinesLine284ch2 OBJECT-TYPE
		SYNTAX		INTEGER { disable(0), enable(1) }
		MAX-ACCESS		read-write
		STATUS			current
		DESCRIPTION
				"TYPE: - Checkbox
				 PAGE: - Channel 2- Video 2
					Line 284  cmdID= 3976 "
		::= { iqdmx32CmdEntry 3976 }


	iqdmx32Video2BlankingBlankHANC OBJECT-TYPE
		SYNTAX		INTEGER { disable(0), enable(1) }
		MAX-ACCESS		read-write
		STATUS			current
		DESCRIPTION
				"TYPE: - Checkbox
				 PAGE: - Channel 2- Video 2
					Blank HANC  cmdID= 3948 "
		::= { iqdmx32CmdEntry 3948 }


	iqdmx32Video2Caption OBJECT-TYPE
		SYNTAX		INTEGER {
							val-Off(0),
							val-On(1)
							}
		MAX-ACCESS		read-write
		STATUS			current
		DESCRIPTION
				"TYPE: - Button
				 PAGE: - Channel 2- Video 2
					Off  cmdID= 1039  value= 0  
					On  cmdID= 1039  value= 1  "
		::= { iqdmx32CmdEntry 1039 }


	iqdmx32Video2CaptionEditCaption OBJECT-TYPE
		SYNTAX		RollCallString
		MAX-ACCESS		read-write
		STATUS			current
		DESCRIPTION
				"TYPE: - Editstring
				 PAGE: - Channel 2- Video 2
					Edit Caption  cmdID= 1040  "
		::= { iqdmx32CmdEntry 1040 }


	iqdmx32Channel2Video2Pattern OBJECT-TYPE
		SYNTAX		INTEGER {
							val-Off(0),
							val-Black(1),
							val-Bars(2)
							}
		MAX-ACCESS		read-write
		STATUS			current
		DESCRIPTION
				"TYPE: - RadiobuttonList
				 PAGE: - Channel 2- Video 2
					Pattern  cmdID= 2629 
					Off  value= 0  
					Black  value= 1  
					Bars  value= 2  "
		::= { iqdmx32CmdEntry 2629 }


	iqdmx32Video2Freeze OBJECT-TYPE
		SYNTAX		INTEGER {
							val-Field(0),
							val-Frame(1)
							}
		MAX-ACCESS		read-write
		STATUS			current
		DESCRIPTION
				"TYPE: - Button
				 PAGE: - Channel 2- Video 2
					Field  cmdID= 5025  value= 0  
					Frame  cmdID= 5025  value= 1  "
		::= { iqdmx32CmdEntry 5025 }


	iqdmx32Video2FreezeManualFreeze OBJECT-TYPE
		SYNTAX		INTEGER { disable(0), enable(1) }
		MAX-ACCESS		read-write
		STATUS			current
		DESCRIPTION
				"TYPE: - Checkbox
				 PAGE: - Channel 2- Video 2
					Manual Freeze  cmdID= 5024 "
		::= { iqdmx32CmdEntry 5024 }


	iqdmx32EmbeddersEmbedder1Enablech2 OBJECT-TYPE
		SYNTAX		INTEGER { disable(0), enable(1) }
		MAX-ACCESS		read-write
		STATUS			current
		DESCRIPTION
				"TYPE: - Checkbox
				 PAGE: - Channel 2- Audio 2- Embedders- Embedder 1
					Enable  cmdID= 5070 "
		::= { iqdmx32CmdEntry 5070 }


	iqdmx32EmbeddersEmbedder1SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 1
					Source L / Non-PCM  cmdID= 5050 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5050 }


	iqdmx32EmbeddersEmbedder1SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 1
					Source R  cmdID= 5051 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5051 }


	iqdmx32EmbeddersEmbedder1MutePair1 OBJECT-TYPE
		SYNTAX		INTEGER { disable(0), enable(1) }
		MAX-ACCESS		read-write
		STATUS			current
		DESCRIPTION
				"TYPE: - Checkbox
				 PAGE: - Channel 2- Audio 2- Embedders- Embedder 1
					Mute  cmdID= 3248 "
		::= { iqdmx32CmdEntry 3248 }


	iqdmx32EmbeddersEmbedder1MuteonVbitPair1 OBJECT-TYPE
		SYNTAX		INTEGER { disable(0), enable(1) }
		MAX-ACCESS		read-write
		STATUS			current
		DESCRIPTION
				"TYPE: - Checkbox
				 PAGE: - Channel 2- Audio 2- Embedders- Embedder 1
					Mute on V bit  cmdID= 3280 "
		::= { iqdmx32CmdEntry 3280 }


	iqdmx32EmbeddersEmbedder1InvertLPair1 OBJECT-TYPE
		SYNTAX		INTEGER { disable(0), enable(1) }
		MAX-ACCESS		read-write
		STATUS			current
		DESCRIPTION
				"TYPE: - Checkbox
				 PAGE: - Channel 2- Audio 2- Embedders- Embedder 1
					Invert L  cmdID= 3176 "
		::= { iqdmx32CmdEntry 3176 }


	iqdmx32EmbeddersEmbedder1InvertRPair1 OBJECT-TYPE
		SYNTAX		INTEGER { disable(0), enable(1) }
		MAX-ACCESS		read-write
		STATUS			current
		DESCRIPTION
				"TYPE: - Checkbox
				 PAGE: - Channel 2- Audio 2- Embedders- Embedder 1
					Invert R  cmdID= 3177 "
		::= { iqdmx32CmdEntry 3177 }


	iqdmx32EmbeddersEmbedder1GainLPair1 OBJECT-TYPE
		SYNTAX		INTEGER
		MAX-ACCESS		read-write
		STATUS			current
		DESCRIPTION
				"TYPE: - Number
				 PAGE: - Channel 2- Audio 2- Embedders- Embedder 1
					Gain L  cmdID= 3096  min= -720  max= 120  step= 1  format= %0.1fdB  div_scale= 10 
					Min = -72.0dB  Max = 12.0dB  Step = 0.1dB "
		::= { iqdmx32CmdEntry 3096 }


	iqdmx32EmbeddersEmbedder1GainRPair1 OBJECT-TYPE
		SYNTAX		INTEGER
		MAX-ACCESS		read-write
		STATUS			current
		DESCRIPTION
				"TYPE: - Number
				 PAGE: - Channel 2- Audio 2- Embedders- Embedder 1
					Gain R  cmdID= 3097  min= -720  max= 120  step= 1  format= %0.1fdB  div_scale= 10 
					Min = -72.0dB  Max = 12.0dB  Step = 0.1dB "
		::= { iqdmx32CmdEntry 3097 }


	iqdmx32EmbeddersEmbedder1PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 1
					Pair Mode  cmdID= 3938 
					2 Channel PCM  value= 0  
					Stereo PCM  value= 1  
					nonPCM  value= 2  "
		::= { iqdmx32CmdEntry 3938 }


	iqdmx32EmbeddersEmbedder1SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 1
					Source L / Non-PCM  cmdID= 5052 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5052 }


	iqdmx32EmbeddersEmbedder1SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 1
					Source R  cmdID= 5053 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5053 }


	iqdmx32EmbeddersEmbedder1MutePair2 OBJECT-TYPE
		SYNTAX		INTEGER { disable(0), enable(1) }
		MAX-ACCESS		read-write
		STATUS			current
		DESCRIPTION
				"TYPE: - Checkbox
				 PAGE: - Channel 2- Audio 2- Embedders- Embedder 1
					Mute  cmdID= 3249 "
		::= { iqdmx32CmdEntry 3249 }


	iqdmx32EmbeddersEmbedder1MuteonVbitPair2 OBJECT-TYPE
		SYNTAX		INTEGER { disable(0), enable(1) }
		MAX-ACCESS		read-write
		STATUS			current
		DESCRIPTION
				"TYPE: - Checkbox
				 PAGE: - Channel 2- Audio 2- Embedders- Embedder 1
					Mute on V bit  cmdID= 3281 "
		::= { iqdmx32CmdEntry 3281 }


	iqdmx32EmbeddersEmbedder1InvertLPair2 OBJECT-TYPE
		SYNTAX		INTEGER { disable(0), enable(1) }
		MAX-ACCESS		read-write
		STATUS			current
		DESCRIPTION
				"TYPE: - Checkbox
				 PAGE: - Channel 2- Audio 2- Embedders- Embedder 1
					Invert L  cmdID= 3178 "
		::= { iqdmx32CmdEntry 3178 }


	iqdmx32EmbeddersEmbedder1InvertRPair2 OBJECT-TYPE
		SYNTAX		INTEGER { disable(0), enable(1) }
		MAX-ACCESS		read-write
		STATUS			current
		DESCRIPTION
				"TYPE: - Checkbox
				 PAGE: - Channel 2- Audio 2- Embedders- Embedder 1
					Invert R  cmdID= 3179 "
		::= { iqdmx32CmdEntry 3179 }


	iqdmx32EmbeddersEmbedder1GainLPair2 OBJECT-TYPE
		SYNTAX		INTEGER
		MAX-ACCESS		read-write
		STATUS			current
		DESCRIPTION
				"TYPE: - Number
				 PAGE: - Channel 2- Audio 2- Embedders- Embedder 1
					Gain L  cmdID= 3098  min= -720  max= 120  step= 1  format= %0.1fdB  div_scale= 10 
					Min = -72.0dB  Max = 12.0dB  Step = 0.1dB "
		::= { iqdmx32CmdEntry 3098 }


	iqdmx32EmbeddersEmbedder1GainRPair2 OBJECT-TYPE
		SYNTAX		INTEGER
		MAX-ACCESS		read-write
		STATUS			current
		DESCRIPTION
				"TYPE: - Number
				 PAGE: - Channel 2- Audio 2- Embedders- Embedder 1
					Gain R  cmdID= 3099  min= -720  max= 120  step= 1  format= %0.1fdB  div_scale= 10 
					Min = -72.0dB  Max = 12.0dB  Step = 0.1dB "
		::= { iqdmx32CmdEntry 3099 }


	iqdmx32EmbeddersEmbedder1PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 1
					Pair Mode  cmdID= 3939 
					2 Channel PCM  value= 0  
					Stereo PCM  value= 1  
					nonPCM  value= 2  "
		::= { iqdmx32CmdEntry 3939 }


	iqdmx32EmbeddersEmbedder2EnablePair2 OBJECT-TYPE
		SYNTAX		INTEGER { disable(0), enable(1) }
		MAX-ACCESS		read-write
		STATUS			current
		DESCRIPTION
				"TYPE: - Checkbox
				 PAGE: - Channel 2- Audio 2- Embedders- Embedder 2
					Enable  cmdID= 5071 "
		::= { iqdmx32CmdEntry 5071 }


	iqdmx32EmbeddersEmbedder2SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 2
					Source L / Non-PCM  cmdID= 5054 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5054 }


	iqdmx32EmbeddersEmbedder2SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 2
					Source R  cmdID= 5055 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5055 }


	iqdmx32EmbeddersEmbedder2MutePair1 OBJECT-TYPE
		SYNTAX		INTEGER { disable(0), enable(1) }
		MAX-ACCESS		read-write
		STATUS			current
		DESCRIPTION
				"TYPE: - Checkbox
				 PAGE: - Channel 2- Audio 2- Embedders- Embedder 2
					Mute  cmdID= 3250 "
		::= { iqdmx32CmdEntry 3250 }


	iqdmx32EmbeddersEmbedder2MuteonVbitPair1 OBJECT-TYPE
		SYNTAX		INTEGER { disable(0), enable(1) }
		MAX-ACCESS		read-write
		STATUS			current
		DESCRIPTION
				"TYPE: - Checkbox
				 PAGE: - Channel 2- Audio 2- Embedders- Embedder 2
					Mute on V bit  cmdID= 3282 "
		::= { iqdmx32CmdEntry 3282 }


	iqdmx32EmbeddersEmbedder2InvertLPair1 OBJECT-TYPE
		SYNTAX		INTEGER { disable(0), enable(1) }
		MAX-ACCESS		read-write
		STATUS			current
		DESCRIPTION
				"TYPE: - Checkbox
				 PAGE: - Channel 2- Audio 2- Embedders- Embedder 2
					Invert L  cmdID= 3180 "
		::= { iqdmx32CmdEntry 3180 }


	iqdmx32EmbeddersEmbedder2InvertRPair1 OBJECT-TYPE
		SYNTAX		INTEGER { disable(0), enable(1) }
		MAX-ACCESS		read-write
		STATUS			current
		DESCRIPTION
				"TYPE: - Checkbox
				 PAGE: - Channel 2- Audio 2- Embedders- Embedder 2
					Invert R  cmdID= 3181 "
		::= { iqdmx32CmdEntry 3181 }


	iqdmx32EmbeddersEmbedder2GainLPair1 OBJECT-TYPE
		SYNTAX		INTEGER
		MAX-ACCESS		read-write
		STATUS			current
		DESCRIPTION
				"TYPE: - Number
				 PAGE: - Channel 2- Audio 2- Embedders- Embedder 2
					Gain L  cmdID= 3100  min= -720  max= 120  step= 1  format= %0.1fdB  div_scale= 10 
					Min = -72.0dB  Max = 12.0dB  Step = 0.1dB "
		::= { iqdmx32CmdEntry 3100 }


	iqdmx32EmbeddersEmbedder2GainRPair1 OBJECT-TYPE
		SYNTAX		INTEGER
		MAX-ACCESS		read-write
		STATUS			current
		DESCRIPTION
				"TYPE: - Number
				 PAGE: - Channel 2- Audio 2- Embedders- Embedder 2
					Gain R  cmdID= 3101  min= -720  max= 120  step= 1  format= %0.1fdB  div_scale= 10 
					Min = -72.0dB  Max = 12.0dB  Step = 0.1dB "
		::= { iqdmx32CmdEntry 3101 }


	iqdmx32EmbeddersEmbedder2PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 2
					Pair Mode  cmdID= 3940 
					2 Channel PCM  value= 0  
					Stereo PCM  value= 1  
					nonPCM  value= 2  "
		::= { iqdmx32CmdEntry 3940 }


	iqdmx32EmbeddersEmbedder2SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 2
					Source L / Non-PCM  cmdID= 5056 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5056 }


	iqdmx32EmbeddersEmbedder2SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 2
					Source R  cmdID= 5057 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5057 }


	iqdmx32EmbeddersEmbedder2MutePair2 OBJECT-TYPE
		SYNTAX		INTEGER { disable(0), enable(1) }
		MAX-ACCESS		read-write
		STATUS			current
		DESCRIPTION
				"TYPE: - Checkbox
				 PAGE: - Channel 2- Audio 2- Embedders- Embedder 2
					Mute  cmdID= 3251 "
		::= { iqdmx32CmdEntry 3251 }


	iqdmx32EmbeddersEmbedder2MuteonVbitPair2 OBJECT-TYPE
		SYNTAX		INTEGER { disable(0), enable(1) }
		MAX-ACCESS		read-write
		STATUS			current
		DESCRIPTION
				"TYPE: - Checkbox
				 PAGE: - Channel 2- Audio 2- Embedders- Embedder 2
					Mute on V bit  cmdID= 3283 "
		::= { iqdmx32CmdEntry 3283 }


	iqdmx32EmbeddersEmbedder2InvertLPair2 OBJECT-TYPE
		SYNTAX		INTEGER { disable(0), enable(1) }
		MAX-ACCESS		read-write
		STATUS			current
		DESCRIPTION
				"TYPE: - Checkbox
				 PAGE: - Channel 2- Audio 2- Embedders- Embedder 2
					Invert L  cmdID= 3182 "
		::= { iqdmx32CmdEntry 3182 }


	iqdmx32EmbeddersEmbedder2InvertRPair2 OBJECT-TYPE
		SYNTAX		INTEGER { disable(0), enable(1) }
		MAX-ACCESS		read-write
		STATUS			current
		DESCRIPTION
				"TYPE: - Checkbox
				 PAGE: - Channel 2- Audio 2- Embedders- Embedder 2
					Invert R  cmdID= 3183 "
		::= { iqdmx32CmdEntry 3183 }


	iqdmx32EmbeddersEmbedder2GainLPair2 OBJECT-TYPE
		SYNTAX		INTEGER
		MAX-ACCESS		read-write
		STATUS			current
		DESCRIPTION
				"TYPE: - Number
				 PAGE: - Channel 2- Audio 2- Embedders- Embedder 2
					Gain L  cmdID= 3102  min= -720  max= 120  step= 1  format= %0.1fdB  div_scale= 10 
					Min = -72.0dB  Max = 12.0dB  Step = 0.1dB "
		::= { iqdmx32CmdEntry 3102 }


	iqdmx32EmbeddersEmbedder2GainRPair2 OBJECT-TYPE
		SYNTAX		INTEGER
		MAX-ACCESS		read-write
		STATUS			current
		DESCRIPTION
				"TYPE: - Number
				 PAGE: - Channel 2- Audio 2- Embedders- Embedder 2
					Gain R  cmdID= 3103  min= -720  max= 120  step= 1  format= %0.1fdB  div_scale= 10 
					Min = -72.0dB  Max = 12.0dB  Step = 0.1dB "
		::= { iqdmx32CmdEntry 3103 }


	iqdmx32EmbeddersEmbedder2PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 2
					Pair Mode  cmdID= 3941 
					2 Channel PCM  value= 0  
					Stereo PCM  value= 1  
					nonPCM  value= 2  "
		::= { iqdmx32CmdEntry 3941 }


	iqdmx32EmbeddersEmbedder3EnablePair2 OBJECT-TYPE
		SYNTAX		INTEGER { disable(0), enable(1) }
		MAX-ACCESS		read-write
		STATUS			current
		DESCRIPTION
				"TYPE: - Checkbox
				 PAGE: - Channel 2- Audio 2- Embedders- Embedder 3
					Enable  cmdID= 5072 "
		::= { iqdmx32CmdEntry 5072 }


	iqdmx32EmbeddersEmbedder3SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 3
					Source L / Non-PCM  cmdID= 5058 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5058 }


	iqdmx32EmbeddersEmbedder3SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 3
					Source R  cmdID= 5059 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5059 }


	iqdmx32EmbeddersEmbedder3MutePair1 OBJECT-TYPE
		SYNTAX		INTEGER { disable(0), enable(1) }
		MAX-ACCESS		read-write
		STATUS			current
		DESCRIPTION
				"TYPE: - Checkbox
				 PAGE: - Channel 2- Audio 2- Embedders- Embedder 3
					Mute  cmdID= 3252 "
		::= { iqdmx32CmdEntry 3252 }


	iqdmx32EmbeddersEmbedder3MuteonVbitPair1 OBJECT-TYPE
		SYNTAX		INTEGER { disable(0), enable(1) }
		MAX-ACCESS		read-write
		STATUS			current
		DESCRIPTION
				"TYPE: - Checkbox
				 PAGE: - Channel 2- Audio 2- Embedders- Embedder 3
					Mute on V bit  cmdID= 3284 "
		::= { iqdmx32CmdEntry 3284 }


	iqdmx32EmbeddersEmbedder3InvertLPair1 OBJECT-TYPE
		SYNTAX		INTEGER { disable(0), enable(1) }
		MAX-ACCESS		read-write
		STATUS			current
		DESCRIPTION
				"TYPE: - Checkbox
				 PAGE: - Channel 2- Audio 2- Embedders- Embedder 3
					Invert L  cmdID= 3184 "
		::= { iqdmx32CmdEntry 3184 }


	iqdmx32EmbeddersEmbedder3InvertRPair1 OBJECT-TYPE
		SYNTAX		INTEGER { disable(0), enable(1) }
		MAX-ACCESS		read-write
		STATUS			current
		DESCRIPTION
				"TYPE: - Checkbox
				 PAGE: - Channel 2- Audio 2- Embedders- Embedder 3
					Invert R  cmdID= 3185 "
		::= { iqdmx32CmdEntry 3185 }


	iqdmx32EmbeddersEmbedder3GainLPair1 OBJECT-TYPE
		SYNTAX		INTEGER
		MAX-ACCESS		read-write
		STATUS			current
		DESCRIPTION
				"TYPE: - Number
				 PAGE: - Channel 2- Audio 2- Embedders- Embedder 3
					Gain L  cmdID= 3104  min= -720  max= 120  step= 1  format= %0.1fdB  div_scale= 10 
					Min = -72.0dB  Max = 12.0dB  Step = 0.1dB "
		::= { iqdmx32CmdEntry 3104 }


	iqdmx32EmbeddersEmbedder3GainRPair1 OBJECT-TYPE
		SYNTAX		INTEGER
		MAX-ACCESS		read-write
		STATUS			current
		DESCRIPTION
				"TYPE: - Number
				 PAGE: - Channel 2- Audio 2- Embedders- Embedder 3
					Gain R  cmdID= 3105  min= -720  max= 120  step= 1  format= %0.1fdB  div_scale= 10 
					Min = -72.0dB  Max = 12.0dB  Step = 0.1dB "
		::= { iqdmx32CmdEntry 3105 }


	iqdmx32EmbeddersEmbedder3PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 3
					Pair Mode  cmdID= 3942 
					2 Channel PCM  value= 0  
					Stereo PCM  value= 1  
					nonPCM  value= 2  "
		::= { iqdmx32CmdEntry 3942 }


	iqdmx32EmbeddersEmbedder3SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 3
					Source L / Non-PCM  cmdID= 5060 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5060 }


	iqdmx32EmbeddersEmbedder3SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 3
					Source R  cmdID= 5061 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5061 }


	iqdmx32EmbeddersEmbedder3MutePair2 OBJECT-TYPE
		SYNTAX		INTEGER { disable(0), enable(1) }
		MAX-ACCESS		read-write
		STATUS			current
		DESCRIPTION
				"TYPE: - Checkbox
				 PAGE: - Channel 2- Audio 2- Embedders- Embedder 3
					Mute  cmdID= 3253 "
		::= { iqdmx32CmdEntry 3253 }


	iqdmx32EmbeddersEmbedder3MuteonVbitPair2 OBJECT-TYPE
		SYNTAX		INTEGER { disable(0), enable(1) }
		MAX-ACCESS		read-write
		STATUS			current
		DESCRIPTION
				"TYPE: - Checkbox
				 PAGE: - Channel 2- Audio 2- Embedders- Embedder 3
					Mute on V bit  cmdID= 3285 "
		::= { iqdmx32CmdEntry 3285 }


	iqdmx32EmbeddersEmbedder3InvertLPair2 OBJECT-TYPE
		SYNTAX		INTEGER { disable(0), enable(1) }
		MAX-ACCESS		read-write
		STATUS			current
		DESCRIPTION
				"TYPE: - Checkbox
				 PAGE: - Channel 2- Audio 2- Embedders- Embedder 3
					Invert L  cmdID= 3186 "
		::= { iqdmx32CmdEntry 3186 }


	iqdmx32EmbeddersEmbedder3InvertRPair2 OBJECT-TYPE
		SYNTAX		INTEGER { disable(0), enable(1) }
		MAX-ACCESS		read-write
		STATUS			current
		DESCRIPTION
				"TYPE: - Checkbox
				 PAGE: - Channel 2- Audio 2- Embedders- Embedder 3
					Invert R  cmdID= 3187 "
		::= { iqdmx32CmdEntry 3187 }


	iqdmx32EmbeddersEmbedder3GainLPair2 OBJECT-TYPE
		SYNTAX		INTEGER
		MAX-ACCESS		read-write
		STATUS			current
		DESCRIPTION
				"TYPE: - Number
				 PAGE: - Channel 2- Audio 2- Embedders- Embedder 3
					Gain L  cmdID= 3106  min= -720  max= 120  step= 1  format= %0.1fdB  div_scale= 10 
					Min = -72.0dB  Max = 12.0dB  Step = 0.1dB "
		::= { iqdmx32CmdEntry 3106 }


	iqdmx32EmbeddersEmbedder3GainRPair2 OBJECT-TYPE
		SYNTAX		INTEGER
		MAX-ACCESS		read-write
		STATUS			current
		DESCRIPTION
				"TYPE: - Number
				 PAGE: - Channel 2- Audio 2- Embedders- Embedder 3
					Gain R  cmdID= 3107  min= -720  max= 120  step= 1  format= %0.1fdB  div_scale= 10 
					Min = -72.0dB  Max = 12.0dB  Step = 0.1dB "
		::= { iqdmx32CmdEntry 3107 }


	iqdmx32EmbeddersEmbedder3PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 3
					Pair Mode  cmdID= 3943 
					2 Channel PCM  value= 0  
					Stereo PCM  value= 1  
					nonPCM  value= 2  "
		::= { iqdmx32CmdEntry 3943 }


	iqdmx32EmbeddersEmbedder4EnablePair2 OBJECT-TYPE
		SYNTAX		INTEGER { disable(0), enable(1) }
		MAX-ACCESS		read-write
		STATUS			current
		DESCRIPTION
				"TYPE: - Checkbox
				 PAGE: - Channel 2- Audio 2- Embedders- Embedder 4
					Enable  cmdID= 5073 "
		::= { iqdmx32CmdEntry 5073 }


	iqdmx32EmbeddersEmbedder4SourceLNonPCMPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 4
					Source L / Non-PCM  cmdID= 5062 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5062 }


	iqdmx32EmbeddersEmbedder4SourceRPair1 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 4
					Source R  cmdID= 5063 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5063 }


	iqdmx32EmbeddersEmbedder4MutePair1 OBJECT-TYPE
		SYNTAX		INTEGER { disable(0), enable(1) }
		MAX-ACCESS		read-write
		STATUS			current
		DESCRIPTION
				"TYPE: - Checkbox
				 PAGE: - Channel 2- Audio 2- Embedders- Embedder 4
					Mute  cmdID= 3254 "
		::= { iqdmx32CmdEntry 3254 }


	iqdmx32EmbeddersEmbedder4MuteonVbitPair1 OBJECT-TYPE
		SYNTAX		INTEGER { disable(0), enable(1) }
		MAX-ACCESS		read-write
		STATUS			current
		DESCRIPTION
				"TYPE: - Checkbox
				 PAGE: - Channel 2- Audio 2- Embedders- Embedder 4
					Mute on V bit  cmdID= 3286 "
		::= { iqdmx32CmdEntry 3286 }


	iqdmx32EmbeddersEmbedder4InvertLPair1 OBJECT-TYPE
		SYNTAX		INTEGER { disable(0), enable(1) }
		MAX-ACCESS		read-write
		STATUS			current
		DESCRIPTION
				"TYPE: - Checkbox
				 PAGE: - Channel 2- Audio 2- Embedders- Embedder 4
					Invert L  cmdID= 3188 "
		::= { iqdmx32CmdEntry 3188 }


	iqdmx32EmbeddersEmbedder4InvertRPair1 OBJECT-TYPE
		SYNTAX		INTEGER { disable(0), enable(1) }
		MAX-ACCESS		read-write
		STATUS			current
		DESCRIPTION
				"TYPE: - Checkbox
				 PAGE: - Channel 2- Audio 2- Embedders- Embedder 4
					Invert R  cmdID= 3189 "
		::= { iqdmx32CmdEntry 3189 }


	iqdmx32EmbeddersEmbedder4GainLPair1 OBJECT-TYPE
		SYNTAX		INTEGER
		MAX-ACCESS		read-write
		STATUS			current
		DESCRIPTION
				"TYPE: - Number
				 PAGE: - Channel 2- Audio 2- Embedders- Embedder 4
					Gain L  cmdID= 3108  min= -720  max= 120  step= 1  format= %0.1fdB  div_scale= 10 
					Min = -72.0dB  Max = 12.0dB  Step = 0.1dB "
		::= { iqdmx32CmdEntry 3108 }


	iqdmx32EmbeddersEmbedder4GainRPair1 OBJECT-TYPE
		SYNTAX		INTEGER
		MAX-ACCESS		read-write
		STATUS			current
		DESCRIPTION
				"TYPE: - Number
				 PAGE: - Channel 2- Audio 2- Embedders- Embedder 4
					Gain R  cmdID= 3109  min= -720  max= 120  step= 1  format= %0.1fdB  div_scale= 10 
					Min = -72.0dB  Max = 12.0dB  Step = 0.1dB "
		::= { iqdmx32CmdEntry 3109 }


	iqdmx32EmbeddersEmbedder4PairModePair1 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 4
					Pair Mode  cmdID= 3944 
					2 Channel PCM  value= 0  
					Stereo PCM  value= 1  
					nonPCM  value= 2  "
		::= { iqdmx32CmdEntry 3944 }


	iqdmx32EmbeddersEmbedder4SourceLNonPCMPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Channel 2- Audio 2- Embedders- Embedder 4
					Source L / Non-PCM  cmdID= 5064 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqdmx32CmdEntry 5064 }


	iqdmx32EmbeddersEmbedder4SourceRPair2 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Channel 2- Audio 2- Embedders- Embedder 4
					Source R  cmdID= 5065 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqdmx32CmdEntry 5065 }


	iqdmx32EmbeddersEmbedder4MutePair2 OBJECT-TYPE
		SYNTAX		INTEGER { disable(0), enable(1) }
		MAX-ACCESS		read-write
		STATUS			current
		DESCRIPTION
				"TYPE: - Checkbox
				 PAGE: - Channel 2- Audio 2- Embedders- Embedder 4
					Mute  cmdID= 3255 "
		::= { iqdmx32CmdEntry 3255 }


	iqdmx32EmbeddersEmbedder4MuteonVbitPair2 OBJECT-TYPE
		SYNTAX		INTEGER { disable(0), enable(1) }
		MAX-ACCESS		read-write
		STATUS			current
		DESCRIPTION
				"TYPE: - Checkbox
				 PAGE: - Channel 2- Audio 2- Embedders- Embedder 4
					Mute on V bit  cmdID= 3287 "
		::= { iqdmx32CmdEntry 3287 }


	iqdmx32EmbeddersEmbedder4InvertLPair2 OBJECT-TYPE
		SYNTAX		INTEGER { disable(0), enable(1) }
		MAX-ACCESS		read-write
		STATUS			current
		DESCRIPTION
				"TYPE: - Checkbox
				 PAGE: - Channel 2- Audio 2- Embedders- Embedder 4
					Invert L  cmdID= 3190 "
		::= { iqdmx32CmdEntry 3190 }


	iqdmx32EmbeddersEmbedder4InvertRPair2 OBJECT-TYPE
		SYNTAX		INTEGER { disable(0), enable(1) }
		MAX-ACCESS		read-write
		STATUS			current
		DESCRIPTION
				"TYPE: - Checkbox
				 PAGE: - Channel 2- Audio 2- Embedders- Embedder 4
					Invert R  cmdID= 3191 "
		::= { iqdmx32CmdEntry 3191 }


	iqdmx32EmbeddersEmbedder4GainLPair2 OBJECT-TYPE
		SYNTAX		INTEGER
		MAX-ACCESS		read-write
		STATUS			current
		DESCRIPTION
				"TYPE: - Number
				 PAGE: - Channel 2- Audio 2- Embedders- Embedder 4
					Gain L  cmdID= 3110  min= -720  max= 120  step= 1  format= %0.1fdB  div_scale= 10 
					Min = -72.0dB  Max = 12.0dB  Step = 0.1dB "
		::= { iqdmx32CmdEntry 3110 }


	iqdmx32EmbeddersEmbedder4GainRPair2 OBJECT-TYPE
		SYNTAX		INTEGER
		MAX-ACCESS		read-write
		STATUS			current
		DESCRIPTION
				"TYPE: - Number
				 PAGE: - Channel 2- Audio 2- Embedders- Embedder 4
					Gain R  cmdID= 3111  min= -720  max= 120  step= 1  format= %0.1fdB  div_scale= 10 
					Min = -72.0dB  Max = 12.0dB  Step = 0.1dB "
		::= { iqdmx32CmdEntry 3111 }


	iqdmx32EmbeddersEmbedder4PairModePair2 OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- Embedders- Embedder 4
					Pair Mode  cmdID= 3945 
					2 Channel PCM  value= 0  
					Stereo PCM  value= 1  
					nonPCM  value= 2  "
		::= { iqdmx32CmdEntry 3945 }


	iqdmx32AESOutAESOut5SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 2- Audio 2- AES Out- AES Out 5
					Source L / Non-PCM  cmdID= 5104 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5104 }


	iqdmx32AESOutAESOut5SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 2- Audio 2- AES Out- AES Out 5
					Source R  cmdID= 5105 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5105 }


	iqdmx32AESOutAESOut5Mute OBJECT-TYPE
		SYNTAX		INTEGER { disable(0), enable(1) }
		MAX-ACCESS		read-write
		STATUS			current
		DESCRIPTION
				"TYPE: - Checkbox
				 PAGE: - Channel 2- Audio 2- AES Out- AES Out 5
					Mute  cmdID= 3260 "
		::= { iqdmx32CmdEntry 3260 }


	iqdmx32AESOutAESOut5MuteonVbit OBJECT-TYPE
		SYNTAX		INTEGER { disable(0), enable(1) }
		MAX-ACCESS		read-write
		STATUS			current
		DESCRIPTION
				"TYPE: - Checkbox
				 PAGE: - Channel 2- Audio 2- AES Out- AES Out 5
					Mute on V bit  cmdID= 3292 "
		::= { iqdmx32CmdEntry 3292 }


	iqdmx32AESOutAESOut5InvertL OBJECT-TYPE
		SYNTAX		INTEGER { disable(0), enable(1) }
		MAX-ACCESS		read-write
		STATUS			current
		DESCRIPTION
				"TYPE: - Checkbox
				 PAGE: - Channel 2- Audio 2- AES Out- AES Out 5
					Invert L  cmdID= 3200 "
		::= { iqdmx32CmdEntry 3200 }


	iqdmx32AESOutAESOut5InvertR OBJECT-TYPE
		SYNTAX		INTEGER { disable(0), enable(1) }
		MAX-ACCESS		read-write
		STATUS			current
		DESCRIPTION
				"TYPE: - Checkbox
				 PAGE: - Channel 2- Audio 2- AES Out- AES Out 5
					Invert R  cmdID= 3201 "
		::= { iqdmx32CmdEntry 3201 }


	iqdmx32AESOutAESOut5GainL OBJECT-TYPE
		SYNTAX		INTEGER
		MAX-ACCESS		read-write
		STATUS			current
		DESCRIPTION
				"TYPE: - Number
				 PAGE: - Channel 2- Audio 2- AES Out- AES Out 5
					Gain L  cmdID= 3120  min= -720  max= 120  step= 1  format= %0.1fdB  div_scale= 10 
					Min = -72.0dB  Max = 12.0dB  Step = 0.1dB "
		::= { iqdmx32CmdEntry 3120 }


	iqdmx32AESOutAESOut5GainR OBJECT-TYPE
		SYNTAX		INTEGER
		MAX-ACCESS		read-write
		STATUS			current
		DESCRIPTION
				"TYPE: - Number
				 PAGE: - Channel 2- Audio 2- AES Out- AES Out 5
					Gain R  cmdID= 3121  min= -720  max= 120  step= 1  format= %0.1fdB  div_scale= 10 
					Min = -72.0dB  Max = 12.0dB  Step = 0.1dB "
		::= { iqdmx32CmdEntry 3121 }


	iqdmx32AESOutAESOut5PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- AES Out- AES Out 5
					Pair Mode  cmdID= 5116 
					2 Channel PCM  value= 0  
					Stereo PCM  value= 1  
					nonPCM  value= 2  "
		::= { iqdmx32CmdEntry 5116 }


	iqdmx32AESOutAESOut6SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 2- Audio 2- AES Out- AES Out 6
					Source L / Non-PCM  cmdID= 5106 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5106 }


	iqdmx32AESOutAESOut6SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 2- Audio 2- AES Out- AES Out 6
					Source R  cmdID= 5107 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5107 }


	iqdmx32AESOutAESOut6Mute OBJECT-TYPE
		SYNTAX		INTEGER { disable(0), enable(1) }
		MAX-ACCESS		read-write
		STATUS			current
		DESCRIPTION
				"TYPE: - Checkbox
				 PAGE: - Channel 2- Audio 2- AES Out- AES Out 6
					Mute  cmdID= 3261 "
		::= { iqdmx32CmdEntry 3261 }


	iqdmx32AESOutAESOut6MuteonVbit OBJECT-TYPE
		SYNTAX		INTEGER { disable(0), enable(1) }
		MAX-ACCESS		read-write
		STATUS			current
		DESCRIPTION
				"TYPE: - Checkbox
				 PAGE: - Channel 2- Audio 2- AES Out- AES Out 6
					Mute on V bit  cmdID= 3293 "
		::= { iqdmx32CmdEntry 3293 }


	iqdmx32AESOutAESOut6InvertL OBJECT-TYPE
		SYNTAX		INTEGER { disable(0), enable(1) }
		MAX-ACCESS		read-write
		STATUS			current
		DESCRIPTION
				"TYPE: - Checkbox
				 PAGE: - Channel 2- Audio 2- AES Out- AES Out 6
					Invert L  cmdID= 3202 "
		::= { iqdmx32CmdEntry 3202 }


	iqdmx32AESOutAESOut6InvertR OBJECT-TYPE
		SYNTAX		INTEGER { disable(0), enable(1) }
		MAX-ACCESS		read-write
		STATUS			current
		DESCRIPTION
				"TYPE: - Checkbox
				 PAGE: - Channel 2- Audio 2- AES Out- AES Out 6
					Invert R  cmdID= 3203 "
		::= { iqdmx32CmdEntry 3203 }


	iqdmx32AESOutAESOut6GainL OBJECT-TYPE
		SYNTAX		INTEGER
		MAX-ACCESS		read-write
		STATUS			current
		DESCRIPTION
				"TYPE: - Number
				 PAGE: - Channel 2- Audio 2- AES Out- AES Out 6
					Gain L  cmdID= 3122  min= -720  max= 120  step= 1  format= %0.1fdB  div_scale= 10 
					Min = -72.0dB  Max = 12.0dB  Step = 0.1dB "
		::= { iqdmx32CmdEntry 3122 }


	iqdmx32AESOutAESOut6GainR OBJECT-TYPE
		SYNTAX		INTEGER
		MAX-ACCESS		read-write
		STATUS			current
		DESCRIPTION
				"TYPE: - Number
				 PAGE: - Channel 2- Audio 2- AES Out- AES Out 6
					Gain R  cmdID= 3123  min= -720  max= 120  step= 1  format= %0.1fdB  div_scale= 10 
					Min = -72.0dB  Max = 12.0dB  Step = 0.1dB "
		::= { iqdmx32CmdEntry 3123 }


	iqdmx32AESOutAESOut6PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- AES Out- AES Out 6
					Pair Mode  cmdID= 5117 
					2 Channel PCM  value= 0  
					Stereo PCM  value= 1  
					nonPCM  value= 2  "
		::= { iqdmx32CmdEntry 5117 }


	iqdmx32AESOutAESOut7SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 2- Audio 2- AES Out- AES Out 7
					Source L / Non-PCM  cmdID= 5108 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5108 }


	iqdmx32AESOutAESOut7SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 2- Audio 2- AES Out- AES Out 7
					Source R  cmdID= 5109 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5109 }


	iqdmx32AESOutAESOut7Mute OBJECT-TYPE
		SYNTAX		INTEGER { disable(0), enable(1) }
		MAX-ACCESS		read-write
		STATUS			current
		DESCRIPTION
				"TYPE: - Checkbox
				 PAGE: - Channel 2- Audio 2- AES Out- AES Out 7
					Mute  cmdID= 3262 "
		::= { iqdmx32CmdEntry 3262 }


	iqdmx32AESOutAESOut7MuteonVbit OBJECT-TYPE
		SYNTAX		INTEGER { disable(0), enable(1) }
		MAX-ACCESS		read-write
		STATUS			current
		DESCRIPTION
				"TYPE: - Checkbox
				 PAGE: - Channel 2- Audio 2- AES Out- AES Out 7
					Mute on V bit  cmdID= 3294 "
		::= { iqdmx32CmdEntry 3294 }


	iqdmx32AESOutAESOut7InvertL OBJECT-TYPE
		SYNTAX		INTEGER { disable(0), enable(1) }
		MAX-ACCESS		read-write
		STATUS			current
		DESCRIPTION
				"TYPE: - Checkbox
				 PAGE: - Channel 2- Audio 2- AES Out- AES Out 7
					Invert L  cmdID= 3204 "
		::= { iqdmx32CmdEntry 3204 }


	iqdmx32AESOutAESOut7InvertR OBJECT-TYPE
		SYNTAX		INTEGER { disable(0), enable(1) }
		MAX-ACCESS		read-write
		STATUS			current
		DESCRIPTION
				"TYPE: - Checkbox
				 PAGE: - Channel 2- Audio 2- AES Out- AES Out 7
					Invert R  cmdID= 3205 "
		::= { iqdmx32CmdEntry 3205 }


	iqdmx32AESOutAESOut7GainL OBJECT-TYPE
		SYNTAX		INTEGER
		MAX-ACCESS		read-write
		STATUS			current
		DESCRIPTION
				"TYPE: - Number
				 PAGE: - Channel 2- Audio 2- AES Out- AES Out 7
					Gain L  cmdID= 3124  min= -720  max= 120  step= 1  format= %0.1fdB  div_scale= 10 
					Min = -72.0dB  Max = 12.0dB  Step = 0.1dB "
		::= { iqdmx32CmdEntry 3124 }


	iqdmx32AESOutAESOut7GainR OBJECT-TYPE
		SYNTAX		INTEGER
		MAX-ACCESS		read-write
		STATUS			current
		DESCRIPTION
				"TYPE: - Number
				 PAGE: - Channel 2- Audio 2- AES Out- AES Out 7
					Gain R  cmdID= 3125  min= -720  max= 120  step= 1  format= %0.1fdB  div_scale= 10 
					Min = -72.0dB  Max = 12.0dB  Step = 0.1dB "
		::= { iqdmx32CmdEntry 3125 }


	iqdmx32AESOutAESOut7PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- AES Out- AES Out 7
					Pair Mode  cmdID= 5118 
					2 Channel PCM  value= 0  
					Stereo PCM  value= 1  
					nonPCM  value= 2  "
		::= { iqdmx32CmdEntry 5118 }


	iqdmx32AESOutAESOut8SourceLNonPCM OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(32),
							val-Silence(34)
							}
		MAX-ACCESS		read-write
		STATUS			current
		DESCRIPTION
				"TYPE: - RadiobuttonList
				 PAGE: - Channel 2- Audio 2- AES Out- AES Out 8
					Source L / Non-PCM  cmdID= 5110 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 32  
					Silence  value= 34  "
		::= { iqdmx32CmdEntry 5110 }


	iqdmx32AESOutAESOut8SourceR OBJECT-TYPE
		SYNTAX		INTEGER {
							val-Disembed-1-1(0),
							val-Disembed-1-2(1),
							val-Disembed-2-1(2),
							val-Disembed-2-2(3),
							val-Disembed-3-1(4),
							val-Disembed-3-2(5),
							val-Disembed-4-1(6),
							val-Disembed-4-2(7),
							val-Disembed-5-1(8),
							val-Disembed-5-2(9),
							val-Disembed-6-1(10),
							val-Disembed-6-2(11),
							val-Disembed-7-1(12),
							val-Disembed-7-2(13),
							val-Disembed-8-1(14),
							val-Disembed-8-2(15),
							val-Tone(33),
							val-Silence(34)
							}
		MAX-ACCESS		read-write
		STATUS			current
		DESCRIPTION
				"TYPE: - RadiobuttonList
				 PAGE: - Channel 2- Audio 2- AES Out- AES Out 8
					Source R  cmdID= 5111 
					Disembed 1_1  value= 0  
					Disembed 1_2  value= 1  
					Disembed 2_1  value= 2  
					Disembed 2_2  value= 3  
					Disembed 3_1  value= 4  
					Disembed 3_2  value= 5  
					Disembed 4_1  value= 6  
					Disembed 4_2  value= 7  
					Disembed 5_1  value= 8  
					Disembed 5_2  value= 9  
					Disembed 6_1  value= 10  
					Disembed 6_2  value= 11  
					Disembed 7_1  value= 12  
					Disembed 7_2  value= 13  
					Disembed 8_1  value= 14  
					Disembed 8_2  value= 15  
					Tone  value= 33  
					Silence  value= 34  "
		::= { iqdmx32CmdEntry 5111 }


	iqdmx32AESOutAESOut8Mute OBJECT-TYPE
		SYNTAX		INTEGER { disable(0), enable(1) }
		MAX-ACCESS		read-write
		STATUS			current
		DESCRIPTION
				"TYPE: - Checkbox
				 PAGE: - Channel 2- Audio 2- AES Out- AES Out 8
					Mute  cmdID= 3263 "
		::= { iqdmx32CmdEntry 3263 }


	iqdmx32AESOutAESOut8MuteonVbit OBJECT-TYPE
		SYNTAX		INTEGER { disable(0), enable(1) }
		MAX-ACCESS		read-write
		STATUS			current
		DESCRIPTION
				"TYPE: - Checkbox
				 PAGE: - Channel 2- Audio 2- AES Out- AES Out 8
					Mute on V bit  cmdID= 3295 "
		::= { iqdmx32CmdEntry 3295 }


	iqdmx32AESOutAESOut8InvertL OBJECT-TYPE
		SYNTAX		INTEGER { disable(0), enable(1) }
		MAX-ACCESS		read-write
		STATUS			current
		DESCRIPTION
				"TYPE: - Checkbox
				 PAGE: - Channel 2- Audio 2- AES Out- AES Out 8
					Invert L  cmdID= 3206 "
		::= { iqdmx32CmdEntry 3206 }


	iqdmx32AESOutAESOut8InvertR OBJECT-TYPE
		SYNTAX		INTEGER { disable(0), enable(1) }
		MAX-ACCESS		read-write
		STATUS			current
		DESCRIPTION
				"TYPE: - Checkbox
				 PAGE: - Channel 2- Audio 2- AES Out- AES Out 8
					Invert R  cmdID= 3207 "
		::= { iqdmx32CmdEntry 3207 }


	iqdmx32AESOutAESOut8GainL OBJECT-TYPE
		SYNTAX		INTEGER
		MAX-ACCESS		read-write
		STATUS			current
		DESCRIPTION
				"TYPE: - Number
				 PAGE: - Channel 2- Audio 2- AES Out- AES Out 8
					Gain L  cmdID= 3126  min= -720  max= 120  step= 1  format= %0.1fdB  div_scale= 10 
					Min = -72.0dB  Max = 12.0dB  Step = 0.1dB "
		::= { iqdmx32CmdEntry 3126 }


	iqdmx32AESOutAESOut8GainR OBJECT-TYPE
		SYNTAX		INTEGER
		MAX-ACCESS		read-write
		STATUS			current
		DESCRIPTION
				"TYPE: - Number
				 PAGE: - Channel 2- Audio 2- AES Out- AES Out 8
					Gain R  cmdID= 3127  min= -720  max= 120  step= 1  format= %0.1fdB  div_scale= 10 
					Min = -72.0dB  Max = 12.0dB  Step = 0.1dB "
		::= { iqdmx32CmdEntry 3127 }


	iqdmx32AESOutAESOut8PairMode OBJECT-TYPE
		SYNTAX		INTEGER {
							val-2-Channel-PCM(0),
							val-Stereo-PCM(1),
							val-nonPCM(2)
							}
		MAX-ACCESS		read-write
		STATUS			current
		DESCRIPTION
				"TYPE: - RadiobuttonList
				 PAGE: - Channel 2- Audio 2- AES Out- AES Out 8
					Pair Mode  cmdID= 5119 
					2 Channel PCM  value= 0  
					Stereo PCM  value= 1  
					nonPCM  value= 2  "
		::= { iqdmx32CmdEntry 5119 }


	iqdmx32AudioDelayDelaysVideoDelayCh2 OBJECT-TYPE
		SYNTAX		INTEGER { disable(0), enable(1) }
		MAX-ACCESS		read-write
		STATUS			current
		DESCRIPTION
				"TYPE: - Checkbox
				 PAGE: - Channel 2- Audio 2
					Video Delay  cmdID= 5089 "
		::= { iqdmx32CmdEntry 5089 }


	iqdmx32AudioDelayDelaysManualDelayCh2 OBJECT-TYPE
		SYNTAX		INTEGER { disable(0), enable(1) }
		MAX-ACCESS		read-write
		STATUS			current
		DESCRIPTION
				"TYPE: - Checkbox
				 PAGE: - Channel 2- Audio 2
					Manual Delay  cmdID= 5090 "
		::= { iqdmx32CmdEntry 5090 }


	iqdmx32AudioDelayDelaysCoarseDelayCh2 OBJECT-TYPE
		SYNTAX		INTEGER
		MAX-ACCESS		read-write
		STATUS			current
		DESCRIPTION
				"TYPE: - Number
				 PAGE: - Channel 2- Audio 2
					Coarse Delay  cmdID= 5086  min= 0  max= 1750  step= 5  format= %5.3fs  div_scale= 1000 
					Min = 0.000s  Max = 1.750s  Step = 0.005s "
		::= { iqdmx32CmdEntry 5086 }


	iqdmx32AudioDelayDelaysFineDelayCh2 OBJECT-TYPE
		SYNTAX		INTEGER
		MAX-ACCESS		read-write
		STATUS			current
		DESCRIPTION
				"TYPE: - Number
				 PAGE: - Channel 2- Audio 2
					Fine Delay  cmdID= 5088  min= -2500  max= 2500  step= 5  format= %0.1fms  div_scale= 10 
					Min = -250.0ms  Max = 250.0ms  Step = 0.5ms "
		::= { iqdmx32CmdEntry 5088 }


	iqdmx32AudioDelayDelayStatusTotalDelayCh2 OBJECT-TYPE
		SYNTAX		RollCallString
		MAX-ACCESS		read-only
		STATUS			current
		DESCRIPTION
				"TYPE: - Display
				 PAGE: - Channel 2- Audio 2
					Total Delay  cmdID= 5095  format=   "
		::= { iqdmx32CmdEntry 5095 }


	iqdmx32AudioDelayDelayStatusVideoDelayCh2 OBJECT-TYPE
		SYNTAX		RollCallString
		MAX-ACCESS		read-only
		STATUS			current
		DESCRIPTION
				"TYPE: - Display
				 PAGE: - Channel 2- Audio 2
					Video Delay  cmdID= 5085  format=   "
		::= { iqdmx32CmdEntry 5085 }


	iqdmx32AudioDelayDelayStatusManualDelayCh2 OBJECT-TYPE
		SYNTAX		RollCallString
		MAX-ACCESS		read-only
		STATUS			current
		DESCRIPTION
				"TYPE: - Display
				 PAGE: - Channel 2- Audio 2
					Manual Delay  cmdID= 5087  format=   "
		::= { iqdmx32CmdEntry 5087 }


	iqdmx32Audio2ToneFrequency OBJECT-TYPE
		SYNTAX		INTEGER
		MAX-ACCESS		read-write
		STATUS			current
		DESCRIPTION
				"TYPE: - Number
				 PAGE: - Channel 2- Audio 2
					Frequency  cmdID= 2488  min= 100  max= 10000  step= 100  format= %5.0fHz  div_scale= 1 
					Min =   100Hz  Max = 10000Hz  Step =   100Hz "
		::= { iqdmx32CmdEntry 2488 }


	iqdmx32Audio2ToneChannelident OBJECT-TYPE
		SYNTAX		INTEGER { disable(0), enable(1) }
		MAX-ACCESS		read-write
		STATUS			current
		DESCRIPTION
				"TYPE: - Checkbox
				 PAGE: - Channel 2- Audio 2
					Channel ident  cmdID= 5031 "
		::= { iqdmx32CmdEntry 5031 }


	iqdmx32Audio2AudioMonitorSilenceLevel OBJECT-TYPE
		SYNTAX		INTEGER
		MAX-ACCESS		read-write
		STATUS			current
		DESCRIPTION
				"TYPE: - Number
				 PAGE: - Channel 2- Audio 2
					Silence Level  cmdID= 3066  min= -80  max= 0  step= 1  format= %1.0f dB  div_scale= 1 
					Min = -80 dB  Max = 0 dB  Step = 1 dB "
		::= { iqdmx32CmdEntry 3066 }


	iqdmx32Audio2AudioMonitorOverloadLevel OBJECT-TYPE
		SYNTAX		INTEGER
		MAX-ACCESS		read-write
		STATUS			current
		DESCRIPTION
				"TYPE: - Number
				 PAGE: - Channel 2- Audio 2
					Overload Level  cmdID= 3069  min= -80  max= 0  step= 1  format= %1.0f dB  div_scale= 1 
					Min = -80 dB  Max = 0 dB  Step = 1 dB "
		::= { iqdmx32CmdEntry 3069 }


	iqdmx32Audio2AudioMonitorWarningTimer OBJECT-TYPE
		SYNTAX		INTEGER
		MAX-ACCESS		read-write
		STATUS			current
		DESCRIPTION
				"TYPE: - Number
				 PAGE: - Channel 2- Audio 2
					Warning Timer  cmdID= 3070  min= 1  max= 20  step= 1  format= %1.0f sec  div_scale= 1 
					Min = 1 sec  Max = 20 sec  Step = 1 sec "
		::= { iqdmx32CmdEntry 3070 }


	iqdmx32Channel2VideoDelay2FreerunFrequency OBJECT-TYPE
		SYNTAX		INTEGER
		MAX-ACCESS		read-write
		STATUS			current
		DESCRIPTION
				"TYPE: - Number
				 PAGE: - Channel 2
					Freerun Frequency  cmdID= 5337  min= -200  max= 200  step= 1  format= %.0f  div_scale= 1 
					Min = -200  Max = 200  Step = 1 "
		::= { iqdmx32CmdEntry 5337 }


	iqdmx32Channel2VideoDelay2VideoHdelay OBJECT-TYPE
		SYNTAX		INTEGER
		MAX-ACCESS		read-write
		STATUS			current
		DESCRIPTION
				"TYPE: - Number
				 PAGE: - Channel 2
					Video H delay  cmdID= 3797  min= 0  max= 2640  step= 1  format= %.0f pixels  div_scale= 1 
					Min = 0 pixels  Max = 2640 pixels  Step = 1 pixels "
		::= { iqdmx32CmdEntry 3797 }


	iqdmx32Channel2VideoDelay2VideoVdelay OBJECT-TYPE
		SYNTAX		INTEGER
		MAX-ACCESS		read-write
		STATUS			current
		DESCRIPTION
				"TYPE: - Number
				 PAGE: - Channel 2
					Video V delay  cmdID= 3798  min= 0  max= 1125  step= 1  format= %.0f lines  div_scale= 1 
					Min = 0 lines  Max = 1125 lines  Step = 1 lines "
		::= { iqdmx32CmdEntry 3798 }


	iqdmx32Channel2VideoDelay2VideoFdelay OBJECT-TYPE
		SYNTAX		INTEGER
		MAX-ACCESS		read-write
		STATUS			current
		DESCRIPTION
				"TYPE: - Number
				 PAGE: - Channel 2
					Video F delay  cmdID= 3799  min= 0  max= 3  step= 1  format= %.0f frames  div_scale= 1 
					Min = 0 frames  Max = 3 frames  Step = 1 frames "
		::= { iqdmx32CmdEntry 3799 }


	iqdmx32CommonMemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Common
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqdmx32CmdEntry 37101 }


	iqdmx32CommonMemoriesSetMemName OBJECT-TYPE
		SYNTAX		RollCallString
		MAX-ACCESS		read-write
		STATUS			current
		DESCRIPTION
				"TYPE: - Editstring
				 PAGE: - Common
					SetMemName  cmdID= 37103  "
		::= { iqdmx32CmdEntry 37103 }


	iqdmx32CommonMemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Common
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqdmx32CmdEntry 37100 }


	iqdmx32CommonMemoriesSaveMemory OBJECT-TYPE
		SYNTAX		INTEGER { noAction(0),val-Save-Memory(1) }
		MAX-ACCESS		read-write
		STATUS			current
		DESCRIPTION
				"TYPE: - Button
				 PAGE: - Common
					Save Memory  cmdID= 37102  value= 1  "
		::= { iqdmx32CmdEntry 37102 }


	iqdmx32CommonMemoriesLastUserMemory OBJECT-TYPE
		SYNTAX		RollCallString
		MAX-ACCESS		read-only
		STATUS			current
		DESCRIPTION
				"TYPE: - Display
				 PAGE: - Common
					Last User Memory  cmdID= 37104  format=   "
		::= { iqdmx32CmdEntry 37104 }


	iqdmx32CommonMemoriesClearMemory OBJECT-TYPE
		SYNTAX		INTEGER { noAction(0),val-Clear-Memory(1) }
		MAX-ACCESS		read-write
		STATUS			current
		DESCRIPTION
				"TYPE: - Button
				 PAGE: - Common
					Clear Memory  cmdID= 37105  value= 1  "
		::= { iqdmx32CmdEntry 37105 }


	iqdmx32MemoriesMemoryNamesMemory1Name OBJECT-TYPE
		SYNTAX		RollCallString
		MAX-ACCESS		read-only
		STATUS			current
		DESCRIPTION
				"TYPE: - Display
				 PAGE: - Common
					Memory 1 Name  cmdID= 37106  format=   "
		::= { iqdmx32CmdEntry 37106 }


	iqdmx32MemoriesMemoryNamesMemory2Name OBJECT-TYPE
		SYNTAX		RollCallString
		MAX-ACCESS		read-only
		STATUS			current
		DESCRIPTION
				"TYPE: - Display
				 PAGE: - Common
					Memory 2 Name  cmdID= 37107  format=   "
		::= { iqdmx32CmdEntry 37107 }


	iqdmx32MemoriesMemoryNamesMemory3Name OBJECT-TYPE
		SYNTAX		RollCallString
		MAX-ACCESS		read-only
		STATUS			current
		DESCRIPTION
				"TYPE: - Display
				 PAGE: - Common
					Memory 3 Name  cmdID= 37108  format=   "
		::= { iqdmx32CmdEntry 37108 }


	iqdmx32MemoriesMemoryNamesMemory4Name OBJECT-TYPE
		SYNTAX		RollCallString
		MAX-ACCESS		read-only
		STATUS			current
		DESCRIPTION
				"TYPE: - Display
				 PAGE: - Common
					Memory 4 Name  cmdID= 37109  format=   "
		::= { iqdmx32CmdEntry 37109 }


	iqdmx32MemoriesMemoryNamesMemory5Name OBJECT-TYPE
		SYNTAX		RollCallString
		MAX-ACCESS		read-only
		STATUS			current
		DESCRIPTION
				"TYPE: - Display
				 PAGE: - Common
					Memory 5 Name  cmdID= 37110  format=   "
		::= { iqdmx32CmdEntry 37110 }


	iqdmx32MemoriesMemoryNamesMemory6Name OBJECT-TYPE
		SYNTAX		RollCallString
		MAX-ACCESS		read-only
		STATUS			current
		DESCRIPTION
				"TYPE: - Display
				 PAGE: - Common
					Memory 6 Name  cmdID= 37111  format=   "
		::= { iqdmx32CmdEntry 37111 }


	iqdmx32MemoriesMemoryNamesMemory7Name OBJECT-TYPE
		SYNTAX		RollCallString
		MAX-ACCESS		read-only
		STATUS			current
		DESCRIPTION
				"TYPE: - Display
				 PAGE: - Common
					Memory 7 Name  cmdID= 37112  format=   "
		::= { iqdmx32CmdEntry 37112 }


	iqdmx32MemoriesMemoryNamesMemory8Name OBJECT-TYPE
		SYNTAX		RollCallString
		MAX-ACCESS		read-only
		STATUS			current
		DESCRIPTION
				"TYPE: - Display
				 PAGE: - Common
					Memory 8 Name  cmdID= 37113  format=   "
		::= { iqdmx32CmdEntry 37113 }


	iqdmx32MemoriesMemoryNamesMemory9Name OBJECT-TYPE
		SYNTAX		RollCallString
		MAX-ACCESS		read-only
		STATUS			current
		DESCRIPTION
				"TYPE: - Display
				 PAGE: - Common
					Memory 9 Name  cmdID= 37114  format=   "
		::= { iqdmx32CmdEntry 37114 }


	iqdmx32MemoriesMemoryNamesMemory10Name OBJECT-TYPE
		SYNTAX		RollCallString
		MAX-ACCESS		read-only
		STATUS			current
		DESCRIPTION
				"TYPE: - Display
				 PAGE: - Common
					Memory 10 Name  cmdID= 37115  format=   "
		::= { iqdmx32CmdEntry 37115 }


	iqdmx32MemoriesMemoryNamesMemory11Name OBJECT-TYPE
		SYNTAX		RollCallString
		MAX-ACCESS		read-only
		STATUS			current
		DESCRIPTION
				"TYPE: - Display
				 PAGE: - Common
					Memory 11 Name  cmdID= 37116  format=   "
		::= { iqdmx32CmdEntry 37116 }


	iqdmx32MemoriesMemoryNamesMemory12Name OBJECT-TYPE
		SYNTAX		RollCallString
		MAX-ACCESS		read-only
		STATUS			current
		DESCRIPTION
				"TYPE: - Display
				 PAGE: - Common
					Memory 12 Name  cmdID= 37117  format=   "
		::= { iqdmx32CmdEntry 37117 }


	iqdmx32MemoriesMemoryNamesMemory13Name OBJECT-TYPE
		SYNTAX		RollCallString
		MAX-ACCESS		read-only
		STATUS			current
		DESCRIPTION
				"TYPE: - Display
				 PAGE: - Common
					Memory 13 Name  cmdID= 37118  format=   "
		::= { iqdmx32CmdEntry 37118 }


	iqdmx32MemoriesMemoryNamesMemory14Name OBJECT-TYPE
		SYNTAX		RollCallString
		MAX-ACCESS		read-only
		STATUS			current
		DESCRIPTION
				"TYPE: - Display
				 PAGE: - Common
					Memory 14 Name  cmdID= 37119  format=   "
		::= { iqdmx32CmdEntry 37119 }


	iqdmx32MemoriesMemoryNamesMemory15Name OBJECT-TYPE
		SYNTAX		RollCallString
		MAX-ACCESS		read-only
		STATUS			current
		DESCRIPTION
				"TYPE: - Display
				 PAGE: - Common
					Memory 15 Name  cmdID= 37120  format=   "
		::= { iqdmx32CmdEntry 37120 }


	iqdmx32MemoriesMemoryNamesMemory16Name OBJECT-TYPE
		SYNTAX		RollCallString
		MAX-ACCESS		read-only
		STATUS			current
		DESCRIPTION
				"TYPE: - Display
				 PAGE: - Common
					Memory 16 Name  cmdID= 37121  format=   "
		::= { iqdmx32CmdEntry 37121 }


	iqdmx32SetupLoggingUptime OBJECT-TYPE
		SYNTAX		INTEGER { disable(0), enable(1) }
		MAX-ACCESS		read-write
		STATUS			current
		DESCRIPTION
				"TYPE: - Checkbox
				 PAGE: - Common- Setup- Logging
					Uptime  cmdID= 4998 "
		::= { iqdmx32CmdEntry 4998 }


	iqdmx32SetupLoggingUptimeLog OBJECT-TYPE
		SYNTAX		RollCallString
		MAX-ACCESS		read-only
		STATUS			current
		DESCRIPTION
				"TYPE: - Display
				 PAGE: - Common- Setup- Logging
					Uptime Log  cmdID= 4999  format=   "
		::= { iqdmx32CmdEntry 4999 }


	iqdmx32SetupLoggingOSVersion OBJECT-TYPE
		SYNTAX		INTEGER { disable(0), enable(1) }
		MAX-ACCESS		read-write
		STATUS			current
		DESCRIPTION
				"TYPE: - Checkbox
				 PAGE: - Common- Setup- Logging
					OS Version  cmdID= 4994 "
		::= { iqdmx32CmdEntry 4994 }


	iqdmx32SetupLoggingOSVersionLog OBJECT-TYPE
		SYNTAX		RollCallString
		MAX-ACCESS		read-only
		STATUS			current
		DESCRIPTION
				"TYPE: - Display
				 PAGE: - Common- Setup- Logging
					OS Version Log  cmdID= 4995  format=   "
		::= { iqdmx32CmdEntry 4995 }


	iqdmx32SetupLoggingHardwareVersion OBJECT-TYPE
		SYNTAX		INTEGER { disable(0), enable(1) }
		MAX-ACCESS		read-write
		STATUS			current
		DESCRIPTION
				"TYPE: - Checkbox
				 PAGE: - Common- Setup- Logging
					Hardware Version  cmdID= 4996 "
		::= { iqdmx32CmdEntry 4996 }


	iqdmx32SetupLoggingHardwareVersionLog OBJECT-TYPE
		SYNTAX		RollCallString
		MAX-ACCESS		read-only
		STATUS			current
		DESCRIPTION
				"TYPE: - Display
				 PAGE: - Common- Setup- Logging
					Hardware Version Log  cmdID= 4997  format=   "
		::= { iqdmx32CmdEntry 4997 }


	iqdmx32SetupLoggingBuildNumber OBJECT-TYPE
		SYNTAX		INTEGER { disable(0), enable(1) }
		MAX-ACCESS		read-write
		STATUS			current
		DESCRIPTION
				"TYPE: - Checkbox
				 PAGE: - Common- Setup- Logging
					Build Number  cmdID= 4992 "
		::= { iqdmx32CmdEntry 4992 }


	iqdmx32SetupLoggingBuildNumberLog OBJECT-TYPE
		SYNTAX		RollCallString
		MAX-ACCESS		read-only
		STATUS			current
		DESCRIPTION
				"TYPE: - Display
				 PAGE: - Common- Setup- Logging
					Build Number Log  cmdID= 4993  format=   "
		::= { iqdmx32CmdEntry 4993 }


	iqdmx32SetupLoggingSerialNumber OBJECT-TYPE
		SYNTAX		INTEGER { disable(0), enable(1) }
		MAX-ACCESS		read-write
		STATUS			current
		DESCRIPTION
				"TYPE: - Checkbox
				 PAGE: - Common- Setup- Logging
					Serial Number  cmdID= 4990 "
		::= { iqdmx32CmdEntry 4990 }


	iqdmx32SetupLoggingSerialNumberLog OBJECT-TYPE
		SYNTAX		RollCallString
		MAX-ACCESS		read-only
		STATUS			current
		DESCRIPTION
				"TYPE: - Display
				 PAGE: - Common- Setup- Logging
					Serial Number Log  cmdID= 4991  format=   "
		::= { iqdmx32CmdEntry 4991 }


	iqdmx32SetupLoggingLicensedOptions OBJECT-TYPE
		SYNTAX		INTEGER { disable(0), enable(1) }
		MAX-ACCESS		read-write
		STATUS			current
		DESCRIPTION
				"TYPE: - Checkbox
				 PAGE: - Common- Setup- Logging
					Licensed Options  cmdID= 4988 "
		::= { iqdmx32CmdEntry 4988 }


	iqdmx32SetupLoggingLicensedOptionsLog OBJECT-TYPE
		SYNTAX		RollCallString
		MAX-ACCESS		read-only
		STATUS			current
		DESCRIPTION
				"TYPE: - Display
				 PAGE: - Common- Setup- Logging
					Licensed Options Log  cmdID= 4989  format=   "
		::= { iqdmx32CmdEntry 4989 }


	iqdmx32SetupLoggingFirmwareVersion OBJECT-TYPE
		SYNTAX		INTEGER { disable(0), enable(1) }
		MAX-ACCESS		read-write
		STATUS			current
		DESCRIPTION
				"TYPE: - Checkbox
				 PAGE: - Common- Setup- Logging
					Firmware Version  cmdID= 4986 "
		::= { iqdmx32CmdEntry 4986 }


	iqdmx32SetupLoggingFirmwareVersionLog OBJECT-TYPE
		SYNTAX		RollCallString
		MAX-ACCESS		read-only
		STATUS			current
		DESCRIPTION
				"TYPE: - Display
				 PAGE: - Common- Setup- Logging
					Firmware Version Log  cmdID= 4987  format=   "
		::= { iqdmx32CmdEntry 4987 }


	iqdmx32SetupLoggingRearid OBJECT-TYPE
		SYNTAX		INTEGER { disable(0), enable(1) }
		MAX-ACCESS		read-write
		STATUS			current
		DESCRIPTION
				"TYPE: - Checkbox
				 PAGE: - Common- Setup- Logging
					Rear id  cmdID= 4982 "
		::= { iqdmx32CmdEntry 4982 }


	iqdmx32SetupLoggingRearidLog OBJECT-TYPE
		SYNTAX		RollCallString
		MAX-ACCESS		read-only
		STATUS			current
		DESCRIPTION
				"TYPE: - Display
				 PAGE: - Common- Setup- Logging
					Rear id Log  cmdID= 4983  format=   "
		::= { iqdmx32CmdEntry 4983 }


	iqdmx32SetupLoggingRearstatus OBJECT-TYPE
		SYNTAX		INTEGER { disable(0), enable(1) }
		MAX-ACCESS		read-write
		STATUS			current
		DESCRIPTION
				"TYPE: - Checkbox
				 PAGE: - Common- Setup- Logging
					Rear status  cmdID= 4980 "
		::= { iqdmx32CmdEntry 4980 }


	iqdmx32SetupLoggingRearstatusLog OBJECT-TYPE
		SYNTAX		RollCallString
		MAX-ACCESS		read-only
		STATUS			current
		DESCRIPTION
				"TYPE: - Display
				 PAGE: - Common- Setup- Logging
					Rear status Log  cmdID= 4981  format=   "
		::= { iqdmx32CmdEntry 4981 }


	iqdmx32SetupLoggingSlotwidth OBJECT-TYPE
		SYNTAX		INTEGER { disable(0), enable(1) }
		MAX-ACCESS		read-write
		STATUS			current
		DESCRIPTION
				"TYPE: - Checkbox
				 PAGE: - Common- Setup- Logging
					Slot width  cmdID= 4978 "
		::= { iqdmx32CmdEntry 4978 }


	iqdmx32SetupLoggingSlotwidthLog OBJECT-TYPE
		SYNTAX		RollCallString
		MAX-ACCESS		read-only
		STATUS			current
		DESCRIPTION
				"TYPE: - Display
				 PAGE: - Common- Setup- Logging
					Slot width Log  cmdID= 4979  format=   "
		::= { iqdmx32CmdEntry 4979 }


	iqdmx32SetupLoggingSlotStart OBJECT-TYPE
		SYNTAX		INTEGER { disable(0), enable(1) }
		MAX-ACCESS		read-write
		STATUS			current
		DESCRIPTION
				"TYPE: - Checkbox
				 PAGE: - Common- Setup- Logging
					Slot Start  cmdID= 4976 "
		::= { iqdmx32CmdEntry 4976 }


	iqdmx32SetupLoggingSlotStartLog OBJECT-TYPE
		SYNTAX		RollCallString
		MAX-ACCESS		read-only
		STATUS			current
		DESCRIPTION
				"TYPE: - Display
				 PAGE: - Common- Setup- Logging
					Slot Start Log  cmdID= 4977  format=   "
		::= { iqdmx32CmdEntry 4977 }


	iqdmx32SetupLoggingInput1 OBJECT-TYPE
		SYNTAX		INTEGER { disable(0), enable(1) }
		MAX-ACCESS		read-write
		STATUS			current
		DESCRIPTION
				"TYPE: - Checkbox
				 PAGE: - Common- Setup- Logging
					Input 1  cmdID= 4000 "
		::= { iqdmx32CmdEntry 4000 }


	iqdmx32SetupLoggingInput1Log OBJECT-TYPE
		SYNTAX		RollCallString
		MAX-ACCESS		read-only
		STATUS			current
		DESCRIPTION
				"TYPE: - Display
				 PAGE: - Common- Setup- Logging
					Input 1 Log  cmdID= 4001  format=   "
		::= { iqdmx32CmdEntry 4001 }


	iqdmx32SetupLoggingInput1Standard OBJECT-TYPE
		SYNTAX		INTEGER { disable(0), enable(1) }
		MAX-ACCESS		read-write
		STATUS			current
		DESCRIPTION
				"TYPE: - Checkbox
				 PAGE: - Common- Setup- Logging
					Input 1 Standard  cmdID= 4004 "
		::= { iqdmx32CmdEntry 4004 }


	iqdmx32SetupLoggingInput1StandardLog OBJECT-TYPE
		SYNTAX		RollCallString
		MAX-ACCESS		read-only
		STATUS			current
		DESCRIPTION
				"TYPE: - Display
				 PAGE: - Common- Setup- Logging
					Input 1 Standard Log  cmdID= 4005  format=   "
		::= { iqdmx32CmdEntry 4005 }


	iqdmx32SetupLoggingInput1Type OBJECT-TYPE
		SYNTAX		INTEGER { disable(0), enable(1) }
		MAX-ACCESS		read-write
		STATUS			current
		DESCRIPTION
				"TYPE: - Checkbox
				 PAGE: - Common- Setup- Logging
					Input 1 Type  cmdID= 4024 "
		::= { iqdmx32CmdEntry 4024 }


	iqdmx32SetupLoggingInput1TypeLog OBJECT-TYPE
		SYNTAX		RollCallString
		MAX-ACCESS		read-only
		STATUS			current
		DESCRIPTION
				"TYPE: - Display
				 PAGE: - Common- Setup- Logging
					Input 1 Type Log  cmdID= 4025  format=   "
		::= { iqdmx32CmdEntry 4025 }


	iqdmx32SetupLoggingInput1Ident OBJECT-TYPE
		SYNTAX		INTEGER { disable(0), enable(1) }
		MAX-ACCESS		read-write
		STATUS			current
		DESCRIPTION
				"TYPE: - Checkbox
				 PAGE: - Common- Setup- Logging
					Input 1 Ident  cmdID= 4028 "
		::= { iqdmx32CmdEntry 4028 }


	iqdmx32SetupLoggingInput1IdentLog OBJECT-TYPE
		SYNTAX		RollCallString
		MAX-ACCESS		read-only
		STATUS			current
		DESCRIPTION
				"TYPE: - Display
				 PAGE: - Common- Setup- Logging
					Input 1 Ident Log  cmdID= 4029  format=   "
		::= { iqdmx32CmdEntry 4029 }


	iqdmx32SetupLoggingIn1SDIERRS OBJECT-TYPE
		SYNTAX		INTEGER { disable(0), enable(1) }
		MAX-ACCESS		read-write
		STATUS			current
		DESCRIPTION
				"TYPE: - Checkbox
				 PAGE: - Common- Setup- Logging
					In 1 SDI ERRS  cmdID= 4012 "
		::= { iqdmx32CmdEntry 4012 }


	iqdmx32SetupLoggingIn1SDIERRSLog OBJECT-TYPE
		SYNTAX		RollCallString
		MAX-ACCESS		read-only
		STATUS			current
		DESCRIPTION
				"TYPE: - Display
				 PAGE: - Common- Setup- Logging
					In 1 SDI ERRS Log  cmdID= 4013  format=   "
		::= { iqdmx32CmdEntry 4013 }


	iqdmx32SetupLoggingIn1SDIANCERRS OBJECT-TYPE
		SYNTAX		INTEGER { disable(0), enable(1) }
		MAX-ACCESS		read-write
		STATUS			current
		DESCRIPTION
				"TYPE: - Checkbox
				 PAGE: - Common- Setup- Logging
					In 1 SDI ANC ERRS  cmdID= 4020 "
		::= { iqdmx32CmdEntry 4020 }


	iqdmx32SetupLoggingIn1SDIANCERRSLog OBJECT-TYPE
		SYNTAX		RollCallString
		MAX-ACCESS		read-only
		STATUS			current
		DESCRIPTION
				"TYPE: - Display
				 PAGE: - Common- Setup- Logging
					In 1 SDI ANC ERRS Log  cmdID= 4021  format=   "
		::= { iqdmx32CmdEntry 4021 }


	iqdmx32SetupLoggingInput1Audio1 OBJECT-TYPE
		SYNTAX		INTEGER { disable(0), enable(1) }
		MAX-ACCESS		read-write
		STATUS			current
		DESCRIPTION
				"TYPE: - Checkbox
				 PAGE: - Common- Setup- Logging
					Input 1 Audio 1  cmdID= 3852 "
		::= { iqdmx32CmdEntry 3852 }


	iqdmx32SetupLoggingInput1Audio1Log OBJECT-TYPE
		SYNTAX		RollCallString
		MAX-ACCESS		read-only
		STATUS			current
		DESCRIPTION
				"TYPE: - Display
				 PAGE: - Common- Setup- Logging
					Input 1 Audio 1 Log  cmdID= 3853  format=   "
		::= { iqdmx32CmdEntry 3853 }


	iqdmx32SetupLoggingInput1Audio2 OBJECT-TYPE
		SYNTAX		INTEGER { disable(0), enable(1) }
		MAX-ACCESS		read-write
		STATUS			current
		DESCRIPTION
				"TYPE: - Checkbox
				 PAGE: - Common- Setup- Logging
					Input 1 Audio 2  cmdID= 3854 "
		::= { iqdmx32CmdEntry 3854 }


	iqdmx32SetupLoggingInput1Audio2Log OBJECT-TYPE
		SYNTAX		RollCallString
		MAX-ACCESS		read-only
		STATUS			current
		DESCRIPTION
				"TYPE: - Display
				 PAGE: - Common- Setup- Logging
					Input 1 Audio 2 Log  cmdID= 3855  format=   "
		::= { iqdmx32CmdEntry 3855 }


	iqdmx32SetupLoggingInput1Audio3 OBJECT-TYPE
		SYNTAX		INTEGER { disable(0), enable(1) }
		MAX-ACCESS		read-write
		STATUS			current
		DESCRIPTION
				"TYPE: - Checkbox
				 PAGE: - Common- Setup- Logging
					Input 1 Audio 3  cmdID= 3856 "
		::= { iqdmx32CmdEntry 3856 }


	iqdmx32SetupLoggingInput1Audio3Log OBJECT-TYPE
		SYNTAX		RollCallString
		MAX-ACCESS		read-only
		STATUS			current
		DESCRIPTION
				"TYPE: - Display
				 PAGE: - Common- Setup- Logging
					Input 1 Audio 3 Log  cmdID= 3857  format=   "
		::= { iqdmx32CmdEntry 3857 }


	iqdmx32SetupLoggingInput1Audio4 OBJECT-TYPE
		SYNTAX		INTEGER { disable(0), enable(1) }
		MAX-ACCESS		read-write
		STATUS			current
		DESCRIPTION
				"TYPE: - Checkbox
				 PAGE: - Common- Setup- Logging
					Input 1 Audio 4  cmdID= 3858 "
		::= { iqdmx32CmdEntry 3858 }


	iqdmx32SetupLoggingInput1Audio4Log OBJECT-TYPE
		SYNTAX		RollCallString
		MAX-ACCESS		read-only
		STATUS			current
		DESCRIPTION
				"TYPE: - Display
				 PAGE: - Common- Setup- Logging
					Input 1 Audio 4 Log  cmdID= 3859  format=   "
		::= { iqdmx32CmdEntry 3859 }


	iqdmx32SetupLoggingInput1Audio5 OBJECT-TYPE
		SYNTAX		INTEGER { disable(0), enable(1) }
		MAX-ACCESS		read-write
		STATUS			current
		DESCRIPTION
				"TYPE: - Checkbox
				 PAGE: - Common- Setup- Logging
					Input 1 Audio 5  cmdID= 3860 "
		::= { iqdmx32CmdEntry 3860 }


	iqdmx32SetupLoggingInput1Audio5Log OBJECT-TYPE
		SYNTAX		RollCallString
		MAX-ACCESS		read-only
		STATUS			current
		DESCRIPTION
				"TYPE: - Display
				 PAGE: - Common- Setup- Logging
					Input 1 Audio 5 Log  cmdID= 3861  format=   "
		::= { iqdmx32CmdEntry 3861 }


	iqdmx32SetupLoggingInput1Audio6 OBJECT-TYPE
		SYNTAX		INTEGER { disable(0), enable(1) }
		MAX-ACCESS		read-write
		STATUS			current
		DESCRIPTION
				"TYPE: - Checkbox
				 PAGE: - Common- Setup- Logging
					Input 1 Audio 6  cmdID= 3862 "
		::= { iqdmx32CmdEntry 3862 }


	iqdmx32SetupLoggingInput1Audio6Log OBJECT-TYPE
		SYNTAX		RollCallString
		MAX-ACCESS		read-only
		STATUS			current
		DESCRIPTION
				"TYPE: - Display
				 PAGE: - Common- Setup- Logging
					Input 1 Audio 6 Log  cmdID= 3863  format=   "
		::= { iqdmx32CmdEntry 3863 }


	iqdmx32SetupLoggingInput1Audio7 OBJECT-TYPE
		SYNTAX		INTEGER { disable(0), enable(1) }
		MAX-ACCESS		read-write
		STATUS			current
		DESCRIPTION
				"TYPE: - Checkbox
				 PAGE: - Common- Setup- Logging
					Input 1 Audio 7  cmdID= 3864 "
		::= { iqdmx32CmdEntry 3864 }


	iqdmx32SetupLoggingInput1Audio7Log OBJECT-TYPE
		SYNTAX		RollCallString
		MAX-ACCESS		read-only
		STATUS			current
		DESCRIPTION
				"TYPE: - Display
				 PAGE: - Common- Setup- Logging
					Input 1 Audio 7 Log  cmdID= 3865  format=   "
		::= { iqdmx32CmdEntry 3865 }


	iqdmx32SetupLoggingInput1Audio8 OBJECT-TYPE
		SYNTAX		INTEGER { disable(0), enable(1) }
		MAX-ACCESS		read-write
		STATUS			current
		DESCRIPTION
				"TYPE: - Checkbox
				 PAGE: - Common- Setup- Logging
					Input 1 Audio 8  cmdID= 3866 "
		::= { iqdmx32CmdEntry 3866 }


	iqdmx32SetupLoggingInput1Audio8Log OBJECT-TYPE
		SYNTAX		RollCallString
		MAX-ACCESS		read-only
		STATUS			current
		DESCRIPTION
				"TYPE: - Display
				 PAGE: - Common- Setup- Logging
					Input 1 Audio 8 Log  cmdID= 3867  format=   "
		::= { iqdmx32CmdEntry 3867 }


	iqdmx32SetupLoggingOutput1Type OBJECT-TYPE
		SYNTAX		INTEGER { disable(0), enable(1) }
		MAX-ACCESS		read-write
		STATUS			current
		DESCRIPTION
				"TYPE: - Checkbox
				 PAGE: - Common- Setup- Logging
					Output 1 Type  cmdID= 4192 "
		::= { iqdmx32CmdEntry 4192 }


	iqdmx32SetupLoggingOutput1TypeLog OBJECT-TYPE
		SYNTAX		RollCallString
		MAX-ACCESS		read-only
		STATUS			current
		DESCRIPTION
				"TYPE: - Display
				 PAGE: - Common- Setup- Logging
					Output 1 Type Log  cmdID= 4193  format=   "
		::= { iqdmx32CmdEntry 4193 }


	iqdmx32SetupLoggingOutput1State OBJECT-TYPE
		SYNTAX		INTEGER { disable(0), enable(1) }
		MAX-ACCESS		read-write
		STATUS			current
		DESCRIPTION
				"TYPE: - Checkbox
				 PAGE: - Common- Setup- Logging
					Output 1 State  cmdID= 4196 "
		::= { iqdmx32CmdEntry 4196 }


	iqdmx32SetupLoggingOutput1StateLog OBJECT-TYPE
		SYNTAX		RollCallString
		MAX-ACCESS		read-only
		STATUS			current
		DESCRIPTION
				"TYPE: - Display
				 PAGE: - Common- Setup- Logging
					Output 1 State Log  cmdID= 4197  format=   "
		::= { iqdmx32CmdEntry 4197 }


	iqdmx32SetupLoggingOutput1Std OBJECT-TYPE
		SYNTAX		INTEGER { disable(0), enable(1) }
		MAX-ACCESS		read-write
		STATUS			current
		DESCRIPTION
				"TYPE: - Checkbox
				 PAGE: - Common- Setup- Logging
					Output 1 Std  cmdID= 4200 "
		::= { iqdmx32CmdEntry 4200 }


	iqdmx32SetupLoggingOutput1StdLog OBJECT-TYPE
		SYNTAX		RollCallString
		MAX-ACCESS		read-only
		STATUS			current
		DESCRIPTION
				"TYPE: - Display
				 PAGE: - Common- Setup- Logging
					Output 1 Std Log  cmdID= 4201  format=   "
		::= { iqdmx32CmdEntry 4201 }


	iqdmx32SetupLoggingOutput1Caption OBJECT-TYPE
		SYNTAX		INTEGER { disable(0), enable(1) }
		MAX-ACCESS		read-write
		STATUS			current
		DESCRIPTION
				"TYPE: - Checkbox
				 PAGE: - Common- Setup- Logging
					Output 1 Caption  cmdID= 4204 "
		::= { iqdmx32CmdEntry 4204 }


	iqdmx32SetupLoggingOutput1CaptionLog OBJECT-TYPE
		SYNTAX		RollCallString
		MAX-ACCESS		read-only
		STATUS			current
		DESCRIPTION
				"TYPE: - Display
				 PAGE: - Common- Setup- Logging
					Output 1 Caption Log  cmdID= 4205  format=   "
		::= { iqdmx32CmdEntry 4205 }


	iqdmx32SetupLoggingInput2 OBJECT-TYPE
		SYNTAX		INTEGER { disable(0), enable(1) }
		MAX-ACCESS		read-write
		STATUS			current
		DESCRIPTION
				"TYPE: - Checkbox
				 PAGE: - Common- Setup- Logging
					Input 2  cmdID= 4002 "
		::= { iqdmx32CmdEntry 4002 }


	iqdmx32SetupLoggingInput2Log OBJECT-TYPE
		SYNTAX		RollCallString
		MAX-ACCESS		read-only
		STATUS			current
		DESCRIPTION
				"TYPE: - Display
				 PAGE: - Common- Setup- Logging
					Input 2 Log  cmdID= 4003  format=   "
		::= { iqdmx32CmdEntry 4003 }


	iqdmx32SetupLoggingInput2Standard OBJECT-TYPE
		SYNTAX		INTEGER { disable(0), enable(1) }
		MAX-ACCESS		read-write
		STATUS			current
		DESCRIPTION
				"TYPE: - Checkbox
				 PAGE: - Common- Setup- Logging
					Input 2 Standard  cmdID= 4006 "
		::= { iqdmx32CmdEntry 4006 }


	iqdmx32SetupLoggingInput2StandardLog OBJECT-TYPE
		SYNTAX		RollCallString
		MAX-ACCESS		read-only
		STATUS			current
		DESCRIPTION
				"TYPE: - Display
				 PAGE: - Common- Setup- Logging
					Input 2 Standard Log  cmdID= 4007  format=   "
		::= { iqdmx32CmdEntry 4007 }


	iqdmx32SetupLoggingInput2Type OBJECT-TYPE
		SYNTAX		INTEGER { disable(0), enable(1) }
		MAX-ACCESS		read-write
		STATUS			current
		DESCRIPTION
				"TYPE: - Checkbox
				 PAGE: - Common- Setup- Logging
					Input 2 Type  cmdID= 4026 "
		::= { iqdmx32CmdEntry 4026 }


	iqdmx32SetupLoggingInput2TypeLog OBJECT-TYPE
		SYNTAX		RollCallString
		MAX-ACCESS		read-only
		STATUS			current
		DESCRIPTION
				"TYPE: - Display
				 PAGE: - Common- Setup- Logging
					Input 2 Type Log  cmdID= 4027  format=   "
		::= { iqdmx32CmdEntry 4027 }


	iqdmx32SetupLoggingInput2Ident OBJECT-TYPE
		SYNTAX		INTEGER { disable(0), enable(1) }
		MAX-ACCESS		read-write
		STATUS			current
		DESCRIPTION
				"TYPE: - Checkbox
				 PAGE: - Common- Setup- Logging
					Input 2 Ident  cmdID= 4030 "
		::= { iqdmx32CmdEntry 4030 }


	iqdmx32SetupLoggingInput2IdentLog OBJECT-TYPE
		SYNTAX		RollCallString
		MAX-ACCESS		read-only
		STATUS			current
		DESCRIPTION
				"TYPE: - Display
				 PAGE: - Common- Setup- Logging
					Input 2 Ident Log  cmdID= 4031  format=   "
		::= { iqdmx32CmdEntry 4031 }


	iqdmx32SetupLoggingIn2SDIERRS OBJECT-TYPE
		SYNTAX		INTEGER { disable(0), enable(1) }
		MAX-ACCESS		read-write
		STATUS			current
		DESCRIPTION
				"TYPE: - Checkbox
				 PAGE: - Common- Setup- Logging
					In 2 SDI ERRS  cmdID= 4014 "
		::= { iqdmx32CmdEntry 4014 }


	iqdmx32SetupLoggingIn2SDIERRSLog OBJECT-TYPE
		SYNTAX		RollCallString
		MAX-ACCESS		read-only
		STATUS			current
		DESCRIPTION
				"TYPE: - Display
				 PAGE: - Common- Setup- Logging
					In 2 SDI ERRS Log  cmdID= 4015  format=   "
		::= { iqdmx32CmdEntry 4015 }


	iqdmx32SetupLoggingIn2SDIANCERRS OBJECT-TYPE
		SYNTAX		INTEGER { disable(0), enable(1) }
		MAX-ACCESS		read-write
		STATUS			current
		DESCRIPTION
				"TYPE: - Checkbox
				 PAGE: - Common- Setup- Logging
					In 2 SDI ANC ERRS  cmdID= 4022 "
		::= { iqdmx32CmdEntry 4022 }


	iqdmx32SetupLoggingIn2SDIANCERRSLog OBJECT-TYPE
		SYNTAX		RollCallString
		MAX-ACCESS		read-only
		STATUS			current
		DESCRIPTION
				"TYPE: - Display
				 PAGE: - Common- Setup- Logging
					In 2 SDI ANC ERRS Log  cmdID= 4023  format=   "
		::= { iqdmx32CmdEntry 4023 }


	iqdmx32SetupLoggingInput2Audio1 OBJECT-TYPE
		SYNTAX		INTEGER { disable(0), enable(1) }
		MAX-ACCESS		read-write
		STATUS			current
		DESCRIPTION
				"TYPE: - Checkbox
				 PAGE: - Common- Setup- Logging
					Input 2 Audio 1  cmdID= 3868 "
		::= { iqdmx32CmdEntry 3868 }


	iqdmx32SetupLoggingInput2Audio1Log OBJECT-TYPE
		SYNTAX		RollCallString
		MAX-ACCESS		read-only
		STATUS			current
		DESCRIPTION
				"TYPE: - Display
				 PAGE: - Common- Setup- Logging
					Input 2 Audio 1 Log  cmdID= 3869  format=   "
		::= { iqdmx32CmdEntry 3869 }


	iqdmx32SetupLoggingInput2Audio2 OBJECT-TYPE
		SYNTAX		INTEGER { disable(0), enable(1) }
		MAX-ACCESS		read-write
		STATUS			current
		DESCRIPTION
				"TYPE: - Checkbox
				 PAGE: - Common- Setup- Logging
					Input 2 Audio 2  cmdID= 3870 "
		::= { iqdmx32CmdEntry 3870 }


	iqdmx32SetupLoggingInput2Audio2Log OBJECT-TYPE
		SYNTAX		RollCallString
		MAX-ACCESS		read-only
		STATUS			current
		DESCRIPTION
				"TYPE: - Display
				 PAGE: - Common- Setup- Logging
					Input 2 Audio 2 Log  cmdID= 3871  format=   "
		::= { iqdmx32CmdEntry 3871 }


	iqdmx32SetupLoggingInput2Audio3 OBJECT-TYPE
		SYNTAX		INTEGER { disable(0), enable(1) }
		MAX-ACCESS		read-write
		STATUS			current
		DESCRIPTION
				"TYPE: - Checkbox
				 PAGE: - Common- Setup- Logging
					Input 2 Audio 3  cmdID= 3872 "
		::= { iqdmx32CmdEntry 3872 }


	iqdmx32SetupLoggingInput2Audio3Log OBJECT-TYPE
		SYNTAX		RollCallString
		MAX-ACCESS		read-only
		STATUS			current
		DESCRIPTION
				"TYPE: - Display
				 PAGE: - Common- Setup- Logging
					Input 2 Audio 3 Log  cmdID= 3873  format=   "
		::= { iqdmx32CmdEntry 3873 }


	iqdmx32SetupLoggingInput2Audio4 OBJECT-TYPE
		SYNTAX		INTEGER { disable(0), enable(1) }
		MAX-ACCESS		read-write
		STATUS			current
		DESCRIPTION
				"TYPE: - Checkbox
				 PAGE: - Common- Setup- Logging
					Input 2 Audio 4  cmdID= 3874 "
		::= { iqdmx32CmdEntry 3874 }


	iqdmx32SetupLoggingInput2Audio4Log OBJECT-TYPE
		SYNTAX		RollCallString
		MAX-ACCESS		read-only
		STATUS			current
		DESCRIPTION
				"TYPE: - Display
				 PAGE: - Common- Setup- Logging
					Input 2 Audio 4 Log  cmdID= 3875  format=   "
		::= { iqdmx32CmdEntry 3875 }


	iqdmx32SetupLoggingInput2Audio5 OBJECT-TYPE
		SYNTAX		INTEGER { disable(0), enable(1) }
		MAX-ACCESS		read-write
		STATUS			current
		DESCRIPTION
				"TYPE: - Checkbox
				 PAGE: - Common- Setup- Logging
					Input 2 Audio 5  cmdID= 3876 "
		::= { iqdmx32CmdEntry 3876 }


	iqdmx32SetupLoggingInput2Audio5Log OBJECT-TYPE
		SYNTAX		RollCallString
		MAX-ACCESS		read-only
		STATUS			current
		DESCRIPTION
				"TYPE: - Display
				 PAGE: - Common- Setup- Logging
					Input 2 Audio 5 Log  cmdID= 3877  format=   "
		::= { iqdmx32CmdEntry 3877 }


	iqdmx32SetupLoggingInput2Audio6 OBJECT-TYPE
		SYNTAX		INTEGER { disable(0), enable(1) }
		MAX-ACCESS		read-write
		STATUS			current
		DESCRIPTION
				"TYPE: - Checkbox
				 PAGE: - Common- Setup- Logging
					Input 2 Audio 6  cmdID= 3878 "
		::= { iqdmx32CmdEntry 3878 }


	iqdmx32SetupLoggingInput2Audio6Log OBJECT-TYPE
		SYNTAX		RollCallString
		MAX-ACCESS		read-only
		STATUS			current
		DESCRIPTION
				"TYPE: - Display
				 PAGE: - Common- Setup- Logging
					Input 2 Audio 6 Log  cmdID= 3879  format=   "
		::= { iqdmx32CmdEntry 3879 }


	iqdmx32SetupLoggingInput2Audio7 OBJECT-TYPE
		SYNTAX		INTEGER { disable(0), enable(1) }
		MAX-ACCESS		read-write
		STATUS			current
		DESCRIPTION
				"TYPE: - Checkbox
				 PAGE: - Common- Setup- Logging
					Input 2 Audio 7  cmdID= 3880 "
		::= { iqdmx32CmdEntry 3880 }


	iqdmx32SetupLoggingInput2Audio7Log OBJECT-TYPE
		SYNTAX		RollCallString
		MAX-ACCESS		read-only
		STATUS			current
		DESCRIPTION
				"TYPE: - Display
				 PAGE: - Common- Setup- Logging
					Input 2 Audio 7 Log  cmdID= 3881  format=   "
		::= { iqdmx32CmdEntry 3881 }


	iqdmx32SetupLoggingInput2Audio8 OBJECT-TYPE
		SYNTAX		INTEGER { disable(0), enable(1) }
		MAX-ACCESS		read-write
		STATUS			current
		DESCRIPTION
				"TYPE: - Checkbox
				 PAGE: - Common- Setup- Logging
					Input 2 Audio 8  cmdID= 3882 "
		::= { iqdmx32CmdEntry 3882 }


	iqdmx32SetupLoggingInput2Audio8Log OBJECT-TYPE
		SYNTAX		RollCallString
		MAX-ACCESS		read-only
		STATUS			current
		DESCRIPTION
				"TYPE: - Display
				 PAGE: - Common- Setup- Logging
					Input 2 Audio 8 Log  cmdID= 3883  format=   "
		::= { iqdmx32CmdEntry 3883 }


	iqdmx32SetupLoggingOutput2Type OBJECT-TYPE
		SYNTAX		INTEGER { disable(0), enable(1) }
		MAX-ACCESS		read-write
		STATUS			current
		DESCRIPTION
				"TYPE: - Checkbox
				 PAGE: - Common- Setup- Logging
					Output 2 Type  cmdID= 4194 "
		::= { iqdmx32CmdEntry 4194 }


	iqdmx32SetupLoggingOutput2TypeLog OBJECT-TYPE
		SYNTAX		RollCallString
		MAX-ACCESS		read-only
		STATUS			current
		DESCRIPTION
				"TYPE: - Display
				 PAGE: - Common- Setup- Logging
					Output 2 Type Log  cmdID= 4195  format=   "
		::= { iqdmx32CmdEntry 4195 }


	iqdmx32SetupLoggingOutput2State OBJECT-TYPE
		SYNTAX		INTEGER { disable(0), enable(1) }
		MAX-ACCESS		read-write
		STATUS			current
		DESCRIPTION
				"TYPE: - Checkbox
				 PAGE: - Common- Setup- Logging
					Output 2 State  cmdID= 4198 "
		::= { iqdmx32CmdEntry 4198 }


	iqdmx32SetupLoggingOutput2StateLog OBJECT-TYPE
		SYNTAX		RollCallString
		MAX-ACCESS		read-only
		STATUS			current
		DESCRIPTION
				"TYPE: - Display
				 PAGE: - Common- Setup- Logging
					Output 2 State Log  cmdID= 4199  format=   "
		::= { iqdmx32CmdEntry 4199 }


	iqdmx32SetupLoggingOutput2Std OBJECT-TYPE
		SYNTAX		INTEGER { disable(0), enable(1) }
		MAX-ACCESS		read-write
		STATUS			current
		DESCRIPTION
				"TYPE: - Checkbox
				 PAGE: - Common- Setup- Logging
					Output 2 Std  cmdID= 4202 "
		::= { iqdmx32CmdEntry 4202 }


	iqdmx32SetupLoggingOutput2StdLog OBJECT-TYPE
		SYNTAX		RollCallString
		MAX-ACCESS		read-only
		STATUS			current
		DESCRIPTION
				"TYPE: - Display
				 PAGE: - Common- Setup- Logging
					Output 2 Std Log  cmdID= 4203  format=   "
		::= { iqdmx32CmdEntry 4203 }


	iqdmx32SetupLoggingOutput2Caption OBJECT-TYPE
		SYNTAX		INTEGER { disable(0), enable(1) }
		MAX-ACCESS		read-write
		STATUS			current
		DESCRIPTION
				"TYPE: - Checkbox
				 PAGE: - Common- Setup- Logging
					Output 2 Caption  cmdID= 4206 "
		::= { iqdmx32CmdEntry 4206 }


	iqdmx32SetupLoggingOutput2CaptionLog OBJECT-TYPE
		SYNTAX		RollCallString
		MAX-ACCESS		read-only
		STATUS			current
		DESCRIPTION
				"TYPE: - Display
				 PAGE: - Common- Setup- Logging
					Output 2 Caption Log  cmdID= 4207  format=   "
		::= { iqdmx32CmdEntry 4207 }


	iqdmx32SetupLoggingop1embed11 OBJECT-TYPE
		SYNTAX		INTEGER { disable(0), enable(1) }
		MAX-ACCESS		read-write
		STATUS			current
		DESCRIPTION
				"TYPE: - Checkbox
				 PAGE: - Common- Setup- Logging
					op_1_embed_1_1  cmdID= 4064 "
		::= { iqdmx32CmdEntry 4064 }


	iqdmx32SetupLoggingop1embed11Log OBJECT-TYPE
		SYNTAX		RollCallString
		MAX-ACCESS		read-only
		STATUS			current
		DESCRIPTION
				"TYPE: - Display
				 PAGE: - Common- Setup- Logging
					op_1_embed_1_1 Log  cmdID= 4065  format=   "
		::= { iqdmx32CmdEntry 4065 }


	iqdmx32SetupLoggingop1embed12 OBJECT-TYPE
		SYNTAX		INTEGER { disable(0), enable(1) }
		MAX-ACCESS		read-write
		STATUS			current
		DESCRIPTION
				"TYPE: - Checkbox
				 PAGE: - Common- Setup- Logging
					op_1_embed_1_2  cmdID= 4068 "
		::= { iqdmx32CmdEntry 4068 }


	iqdmx32SetupLoggingop1embed12Log OBJECT-TYPE
		SYNTAX		RollCallString
		MAX-ACCESS		read-only
		STATUS			current
		DESCRIPTION
				"TYPE: - Display
				 PAGE: - Common- Setup- Logging
					op_1_embed_1_2 Log  cmdID= 4069  format=   "
		::= { iqdmx32CmdEntry 4069 }


	iqdmx32SetupLoggingop1embed21 OBJECT-TYPE
		SYNTAX		INTEGER { disable(0), enable(1) }
		MAX-ACCESS		read-write
		STATUS			current
		DESCRIPTION
				"TYPE: - Checkbox
				 PAGE: - Common- Setup- Logging
					op_1_embed_2_1  cmdID= 4072 "
		::= { iqdmx32CmdEntry 4072 }


	iqdmx32SetupLoggingop1embed21Log OBJECT-TYPE
		SYNTAX		RollCallString
		MAX-ACCESS		read-only
		STATUS			current
		DESCRIPTION
				"TYPE: - Display
				 PAGE: - Common- Setup- Logging
					op_1_embed_2_1 Log  cmdID= 4073  format=   "
		::= { iqdmx32CmdEntry 4073 }


	iqdmx32SetupLoggingop1embed22 OBJECT-TYPE
		SYNTAX		INTEGER { disable(0), enable(1) }
		MAX-ACCESS		read-write
		STATUS			current
		DESCRIPTION
				"TYPE: - Checkbox
				 PAGE: - Common- Setup- Logging
					op_1_embed_2_2  cmdID= 4076 "
		::= { iqdmx32CmdEntry 4076 }


	iqdmx32SetupLoggingop1embed22Log OBJECT-TYPE
		SYNTAX		RollCallString
		MAX-ACCESS		read-only
		STATUS			current
		DESCRIPTION
				"TYPE: - Display
				 PAGE: - Common- Setup- Logging
					op_1_embed_2_2 Log  cmdID= 4077  format=   "
		::= { iqdmx32CmdEntry 4077 }


	iqdmx32SetupLoggingop1embed31 OBJECT-TYPE
		SYNTAX		INTEGER { disable(0), enable(1) }
		MAX-ACCESS		read-write
		STATUS			current
		DESCRIPTION
				"TYPE: - Checkbox
				 PAGE: - Common- Setup- Logging
					op_1_embed_3_1  cmdID= 4080 "
		::= { iqdmx32CmdEntry 4080 }


	iqdmx32SetupLoggingop1embed31Log OBJECT-TYPE
		SYNTAX		RollCallString
		MAX-ACCESS		read-only
		STATUS			current
		DESCRIPTION
				"TYPE: - Display
				 PAGE: - Common- Setup- Logging
					op_1_embed_3_1 Log  cmdID= 4081  format=   "
		::= { iqdmx32CmdEntry 4081 }


	iqdmx32SetupLoggingop1embed32 OBJECT-TYPE
		SYNTAX		INTEGER { disable(0), enable(1) }
		MAX-ACCESS		read-write
		STATUS			current
		DESCRIPTION
				"TYPE: - Checkbox
				 PAGE: - Common- Setup- Logging
					op_1_embed_3_2  cmdID= 4084 "
		::= { iqdmx32CmdEntry 4084 }


	iqdmx32SetupLoggingop1embed32Log OBJECT-TYPE
		SYNTAX		RollCallString
		MAX-ACCESS		read-only
		STATUS			current
		DESCRIPTION
				"TYPE: - Display
				 PAGE: - Common- Setup- Logging
					op_1_embed_3_2 Log  cmdID= 4085  format=   "
		::= { iqdmx32CmdEntry 4085 }


	iqdmx32SetupLoggingop1embed41 OBJECT-TYPE
		SYNTAX		INTEGER { disable(0), enable(1) }
		MAX-ACCESS		read-write
		STATUS			current
		DESCRIPTION
				"TYPE: - Checkbox
				 PAGE: - Common- Setup- Logging
					op_1_embed_4_1  cmdID= 4088 "
		::= { iqdmx32CmdEntry 4088 }


	iqdmx32SetupLoggingop1embed41Log OBJECT-TYPE
		SYNTAX		RollCallString
		MAX-ACCESS		read-only
		STATUS			current
		DESCRIPTION
				"TYPE: - Display
				 PAGE: - Common- Setup- Logging
					op_1_embed_4_1 Log  cmdID= 4089  format=   "
		::= { iqdmx32CmdEntry 4089 }


	iqdmx32SetupLoggingop1embed42 OBJECT-TYPE
		SYNTAX		INTEGER { disable(0), enable(1) }
		MAX-ACCESS		read-write
		STATUS			current
		DESCRIPTION
				"TYPE: - Checkbox
				 PAGE: - Common- Setup- Logging
					op_1_embed_4_2  cmdID= 4092 "
		::= { iqdmx32CmdEntry 4092 }


	iqdmx32SetupLoggingop1embed42Log OBJECT-TYPE
		SYNTAX		RollCallString
		MAX-ACCESS		read-only
		STATUS			current
		DESCRIPTION
				"TYPE: - Display
				 PAGE: - Common- Setup- Logging
					op_1_embed_4_2 Log  cmdID= 4093  format=   "
		::= { iqdmx32CmdEntry 4093 }


	iqdmx32SetupLoggingop1embed51 OBJECT-TYPE
		SYNTAX		INTEGER { disable(0), enable(1) }
		MAX-ACCESS		read-write
		STATUS			current
		DESCRIPTION
				"TYPE: - Checkbox
				 PAGE: - Common- Setup- Logging
					op_1_embed_5_1  cmdID= 4096 "
		::= { iqdmx32CmdEntry 4096 }


	iqdmx32SetupLoggingop1embed51Log OBJECT-TYPE
		SYNTAX		RollCallString
		MAX-ACCESS		read-only
		STATUS			current
		DESCRIPTION
				"TYPE: - Display
				 PAGE: - Common- Setup- Logging
					op_1_embed_5_1 Log  cmdID= 4097  format=   "
		::= { iqdmx32CmdEntry 4097 }


	iqdmx32SetupLoggingop1embed52 OBJECT-TYPE
		SYNTAX		INTEGER { disable(0), enable(1) }
		MAX-ACCESS		read-write
		STATUS			current
		DESCRIPTION
				"TYPE: - Checkbox
				 PAGE: - Common- Setup- Logging
					op_1_embed_5_2  cmdID= 4100 "
		::= { iqdmx32CmdEntry 4100 }


	iqdmx32SetupLoggingop1embed52Log OBJECT-TYPE
		SYNTAX		RollCallString
		MAX-ACCESS		read-only
		STATUS			current
		DESCRIPTION
				"TYPE: - Display
				 PAGE: - Common- Setup- Logging
					op_1_embed_5_2 Log  cmdID= 4101  format=   "
		::= { iqdmx32CmdEntry 4101 }


	iqdmx32SetupLoggingop1embed61 OBJECT-TYPE
		SYNTAX		INTEGER { disable(0), enable(1) }
		MAX-ACCESS		read-write
		STATUS			current
		DESCRIPTION
				"TYPE: - Checkbox
				 PAGE: - Common- Setup- Logging
					op_1_embed_6_1  cmdID= 4104 "
		::= { iqdmx32CmdEntry 4104 }


	iqdmx32SetupLoggingop1embed61Log OBJECT-TYPE
		SYNTAX		RollCallString
		MAX-ACCESS		read-only
		STATUS			current
		DESCRIPTION
				"TYPE: - Display
				 PAGE: - Common- Setup- Logging
					op_1_embed_6_1 Log  cmdID= 4105  format=   "
		::= { iqdmx32CmdEntry 4105 }


	iqdmx32SetupLoggingop1embed62 OBJECT-TYPE
		SYNTAX		INTEGER { disable(0), enable(1) }
		MAX-ACCESS		read-write
		STATUS			current
		DESCRIPTION
				"TYPE: - Checkbox
				 PAGE: - Common- Setup- Logging
					op_1_embed_6_2  cmdID= 4108 "
		::= { iqdmx32CmdEntry 4108 }


	iqdmx32SetupLoggingop1embed62Log OBJECT-TYPE
		SYNTAX		RollCallString
		MAX-ACCESS		read-only
		STATUS			current
		DESCRIPTION
				"TYPE: - Display
				 PAGE: - Common- Setup- Logging
					op_1_embed_6_2 Log  cmdID= 4109  format=   "
		::= { iqdmx32CmdEntry 4109 }


	iqdmx32SetupLoggingop1embed71 OBJECT-TYPE
		SYNTAX		INTEGER { disable(0), enable(1) }
		MAX-ACCESS		read-write
		STATUS			current
		DESCRIPTION
				"TYPE: - Checkbox
				 PAGE: - Common- Setup- Logging
					op_1_embed_7_1  cmdID= 4112 "
		::= { iqdmx32CmdEntry 4112 }


	iqdmx32SetupLoggingop1embed71Log OBJECT-TYPE
		SYNTAX		RollCallString
		MAX-ACCESS		read-only
		STATUS			current
		DESCRIPTION
				"TYPE: - Display
				 PAGE: - Common- Setup- Logging
					op_1_embed_7_1 Log  cmdID= 4113  format=   "
		::= { iqdmx32CmdEntry 4113 }


	iqdmx32SetupLoggingop1embed72 OBJECT-TYPE
		SYNTAX		INTEGER { disable(0), enable(1) }
		MAX-ACCESS		read-write
		STATUS			current
		DESCRIPTION
				"TYPE: - Checkbox
				 PAGE: - Common- Setup- Logging
					op_1_embed_7_2  cmdID= 4116 "
		::= { iqdmx32CmdEntry 4116 }


	iqdmx32SetupLoggingop1embed72Log OBJECT-TYPE
		SYNTAX		RollCallString
		MAX-ACCESS		read-only
		STATUS			current
		DESCRIPTION
				"TYPE: - Display
				 PAGE: - Common- Setup- Logging
					op_1_embed_7_2 Log  cmdID= 4117  format=   "
		::= { iqdmx32CmdEntry 4117 }


	iqdmx32SetupLoggingop1embed81 OBJECT-TYPE
		SYNTAX		INTEGER { disable(0), enable(1) }
		MAX-ACCESS		read-write
		STATUS			current
		DESCRIPTION
				"TYPE: - Checkbox
				 PAGE: - Common- Setup- Logging
					op_1_embed_8_1  cmdID= 4120 "
		::= { iqdmx32CmdEntry 4120 }


	iqdmx32SetupLoggingop1embed81Log OBJECT-TYPE
		SYNTAX		RollCallString
		MAX-ACCESS		read-only
		STATUS			current
		DESCRIPTION
				"TYPE: - Display
				 PAGE: - Common- Setup- Logging
					op_1_embed_8_1 Log  cmdID= 4121  format=   "
		::= { iqdmx32CmdEntry 4121 }


	iqdmx32SetupLoggingop1embed82 OBJECT-TYPE
		SYNTAX		INTEGER { disable(0), enable(1) }
		MAX-ACCESS		read-write
		STATUS			current
		DESCRIPTION
				"TYPE: - Checkbox
				 PAGE: - Common- Setup- Logging
					op_1_embed_8_2  cmdID= 4124 "
		::= { iqdmx32CmdEntry 4124 }


	iqdmx32SetupLoggingop1embed82Log OBJECT-TYPE
		SYNTAX		RollCallString
		MAX-ACCESS		read-only
		STATUS			current
		DESCRIPTION
				"TYPE: - Display
				 PAGE: - Common- Setup- Logging
					op_1_embed_8_2 Log  cmdID= 4125  format=   "
		::= { iqdmx32CmdEntry 4125 }


	iqdmx32SetupLoggingop1aes11 OBJECT-TYPE
		SYNTAX		INTEGER { disable(0), enable(1) }
		MAX-ACCESS		read-write
		STATUS			current
		DESCRIPTION
				"TYPE: - Checkbox
				 PAGE: - Common- Setup- Logging
					op_1_aes_1_1  cmdID= 4128 "
		::= { iqdmx32CmdEntry 4128 }


	iqdmx32SetupLoggingop1aes11Log OBJECT-TYPE
		SYNTAX		RollCallString
		MAX-ACCESS		read-only
		STATUS			current
		DESCRIPTION
				"TYPE: - Display
				 PAGE: - Common- Setup- Logging
					op_1_aes_1_1 Log  cmdID= 4129  format=   "
		::= { iqdmx32CmdEntry 4129 }


	iqdmx32SetupLoggingop1aes12 OBJECT-TYPE
		SYNTAX		INTEGER { disable(0), enable(1) }
		MAX-ACCESS		read-write
		STATUS			current
		DESCRIPTION
				"TYPE: - Checkbox
				 PAGE: - Common- Setup- Logging
					op_1_aes_1_2  cmdID= 4132 "
		::= { iqdmx32CmdEntry 4132 }


	iqdmx32SetupLoggingop1aes12Log OBJECT-TYPE
		SYNTAX		RollCallString
		MAX-ACCESS		read-only
		STATUS			current
		DESCRIPTION
				"TYPE: - Display
				 PAGE: - Common- Setup- Logging
					op_1_aes_1_2 Log  cmdID= 4133  format=   "
		::= { iqdmx32CmdEntry 4133 }


	iqdmx32SetupLoggingop1aes21 OBJECT-TYPE
		SYNTAX		INTEGER { disable(0), enable(1) }
		MAX-ACCESS		read-write
		STATUS			current
		DESCRIPTION
				"TYPE: - Checkbox
				 PAGE: - Common- Setup- Logging
					op_1_aes_2_1  cmdID= 4136 "
		::= { iqdmx32CmdEntry 4136 }


	iqdmx32SetupLoggingop1aes21Log OBJECT-TYPE
		SYNTAX		RollCallString
		MAX-ACCESS		read-only
		STATUS			current
		DESCRIPTION
				"TYPE: - Display
				 PAGE: - Common- Setup- Logging
					op_1_aes_2_1 Log  cmdID= 4137  format=   "
		::= { iqdmx32CmdEntry 4137 }


	iqdmx32SetupLoggingop1aes22 OBJECT-TYPE
		SYNTAX		INTEGER { disable(0), enable(1) }
		MAX-ACCESS		read-write
		STATUS			current
		DESCRIPTION
				"TYPE: - Checkbox
				 PAGE: - Common- Setup- Logging
					op_1_aes_2_2  cmdID= 4140 "
		::= { iqdmx32CmdEntry 4140 }


	iqdmx32SetupLoggingop1aes22Log OBJECT-TYPE
		SYNTAX		RollCallString
		MAX-ACCESS		read-only
		STATUS			current
		DESCRIPTION
				"TYPE: - Display
				 PAGE: - Common- Setup- Logging
					op_1_aes_2_2 Log  cmdID= 4141  format=   "
		::= { iqdmx32CmdEntry 4141 }


	iqdmx32SetupLoggingop1aes31 OBJECT-TYPE
		SYNTAX		INTEGER { disable(0), enable(1) }
		MAX-ACCESS		read-write
		STATUS			current
		DESCRIPTION
				"TYPE: - Checkbox
				 PAGE: - Common- Setup- Logging
					op_1_aes_3_1  cmdID= 4144 "
		::= { iqdmx32CmdEntry 4144 }


	iqdmx32SetupLoggingop1aes31Log OBJECT-TYPE
		SYNTAX		RollCallString
		MAX-ACCESS		read-only
		STATUS			current
		DESCRIPTION
				"TYPE: - Display
				 PAGE: - Common- Setup- Logging
					op_1_aes_3_1 Log  cmdID= 4145  format=   "
		::= { iqdmx32CmdEntry 4145 }


	iqdmx32SetupLoggingop1aes32 OBJECT-TYPE
		SYNTAX		INTEGER { disable(0), enable(1) }
		MAX-ACCESS		read-write
		STATUS			current
		DESCRIPTION
				"TYPE: - Checkbox
				 PAGE: - Common- Setup- Logging
					op_1_aes_3_2  cmdID= 4148 "
		::= { iqdmx32CmdEntry 4148 }


	iqdmx32SetupLoggingop1aes32Log OBJECT-TYPE
		SYNTAX		RollCallString
		MAX-ACCESS		read-only
		STATUS			current
		DESCRIPTION
				"TYPE: - Display
				 PAGE: - Common- Setup- Logging
					op_1_aes_3_2 Log  cmdID= 4149  format=   "
		::= { iqdmx32CmdEntry 4149 }


	iqdmx32SetupLoggingop1aes41 OBJECT-TYPE
		SYNTAX		INTEGER { disable(0), enable(1) }
		MAX-ACCESS		read-write
		STATUS			current
		DESCRIPTION
				"TYPE: - Checkbox
				 PAGE: - Common- Setup- Logging
					op_1_aes_4_1  cmdID= 4152 "
		::= { iqdmx32CmdEntry 4152 }


	iqdmx32SetupLoggingop1aes41Log OBJECT-TYPE
		SYNTAX		RollCallString
		MAX-ACCESS		read-only
		STATUS			current
		DESCRIPTION
				"TYPE: - Display
				 PAGE: - Common- Setup- Logging
					op_1_aes_4_1 Log  cmdID= 4153  format=   "
		::= { iqdmx32CmdEntry 4153 }


	iqdmx32SetupLoggingop1aes42 OBJECT-TYPE
		SYNTAX		INTEGER { disable(0), enable(1) }
		MAX-ACCESS		read-write
		STATUS			current
		DESCRIPTION
				"TYPE: - Checkbox
				 PAGE: - Common- Setup- Logging
					op_1_aes_4_2  cmdID= 4156 "
		::= { iqdmx32CmdEntry 4156 }


	iqdmx32SetupLoggingop1aes42Log OBJECT-TYPE
		SYNTAX		RollCallString
		MAX-ACCESS		read-only
		STATUS			current
		DESCRIPTION
				"TYPE: - Display
				 PAGE: - Common- Setup- Logging
					op_1_aes_4_2 Log  cmdID= 4157  format=   "
		::= { iqdmx32CmdEntry 4157 }


	iqdmx32SetupLoggingop2embed11 OBJECT-TYPE
		SYNTAX		INTEGER { disable(0), enable(1) }
		MAX-ACCESS		read-write
		STATUS			current
		DESCRIPTION
				"TYPE: - Checkbox
				 PAGE: - Common- Setup- Logging
					op_2_embed_1_1  cmdID= 4066 "
		::= { iqdmx32CmdEntry 4066 }


	iqdmx32SetupLoggingop2embed11Log OBJECT-TYPE
		SYNTAX		RollCallString
		MAX-ACCESS		read-only
		STATUS			current
		DESCRIPTION
				"TYPE: - Display
				 PAGE: - Common- Setup- Logging
					op_2_embed_1_1 Log  cmdID= 4067  format=   "
		::= { iqdmx32CmdEntry 4067 }


	iqdmx32SetupLoggingop2embed12 OBJECT-TYPE
		SYNTAX		INTEGER { disable(0), enable(1) }
		MAX-ACCESS		read-write
		STATUS			current
		DESCRIPTION
				"TYPE: - Checkbox
				 PAGE: - Common- Setup- Logging
					op_2_embed_1_2  cmdID= 4070 "
		::= { iqdmx32CmdEntry 4070 }


	iqdmx32SetupLoggingop2embed12Log OBJECT-TYPE
		SYNTAX		RollCallString
		MAX-ACCESS		read-only
		STATUS			current
		DESCRIPTION
				"TYPE: - Display
				 PAGE: - Common- Setup- Logging
					op_2_embed_1_2 Log  cmdID= 4071  format=   "
		::= { iqdmx32CmdEntry 4071 }


	iqdmx32SetupLoggingop2embed21 OBJECT-TYPE
		SYNTAX		INTEGER { disable(0), enable(1) }
		MAX-ACCESS		read-write
		STATUS			current
		DESCRIPTION
				"TYPE: - Checkbox
				 PAGE: - Common- Setup- Logging
					op_2_embed_2_1  cmdID= 4074 "
		::= { iqdmx32CmdEntry 4074 }


	iqdmx32SetupLoggingop2embed21Log OBJECT-TYPE
		SYNTAX		RollCallString
		MAX-ACCESS		read-only
		STATUS			current
		DESCRIPTION
				"TYPE: - Display
				 PAGE: - Common- Setup- Logging
					op_2_embed_2_1 Log  cmdID= 4075  format=   "
		::= { iqdmx32CmdEntry 4075 }


	iqdmx32SetupLoggingop2embed22 OBJECT-TYPE
		SYNTAX		INTEGER { disable(0), enable(1) }
		MAX-ACCESS		read-write
		STATUS			current
		DESCRIPTION
				"TYPE: - Checkbox
				 PAGE: - Common- Setup- Logging
					op_2_embed_2_2  cmdID= 4078 "
		::= { iqdmx32CmdEntry 4078 }


	iqdmx32SetupLoggingop2embed22Log OBJECT-TYPE
		SYNTAX		RollCallString
		MAX-ACCESS		read-only
		STATUS			current
		DESCRIPTION
				"TYPE: - Display
				 PAGE: - Common- Setup- Logging
					op_2_embed_2_2 Log  cmdID= 4079  format=   "
		::= { iqdmx32CmdEntry 4079 }


	iqdmx32SetupLoggingop2embed31 OBJECT-TYPE
		SYNTAX		INTEGER { disable(0), enable(1) }
		MAX-ACCESS		read-write
		STATUS			current
		DESCRIPTION
				"TYPE: - Checkbox
				 PAGE: - Common- Setup- Logging
					op_2_embed_3_1  cmdID= 4082 "
		::= { iqdmx32CmdEntry 4082 }


	iqdmx32SetupLoggingop2embed31Log OBJECT-TYPE
		SYNTAX		RollCallString
		MAX-ACCESS		read-only
		STATUS			current
		DESCRIPTION
				"TYPE: - Display
				 PAGE: - Common- Setup- Logging
					op_2_embed_3_1 Log  cmdID= 4083  format=   "
		::= { iqdmx32CmdEntry 4083 }


	iqdmx32SetupLoggingop2embed32 OBJECT-TYPE
		SYNTAX		INTEGER { disable(0), enable(1) }
		MAX-ACCESS		read-write
		STATUS			current
		DESCRIPTION
				"TYPE: - Checkbox
				 PAGE: - Common- Setup- Logging
					op_2_embed_3_2  cmdID= 4086 "
		::= { iqdmx32CmdEntry 4086 }


	iqdmx32SetupLoggingop2embed32Log OBJECT-TYPE
		SYNTAX		RollCallString
		MAX-ACCESS		read-only
		STATUS			current
		DESCRIPTION
				"TYPE: - Display
				 PAGE: - Common- Setup- Logging
					op_2_embed_3_2 Log  cmdID= 4087  format=   "
		::= { iqdmx32CmdEntry 4087 }


	iqdmx32SetupLoggingop2embed41 OBJECT-TYPE
		SYNTAX		INTEGER { disable(0), enable(1) }
		MAX-ACCESS		read-write
		STATUS			current
		DESCRIPTION
				"TYPE: - Checkbox
				 PAGE: - Common- Setup- Logging
					op_2_embed_4_1  cmdID= 4090 "
		::= { iqdmx32CmdEntry 4090 }


	iqdmx32SetupLoggingop2embed41Log OBJECT-TYPE
		SYNTAX		RollCallString
		MAX-ACCESS		read-only
		STATUS			current
		DESCRIPTION
				"TYPE: - Display
				 PAGE: - Common- Setup- Logging
					op_2_embed_4_1 Log  cmdID= 4091  format=   "
		::= { iqdmx32CmdEntry 4091 }


	iqdmx32SetupLoggingop2embed42 OBJECT-TYPE
		SYNTAX		INTEGER { disable(0), enable(1) }
		MAX-ACCESS		read-write
		STATUS			current
		DESCRIPTION
				"TYPE: - Checkbox
				 PAGE: - Common- Setup- Logging
					op_2_embed_4_2  cmdID= 4094 "
		::= { iqdmx32CmdEntry 4094 }


	iqdmx32SetupLoggingop2embed42Log OBJECT-TYPE
		SYNTAX		RollCallString
		MAX-ACCESS		read-only
		STATUS			current
		DESCRIPTION
				"TYPE: - Display
				 PAGE: - Common- Setup- Logging
					op_2_embed_4_2 Log  cmdID= 4095  format=   "
		::= { iqdmx32CmdEntry 4095 }


	iqdmx32SetupLoggingop2embed51 OBJECT-TYPE
		SYNTAX		INTEGER { disable(0), enable(1) }
		MAX-ACCESS		read-write
		STATUS			current
		DESCRIPTION
				"TYPE: - Checkbox
				 PAGE: - Common- Setup- Logging
					op_2_embed_5_1  cmdID= 4098 "
		::= { iqdmx32CmdEntry 4098 }


	iqdmx32SetupLoggingop2embed51Log OBJECT-TYPE
		SYNTAX		RollCallString
		MAX-ACCESS		read-only
		STATUS			current
		DESCRIPTION
				"TYPE: - Display
				 PAGE: - Common- Setup- Logging
					op_2_embed_5_1 Log  cmdID= 4099  format=   "
		::= { iqdmx32CmdEntry 4099 }


	iqdmx32SetupLoggingop2embed52 OBJECT-TYPE
		SYNTAX		INTEGER { disable(0), enable(1) }
		MAX-ACCESS		read-write
		STATUS			current
		DESCRIPTION
				"TYPE: - Checkbox
				 PAGE: - Common- Setup- Logging
					op_2_embed_5_2  cmdID= 4102 "
		::= { iqdmx32CmdEntry 4102 }


	iqdmx32SetupLoggingop2embed52Log OBJECT-TYPE
		SYNTAX		RollCallString
		MAX-ACCESS		read-only
		STATUS			current
		DESCRIPTION
				"TYPE: - Display
				 PAGE: - Common- Setup- Logging
					op_2_embed_5_2 Log  cmdID= 4103  format=   "
		::= { iqdmx32CmdEntry 4103 }


	iqdmx32SetupLoggingop2embed61 OBJECT-TYPE
		SYNTAX		INTEGER { disable(0), enable(1) }
		MAX-ACCESS		read-write
		STATUS			current
		DESCRIPTION
				"TYPE: - Checkbox
				 PAGE: - Common- Setup- Logging
					op_2_embed_6_1  cmdID= 4106 "
		::= { iqdmx32CmdEntry 4106 }


	iqdmx32SetupLoggingop2embed61Log OBJECT-TYPE
		SYNTAX		RollCallString
		MAX-ACCESS		read-only
		STATUS			current
		DESCRIPTION
				"TYPE: - Display
				 PAGE: - Common- Setup- Logging
					op_2_embed_6_1 Log  cmdID= 4107  format=   "
		::= { iqdmx32CmdEntry 4107 }


	iqdmx32SetupLoggingop2embed62 OBJECT-TYPE
		SYNTAX		INTEGER { disable(0), enable(1) }
		MAX-ACCESS		read-write
		STATUS			current
		DESCRIPTION
				"TYPE: - Checkbox
				 PAGE: - Common- Setup- Logging
					op_2_embed_6_2  cmdID= 4110 "
		::= { iqdmx32CmdEntry 4110 }


	iqdmx32SetupLoggingop2embed62Log OBJECT-TYPE
		SYNTAX		RollCallString
		MAX-ACCESS		read-only
		STATUS			current
		DESCRIPTION
				"TYPE: - Display
				 PAGE: - Common- Setup- Logging
					op_2_embed_6_2 Log  cmdID= 4111  format=   "
		::= { iqdmx32CmdEntry 4111 }


	iqdmx32SetupLoggingop2embed71 OBJECT-TYPE
		SYNTAX		INTEGER { disable(0), enable(1) }
		MAX-ACCESS		read-write
		STATUS			current
		DESCRIPTION
				"TYPE: - Checkbox
				 PAGE: - Common- Setup- Logging
					op_2_embed_7_1  cmdID= 4114 "
		::= { iqdmx32CmdEntry 4114 }


	iqdmx32SetupLoggingop2embed71Log OBJECT-TYPE
		SYNTAX		RollCallString
		MAX-ACCESS		read-only
		STATUS			current
		DESCRIPTION
				"TYPE: - Display
				 PAGE: - Common- Setup- Logging
					op_2_embed_7_1 Log  cmdID= 4115  format=   "
		::= { iqdmx32CmdEntry 4115 }


	iqdmx32SetupLoggingop2embed72 OBJECT-TYPE
		SYNTAX		INTEGER { disable(0), enable(1) }
		MAX-ACCESS		read-write
		STATUS			current
		DESCRIPTION
				"TYPE: - Checkbox
				 PAGE: - Common- Setup- Logging
					op_2_embed_7_2  cmdID= 4118 "
		::= { iqdmx32CmdEntry 4118 }


	iqdmx32SetupLoggingop2embed72Log OBJECT-TYPE
		SYNTAX		RollCallString
		MAX-ACCESS		read-only
		STATUS			current
		DESCRIPTION
				"TYPE: - Display
				 PAGE: - Common- Setup- Logging
					op_2_embed_7_2 Log  cmdID= 4119  format=   "
		::= { iqdmx32CmdEntry 4119 }


	iqdmx32SetupLoggingop2embed81 OBJECT-TYPE
		SYNTAX		INTEGER { disable(0), enable(1) }
		MAX-ACCESS		read-write
		STATUS			current
		DESCRIPTION
				"TYPE: - Checkbox
				 PAGE: - Common- Setup- Logging
					op_2_embed_8_1  cmdID= 4122 "
		::= { iqdmx32CmdEntry 4122 }


	iqdmx32SetupLoggingop2embed81Log OBJECT-TYPE
		SYNTAX		RollCallString
		MAX-ACCESS		read-only
		STATUS			current
		DESCRIPTION
				"TYPE: - Display
				 PAGE: - Common- Setup- Logging
					op_2_embed_8_1 Log  cmdID= 4123  format=   "
		::= { iqdmx32CmdEntry 4123 }


	iqdmx32SetupLoggingop2embed82 OBJECT-TYPE
		SYNTAX		INTEGER { disable(0), enable(1) }
		MAX-ACCESS		read-write
		STATUS			current
		DESCRIPTION
				"TYPE: - Checkbox
				 PAGE: - Common- Setup- Logging
					op_2_embed_8_2  cmdID= 4126 "
		::= { iqdmx32CmdEntry 4126 }


	iqdmx32SetupLoggingop2embed82Log OBJECT-TYPE
		SYNTAX		RollCallString
		MAX-ACCESS		read-only
		STATUS			current
		DESCRIPTION
				"TYPE: - Display
				 PAGE: - Common- Setup- Logging
					op_2_embed_8_2 Log  cmdID= 4127  format=   "
		::= { iqdmx32CmdEntry 4127 }


	iqdmx32SetupLoggingop2aes11 OBJECT-TYPE
		SYNTAX		INTEGER { disable(0), enable(1) }
		MAX-ACCESS		read-write
		STATUS			current
		DESCRIPTION
				"TYPE: - Checkbox
				 PAGE: - Common- Setup- Logging
					op_2_aes_1_1  cmdID= 4130 "
		::= { iqdmx32CmdEntry 4130 }


	iqdmx32SetupLoggingop2aes11Log OBJECT-TYPE
		SYNTAX		RollCallString
		MAX-ACCESS		read-only
		STATUS			current
		DESCRIPTION
				"TYPE: - Display
				 PAGE: - Common- Setup- Logging
					op_2_aes_1_1 Log  cmdID= 4131  format=   "
		::= { iqdmx32CmdEntry 4131 }


	iqdmx32SetupLoggingop2aes12 OBJECT-TYPE
		SYNTAX		INTEGER { disable(0), enable(1) }
		MAX-ACCESS		read-write
		STATUS			current
		DESCRIPTION
				"TYPE: - Checkbox
				 PAGE: - Common- Setup- Logging
					op_2_aes_1_2  cmdID= 4134 "
		::= { iqdmx32CmdEntry 4134 }


	iqdmx32SetupLoggingop2aes12Log OBJECT-TYPE
		SYNTAX		RollCallString
		MAX-ACCESS		read-only
		STATUS			current
		DESCRIPTION
				"TYPE: - Display
				 PAGE: - Common- Setup- Logging
					op_2_aes_1_2 Log  cmdID= 4135  format=   "
		::= { iqdmx32CmdEntry 4135 }


	iqdmx32SetupLoggingop2aes21 OBJECT-TYPE
		SYNTAX		INTEGER { disable(0), enable(1) }
		MAX-ACCESS		read-write
		STATUS			current
		DESCRIPTION
				"TYPE: - Checkbox
				 PAGE: - Common- Setup- Logging
					op_2_aes_2_1  cmdID= 4138 "
		::= { iqdmx32CmdEntry 4138 }


	iqdmx32SetupLoggingop2aes21Log OBJECT-TYPE
		SYNTAX		RollCallString
		MAX-ACCESS		read-only
		STATUS			current
		DESCRIPTION
				"TYPE: - Display
				 PAGE: - Common- Setup- Logging
					op_2_aes_2_1 Log  cmdID= 4139  format=   "
		::= { iqdmx32CmdEntry 4139 }


	iqdmx32SetupLoggingop2aes22 OBJECT-TYPE
		SYNTAX		INTEGER { disable(0), enable(1) }
		MAX-ACCESS		read-write
		STATUS			current
		DESCRIPTION
				"TYPE: - Checkbox
				 PAGE: - Common- Setup- Logging
					op_2_aes_2_2  cmdID= 4142 "
		::= { iqdmx32CmdEntry 4142 }


	iqdmx32SetupLoggingop2aes22Log OBJECT-TYPE
		SYNTAX		RollCallString
		MAX-ACCESS		read-only
		STATUS			current
		DESCRIPTION
				"TYPE: - Display
				 PAGE: - Common- Setup- Logging
					op_2_aes_2_2 Log  cmdID= 4143  format=   "
		::= { iqdmx32CmdEntry 4143 }


	iqdmx32SetupLoggingop2aes31 OBJECT-TYPE
		SYNTAX		INTEGER { disable(0), enable(1) }
		MAX-ACCESS		read-write
		STATUS			current
		DESCRIPTION
				"TYPE: - Checkbox
				 PAGE: - Common- Setup- Logging
					op_2_aes_3_1  cmdID= 4146 "
		::= { iqdmx32CmdEntry 4146 }


	iqdmx32SetupLoggingop2aes31Log OBJECT-TYPE
		SYNTAX		RollCallString
		MAX-ACCESS		read-only
		STATUS			current
		DESCRIPTION
				"TYPE: - Display
				 PAGE: - Common- Setup- Logging
					op_2_aes_3_1 Log  cmdID= 4147  format=   "
		::= { iqdmx32CmdEntry 4147 }


	iqdmx32SetupLoggingop2aes32 OBJECT-TYPE
		SYNTAX		INTEGER { disable(0), enable(1) }
		MAX-ACCESS		read-write
		STATUS			current
		DESCRIPTION
				"TYPE: - Checkbox
				 PAGE: - Common- Setup- Logging
					op_2_aes_3_2  cmdID= 4150 "
		::= { iqdmx32CmdEntry 4150 }


	iqdmx32SetupLoggingop2aes32Log OBJECT-TYPE
		SYNTAX		RollCallString
		MAX-ACCESS		read-only
		STATUS			current
		DESCRIPTION
				"TYPE: - Display
				 PAGE: - Common- Setup- Logging
					op_2_aes_3_2 Log  cmdID= 4151  format=   "
		::= { iqdmx32CmdEntry 4151 }


	iqdmx32SetupLoggingop2aes41 OBJECT-TYPE
		SYNTAX		INTEGER { disable(0), enable(1) }
		MAX-ACCESS		read-write
		STATUS			current
		DESCRIPTION
				"TYPE: - Checkbox
				 PAGE: - Common- Setup- Logging
					op_2_aes_4_1  cmdID= 4154 "
		::= { iqdmx32CmdEntry 4154 }


	iqdmx32SetupLoggingop2aes41Log OBJECT-TYPE
		SYNTAX		RollCallString
		MAX-ACCESS		read-only
		STATUS			current
		DESCRIPTION
				"TYPE: - Display
				 PAGE: - Common- Setup- Logging
					op_2_aes_4_1 Log  cmdID= 4155  format=   "
		::= { iqdmx32CmdEntry 4155 }


	iqdmx32SetupLoggingop2aes42 OBJECT-TYPE
		SYNTAX		INTEGER { disable(0), enable(1) }
		MAX-ACCESS		read-write
		STATUS			current
		DESCRIPTION
				"TYPE: - Checkbox
				 PAGE: - Common- Setup- Logging
					op_2_aes_4_2  cmdID= 4158 "
		::= { iqdmx32CmdEntry 4158 }


	iqdmx32SetupLoggingop2aes42Log OBJECT-TYPE
		SYNTAX		RollCallString
		MAX-ACCESS		read-only
		STATUS			current
		DESCRIPTION
				"TYPE: - Display
				 PAGE: - Common- Setup- Logging
					op_2_aes_4_2 Log  cmdID= 4159  format=   "
		::= { iqdmx32CmdEntry 4159 }


	iqdmx32SetupRollTracksRollTrackIndex OBJECT-TYPE
		SYNTAX		INTEGER
		MAX-ACCESS		read-write
		STATUS			current
		DESCRIPTION
				"TYPE: - Number
				 PAGE: - Common- Setup- RollTracks
					RollTrack Index  cmdID= 1495  min= 1  max= 70  step= 1  format= %.0f  div_scale= 1 
					Min = 1  Max = 70  Step = 1 "
		::= { iqdmx32CmdEntry 1495 }


	iqdmx32SetupRollTracksRollTrackSource OBJECT-TYPE
		SYNTAX		INTEGER
		MAX-ACCESS		read-write
		STATUS			current
		DESCRIPTION
				"TYPE: - Number
				 PAGE: - Common- Setup- RollTracks
					RollTrack Source  cmdID= 1496  min= -1  max= 113  step= 1  format= %.0f  div_scale= 1 
					Min = -1  Max = 113  Step = 1 "
		::= { iqdmx32CmdEntry 1496 }


	iqdmx32SetupRollTracksRollTrackDisable OBJECT-TYPE
		SYNTAX		INTEGER { disable(0), enable(1) }
		MAX-ACCESS		read-write
		STATUS			current
		DESCRIPTION
				"TYPE: - Checkbox
				 PAGE: - Common- Setup- RollTracks
					RollTrack Disable  cmdID= 1513 "
		::= { iqdmx32CmdEntry 1513 }


	iqdmx32SetupRollTracksRollTrackAddress OBJECT-TYPE
		SYNTAX		RollCallString
		MAX-ACCESS		read-write
		STATUS			current
		DESCRIPTION
				"TYPE: - Editstring
				 PAGE: - Common- Setup- RollTracks
					RollTrack Address  cmdID= 1497  "
		::= { iqdmx32CmdEntry 1497 }


	iqdmx32SetupRollTracksRollTrackCommand OBJECT-TYPE
		SYNTAX		RollCallString
		MAX-ACCESS		read-write
		STATUS			current
		DESCRIPTION
				"TYPE: - Editstring
				 PAGE: - Common- Setup- RollTracks
					RollTrack Command  cmdID= 1498  "
		::= { iqdmx32CmdEntry 1498 }


	iqdmx32SetupRollTracksRollTrackSending OBJECT-TYPE
		SYNTAX		RollCallString
		MAX-ACCESS		read-only
		STATUS			current
		DESCRIPTION
				"TYPE: - Display
				 PAGE: - Common- Setup- RollTracks
					RollTrack Sending  cmdID= 1514  format=   "
		::= { iqdmx32CmdEntry 1514 }


	iqdmx32SetupRollTracksRollTrackStatus OBJECT-TYPE
		SYNTAX		RollCallString
		MAX-ACCESS		read-only
		STATUS			current
		DESCRIPTION
				"TYPE: - Display
				 PAGE: - Common- Setup- RollTracks
					RollTrack Status  cmdID= 1511  format=   "
		::= { iqdmx32CmdEntry 1511 }


	iqdmx32SetupRollTracksRollTrackIndexSave OBJECT-TYPE
		SYNTAX		INTEGER
		MAX-ACCESS		read-write
		STATUS			current
		DESCRIPTION
				"TYPE: - Number
				 PAGE: - Common- Setup- RollTracks
					RollTrack Index  cmdID= 2870  min= 1  max= 70  step= 1  format= %.0f  div_scale= 1 
					Min = 1  Max = 70  Step = 1 "
		::= { iqdmx32CmdEntry 2870 }


	iqdmx32SetupRollTracksRollTrackSourceSave OBJECT-TYPE
		SYNTAX		INTEGER
		MAX-ACCESS		read-write
		STATUS			current
		DESCRIPTION
				"TYPE: - Number
				 PAGE: - Common- Setup- RollTracks
					RollTrack Source  cmdID= 2871  min= -1  max= 113  step= 1  format= %.0f  div_scale= 1 
					Min = -1  Max = 113  Step = 1 "
		::= { iqdmx32CmdEntry 2871 }


	iqdmx32SetupRollTracksRollTrackAddressSave OBJECT-TYPE
		SYNTAX		RollCallString
		MAX-ACCESS		read-write
		STATUS			current
		DESCRIPTION
				"TYPE: - Editstring
				 PAGE: - Common- Setup- RollTracks
					RollTrack Address  cmdID= 2872  "
		::= { iqdmx32CmdEntry 2872 }


	iqdmx32SetupRollTracksRollTrackCommandSave OBJECT-TYPE
		SYNTAX		RollCallString
		MAX-ACCESS		read-write
		STATUS			current
		DESCRIPTION
				"TYPE: - Editstring
				 PAGE: - Common- Setup- RollTracks
					RollTrack Command  cmdID= 2873  "
		::= { iqdmx32CmdEntry 2873 }


	iqdmx32CommonStatusStatusDisplay OBJECT-TYPE
		SYNTAX		INTEGER {
							val-Video-Status(0),
							val-Audio-Input-Status(1)
							}
		MAX-ACCESS		read-write
		STATUS			current
		DESCRIPTION
				"TYPE: - RadiobuttonList
				 PAGE: - Common
					Status Display  cmdID= 1915 
					Video Status  value= 0  
					Audio Input Status  value= 1  "
		::= { iqdmx32CmdEntry 1915 }


	iqdmx32CommonStatusProduct OBJECT-TYPE
		SYNTAX		RollCallString
		MAX-ACCESS		read-only
		STATUS			current
		DESCRIPTION
				"TYPE: - Display
				 PAGE: - Common
					Product  cmdID= 5000  format=   "
		::= { iqdmx32CmdEntry 5000 }


	iqdmx32CommonStatusSoftwareVersion OBJECT-TYPE
		SYNTAX		RollCallString
		MAX-ACCESS		read-only
		STATUS			current
		DESCRIPTION
				"TYPE: - Display
				 PAGE: - Common
					Software Version  cmdID= 2  format=   "
		::= { iqdmx32CmdEntry 2 }


	iqdmx32CommonStatusSerialNo OBJECT-TYPE
		SYNTAX		RollCallString
		MAX-ACCESS		read-only
		STATUS			current
		DESCRIPTION
				"TYPE: - Display
				 PAGE: - Common
					Serial No  cmdID= 1  format=   "
		::= { iqdmx32CmdEntry 1 }


	iqdmx32CommonStatusFactoryDefaults OBJECT-TYPE
		SYNTAX		INTEGER { noAction(0),val-Factory-Defaults(1) }
		MAX-ACCESS		read-write
		STATUS			current
		DESCRIPTION
				"TYPE: - Button
				 PAGE: - Common
					Factory Defaults  cmdID= 5020  value= 1  "
		::= { iqdmx32CmdEntry 5020 }


	iqdmx32CommonStatusDefaultSetting OBJECT-TYPE
		SYNTAX		INTEGER { noAction(0),val-Default-Setting(1) }
		MAX-ACCESS		read-write
		STATUS			current
		DESCRIPTION
				"TYPE: - Button
				 PAGE: - Common
					Default Setting  cmdID= 5021  value= 1  "
		::= { iqdmx32CmdEntry 5021 }


	iqdmx32CommonStatusRestart OBJECT-TYPE
		SYNTAX		INTEGER { noAction(0),val-Restart(1) }
		MAX-ACCESS		read-write
		STATUS			current
		DESCRIPTION
				"TYPE: - Button
				 PAGE: - Common
					Restart  cmdID= 4  value= 1  "
		::= { iqdmx32CmdEntry 4 }


	iqdmx32CommonStatusBuild OBJECT-TYPE
		SYNTAX		RollCallString
		MAX-ACCESS		read-only
		STATUS			current
		DESCRIPTION
				"TYPE: - Display
				 PAGE: - Common
					Build  cmdID= 5  format=   "
		::= { iqdmx32CmdEntry 5 }


	iqdmx32CommonStatusPCB OBJECT-TYPE
		SYNTAX		RollCallString
		MAX-ACCESS		read-only
		STATUS			current
		DESCRIPTION
				"TYPE: - Display
				 PAGE: - Common
					PCB  cmdID= 6  format=   "
		::= { iqdmx32CmdEntry 6 }


	iqdmx32CommonStatusKOSVersion OBJECT-TYPE
		SYNTAX		RollCallString
		MAX-ACCESS		read-only
		STATUS			current
		DESCRIPTION
				"TYPE: - Display
				 PAGE: - Common
					KOS Version  cmdID= 7  format=   "
		::= { iqdmx32CmdEntry 7 }


	iqdmx32CommonStatusFirmwareVersion OBJECT-TYPE
		SYNTAX		RollCallString
		MAX-ACCESS		read-only
		STATUS			current
		DESCRIPTION
				"TYPE: - Display
				 PAGE: - Common
					Firmware Version  cmdID= 5001  format=   "
		::= { iqdmx32CmdEntry 5001 }


	iqdmx32CommonStatusUpTime OBJECT-TYPE
		SYNTAX		RollCallString
		MAX-ACCESS		read-only
		STATUS			current
		DESCRIPTION
				"TYPE: - Display
				 PAGE: - Common
					Up Time  cmdID= 8  format=   "
		::= { iqdmx32CmdEntry 8 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S12345678
-- Comments		: Serial number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 000:01:26:00
-- Comments		: Uptime of unit
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
--
-- Value(s)		: 238
-- Comments		: Rear Interface ID
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: V115 Release
-- Comments		:
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
--
-- Value(s)		: 12
-- Comments		: Rear Interface Slot start pos
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
--
-- Value(s)		: 2
-- Comments		: Rear Interface Slot WIDTH
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 3731.3731.3731
-- Comments		: Embedded code build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD/SD/3G SDI
-- Comments		: Input 1 type
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD/SD/3G SDI
-- Comments		: Input 1 type
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
--
-- Value(s)		: SERIAL IN 1
-- Comments		: Input 1 editable name
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: OK
--				: FAIL:Lost
-- Comments		:
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
--
-- Value(s)		: SERIAL IN 2
-- Comments		: Input 2 editable name
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: OK
--				: FAIL:Lost
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
--
-- Value(s)		: 2011-08-19T10:52:12Z
-- Comments		: Time of last control mod
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: 3G / HD / SD SDI
-- Comments		:
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
--
-- Value(s)		: 3G / HD / SD SDI
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: WARN:Black
--				: WARN:Caption
--				: WARN:Pattern
--				: OK
-- Comments		:
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
--
-- Value(s)		: WARN:Black
--				: WARN:Caption
--				: WARN:Pattern
--				: OK
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 3711
-- Comments		:
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: HDBASP1B
-- Comments		:
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: 1080/59p-A
--				: 1080/50p-A
--				: 1080/59p-B
--				: 1080/50p-B
--				: 1080/29i
--				: 1080/25i
--				: 720/59p
--				: 720/50p
--				: 525/29i
--				: 625/25i
--				: Unknown
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: 1080/59p-A
--				: 1080/50p-A
--				: 1080/59p-B
--				: 1080/50p-B
--				: 1080/29i
--				: 1080/25i
--				: 720/59p
--				: 720/50p
--				: 525/29i
--				: 625/25i
--				: Unknown
-- Comments		:
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
--
-- Value(s)		: SDHD
--				: SDHD;3G
-- Comments		: Licensed options
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
--
-- Value(s)		: OK:off
--				: WARN:On[text]
-- Comments		:
--
---------------------------------------------------------------------------------------------------
-- Header		: OUTPUT_2_CAPTION
--
-- MIB ref		: swCardEventLogSlotXX       .16.79.85.84.80.85.84.95.50.95.67.65.80.84.73.79.78
-- absolute OID	: 1.3.6.1.4.1.7995.2.6.1.1.XX.16.79.85.84.80.85.84.95.50.95.67.65.80.84.73.79.78
--
-- Value(s)		: OK:off
--				: WARN:On[text]
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: 1080/59p-A
--				: 1080/50p-A
--				: 1080/59p-B
--				: 1080/50p-B
--				: 1080/29i
--				: 1080/25i
--				: 720/59p
--				: 720/50p
--				: 525/29i
--				: 625/25i
-- Comments		:
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
--
-- Value(s)		: 1080/59p-A
--				: 1080/50p-A
--				: 1080/59p-B
--				: 1080/50p-B
--				: 1080/29i
--				: 1080/25i
--				: 720/59p
--				: 720/50p
--				: 525/29i
--				: 625/25i
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: WARN
-- Comments		:
--
---------------------------------------------------------------------------------------------------
-- Header		: OUTPUT_1_AES_1_1_STATE
--
-- MIB ref		: swCardEventLogSlotXX       .22.79.85.84.80.85.84.95.49.95.65.69.83.95.49.95.49.95.83.84.65.84.69
-- absolute OID	: 1.3.6.1.4.1.7995.2.6.1.1.XX.22.79.85.84.80.85.84.95.49.95.65.69.83.95.49.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_1_2_STATE
--
-- MIB ref		: swCardEventLogSlotXX       .22.79.85.84.80.85.84.95.49.95.65.69.83.95.49.95.50.95.83.84.65.84.69
-- absolute OID	: 1.3.6.1.4.1.7995.2.6.1.1.XX.22.79.85.84.80.85.84.95.49.95.65.69.83.95.49.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_2_1_STATE
--
-- MIB ref		: swCardEventLogSlotXX       .22.79.85.84.80.85.84.95.49.95.65.69.83.95.50.95.49.95.83.84.65.84.69
-- absolute OID	: 1.3.6.1.4.1.7995.2.6.1.1.XX.22.79.85.84.80.85.84.95.49.95.65.69.83.95.50.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_2_2_STATE
--
-- MIB ref		: swCardEventLogSlotXX       .22.79.85.84.80.85.84.95.49.95.65.69.83.95.50.95.50.95.83.84.65.84.69
-- absolute OID	: 1.3.6.1.4.1.7995.2.6.1.1.XX.22.79.85.84.80.85.84.95.49.95.65.69.83.95.50.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_3_1_STATE
--
-- MIB ref		: swCardEventLogSlotXX       .22.79.85.84.80.85.84.95.49.95.65.69.83.95.51.95.49.95.83.84.65.84.69
-- absolute OID	: 1.3.6.1.4.1.7995.2.6.1.1.XX.22.79.85.84.80.85.84.95.49.95.65.69.83.95.51.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_3_2_STATE
--
-- MIB ref		: swCardEventLogSlotXX       .22.79.85.84.80.85.84.95.49.95.65.69.83.95.51.95.50.95.83.84.65.84.69
-- absolute OID	: 1.3.6.1.4.1.7995.2.6.1.1.XX.22.79.85.84.80.85.84.95.49.95.65.69.83.95.51.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_4_1_STATE
--
-- MIB ref		: swCardEventLogSlotXX       .22.79.85.84.80.85.84.95.49.95.65.69.83.95.52.95.49.95.83.84.65.84.69
-- absolute OID	: 1.3.6.1.4.1.7995.2.6.1.1.XX.22.79.85.84.80.85.84.95.49.95.65.69.83.95.52.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_AES_4_2_STATE
--
-- MIB ref		: swCardEventLogSlotXX       .22.79.85.84.80.85.84.95.49.95.65.69.83.95.52.95.50.95.83.84.65.84.69
-- absolute OID	: 1.3.6.1.4.1.7995.2.6.1.1.XX.22.79.85.84.80.85.84.95.49.95.65.69.83.95.52.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_1_1_STATE
--
-- MIB ref		: swCardEventLogSlotXX       .22.79.85.84.80.85.84.95.50.95.65.69.83.95.49.95.49.95.83.84.65.84.69
-- absolute OID	: 1.3.6.1.4.1.7995.2.6.1.1.XX.22.79.85.84.80.85.84.95.50.95.65.69.83.95.49.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_1_2_STATE
--
-- MIB ref		: swCardEventLogSlotXX       .22.79.85.84.80.85.84.95.50.95.65.69.83.95.49.95.50.95.83.84.65.84.69
-- absolute OID	: 1.3.6.1.4.1.7995.2.6.1.1.XX.22.79.85.84.80.85.84.95.50.95.65.69.83.95.49.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_2_1_STATE
--
-- MIB ref		: swCardEventLogSlotXX       .22.79.85.84.80.85.84.95.50.95.65.69.83.95.50.95.49.95.83.84.65.84.69
-- absolute OID	: 1.3.6.1.4.1.7995.2.6.1.1.XX.22.79.85.84.80.85.84.95.50.95.65.69.83.95.50.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_2_2_STATE
--
-- MIB ref		: swCardEventLogSlotXX       .22.79.85.84.80.85.84.95.50.95.65.69.83.95.50.95.50.95.83.84.65.84.69
-- absolute OID	: 1.3.6.1.4.1.7995.2.6.1.1.XX.22.79.85.84.80.85.84.95.50.95.65.69.83.95.50.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_3_1_STATE
--
-- MIB ref		: swCardEventLogSlotXX       .22.79.85.84.80.85.84.95.50.95.65.69.83.95.51.95.49.95.83.84.65.84.69
-- absolute OID	: 1.3.6.1.4.1.7995.2.6.1.1.XX.22.79.85.84.80.85.84.95.50.95.65.69.83.95.51.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_3_2_STATE
--
-- MIB ref		: swCardEventLogSlotXX       .22.79.85.84.80.85.84.95.50.95.65.69.83.95.51.95.50.95.83.84.65.84.69
-- absolute OID	: 1.3.6.1.4.1.7995.2.6.1.1.XX.22.79.85.84.80.85.84.95.50.95.65.69.83.95.51.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_4_1_STATE
--
-- MIB ref		: swCardEventLogSlotXX       .22.79.85.84.80.85.84.95.50.95.65.69.83.95.52.95.49.95.83.84.65.84.69
-- absolute OID	: 1.3.6.1.4.1.7995.2.6.1.1.XX.22.79.85.84.80.85.84.95.50.95.65.69.83.95.52.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_AES_4_2_STATE
--
-- MIB ref		: swCardEventLogSlotXX       .22.79.85.84.80.85.84.95.50.95.65.69.83.95.52.95.50.95.83.84.65.84.69
-- absolute OID	: 1.3.6.1.4.1.7995.2.6.1.1.XX.22.79.85.84.80.85.84.95.50.95.65.69.83.95.52.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: OK:PCM
--				: OK:Data
--				: OK:DolbyE
--				: WARN:No Input
--				: WARN:Validity Bit
--				: FAIL:Lost
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: OK:PCM
--				: OK:Data
--				: OK:DolbyE
--				: WARN:No Input
--				: WARN:Validity Bit
--				: FAIL:Lost
-- Comments		:
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_1_1_STATE
--
-- MIB ref		: swCardEventLogSlotXX       .30.79.85.84.80.85.84.95.50.95.69.77.66.69.68.95.65.85.68.73.79.95.49.95.49.95.83.84.65.84.69
-- absolute OID	: 1.3.6.1.4.1.7995.2.6.1.1.XX.30.79.85.84.80.85.84.95.50.95.69.77.66.69.68.95.65.85.68.73.79.95.49.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_1_2_STATE
--
-- MIB ref		: swCardEventLogSlotXX       .30.79.85.84.80.85.84.95.50.95.69.77.66.69.68.95.65.85.68.73.79.95.49.95.50.95.83.84.65.84.69
-- absolute OID	: 1.3.6.1.4.1.7995.2.6.1.1.XX.30.79.85.84.80.85.84.95.50.95.69.77.66.69.68.95.65.85.68.73.79.95.49.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_2_1_STATE
--
-- MIB ref		: swCardEventLogSlotXX       .30.79.85.84.80.85.84.95.50.95.69.77.66.69.68.95.65.85.68.73.79.95.50.95.49.95.83.84.65.84.69
-- absolute OID	: 1.3.6.1.4.1.7995.2.6.1.1.XX.30.79.85.84.80.85.84.95.50.95.69.77.66.69.68.95.65.85.68.73.79.95.50.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_2_2_STATE
--
-- MIB ref		: swCardEventLogSlotXX       .30.79.85.84.80.85.84.95.50.95.69.77.66.69.68.95.65.85.68.73.79.95.50.95.50.95.83.84.65.84.69
-- absolute OID	: 1.3.6.1.4.1.7995.2.6.1.1.XX.30.79.85.84.80.85.84.95.50.95.69.77.66.69.68.95.65.85.68.73.79.95.50.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_3_1_STATE
--
-- MIB ref		: swCardEventLogSlotXX       .30.79.85.84.80.85.84.95.50.95.69.77.66.69.68.95.65.85.68.73.79.95.51.95.49.95.83.84.65.84.69
-- absolute OID	: 1.3.6.1.4.1.7995.2.6.1.1.XX.30.79.85.84.80.85.84.95.50.95.69.77.66.69.68.95.65.85.68.73.79.95.51.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_3_2_STATE
--
-- MIB ref		: swCardEventLogSlotXX       .30.79.85.84.80.85.84.95.50.95.69.77.66.69.68.95.65.85.68.73.79.95.51.95.50.95.83.84.65.84.69
-- absolute OID	: 1.3.6.1.4.1.7995.2.6.1.1.XX.30.79.85.84.80.85.84.95.50.95.69.77.66.69.68.95.65.85.68.73.79.95.51.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_4_1_STATE
--
-- MIB ref		: swCardEventLogSlotXX       .30.79.85.84.80.85.84.95.50.95.69.77.66.69.68.95.65.85.68.73.79.95.52.95.49.95.83.84.65.84.69
-- absolute OID	: 1.3.6.1.4.1.7995.2.6.1.1.XX.30.79.85.84.80.85.84.95.50.95.69.77.66.69.68.95.65.85.68.73.79.95.52.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_4_2_STATE
--
-- MIB ref		: swCardEventLogSlotXX       .30.79.85.84.80.85.84.95.50.95.69.77.66.69.68.95.65.85.68.73.79.95.52.95.50.95.83.84.65.84.69
-- absolute OID	: 1.3.6.1.4.1.7995.2.6.1.1.XX.30.79.85.84.80.85.84.95.50.95.69.77.66.69.68.95.65.85.68.73.79.95.52.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_5_1_STATE
--
-- MIB ref		: swCardEventLogSlotXX       .30.79.85.84.80.85.84.95.50.95.69.77.66.69.68.95.65.85.68.73.79.95.53.95.49.95.83.84.65.84.69
-- absolute OID	: 1.3.6.1.4.1.7995.2.6.1.1.XX.30.79.85.84.80.85.84.95.50.95.69.77.66.69.68.95.65.85.68.73.79.95.53.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_5_2_STATE
--
-- MIB ref		: swCardEventLogSlotXX       .30.79.85.84.80.85.84.95.50.95.69.77.66.69.68.95.65.85.68.73.79.95.53.95.50.95.83.84.65.84.69
-- absolute OID	: 1.3.6.1.4.1.7995.2.6.1.1.XX.30.79.85.84.80.85.84.95.50.95.69.77.66.69.68.95.65.85.68.73.79.95.53.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_6_1_STATE
--
-- MIB ref		: swCardEventLogSlotXX       .30.79.85.84.80.85.84.95.50.95.69.77.66.69.68.95.65.85.68.73.79.95.54.95.49.95.83.84.65.84.69
-- absolute OID	: 1.3.6.1.4.1.7995.2.6.1.1.XX.30.79.85.84.80.85.84.95.50.95.69.77.66.69.68.95.65.85.68.73.79.95.54.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_6_2_STATE
--
-- MIB ref		: swCardEventLogSlotXX       .30.79.85.84.80.85.84.95.50.95.69.77.66.69.68.95.65.85.68.73.79.95.54.95.50.95.83.84.65.84.69
-- absolute OID	: 1.3.6.1.4.1.7995.2.6.1.1.XX.30.79.85.84.80.85.84.95.50.95.69.77.66.69.68.95.65.85.68.73.79.95.54.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_7_1_STATE
--
-- MIB ref		: swCardEventLogSlotXX       .30.79.85.84.80.85.84.95.50.95.69.77.66.69.68.95.65.85.68.73.79.95.55.95.49.95.83.84.65.84.69
-- absolute OID	: 1.3.6.1.4.1.7995.2.6.1.1.XX.30.79.85.84.80.85.84.95.50.95.69.77.66.69.68.95.65.85.68.73.79.95.55.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_7_2_STATE
--
-- MIB ref		: swCardEventLogSlotXX       .30.79.85.84.80.85.84.95.50.95.69.77.66.69.68.95.65.85.68.73.79.95.55.95.50.95.83.84.65.84.69
-- absolute OID	: 1.3.6.1.4.1.7995.2.6.1.1.XX.30.79.85.84.80.85.84.95.50.95.69.77.66.69.68.95.65.85.68.73.79.95.55.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_8_1_STATE
--
-- MIB ref		: swCardEventLogSlotXX       .30.79.85.84.80.85.84.95.50.95.69.77.66.69.68.95.65.85.68.73.79.95.56.95.49.95.83.84.65.84.69
-- absolute OID	: 1.3.6.1.4.1.7995.2.6.1.1.XX.30.79.85.84.80.85.84.95.50.95.69.77.66.69.68.95.65.85.68.73.79.95.56.95.49.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
-- Header		: OUTPUT_2_EMBED_AUDIO_8_2_STATE
--
-- MIB ref		: swCardEventLogSlotXX       .30.79.85.84.80.85.84.95.50.95.69.77.66.69.68.95.65.85.68.73.79.95.56.95.50.95.83.84.65.84.69
-- absolute OID	: 1.3.6.1.4.1.7995.2.6.1.1.XX.30.79.85.84.80.85.84.95.50.95.69.77.66.69.68.95.65.85.68.73.79.95.56.95.50.95.83.84.65.84.69
--
-- Value(s)		: WARN:Silent PCM
--				: OK:PCM
--				: OK:Data
--				: OK:DolbyE
--				: WARN:Overload PCM
--				: FAIL:Input Lost
--				: FAIL:Mixed
-- Comments		:
--
---------------------------------------------------------------------------------------------------
