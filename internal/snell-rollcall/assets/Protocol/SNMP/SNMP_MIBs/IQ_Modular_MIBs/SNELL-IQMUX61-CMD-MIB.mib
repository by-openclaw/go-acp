-- ************************************************************************************
-- Snell&Wilcox Card:IQMUX61
--        Module Id#:405
--       Command Set:5
--          Filename:SNELL-IQMUX61-CMD-MIB.mib
--            Author:Jonathan Riches
--              Date:13/07/2006
--              Time:16:25
--
-- Copyright (c) 2005 Snell & Wilcox Ltd
-- All rights reserved.
--
-- ************************************************************************************

SNELL-IQMUX61-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQMUX61,
    moduleIQMUX61MIB
        FROM SNELL-WILCOX-PRODUCT-REG;

 moduleIQMUX61CmdMi MODULE-IDENTITY
    LAST-UPDATED "0607131625Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQMUX61MIB 1 }




--********************************************************************************
--*
--*  Snell Wilcox Card:
--*  command set:
--*  list commands/menus:
--*
--******************************************************************************
	iqmux61CmdTable OBJECT-TYPE
		SYNTAX			SEQUENCE OF Iqmux61CmdEntry
		MAX-ACCESS		not-accessible
		STATUS			current
		DESCRIPTION
				"Note the instance of this table is relected in the command set Version"
		::= { moduleIQMUX61 1 }

	iqmux61CmdEntry OBJECT-TYPE
		SYNTAX		Iqmux61CmdEntry
		MAX-ACCESS		not-accessible
		STATUS			current
		DESCRIPTION
				"Entry in command table."
		INDEX	{ iqmux61SlotIndex }
		::= { iqmux61CmdTable 1 }

	Iqmux61CmdEntry ::=
		SEQUENCE {
			iqmux61SlotIndex
				Unsigned32,
			iqmux61VideoInput
				INTEGER,
			iqmux61VideoInput525
				INTEGER,
			iqmux61VideoInput625
				INTEGER,
			iqmux61VideoProcAmp1In1ProcAmpEnable
				INTEGER,
			iqmux61VideoProcAmp1LumaGain
				INTEGER,
			iqmux61VideoProcAmp1ChromaGain
				INTEGER,
			iqmux61VideoProcAmp1BlackLevel
				INTEGER,
			iqmux61VideoProcAmp1PicturePosition
				INTEGER,
			iqmux61VideoProcAmp1YCTiming
				INTEGER,
			iqmux61VideoProcAmp2In2ProcAmpEnable
				INTEGER,
			iqmux61VideoProcAmp2LumaGain
				INTEGER,
			iqmux61VideoProcAmp2ChromaGain
				INTEGER,
			iqmux61VideoProcAmp2BlackLevel
				INTEGER,
			iqmux61VideoProcAmp2PicturePosition
				INTEGER,
			iqmux61VideoProcAmp2YCTiming
				INTEGER,
			iqmux61AudioDeembed
				INTEGER,
			iqmux61AudioAESOutputAES1Source
				INTEGER,
			iqmux61AudioAESOutputAES2Source
				INTEGER,
			iqmux61AudioProcAmpDeembedStereo1
				INTEGER,
			iqmux61ProcAmpDeembed1LGainDeembed1L
				INTEGER,
			iqmux61ProcAmpDeembed1LInvert
				INTEGER,
			iqmux61ProcAmpDeembed1LMute
				INTEGER,
			iqmux61ProcAmpDeembed1RGainDeembed1R
				INTEGER,
			iqmux61ProcAmpDeembed1RInvert
				INTEGER,
			iqmux61ProcAmpDeembed1RMute
				INTEGER,
			iqmux61AudioProcAmpDeembedStereo2
				INTEGER,
			iqmux61ProcAmpDeembed2LGainDeembed2L
				INTEGER,
			iqmux61ProcAmpDeembed2LInvert
				INTEGER,
			iqmux61ProcAmpDeembed2LMute
				INTEGER,
			iqmux61ProcAmpDeembed2RGainDeembed2R
				INTEGER,
			iqmux61ProcAmpDeembed2RInvert
				INTEGER,
			iqmux61ProcAmpDeembed2RMute
				INTEGER,
			iqmux61AudioProcAmpDeembedStereo3
				INTEGER,
			iqmux61ProcAmpDeembed3LGainDeembed3L
				INTEGER,
			iqmux61ProcAmpDeembed3LInvert
				INTEGER,
			iqmux61ProcAmpDeembed3LMute
				INTEGER,
			iqmux61ProcAmpDeembed3RGainDeembed3R
				INTEGER,
			iqmux61ProcAmpDeembed3RInvert
				INTEGER,
			iqmux61ProcAmpDeembed3RMute
				INTEGER,
			iqmux61AudioProcAmpDeembedStereo4
				INTEGER,
			iqmux61ProcAmpDeembed4LGainDeembed4L
				INTEGER,
			iqmux61ProcAmpDeembed4LInvert
				INTEGER,
			iqmux61ProcAmpDeembed4LMute
				INTEGER,
			iqmux61ProcAmpDeembed4RGainDeembed4R
				INTEGER,
			iqmux61ProcAmpDeembed4RInvert
				INTEGER,
			iqmux61ProcAmpDeembed4RMute
				INTEGER,
			iqmux61AudioProcAmpDeembedStereo5
				INTEGER,
			iqmux61ProcAmpDeembed5LGainDeembed5L
				INTEGER,
			iqmux61ProcAmpDeembed5LInvert
				INTEGER,
			iqmux61ProcAmpDeembed5LMute
				INTEGER,
			iqmux61ProcAmpDeembed5RGainDeembed5R
				INTEGER,
			iqmux61ProcAmpDeembed5RInvert
				INTEGER,
			iqmux61ProcAmpDeembed5RMute
				INTEGER,
			iqmux61AudioProcAmpDeembedStereo6
				INTEGER,
			iqmux61ProcAmpDeembed6LGainDeembed6L
				INTEGER,
			iqmux61ProcAmpDeembed6LInvert
				INTEGER,
			iqmux61ProcAmpDeembed6LMute
				INTEGER,
			iqmux61ProcAmpDeembed6RGainDeembed6R
				INTEGER,
			iqmux61ProcAmpDeembed6RInvert
				INTEGER,
			iqmux61ProcAmpDeembed6RMute
				INTEGER,
			iqmux61AudioProcAmpDeembedStereo7
				INTEGER,
			iqmux61ProcAmpDeembed7LGainDeembed7L
				INTEGER,
			iqmux61ProcAmpDeembed7LInvert
				INTEGER,
			iqmux61ProcAmpDeembed7LMute
				INTEGER,
			iqmux61ProcAmpDeembed7RGainDeembed7R
				INTEGER,
			iqmux61ProcAmpDeembed7RInvert
				INTEGER,
			iqmux61ProcAmpDeembed7RMute
				INTEGER,
			iqmux61AudioProcAmpDeembedStereo8
				INTEGER,
			iqmux61ProcAmpDeembed8LGainDeembed8L
				INTEGER,
			iqmux61ProcAmpDeembed8LInvert
				INTEGER,
			iqmux61ProcAmpDeembed8LMute
				INTEGER,
			iqmux61ProcAmpDeembed8RGainDeembed8R
				INTEGER,
			iqmux61ProcAmpDeembed8RInvert
				INTEGER,
			iqmux61ProcAmpDeembed8RMute
				INTEGER,
			iqmux61AudioProcAmpAESStereo1
				INTEGER,
			iqmux61ProcAmpAES1LGainAES1L
				INTEGER,
			iqmux61ProcAmpAES1LInvert
				INTEGER,
			iqmux61ProcAmpAES1LMute
				INTEGER,
			iqmux61ProcAmpAES1RGainAES1R
				INTEGER,
			iqmux61ProcAmpAES1RInvert
				INTEGER,
			iqmux61ProcAmpAES1RMute
				INTEGER,
			iqmux61AudioProcAmpAESStereo2
				INTEGER,
			iqmux61ProcAmpAES2LGainAES2L
				INTEGER,
			iqmux61ProcAmpAES2LInvert
				INTEGER,
			iqmux61ProcAmpAES2LMute
				INTEGER,
			iqmux61ProcAmpAES2RGainAES2R
				INTEGER,
			iqmux61ProcAmpAES2RInvert
				INTEGER,
			iqmux61ProcAmpAES2RMute
				INTEGER,
			iqmux61AudioProcAmpStereo1
				INTEGER,
			iqmux61ProcAmpAnalog1LGainAnalog1L
				INTEGER,
			iqmux61ProcAmpAnalog1LInvert
				INTEGER,
			iqmux61ProcAmpAnalog1LMute
				INTEGER,
			iqmux61ProcAmpAnalog1RGainAnalog1R
				INTEGER,
			iqmux61ProcAmpAnalog1RInvert
				INTEGER,
			iqmux61ProcAmpAnalog1RMute
				INTEGER,
			iqmux61AudioProcAmpStereo2
				INTEGER,
			iqmux61ProcAmpAnalog2LGainAnalog2L
				INTEGER,
			iqmux61ProcAmpAnalog2LInvert
				INTEGER,
			iqmux61ProcAmpAnalog2LMute
				INTEGER,
			iqmux61ProcAmpAnalog2RGainAnalog2R
				INTEGER,
			iqmux61ProcAmpAnalog2RInvert
				INTEGER,
			iqmux61ProcAmpAnalog2RMute
				INTEGER,
			iqmux61EmbedEmbedder1Embed1Source
				INTEGER,
			iqmux61EmbedEmbedder1PairSelection
				INTEGER,
			iqmux61EmbedEmbedder1Disable
				INTEGER,
			iqmux61EmbedEmbedder2Embed2Source
				INTEGER,
			iqmux61EmbedEmbedder2PairSelection
				INTEGER,
			iqmux61EmbedEmbedder2Disable
				INTEGER,
			iqmux61EmbedEmbedder3Embed3Source
				INTEGER,
			iqmux61EmbedEmbedder3PairSelection
				INTEGER,
			iqmux61EmbedEmbedder3Disable
				INTEGER,
			iqmux61EmbedEmbedder4Embed4Source
				INTEGER,
			iqmux61EmbedEmbedder4PairSelection
				INTEGER,
			iqmux61EmbedEmbedder4Disable
				INTEGER,
			iqmux61Mixer1Mix1Source1
				INTEGER,
			iqmux61MixMixer1Gain1
				INTEGER,
			iqmux61Mixer1Mix1Source2
				INTEGER,
			iqmux61MixMixer1Gain2
				INTEGER,
			iqmux61Mixer1Mix1Source3
				INTEGER,
			iqmux61MixMixer1Gain3
				INTEGER,
			iqmux61Mixer1Mix1Source4
				INTEGER,
			iqmux61MixMixer1Gain4
				INTEGER,
			iqmux61Mixer2Mix2Source1
				INTEGER,
			iqmux61MixMixer2Gain1
				INTEGER,
			iqmux61Mixer2Mix2Source2
				INTEGER,
			iqmux61MixMixer2Gain2
				INTEGER,
			iqmux61Mixer2Mix2Source3
				INTEGER,
			iqmux61MixMixer2Gain3
				INTEGER,
			iqmux61Mixer2Mix2Source4
				INTEGER,
			iqmux61MixMixer2Gain4
				INTEGER,
			iqmux61Mixer3Mix3Source1
				INTEGER,
			iqmux61MixMixer3Gain1
				INTEGER,
			iqmux61Mixer3Mix3Source2
				INTEGER,
			iqmux61MixMixer3Gain2
				INTEGER,
			iqmux61Mixer3Mix3Source3
				INTEGER,
			iqmux61MixMixer3Gain3
				INTEGER,
			iqmux61Mixer3Mix3Source4
				INTEGER,
			iqmux61MixMixer3Gain4
				INTEGER,
			iqmux61Mixer4Mix4Source1
				INTEGER,
			iqmux61MixMixer4Gain1
				INTEGER,
			iqmux61Mixer4Mix4Source2
				INTEGER,
			iqmux61MixMixer4Gain2
				INTEGER,
			iqmux61Mixer4Mix4Source3
				INTEGER,
			iqmux61MixMixer4Gain3
				INTEGER,
			iqmux61Mixer4Mix4Source4
				INTEGER,
			iqmux61MixMixer4Gain4
				INTEGER,
			iqmux61BusSourceBusALSource
				INTEGER,
			iqmux61BusSourceBusARSource
				INTEGER,
			iqmux61BusSourceBusBLSource
				INTEGER,
			iqmux61BusSourceBusBRSource
				INTEGER,
			iqmux61BusSourceBusCLSource
				INTEGER,
			iqmux61BusSourceBusCRSource
				INTEGER,
			iqmux61BusSourceBusDLSource
				INTEGER,
			iqmux61BusSourceBusDRSource
				INTEGER,
			iqmux61BusesBusProcAmpStereoA
				INTEGER,
			iqmux61BusProcAmpBusALGainBusAL
				INTEGER,
			iqmux61BusProcAmpBusALInvert
				INTEGER,
			iqmux61BusProcAmpBusALMute
				INTEGER,
			iqmux61BusProcAmpBusARGainBusAR
				INTEGER,
			iqmux61BusProcAmpBusARInvert
				INTEGER,
			iqmux61BusProcAmpBusARMute
				INTEGER,
			iqmux61BusesBusProcAmpStereoB
				INTEGER,
			iqmux61BusProcAmpBusBLGainBusBL
				INTEGER,
			iqmux61BusProcAmpBusBLInvert
				INTEGER,
			iqmux61BusProcAmpBusBLMute
				INTEGER,
			iqmux61BusProcAmpBusBRGainBusBR
				INTEGER,
			iqmux61BusProcAmpBusBRInvert
				INTEGER,
			iqmux61BusProcAmpBusBRMute
				INTEGER,
			iqmux61BusesBusProcAmpStereoC
				INTEGER,
			iqmux61BusProcAmpBusCLGainBusCL
				INTEGER,
			iqmux61BusProcAmpBusCLInvert
				INTEGER,
			iqmux61BusProcAmpBusCLMute
				INTEGER,
			iqmux61BusProcAmpBusCRGainBusCR
				INTEGER,
			iqmux61BusProcAmpBusCRInvert
				INTEGER,
			iqmux61BusProcAmpBusCRMute
				INTEGER,
			iqmux61BusesBusProcAmpStereoD
				INTEGER,
			iqmux61BusProcAmpBusDLGainBusDL
				INTEGER,
			iqmux61BusProcAmpBusDLInvert
				INTEGER,
			iqmux61BusProcAmpBusDLMute
				INTEGER,
			iqmux61BusProcAmpBusDRGainBusDR
				INTEGER,
			iqmux61BusProcAmpBusDRInvert
				INTEGER,
			iqmux61BusProcAmpBusDRMute
				INTEGER,
			iqmux61AudioDelayAESInput1Delay
				INTEGER,
			iqmux61AudioDelayAESInput2Delay
				INTEGER,
			iqmux61AudioDelayAnalogIn1Delay
				INTEGER,
			iqmux61AudioDelayAnalogIn2Delay
				INTEGER,
			iqmux61DelayDelaySelectInternal
				INTEGER,
			iqmux61DelayDelaySelectManual
				INTEGER,
			iqmux61DelayDelaySelectRolltrack14
				INTEGER,
			iqmux61DelayDelaySelectRolltrack15
				INTEGER,
			iqmux61DelayDelaySelectRolltrack16
				INTEGER,
			iqmux61DelayDelaySelectRolltrack17
				INTEGER,
			iqmux61DelayDelaySelectGPIDelaySelect
				INTEGER,
			iqmux61DelayDelayStatusManual
				INTEGER,
			iqmux61DelayDelayStatusInternal
				RollCallString,
			iqmux61DelayDelayStatusRolltrack14
				RollCallString,
			iqmux61DelayDelayStatusRolltrack15
				RollCallString,
			iqmux61DelayDelayStatusRolltrack16
				RollCallString,
			iqmux61DelayDelayStatusRolltrack17
				RollCallString,
			iqmux61DelayDelayStatusGPIDelayDisplay
				RollCallString,
			iqmux61DelayDelayStatusTotalDelayDisplay
				RollCallString,
			iqmux61AudioMonitorSilenceLevel
				INTEGER,
			iqmux61AudioMonitorLowLevel
				INTEGER,
			iqmux61AudioMonitorHighLevel
				INTEGER,
			iqmux61AudioMonitorOverloadLevel
				INTEGER,
			iqmux61AudioMonitorWarningTimer
				INTEGER,
			iqmux61Freeze
				INTEGER,
			iqmux61VideoDelay
				INTEGER,
			iqmux61VideoDelayDelayPhase625HPhase
				INTEGER,
			iqmux61VideoDelayDelayPhase625VPhase
				INTEGER,
			iqmux61VideoDelayDelayPhase525HPhase
				INTEGER,
			iqmux61VideoDelayDelayPhase525VPhase
				INTEGER,
			iqmux61UserMemMemory1Save1
				INTEGER,
			iqmux61UserMemMemory1Recall1
				INTEGER,
			iqmux61UserMemMemory1Clear1
				INTEGER,
			iqmux61UserMemMemory1Name1
				RollCallString,
			iqmux61UserMemMemory2Save2
				INTEGER,
			iqmux61UserMemMemory2Recall2
				INTEGER,
			iqmux61UserMemMemory2Clear2
				INTEGER,
			iqmux61UserMemMemory2Name2
				RollCallString,
			iqmux61UserMemMemory3Save3
				INTEGER,
			iqmux61UserMemMemory3Recall3
				INTEGER,
			iqmux61UserMemMemory3Clear3
				INTEGER,
			iqmux61UserMemMemory3Name3
				RollCallString,
			iqmux61UserMemMemory4Save4
				INTEGER,
			iqmux61UserMemMemory4Recall4
				INTEGER,
			iqmux61UserMemMemory4Clear4
				INTEGER,
			iqmux61UserMemMemory4Name4
				RollCallString,
			iqmux61UserMemMemory5Save5
				INTEGER,
			iqmux61UserMemMemory5Recall5
				INTEGER,
			iqmux61UserMemMemory5Clear5
				INTEGER,
			iqmux61UserMemMemory5Name5
				RollCallString,
			iqmux61UserMemMemory6Save6
				INTEGER,
			iqmux61UserMemMemory6Recall6
				INTEGER,
			iqmux61UserMemMemory6Clear6
				INTEGER,
			iqmux61UserMemMemory6Name6
				RollCallString,
			iqmux61UserMemMemory7Save7
				INTEGER,
			iqmux61UserMemMemory7Recall7
				INTEGER,
			iqmux61UserMemMemory7Clear7
				INTEGER,
			iqmux61UserMemMemory7Name7
				RollCallString,
			iqmux61UserMemMemory8Save8
				INTEGER,
			iqmux61UserMemMemory8Recall8
				INTEGER,
			iqmux61UserMemMemory8Clear8
				INTEGER,
			iqmux61UserMemMemory8Name8
				RollCallString,
			iqmux61SetupPatternAnimatedPattern
				INTEGER,
			iqmux61SetupPatternEnablePattern
				INTEGER,
			iqmux61SetupPattern
				INTEGER,
			iqmux61SetupCaptionEditCaption
				RollCallString,
			iqmux61SetupCaption
				INTEGER,
			iqmux61BlankingVIPass525BlankAll
				INTEGER,
			iqmux61BlankingVIPass525PassAll
				INTEGER,
			iqmux61BlankingVIPass525Line11
				INTEGER,
			iqmux61BlankingVIPass525Line274
				INTEGER,
			iqmux61BlankingVIPass525Line12
				INTEGER,
			iqmux61BlankingVIPass525Line275
				INTEGER,
			iqmux61BlankingVIPass525Line13
				INTEGER,
			iqmux61BlankingVIPass525Line276
				INTEGER,
			iqmux61BlankingVIPass525Line14
				INTEGER,
			iqmux61BlankingVIPass525Line277
				INTEGER,
			iqmux61BlankingVIPass525Line15
				INTEGER,
			iqmux61BlankingVIPass525Line278
				INTEGER,
			iqmux61BlankingVIPass525Line16
				INTEGER,
			iqmux61BlankingVIPass525Line279
				INTEGER,
			iqmux61BlankingVIPass525Line17
				INTEGER,
			iqmux61BlankingVIPass525Line280
				INTEGER,
			iqmux61BlankingVIPass525Line18
				INTEGER,
			iqmux61BlankingVIPass525Line281
				INTEGER,
			iqmux61BlankingVIPass525Line19
				INTEGER,
			iqmux61BlankingVIPass525Line282
				INTEGER,
			iqmux61BlankingVIPass525Line20
				INTEGER,
			iqmux61BlankingVIPass525Line283
				INTEGER,
			iqmux61BlankingVIPass525Line21
				INTEGER,
			iqmux61BlankingVIPass625BlankAll
				INTEGER,
			iqmux61BlankingVIPass625PassAll
				INTEGER,
			iqmux61BlankingVIPass625Line7
				INTEGER,
			iqmux61BlankingVIPass625Line320
				INTEGER,
			iqmux61BlankingVIPass625Line8
				INTEGER,
			iqmux61BlankingVIPass625Line321
				INTEGER,
			iqmux61BlankingVIPass625Line9
				INTEGER,
			iqmux61BlankingVIPass625Line322
				INTEGER,
			iqmux61BlankingVIPass625Line10
				INTEGER,
			iqmux61BlankingVIPass625Line323
				INTEGER,
			iqmux61BlankingVIPass625Line11
				INTEGER,
			iqmux61BlankingVIPass625Line324
				INTEGER,
			iqmux61BlankingVIPass625Line12
				INTEGER,
			iqmux61BlankingVIPass625Line325
				INTEGER,
			iqmux61BlankingVIPass625Line13
				INTEGER,
			iqmux61BlankingVIPass625Line326
				INTEGER,
			iqmux61BlankingVIPass625Line14
				INTEGER,
			iqmux61BlankingVIPass625Line327
				INTEGER,
			iqmux61BlankingVIPass625Line15
				INTEGER,
			iqmux61BlankingVIPass625Line328
				INTEGER,
			iqmux61BlankingVIPass625Line16
				INTEGER,
			iqmux61BlankingVIPass625Line329
				INTEGER,
			iqmux61BlankingVIPass625Line17
				INTEGER,
			iqmux61BlankingVIPass625Line330
				INTEGER,
			iqmux61BlankingVIPass625Line18
				INTEGER,
			iqmux61BlankingVIPass625Line331
				INTEGER,
			iqmux61BlankingVIPass625Line19
				INTEGER,
			iqmux61BlankingVIPass625Line332
				INTEGER,
			iqmux61BlankingVIPass625Line20
				INTEGER,
			iqmux61BlankingVIPass625Line333
				INTEGER,
			iqmux61BlankingVIPass625Line21
				INTEGER,
			iqmux61BlankingVIPass625Line334
				INTEGER,
			iqmux61BlankingVIPass625Line22
				INTEGER,
			iqmux61BlankingVIPass625Line335
				INTEGER,
			iqmux61BlankingVIPass625Line23
				INTEGER,
			iqmux61SetupBlankingHancBlank
				INTEGER,
			iqmux61SetupAudioToneIdentEnable
				INTEGER,
			iqmux61SetupAudioToneFrequency
				INTEGER,
			iqmux61SetupAudioToneFrequencyR
				INTEGER,
			iqmux61SetupAudioToneHeadRoom
				INTEGER,
			iqmux61SetupAudioToneADCLineUp
				INTEGER,
			iqmux61SetupSlewRate
				INTEGER,
			iqmux61SetupChannelStatus
				RollCallString,
			iqmux61GPIIOGPIInputDisableInputs
				INTEGER,
			iqmux61GPIIOGPIInputInputTimerEnable
				INTEGER,
			iqmux61GPIIOGPIInputTimerActiveHigh
				INTEGER,
			iqmux61GPIIOGPIInputInputSelection
				INTEGER,
			iqmux61GPIIOGPIInputGPIInStatus
				RollCallString,
			iqmux61GPIIOGPIOutputOutActiveHigh
				INTEGER,
			iqmux61GPIIOGPIOutputOutputSelection
				INTEGER,
			iqmux61GPIIOGPIOutputGPIOutStatus
				RollCallString,
			iqmux61GPIIOGPIInputOutputGPIO1
				INTEGER,
			iqmux61SetupGPIIOInputSelection
				INTEGER,
			iqmux61SetupGPIIOOutputSelection
				INTEGER,
			iqmux61SetupRollTrackRollTrackIndex
				INTEGER,
			iqmux61SetupRollTrackRollTrackSource
				INTEGER,
			iqmux61SetupRollTrackRollTrackDisable
				INTEGER,
			iqmux61SetupRollTrackRollTrackAddress
				RollCallString,
			iqmux61SetupRollTrackRollTrackCommand
				RollCallString,
			iqmux61SetupRollTrackRollTrackSending
				RollCallString,
			iqmux61SetupRollTrackRollTrackStatus
				RollCallString,
			iqmux61SetupRollTrackRollTrackIndexExt
				INTEGER,
			iqmux61SetupRollTrackRollTrackSourceExt
				INTEGER,
			iqmux61SetupRollTrackRollTrackAddressExt
				RollCallString,
			iqmux61SetupRollTrackRollTrackCommandExt
				RollCallString,
			iqmux61SetupLoggingInput
				INTEGER,
			iqmux61SetupLoggingStd
				INTEGER,
			iqmux61SetupLoggingInput1
				INTEGER,
			iqmux61SetupLoggingStd1
				INTEGER,
			iqmux61SetupLoggingInput2
				INTEGER,
			iqmux61SetupLoggingStd2
				INTEGER,
			iqmux61SetupLoggingEDH
				INTEGER,
			iqmux61SetupLoggingEDHErrors
				INTEGER,
			iqmux61SetupLoggingRollTrack
				INTEGER,
			iqmux61SetupLoggingDeembed1
				INTEGER,
			iqmux61SetupLoggingDeembed2
				INTEGER,
			iqmux61SetupLoggingDeembed3
				INTEGER,
			iqmux61SetupLoggingDeembed4
				INTEGER,
			iqmux61SetupLoggingDeembed5
				INTEGER,
			iqmux61SetupLoggingDeembed6
				INTEGER,
			iqmux61SetupLoggingDeembed7
				INTEGER,
			iqmux61SetupLoggingDeembed8
				INTEGER,
			iqmux61SetupLoggingnPCM1
				INTEGER,
			iqmux61SetupLoggingnPCM2
				INTEGER,
			iqmux61SetupLoggingnPCM3
				INTEGER,
			iqmux61SetupLoggingnPCM4
				INTEGER,
			iqmux61SetupLoggingnPCM5
				INTEGER,
			iqmux61SetupLoggingnPCM6
				INTEGER,
			iqmux61SetupLoggingnPCM7
				INTEGER,
			iqmux61SetupLoggingnPCM8
				INTEGER,
			iqmux61SetupLoggingAES1
				INTEGER,
			iqmux61SetupLoggingAES2
				INTEGER,
			iqmux61SetupLoggingBusAL
				INTEGER,
			iqmux61SetupLoggingBusAR
				INTEGER,
			iqmux61SetupLoggingBusBL
				INTEGER,
			iqmux61SetupLoggingBusBR
				INTEGER,
			iqmux61SetupLoggingBusCL
				INTEGER,
			iqmux61SetupLoggingBusCR
				INTEGER,
			iqmux61SetupLoggingBusDL
				INTEGER,
			iqmux61SetupLoggingBusDR
				INTEGER,
			iqmux61SetupLoggingFault
				INTEGER,
			iqmux61SetupLoggingStatusINPUT
				RollCallString,
			iqmux61SetupLoggingStatusSTD
				RollCallString,
			iqmux61SetupLoggingStatusINPUT1
				RollCallString,
			iqmux61SetupLoggingStatusSTD1
				RollCallString,
			iqmux61SetupLoggingStatusINPUT2
				RollCallString,
			iqmux61SetupLoggingStatusSTD2
				RollCallString,
			iqmux61SetupLoggingStatusEDH
				RollCallString,
			iqmux61SetupLoggingStatusERRSEC
				RollCallString,
			iqmux61SetupLoggingStatusROLLTRACK
				RollCallString,
			iqmux61SetupLoggingStatusDEEMBED1
				RollCallString,
			iqmux61SetupLoggingStatusDEEMBED2
				RollCallString,
			iqmux61SetupLoggingStatusDEEMBED3
				RollCallString,
			iqmux61SetupLoggingStatusDEEMBED4
				RollCallString,
			iqmux61SetupLoggingStatusDEEMBED5
				RollCallString,
			iqmux61SetupLoggingStatusDEEMBED6
				RollCallString,
			iqmux61SetupLoggingStatusDEEMBED7
				RollCallString,
			iqmux61SetupLoggingStatusDEEMBED8
				RollCallString,
			iqmux61SetupLoggingStatusNPCM1
				RollCallString,
			iqmux61SetupLoggingStatusNPCM2
				RollCallString,
			iqmux61SetupLoggingStatusNPCM3
				RollCallString,
			iqmux61SetupLoggingStatusNPCM4
				RollCallString,
			iqmux61SetupLoggingStatusNPCM5
				RollCallString,
			iqmux61SetupLoggingStatusNPCM6
				RollCallString,
			iqmux61SetupLoggingStatusNPCM7
				RollCallString,
			iqmux61SetupLoggingStatusNPCM8
				RollCallString,
			iqmux61SetupLoggingStatusAES1
				RollCallString,
			iqmux61SetupLoggingStatusAES2
				RollCallString,
			iqmux61SetupLoggingStatusBUSAL
				RollCallString,
			iqmux61SetupLoggingStatusBUSAR
				RollCallString,
			iqmux61SetupLoggingStatusBUSBL
				RollCallString,
			iqmux61SetupLoggingStatusBUSBR
				RollCallString,
			iqmux61SetupLoggingStatusBUSCL
				RollCallString,
			iqmux61SetupLoggingStatusBUSCR
				RollCallString,
			iqmux61SetupLoggingStatusBUSDL
				RollCallString,
			iqmux61SetupLoggingStatusBUSDR
				RollCallString,
			iqmux61SetupLoggingStatusFAULT
				RollCallString,
			iqmux61SetupInformationWindow
				INTEGER,
			iqmux61SetupInformationWindowResetErrors
				INTEGER,
			iqmux61SetupDefaultOutput
				INTEGER,
			iqmux61SetupDefaultPattern
				INTEGER,
			iqmux61SetupUnitSoftwareVersion
				RollCallString,
			iqmux61SetupUnitSerialNo
				RollCallString,
			iqmux61SetupUnitPresetUnit
				INTEGER,
			iqmux61SetupUnitRestart
				INTEGER,
			iqmux61SetupUnitBuildNo
				RollCallString
		}

	iqmux61SlotIndex OBJECT-TYPE
		SYNTAX		Unsigned32
		MAX-ACCESS		not-accessible
		STATUS			current
		DESCRIPTION
				"The unique Index value for each slot.  Its value
					ranges between 1 and the value of slotNumber."
		::= { iqmux61CmdEntry 0 }


	iqmux61VideoInput OBJECT-TYPE
		SYNTAX		INTEGER {
							val_Input_1_SDI(0),
							val_Input_2_SDI(1)
							}
		MAX-ACCESS		read-write
		STATUS			current
		DESCRIPTION
				"TYPE: - Button
				 PAGE: - Video- Input
					input 1 SDI  cmdID= 2251  value= 0
					input 2 SDI  cmdID= 2251  value= 1  "
		::= { iqmux61CmdEntry 2251 }


	iqmux61VideoInput525 OBJECT-TYPE
		SYNTAX		INTEGER { disable(0), enable(1) }
		MAX-ACCESS		read-write
		STATUS			current
		DESCRIPTION
				"TYPE: - Checkbox
				 PAGE: - Video- Input
					525  cmdID= 1405 "
		::= { iqmux61CmdEntry 1405 }


	iqmux61VideoInput625 OBJECT-TYPE
		SYNTAX		INTEGER { disable(0), enable(1) }
		MAX-ACCESS		read-write
		STATUS			current
		DESCRIPTION
				"TYPE: - Checkbox
				 PAGE: - Video- Input
					625  cmdID= 1406 "
		::= { iqmux61CmdEntry 1406 }


	iqmux61VideoProcAmp1In1ProcAmpEnable OBJECT-TYPE
		SYNTAX		INTEGER { disable(0), enable(1) }
		MAX-ACCESS		read-write
		STATUS			current
		DESCRIPTION
				"TYPE: - Checkbox
				 PAGE: - Video- ProcAmp 1
					In1 ProcAmp Enable  cmdID= 2864 "
		::= { iqmux61CmdEntry 2864 }


	iqmux61VideoProcAmp1LumaGain OBJECT-TYPE
		SYNTAX		INTEGER
		MAX-ACCESS		read-write
		STATUS			current
		DESCRIPTION
				"TYPE: - Number
				 PAGE: - Video- ProcAmp 1
					Luma Gain  cmdID= 2707  min= -60  max= 60  step= 1  format= %1.1f dB  div_scale= 10
					Min = -6.0 dB  Max = 6.0 dB  Step = 0.1 dB "
		::= { iqmux61CmdEntry 2707 }


	iqmux61VideoProcAmp1ChromaGain OBJECT-TYPE
		SYNTAX		INTEGER
		MAX-ACCESS		read-write
		STATUS			current
		DESCRIPTION
				"TYPE: - Number
				 PAGE: - Video- ProcAmp 1
					Chroma Gain  cmdID= 2706  min= -60  max= 60  step= 1  format= %1.1f dB  div_scale= 10
					Min = -6.0 dB  Max = 6.0 dB  Step = 0.1 dB "
		::= { iqmux61CmdEntry 2706 }


	iqmux61VideoProcAmp1BlackLevel OBJECT-TYPE
		SYNTAX		INTEGER
		MAX-ACCESS		read-write
		STATUS			current
		DESCRIPTION
				"TYPE: - Number
				 PAGE: - Video- ProcAmp 1
					Black Level  cmdID= 2708  min= -1000  max= 1000  step= 8  format= %1.1f mV  div_scale= 10
					Min = -100.0 mV  Max = 100.0 mV  Step = 0.8 mV "
		::= { iqmux61CmdEntry 2708 }


	iqmux61VideoProcAmp1PicturePosition OBJECT-TYPE
		SYNTAX		INTEGER
		MAX-ACCESS		read-write
		STATUS			current
		DESCRIPTION
				"TYPE: - Number
				 PAGE: - Video- ProcAmp 1
					Picture Position  cmdID= 2709  min= -592  max= 592  step= 148  format= %3.0f ns  div_scale= 1
					Min = -592 ns  Max = 592 ns  Step = 148 ns "
		::= { iqmux61CmdEntry 2709 }


	iqmux61VideoProcAmp1YCTiming OBJECT-TYPE
		SYNTAX		INTEGER
		MAX-ACCESS		read-write
		STATUS			current
		DESCRIPTION
				"TYPE: - Number
				 PAGE: - Video- ProcAmp 1
					Y/C Timing  cmdID= 2924  min= -592  max= 592  step= 148  format= %3.0fns  div_scale= 1
					Min = -592ns  Max = 592ns  Step = 148ns "
		::= { iqmux61CmdEntry 2924 }


	iqmux61VideoProcAmp2In2ProcAmpEnable OBJECT-TYPE
		SYNTAX		INTEGER { disable(0), enable(1) }
		MAX-ACCESS		read-write
		STATUS			current
		DESCRIPTION
				"TYPE: - Checkbox
				 PAGE: - Video- ProcAmp 2
					In2 ProcAmp Enable  cmdID= 2865 "
		::= { iqmux61CmdEntry 2865 }


	iqmux61VideoProcAmp2LumaGain OBJECT-TYPE
		SYNTAX		INTEGER
		MAX-ACCESS		read-write
		STATUS			current
		DESCRIPTION
				"TYPE: - Number
				 PAGE: - Video- ProcAmp 2
					Luma Gain  cmdID= 2711  min= -60  max= 60  step= 1  format= %1.1f dB  div_scale= 10
					Min = -6.0 dB  Max = 6.0 dB  Step = 0.1 dB "
		::= { iqmux61CmdEntry 2711 }


	iqmux61VideoProcAmp2ChromaGain OBJECT-TYPE
		SYNTAX		INTEGER
		MAX-ACCESS		read-write
		STATUS			current
		DESCRIPTION
				"TYPE: - Number
				 PAGE: - Video- ProcAmp 2
					Chroma Gain  cmdID= 2710  min= -60  max= 60  step= 1  format= %1.1f dB  div_scale= 10
					Min = -6.0 dB  Max = 6.0 dB  Step = 0.1 dB "
		::= { iqmux61CmdEntry 2710 }


	iqmux61VideoProcAmp2BlackLevel OBJECT-TYPE
		SYNTAX		INTEGER
		MAX-ACCESS		read-write
		STATUS			current
		DESCRIPTION
				"TYPE: - Number
				 PAGE: - Video- ProcAmp 2
					Black Level  cmdID= 2712  min= -1000  max= 1000  step= 8  format= %1.1f mV  div_scale= 10
					Min = -100.0 mV  Max = 100.0 mV  Step = 0.8 mV "
		::= { iqmux61CmdEntry 2712 }


	iqmux61VideoProcAmp2PicturePosition OBJECT-TYPE
		SYNTAX		INTEGER
		MAX-ACCESS		read-write
		STATUS			current
		DESCRIPTION
				"TYPE: - Number
				 PAGE: - Video- ProcAmp 2
					Picture Position  cmdID= 2713  min= -592  max= 592  step= 148  format= %3.0f ns  div_scale= 1
					Min = -592 ns  Max = 592 ns  Step = 148 ns "
		::= { iqmux61CmdEntry 2713 }


	iqmux61VideoProcAmp2YCTiming OBJECT-TYPE
		SYNTAX		INTEGER
		MAX-ACCESS		read-write
		STATUS			current
		DESCRIPTION
				"TYPE: - Number
				 PAGE: - Video- ProcAmp 2
					Y/C Timing  cmdID= 2925  min= -592  max= 592  step= 148  format= %3.0fns  div_scale= 1
					Min = -592ns  Max = 592ns  Step = 148ns "
		::= { iqmux61CmdEntry 2925 }


	iqmux61AudioDeembed OBJECT-TYPE
		SYNTAX		INTEGER {
							val_Input_1_SDI(0),
							val_Input_2_SDI(1),
							val_Follow_Video(2)
							}
		MAX-ACCESS		read-write
		STATUS			current
		DESCRIPTION
				"TYPE: - Button
				 PAGE: - Audio- De-embed
					input 1 SDI  cmdID= 2923  value= 0
					input 2 SDI  cmdID= 2923  value= 1
					follow Video  cmdID= 2923  value= 2  "
		::= { iqmux61CmdEntry 2923 }


	iqmux61AudioAESOutputAES1Source OBJECT-TYPE
		SYNTAX		INTEGER {
							val_BUS_A(0),
							val_BUS_B(1),
							val_BUS_C(2),
							val_BUS_D(3),
							val_AES_1_Direct(4),
							val_AES_2_Direct(5),
							val_DeEmbed_1(6),
							val_DeEmbed_2(7),
							val_DeEmbed_3(8),
							val_DeEmbed_4(9),
							val_DeEmbed_5(10),
							val_DeEmbed_6(11),
							val_DeEmbed_7(12),
							val_DeEmbed_8(13),
							val_Test_tone(14),
							val_Silence(15)
							}
		MAX-ACCESS		read-write
		STATUS			current
		DESCRIPTION
				"TYPE: - RadiobuttonList
				 PAGE: - Audio- AES Output
					AES 1 Source  cmdID= 2951
					bUS A  value= 0
					bUS B  value= 1
					bUS C  value= 2
					bUS D  value= 3
					aES 1 Direct  value= 4
					aES 2 Direct  value= 5
					deEmbed 1  value= 6
					deEmbed 2  value= 7
					deEmbed 3  value= 8
					deEmbed 4  value= 9
					deEmbed 5  value= 10
					deEmbed 6  value= 11
					deEmbed 7  value= 12
					deEmbed 8  value= 13
					test tone  value= 14
					silence  value= 15  "
		::= { iqmux61CmdEntry 2951 }


	iqmux61AudioAESOutputAES2Source OBJECT-TYPE
		SYNTAX		INTEGER {
							val_BUS_A(0),
							val_BUS_B(1),
							val_BUS_C(2),
							val_BUS_D(3),
							val_AES_1_Direct(4),
							val_AES_2_Direct(5),
							val_DeEmbed_1(6),
							val_DeEmbed_2(7),
							val_DeEmbed_3(8),
							val_DeEmbed_4(9),
							val_DeEmbed_5(10),
							val_DeEmbed_6(11),
							val_DeEmbed_7(12),
							val_DeEmbed_8(13),
							val_Test_tone(14),
							val_Silence(15)
							}
		MAX-ACCESS		read-write
		STATUS			current
		DESCRIPTION
				"TYPE: - RadiobuttonList
				 PAGE: - Audio- AES Output
					AES 2 Source  cmdID= 2952
					bUS A  value= 0
					bUS B  value= 1
					bUS C  value= 2
					bUS D  value= 3
					aES 1 Direct  value= 4
					aES 2 Direct  value= 5
					deEmbed 1  value= 6
					deEmbed 2  value= 7
					deEmbed 3  value= 8
					deEmbed 4  value= 9
					deEmbed 5  value= 10
					deEmbed 6  value= 11
					deEmbed 7  value= 12
					deEmbed 8  value= 13
					test tone  value= 14
					silence  value= 15  "
		::= { iqmux61CmdEntry 2952 }


	iqmux61AudioProcAmpDeembedStereo1 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqmux61CmdEntry 3324 }


	iqmux61ProcAmpDeembed1LGainDeembed1L OBJECT-TYPE
		SYNTAX		INTEGER
		MAX-ACCESS		read-write
		STATUS			current
		DESCRIPTION
				"TYPE: - Number
				 PAGE: - Audio- ProcAmp
					Gain De-embed 1L  cmdID= 3088  min= -180  max= 180  step= 1  format= %0.1fdB  div_scale= 10
					Min = -18.0dB  Max = 18.0dB  Step = 0.1dB "
		::= { iqmux61CmdEntry 3088 }


	iqmux61ProcAmpDeembed1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqmux61CmdEntry 3168 }


	iqmux61ProcAmpDeembed1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqmux61CmdEntry 3248 }


	iqmux61ProcAmpDeembed1RGainDeembed1R OBJECT-TYPE
		SYNTAX		INTEGER
		MAX-ACCESS		read-write
		STATUS			current
		DESCRIPTION
				"TYPE: - Number
				 PAGE: - Audio- ProcAmp
					Gain De-embed 1R  cmdID= 3089  min= -180  max= 180  step= 1  format= %0.1fdB  div_scale= 10
					Min = -18.0dB  Max = 18.0dB  Step = 0.1dB "
		::= { iqmux61CmdEntry 3089 }


	iqmux61ProcAmpDeembed1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqmux61CmdEntry 3169 }


	iqmux61ProcAmpDeembed1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqmux61CmdEntry 3249 }


	iqmux61AudioProcAmpDeembedStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqmux61CmdEntry 3325 }


	iqmux61ProcAmpDeembed2LGainDeembed2L OBJECT-TYPE
		SYNTAX		INTEGER
		MAX-ACCESS		read-write
		STATUS			current
		DESCRIPTION
				"TYPE: - Number
				 PAGE: - Audio- ProcAmp
					Gain De-embed 2L  cmdID= 3090  min= -180  max= 180  step= 1  format= %0.1fdB  div_scale= 10
					Min = -18.0dB  Max = 18.0dB  Step = 0.1dB "
		::= { iqmux61CmdEntry 3090 }


	iqmux61ProcAmpDeembed2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqmux61CmdEntry 3170 }


	iqmux61ProcAmpDeembed2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqmux61CmdEntry 3250 }


	iqmux61ProcAmpDeembed2RGainDeembed2R OBJECT-TYPE
		SYNTAX		INTEGER
		MAX-ACCESS		read-write
		STATUS			current
		DESCRIPTION
				"TYPE: - Number
				 PAGE: - Audio- ProcAmp
					Gain De-embed 2R  cmdID= 3091  min= -180  max= 180  step= 1  format= %0.1fdB  div_scale= 10
					Min = -18.0dB  Max = 18.0dB  Step = 0.1dB "
		::= { iqmux61CmdEntry 3091 }


	iqmux61ProcAmpDeembed2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqmux61CmdEntry 3171 }


	iqmux61ProcAmpDeembed2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqmux61CmdEntry 3251 }


	iqmux61AudioProcAmpDeembedStereo3 OBJECT-TYPE
		SYNTAX		INTEGER { disable(0), enable(1) }
		MAX-ACCESS		read-write
		STATUS			current
		DESCRIPTION
				"TYPE: - Checkbox
				 PAGE: - Audio- ProcAmp
					Stereo 3  cmdID= 3326 "
		::= { iqmux61CmdEntry 3326 }


	iqmux61ProcAmpDeembed3LGainDeembed3L OBJECT-TYPE
		SYNTAX		INTEGER
		MAX-ACCESS		read-write
		STATUS			current
		DESCRIPTION
				"TYPE: - Number
				 PAGE: - Audio- ProcAmp
					Gain De-embed 3L  cmdID= 3092  min= -180  max= 180  step= 1  format= %0.1fdB  div_scale= 10
					Min = -18.0dB  Max = 18.0dB  Step = 0.1dB "
		::= { iqmux61CmdEntry 3092 }


	iqmux61ProcAmpDeembed3LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqmux61CmdEntry 3172 }


	iqmux61ProcAmpDeembed3LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqmux61CmdEntry 3252 }


	iqmux61ProcAmpDeembed3RGainDeembed3R OBJECT-TYPE
		SYNTAX		INTEGER
		MAX-ACCESS		read-write
		STATUS			current
		DESCRIPTION
				"TYPE: - Number
				 PAGE: - Audio- ProcAmp
					Gain De-embed 3R  cmdID= 3093  min= -180  max= 180  step= 1  format= %0.1fdB  div_scale= 10
					Min = -18.0dB  Max = 18.0dB  Step = 0.1dB "
		::= { iqmux61CmdEntry 3093 }


	iqmux61ProcAmpDeembed3RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqmux61CmdEntry 3173 }


	iqmux61ProcAmpDeembed3RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqmux61CmdEntry 3253 }


	iqmux61AudioProcAmpDeembedStereo4 OBJECT-TYPE
		SYNTAX		INTEGER { disable(0), enable(1) }
		MAX-ACCESS		read-write
		STATUS			current
		DESCRIPTION
				"TYPE: - Checkbox
				 PAGE: - Audio- ProcAmp
					Stereo 4  cmdID= 3327 "
		::= { iqmux61CmdEntry 3327 }


	iqmux61ProcAmpDeembed4LGainDeembed4L OBJECT-TYPE
		SYNTAX		INTEGER
		MAX-ACCESS		read-write
		STATUS			current
		DESCRIPTION
				"TYPE: - Number
				 PAGE: - Audio- ProcAmp
					Gain De-embed 4L  cmdID= 3094  min= -180  max= 180  step= 1  format= %0.1fdB  div_scale= 10
					Min = -18.0dB  Max = 18.0dB  Step = 0.1dB "
		::= { iqmux61CmdEntry 3094 }


	iqmux61ProcAmpDeembed4LInvert OBJECT-TYPE
		SYNTAX		INTEGER { disable(0), enable(1) }
		MAX-ACCESS		read-write
		STATUS			current
		DESCRIPTION
				"TYPE: - Checkbox
				 PAGE: - Audio- ProcAmp
					Invert  cmdID= 3174 "
		::= { iqmux61CmdEntry 3174 }


	iqmux61ProcAmpDeembed4LMute OBJECT-TYPE
		SYNTAX		INTEGER { disable(0), enable(1) }
		MAX-ACCESS		read-write
		STATUS			current
		DESCRIPTION
				"TYPE: - Checkbox
				 PAGE: - Audio- ProcAmp
					Mute  cmdID= 3254 "
		::= { iqmux61CmdEntry 3254 }


	iqmux61ProcAmpDeembed4RGainDeembed4R OBJECT-TYPE
		SYNTAX		INTEGER
		MAX-ACCESS		read-write
		STATUS			current
		DESCRIPTION
				"TYPE: - Number
				 PAGE: - Audio- ProcAmp
					Gain De-embed 4R  cmdID= 3095  min= -180  max= 180  step= 1  format= %0.1fdB  div_scale= 10
					Min = -18.0dB  Max = 18.0dB  Step = 0.1dB "
		::= { iqmux61CmdEntry 3095 }


	iqmux61ProcAmpDeembed4RInvert OBJECT-TYPE
		SYNTAX		INTEGER { disable(0), enable(1) }
		MAX-ACCESS		read-write
		STATUS			current
		DESCRIPTION
				"TYPE: - Checkbox
				 PAGE: - Audio- ProcAmp
					Invert  cmdID= 3175 "
		::= { iqmux61CmdEntry 3175 }


	iqmux61ProcAmpDeembed4RMute OBJECT-TYPE
		SYNTAX		INTEGER { disable(0), enable(1) }
		MAX-ACCESS		read-write
		STATUS			current
		DESCRIPTION
				"TYPE: - Checkbox
				 PAGE: - Audio- ProcAmp
					Mute  cmdID= 3255 "
		::= { iqmux61CmdEntry 3255 }


	iqmux61AudioProcAmpDeembedStereo5 OBJECT-TYPE
		SYNTAX		INTEGER { disable(0), enable(1) }
		MAX-ACCESS		read-write
		STATUS			current
		DESCRIPTION
				"TYPE: - Checkbox
				 PAGE: - Audio- ProcAmp
					Stereo 5  cmdID= 3328 "
		::= { iqmux61CmdEntry 3328 }


	iqmux61ProcAmpDeembed5LGainDeembed5L OBJECT-TYPE
		SYNTAX		INTEGER
		MAX-ACCESS		read-write
		STATUS			current
		DESCRIPTION
				"TYPE: - Number
				 PAGE: - Audio- ProcAmp
					Gain De-embed 5L  cmdID= 3096  min= -180  max= 180  step= 1  format= %0.1fdB  div_scale= 10
					Min = -18.0dB  Max = 18.0dB  Step = 0.1dB "
		::= { iqmux61CmdEntry 3096 }


	iqmux61ProcAmpDeembed5LInvert OBJECT-TYPE
		SYNTAX		INTEGER { disable(0), enable(1) }
		MAX-ACCESS		read-write
		STATUS			current
		DESCRIPTION
				"TYPE: - Checkbox
				 PAGE: - Audio- ProcAmp
					Invert  cmdID= 3176 "
		::= { iqmux61CmdEntry 3176 }


	iqmux61ProcAmpDeembed5LMute OBJECT-TYPE
		SYNTAX		INTEGER { disable(0), enable(1) }
		MAX-ACCESS		read-write
		STATUS			current
		DESCRIPTION
				"TYPE: - Checkbox
				 PAGE: - Audio- ProcAmp
					Mute  cmdID= 3256 "
		::= { iqmux61CmdEntry 3256 }


	iqmux61ProcAmpDeembed5RGainDeembed5R OBJECT-TYPE
		SYNTAX		INTEGER
		MAX-ACCESS		read-write
		STATUS			current
		DESCRIPTION
				"TYPE: - Number
				 PAGE: - Audio- ProcAmp
					Gain De-embed 5R  cmdID= 3097  min= -180  max= 180  step= 1  format= %0.1fdB  div_scale= 10
					Min = -18.0dB  Max = 18.0dB  Step = 0.1dB "
		::= { iqmux61CmdEntry 3097 }


	iqmux61ProcAmpDeembed5RInvert OBJECT-TYPE
		SYNTAX		INTEGER { disable(0), enable(1) }
		MAX-ACCESS		read-write
		STATUS			current
		DESCRIPTION
				"TYPE: - Checkbox
				 PAGE: - Audio- ProcAmp
					Invert  cmdID= 3177 "
		::= { iqmux61CmdEntry 3177 }


	iqmux61ProcAmpDeembed5RMute OBJECT-TYPE
		SYNTAX		INTEGER { disable(0), enable(1) }
		MAX-ACCESS		read-write
		STATUS			current
		DESCRIPTION
				"TYPE: - Checkbox
				 PAGE: - Audio- ProcAmp
					Mute  cmdID= 3257 "
		::= { iqmux61CmdEntry 3257 }


	iqmux61AudioProcAmpDeembedStereo6 OBJECT-TYPE
		SYNTAX		INTEGER { disable(0), enable(1) }
		MAX-ACCESS		read-write
		STATUS			current
		DESCRIPTION
				"TYPE: - Checkbox
				 PAGE: - Audio- ProcAmp
					Stereo 6  cmdID= 3329 "
		::= { iqmux61CmdEntry 3329 }


	iqmux61ProcAmpDeembed6LGainDeembed6L OBJECT-TYPE
		SYNTAX		INTEGER
		MAX-ACCESS		read-write
		STATUS			current
		DESCRIPTION
				"TYPE: - Number
				 PAGE: - Audio- ProcAmp
					Gain De-embed 6L  cmdID= 3098  min= -180  max= 180  step= 1  format= %0.1fdB  div_scale= 10
					Min = -18.0dB  Max = 18.0dB  Step = 0.1dB "
		::= { iqmux61CmdEntry 3098 }


	iqmux61ProcAmpDeembed6LInvert OBJECT-TYPE
		SYNTAX		INTEGER { disable(0), enable(1) }
		MAX-ACCESS		read-write
		STATUS			current
		DESCRIPTION
				"TYPE: - Checkbox
				 PAGE: - Audio- ProcAmp
					Invert  cmdID= 3178 "
		::= { iqmux61CmdEntry 3178 }


	iqmux61ProcAmpDeembed6LMute OBJECT-TYPE
		SYNTAX		INTEGER { disable(0), enable(1) }
		MAX-ACCESS		read-write
		STATUS			current
		DESCRIPTION
				"TYPE: - Checkbox
				 PAGE: - Audio- ProcAmp
					Mute  cmdID= 3258 "
		::= { iqmux61CmdEntry 3258 }


	iqmux61ProcAmpDeembed6RGainDeembed6R OBJECT-TYPE
		SYNTAX		INTEGER
		MAX-ACCESS		read-write
		STATUS			current
		DESCRIPTION
				"TYPE: - Number
				 PAGE: - Audio- ProcAmp
					Gain De-embed 6R  cmdID= 3099  min= -180  max= 180  step= 1  format= %0.1fdB  div_scale= 10
					Min = -18.0dB  Max = 18.0dB  Step = 0.1dB "
		::= { iqmux61CmdEntry 3099 }


	iqmux61ProcAmpDeembed6RInvert OBJECT-TYPE
		SYNTAX		INTEGER { disable(0), enable(1) }
		MAX-ACCESS		read-write
		STATUS			current
		DESCRIPTION
				"TYPE: - Checkbox
				 PAGE: - Audio- ProcAmp
					Invert  cmdID= 3179 "
		::= { iqmux61CmdEntry 3179 }


	iqmux61ProcAmpDeembed6RMute OBJECT-TYPE
		SYNTAX		INTEGER { disable(0), enable(1) }
		MAX-ACCESS		read-write
		STATUS			current
		DESCRIPTION
				"TYPE: - Checkbox
				 PAGE: - Audio- ProcAmp
					Mute  cmdID= 3259 "
		::= { iqmux61CmdEntry 3259 }


	iqmux61AudioProcAmpDeembedStereo7 OBJECT-TYPE
		SYNTAX		INTEGER { disable(0), enable(1) }
		MAX-ACCESS		read-write
		STATUS			current
		DESCRIPTION
				"TYPE: - Checkbox
				 PAGE: - Audio- ProcAmp
					Stereo 7  cmdID= 3330 "
		::= { iqmux61CmdEntry 3330 }


	iqmux61ProcAmpDeembed7LGainDeembed7L OBJECT-TYPE
		SYNTAX		INTEGER
		MAX-ACCESS		read-write
		STATUS			current
		DESCRIPTION
				"TYPE: - Number
				 PAGE: - Audio- ProcAmp
					Gain De-embed 7L  cmdID= 3100  min= -180  max= 180  step= 1  format= %0.1fdB  div_scale= 10
					Min = -18.0dB  Max = 18.0dB  Step = 0.1dB "
		::= { iqmux61CmdEntry 3100 }


	iqmux61ProcAmpDeembed7LInvert OBJECT-TYPE
		SYNTAX		INTEGER { disable(0), enable(1) }
		MAX-ACCESS		read-write
		STATUS			current
		DESCRIPTION
				"TYPE: - Checkbox
				 PAGE: - Audio- ProcAmp
					Invert  cmdID= 3180 "
		::= { iqmux61CmdEntry 3180 }


	iqmux61ProcAmpDeembed7LMute OBJECT-TYPE
		SYNTAX		INTEGER { disable(0), enable(1) }
		MAX-ACCESS		read-write
		STATUS			current
		DESCRIPTION
				"TYPE: - Checkbox
				 PAGE: - Audio- ProcAmp
					Mute  cmdID= 3260 "
		::= { iqmux61CmdEntry 3260 }


	iqmux61ProcAmpDeembed7RGainDeembed7R OBJECT-TYPE
		SYNTAX		INTEGER
		MAX-ACCESS		read-write
		STATUS			current
		DESCRIPTION
				"TYPE: - Number
				 PAGE: - Audio- ProcAmp
					Gain De-embed 7R  cmdID= 3101  min= -180  max= 180  step= 1  format= %0.1fdB  div_scale= 10
					Min = -18.0dB  Max = 18.0dB  Step = 0.1dB "
		::= { iqmux61CmdEntry 3101 }


	iqmux61ProcAmpDeembed7RInvert OBJECT-TYPE
		SYNTAX		INTEGER { disable(0), enable(1) }
		MAX-ACCESS		read-write
		STATUS			current
		DESCRIPTION
				"TYPE: - Checkbox
				 PAGE: - Audio- ProcAmp
					Invert  cmdID= 3181 "
		::= { iqmux61CmdEntry 3181 }


	iqmux61ProcAmpDeembed7RMute OBJECT-TYPE
		SYNTAX		INTEGER { disable(0), enable(1) }
		MAX-ACCESS		read-write
		STATUS			current
		DESCRIPTION
				"TYPE: - Checkbox
				 PAGE: - Audio- ProcAmp
					Mute  cmdID= 3261 "
		::= { iqmux61CmdEntry 3261 }


	iqmux61AudioProcAmpDeembedStereo8 OBJECT-TYPE
		SYNTAX		INTEGER { disable(0), enable(1) }
		MAX-ACCESS		read-write
		STATUS			current
		DESCRIPTION
				"TYPE: - Checkbox
				 PAGE: - Audio- ProcAmp
					Stereo 8  cmdID= 3331 "
		::= { iqmux61CmdEntry 3331 }


	iqmux61ProcAmpDeembed8LGainDeembed8L OBJECT-TYPE
		SYNTAX		INTEGER
		MAX-ACCESS		read-write
		STATUS			current
		DESCRIPTION
				"TYPE: - Number
				 PAGE: - Audio- ProcAmp
					Gain De-embed 8L  cmdID= 3102  min= -180  max= 180  step= 1  format= %0.1fdB  div_scale= 10
					Min = -18.0dB  Max = 18.0dB  Step = 0.1dB "
		::= { iqmux61CmdEntry 3102 }


	iqmux61ProcAmpDeembed8LInvert OBJECT-TYPE
		SYNTAX		INTEGER { disable(0), enable(1) }
		MAX-ACCESS		read-write
		STATUS			current
		DESCRIPTION
				"TYPE: - Checkbox
				 PAGE: - Audio- ProcAmp
					Invert  cmdID= 3182 "
		::= { iqmux61CmdEntry 3182 }


	iqmux61ProcAmpDeembed8LMute OBJECT-TYPE
		SYNTAX		INTEGER { disable(0), enable(1) }
		MAX-ACCESS		read-write
		STATUS			current
		DESCRIPTION
				"TYPE: - Checkbox
				 PAGE: - Audio- ProcAmp
					Mute  cmdID= 3262 "
		::= { iqmux61CmdEntry 3262 }


	iqmux61ProcAmpDeembed8RGainDeembed8R OBJECT-TYPE
		SYNTAX		INTEGER
		MAX-ACCESS		read-write
		STATUS			current
		DESCRIPTION
				"TYPE: - Number
				 PAGE: - Audio- ProcAmp
					Gain De-embed 8R  cmdID= 3103  min= -180  max= 180  step= 1  format= %0.1fdB  div_scale= 10
					Min = -18.0dB  Max = 18.0dB  Step = 0.1dB "
		::= { iqmux61CmdEntry 3103 }


	iqmux61ProcAmpDeembed8RInvert OBJECT-TYPE
		SYNTAX		INTEGER { disable(0), enable(1) }
		MAX-ACCESS		read-write
		STATUS			current
		DESCRIPTION
				"TYPE: - Checkbox
				 PAGE: - Audio- ProcAmp
					Invert  cmdID= 3183 "
		::= { iqmux61CmdEntry 3183 }


	iqmux61ProcAmpDeembed8RMute OBJECT-TYPE
		SYNTAX		INTEGER { disable(0), enable(1) }
		MAX-ACCESS		read-write
		STATUS			current
		DESCRIPTION
				"TYPE: - Checkbox
				 PAGE: - Audio- ProcAmp
					Mute  cmdID= 3263 "
		::= { iqmux61CmdEntry 3263 }


	iqmux61AudioProcAmpAESStereo1 OBJECT-TYPE
		SYNTAX		INTEGER { disable(0), enable(1) }
		MAX-ACCESS		read-write
		STATUS			current
		DESCRIPTION
				"TYPE: - Checkbox
				 PAGE: - Audio- ProcAmp
					Stereo 1  cmdID= 3332 "
		::= { iqmux61CmdEntry 3332 }


	iqmux61ProcAmpAES1LGainAES1L OBJECT-TYPE
		SYNTAX		INTEGER
		MAX-ACCESS		read-write
		STATUS			current
		DESCRIPTION
				"TYPE: - Number
				 PAGE: - Audio- ProcAmp
					Gain AES 1L  cmdID= 3104  min= -180  max= 180  step= 1  format= %0.1fdB  div_scale= 10
					Min = -18.0dB  Max = 18.0dB  Step = 0.1dB "
		::= { iqmux61CmdEntry 3104 }


	iqmux61ProcAmpAES1LInvert OBJECT-TYPE
		SYNTAX		INTEGER { disable(0), enable(1) }
		MAX-ACCESS		read-write
		STATUS			current
		DESCRIPTION
				"TYPE: - Checkbox
				 PAGE: - Audio- ProcAmp
					Invert  cmdID= 3184 "
		::= { iqmux61CmdEntry 3184 }


	iqmux61ProcAmpAES1LMute OBJECT-TYPE
		SYNTAX		INTEGER { disable(0), enable(1) }
		MAX-ACCESS		read-write
		STATUS			current
		DESCRIPTION
				"TYPE: - Checkbox
				 PAGE: - Audio- ProcAmp
					Mute  cmdID= 3264 "
		::= { iqmux61CmdEntry 3264 }


	iqmux61ProcAmpAES1RGainAES1R OBJECT-TYPE
		SYNTAX		INTEGER
		MAX-ACCESS		read-write
		STATUS			current
		DESCRIPTION
				"TYPE: - Number
				 PAGE: - Audio- ProcAmp
					Gain AES 1R  cmdID= 3105  min= -180  max= 180  step= 1  format= %0.1fdB  div_scale= 10
					Min = -18.0dB  Max = 18.0dB  Step = 0.1dB "
		::= { iqmux61CmdEntry 3105 }


	iqmux61ProcAmpAES1RInvert OBJECT-TYPE
		SYNTAX		INTEGER { disable(0), enable(1) }
		MAX-ACCESS		read-write
		STATUS			current
		DESCRIPTION
				"TYPE: - Checkbox
				 PAGE: - Audio- ProcAmp
					Invert  cmdID= 3185 "
		::= { iqmux61CmdEntry 3185 }


	iqmux61ProcAmpAES1RMute OBJECT-TYPE
		SYNTAX		INTEGER { disable(0), enable(1) }
		MAX-ACCESS		read-write
		STATUS			current
		DESCRIPTION
				"TYPE: - Checkbox
				 PAGE: - Audio- ProcAmp
					Mute  cmdID= 3265 "
		::= { iqmux61CmdEntry 3265 }


	iqmux61AudioProcAmpAESStereo2 OBJECT-TYPE
		SYNTAX		INTEGER { disable(0), enable(1) }
		MAX-ACCESS		read-write
		STATUS			current
		DESCRIPTION
				"TYPE: - Checkbox
				 PAGE: - Audio- ProcAmp
					Stereo 2  cmdID= 3333 "
		::= { iqmux61CmdEntry 3333 }


	iqmux61ProcAmpAES2LGainAES2L OBJECT-TYPE
		SYNTAX		INTEGER
		MAX-ACCESS		read-write
		STATUS			current
		DESCRIPTION
				"TYPE: - Number
				 PAGE: - Audio- ProcAmp
					Gain AES 2L  cmdID= 3106  min= -180  max= 180  step= 1  format= %0.1fdB  div_scale= 10
					Min = -18.0dB  Max = 18.0dB  Step = 0.1dB "
		::= { iqmux61CmdEntry 3106 }


	iqmux61ProcAmpAES2LInvert OBJECT-TYPE
		SYNTAX		INTEGER { disable(0), enable(1) }
		MAX-ACCESS		read-write
		STATUS			current
		DESCRIPTION
				"TYPE: - Checkbox
				 PAGE: - Audio- ProcAmp
					Invert  cmdID= 3186 "
		::= { iqmux61CmdEntry 3186 }


	iqmux61ProcAmpAES2LMute OBJECT-TYPE
		SYNTAX		INTEGER { disable(0), enable(1) }
		MAX-ACCESS		read-write
		STATUS			current
		DESCRIPTION
				"TYPE: - Checkbox
				 PAGE: - Audio- ProcAmp
					Mute  cmdID= 3266 "
		::= { iqmux61CmdEntry 3266 }


	iqmux61ProcAmpAES2RGainAES2R OBJECT-TYPE
		SYNTAX		INTEGER
		MAX-ACCESS		read-write
		STATUS			current
		DESCRIPTION
				"TYPE: - Number
				 PAGE: - Audio- ProcAmp
					Gain AES 2R  cmdID= 3107  min= -180  max= 180  step= 1  format= %0.1fdB  div_scale= 10
					Min = -18.0dB  Max = 18.0dB  Step = 0.1dB "
		::= { iqmux61CmdEntry 3107 }


	iqmux61ProcAmpAES2RInvert OBJECT-TYPE
		SYNTAX		INTEGER { disable(0), enable(1) }
		MAX-ACCESS		read-write
		STATUS			current
		DESCRIPTION
				"TYPE: - Checkbox
				 PAGE: - Audio- ProcAmp
					Invert  cmdID= 3187 "
		::= { iqmux61CmdEntry 3187 }


	iqmux61ProcAmpAES2RMute OBJECT-TYPE
		SYNTAX		INTEGER { disable(0), enable(1) }
		MAX-ACCESS		read-write
		STATUS			current
		DESCRIPTION
				"TYPE: - Checkbox
				 PAGE: - Audio- ProcAmp
					Mute  cmdID= 3267 "
		::= { iqmux61CmdEntry 3267 }


	iqmux61AudioProcAmpStereo1 OBJECT-TYPE
		SYNTAX		INTEGER { disable(0), enable(1) }
		MAX-ACCESS		read-write
		STATUS			current
		DESCRIPTION
				"TYPE: - Checkbox
				 PAGE: - Audio- ProcAmp
					Stereo 1  cmdID= 3334 "
		::= { iqmux61CmdEntry 3334 }


	iqmux61ProcAmpAnalog1LGainAnalog1L OBJECT-TYPE
		SYNTAX		INTEGER
		MAX-ACCESS		read-write
		STATUS			current
		DESCRIPTION
				"TYPE: - Number
				 PAGE: - Audio- ProcAmp
					Gain Analog 1L  cmdID= 3108  min= -180  max= 180  step= 1  format= %0.1fdB  div_scale= 10
					Min = -18.0dB  Max = 18.0dB  Step = 0.1dB "
		::= { iqmux61CmdEntry 3108 }


	iqmux61ProcAmpAnalog1LInvert OBJECT-TYPE
		SYNTAX		INTEGER { disable(0), enable(1) }
		MAX-ACCESS		read-write
		STATUS			current
		DESCRIPTION
				"TYPE: - Checkbox
				 PAGE: - Audio- ProcAmp
					Invert  cmdID= 3188 "
		::= { iqmux61CmdEntry 3188 }


	iqmux61ProcAmpAnalog1LMute OBJECT-TYPE
		SYNTAX		INTEGER { disable(0), enable(1) }
		MAX-ACCESS		read-write
		STATUS			current
		DESCRIPTION
				"TYPE: - Checkbox
				 PAGE: - Audio- ProcAmp
					Mute  cmdID= 3268 "
		::= { iqmux61CmdEntry 3268 }


	iqmux61ProcAmpAnalog1RGainAnalog1R OBJECT-TYPE
		SYNTAX		INTEGER
		MAX-ACCESS		read-write
		STATUS			current
		DESCRIPTION
				"TYPE: - Number
				 PAGE: - Audio- ProcAmp
					Gain Analog 1R  cmdID= 3109  min= -180  max= 180  step= 1  format= %0.1fdB  div_scale= 10
					Min = -18.0dB  Max = 18.0dB  Step = 0.1dB "
		::= { iqmux61CmdEntry 3109 }


	iqmux61ProcAmpAnalog1RInvert OBJECT-TYPE
		SYNTAX		INTEGER { disable(0), enable(1) }
		MAX-ACCESS		read-write
		STATUS			current
		DESCRIPTION
				"TYPE: - Checkbox
				 PAGE: - Audio- ProcAmp
					Invert  cmdID= 3189 "
		::= { iqmux61CmdEntry 3189 }


	iqmux61ProcAmpAnalog1RMute OBJECT-TYPE
		SYNTAX		INTEGER { disable(0), enable(1) }
		MAX-ACCESS		read-write
		STATUS			current
		DESCRIPTION
				"TYPE: - Checkbox
				 PAGE: - Audio- ProcAmp
					Mute  cmdID= 3269 "
		::= { iqmux61CmdEntry 3269 }


	iqmux61AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3335 "
		::= { iqmux61CmdEntry 3335 }


	iqmux61ProcAmpAnalog2LGainAnalog2L OBJECT-TYPE
		SYNTAX		INTEGER
		MAX-ACCESS		read-write
		STATUS			current
		DESCRIPTION
				"TYPE: - Number
				 PAGE: - Audio- ProcAmp
					Gain Analog 2L  cmdID= 3110  min= -180  max= 180  step= 1  format= %0.1fdB  div_scale= 10
					Min = -18.0dB  Max = 18.0dB  Step = 0.1dB "
		::= { iqmux61CmdEntry 3110 }


	iqmux61ProcAmpAnalog2LInvert OBJECT-TYPE
		SYNTAX		INTEGER { disable(0), enable(1) }
		MAX-ACCESS		read-write
		STATUS			current
		DESCRIPTION
				"TYPE: - Checkbox
				 PAGE: - Audio- ProcAmp
					Invert  cmdID= 3190 "
		::= { iqmux61CmdEntry 3190 }


	iqmux61ProcAmpAnalog2LMute OBJECT-TYPE
		SYNTAX		INTEGER { disable(0), enable(1) }
		MAX-ACCESS		read-write
		STATUS			current
		DESCRIPTION
				"TYPE: - Checkbox
				 PAGE: - Audio- ProcAmp
					Mute  cmdID= 3270 "
		::= { iqmux61CmdEntry 3270 }


	iqmux61ProcAmpAnalog2RGainAnalog2R OBJECT-TYPE
		SYNTAX		INTEGER
		MAX-ACCESS		read-write
		STATUS			current
		DESCRIPTION
				"TYPE: - Number
				 PAGE: - Audio- ProcAmp
					Gain Analog 2R  cmdID= 3111  min= -180  max= 180  step= 1  format= %0.1fdB  div_scale= 10
					Min = -18.0dB  Max = 18.0dB  Step = 0.1dB "
		::= { iqmux61CmdEntry 3111 }


	iqmux61ProcAmpAnalog2RInvert OBJECT-TYPE
		SYNTAX		INTEGER { disable(0), enable(1) }
		MAX-ACCESS		read-write
		STATUS			current
		DESCRIPTION
				"TYPE: - Checkbox
				 PAGE: - Audio- ProcAmp
					Invert  cmdID= 3191 "
		::= { iqmux61CmdEntry 3191 }


	iqmux61ProcAmpAnalog2RMute OBJECT-TYPE
		SYNTAX		INTEGER { disable(0), enable(1) }
		MAX-ACCESS		read-write
		STATUS			current
		DESCRIPTION
				"TYPE: - Checkbox
				 PAGE: - Audio- ProcAmp
					Mute  cmdID= 3271 "
		::= { iqmux61CmdEntry 3271 }


	iqmux61EmbedEmbedder1Embed1Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 1
					Embed 1 Source  cmdID= 2941
					bUS A  value= 0
					bUS B  value= 1
					bUS C  value= 2
					bUS D  value= 3
					aES 1 Direct  value= 4
					aES 2 Direct  value= 5
					test tone  value= 6
					silence  value= 7  "
		::= { iqmux61CmdEntry 2941 }


	iqmux61EmbedEmbedder1PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 1
					Pair Selection  cmdID= 2531
					select Pair 1  value= 0
					select Pair 2  value= 1
					select Pair 3  value= 2
					select Pair 4  value= 3
					select Pair 5  value= 4
					select Pair 6  value= 5
					select Pair 7  value= 6
					select Pair 8  value= 7  "
		::= { iqmux61CmdEntry 2531 }


	iqmux61EmbedEmbedder1Disable OBJECT-TYPE
		SYNTAX		INTEGER { disable(0), enable(1) }
		MAX-ACCESS		read-write
		STATUS			current
		DESCRIPTION
				"TYPE: - Checkbox
				 PAGE: - Audio- Embed- Embedder 1
					Disable  cmdID= 2541 "
		::= { iqmux61CmdEntry 2541 }


	iqmux61EmbedEmbedder2Embed2Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 2
					Embed 2 Source  cmdID= 2942
					bUS A  value= 0
					bUS B  value= 1
					bUS C  value= 2
					bUS D  value= 3
					aES 1 Direct  value= 4
					aES 2 Direct  value= 5
					test tone  value= 6
					silence  value= 7  "
		::= { iqmux61CmdEntry 2942 }


	iqmux61EmbedEmbedder2PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 2
					Pair Selection  cmdID= 2532
					select Pair 1  value= 0
					select Pair 2  value= 1
					select Pair 3  value= 2
					select Pair 4  value= 3
					select Pair 5  value= 4
					select Pair 6  value= 5
					select Pair 7  value= 6
					select Pair 8  value= 7  "
		::= { iqmux61CmdEntry 2532 }


	iqmux61EmbedEmbedder2Disable OBJECT-TYPE
		SYNTAX		INTEGER { disable(0), enable(1) }
		MAX-ACCESS		read-write
		STATUS			current
		DESCRIPTION
				"TYPE: - Checkbox
				 PAGE: - Audio- Embed- Embedder 2
					Disable  cmdID= 2542 "
		::= { iqmux61CmdEntry 2542 }


	iqmux61EmbedEmbedder3Embed3Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 3
					Embed 3 Source  cmdID= 2943
					bUS A  value= 0
					bUS B  value= 1
					bUS C  value= 2
					bUS D  value= 3
					aES 1 Direct  value= 4
					aES 2 Direct  value= 5
					test tone  value= 6
					silence  value= 7  "
		::= { iqmux61CmdEntry 2943 }


	iqmux61EmbedEmbedder3PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 3
					Pair Selection  cmdID= 2533
					select Pair 1  value= 0
					select Pair 2  value= 1
					select Pair 3  value= 2
					select Pair 4  value= 3
					select Pair 5  value= 4
					select Pair 6  value= 5
					select Pair 7  value= 6
					select Pair 8  value= 7  "
		::= { iqmux61CmdEntry 2533 }


	iqmux61EmbedEmbedder3Disable OBJECT-TYPE
		SYNTAX		INTEGER { disable(0), enable(1) }
		MAX-ACCESS		read-write
		STATUS			current
		DESCRIPTION
				"TYPE: - Checkbox
				 PAGE: - Audio- Embed- Embedder 3
					Disable  cmdID= 2543 "
		::= { iqmux61CmdEntry 2543 }


	iqmux61EmbedEmbedder4Embed4Source OBJECT-TYPE
		SYNTAX		INTEGER {
							val_BUS_A(0),
							val_BUS_B(1),
							val_BUS_C(2),
							val_BUS_D(3),
							val_AES_1_Direct(4),
							val_AES_2_Direct(5),
							val_Test_tone(6),
							val_Silence(7)
							}
		MAX-ACCESS		read-write
		STATUS			current
		DESCRIPTION
				"TYPE: - RadiobuttonList
				 PAGE: - Audio- Embed- Embedder 4
					Embed 4 Source  cmdID= 2944
					bUS A  value= 0
					bUS B  value= 1
					bUS C  value= 2
					bUS D  value= 3
					aES 1 Direct  value= 4
					aES 2 Direct  value= 5
					test tone  value= 6
					silence  value= 7  "
		::= { iqmux61CmdEntry 2944 }


	iqmux61EmbedEmbedder4PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 4
					Pair Selection  cmdID= 2534
					select Pair 1  value= 0
					select Pair 2  value= 1
					select Pair 3  value= 2
					select Pair 4  value= 3
					select Pair 5  value= 4
					select Pair 6  value= 5
					select Pair 7  value= 6
					select Pair 8  value= 7  "
		::= { iqmux61CmdEntry 2534 }


	iqmux61EmbedEmbedder4Disable OBJECT-TYPE
		SYNTAX		INTEGER { disable(0), enable(1) }
		MAX-ACCESS		read-write
		STATUS			current
		DESCRIPTION
				"TYPE: - Checkbox
				 PAGE: - Audio- Embed- Embedder 4
					Disable  cmdID= 2544 "
		::= { iqmux61CmdEntry 2544 }


	iqmux61Mixer1Mix1Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source1
					Mix1 Source1  cmdID= 3440
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3440 }


	iqmux61MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1
					Min = -71dB  Max = 0dB  Step = 1dB "
		::= { iqmux61CmdEntry 3360 }


	iqmux61Mixer1Mix1Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source2
					Mix1 Source2  cmdID= 3441
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3441 }


	iqmux61MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1
					Min = -71dB  Max = 0dB  Step = 1dB "
		::= { iqmux61CmdEntry 3361 }


	iqmux61Mixer1Mix1Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source3
					Mix1 Source3  cmdID= 3442
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3442 }


	iqmux61MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1
					Min = -71dB  Max = 0dB  Step = 1dB "
		::= { iqmux61CmdEntry 3362 }


	iqmux61Mixer1Mix1Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 1- Mix1 Source4
					Mix1 Source4  cmdID= 3443
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3443 }


	iqmux61MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1
					Min = -71dB  Max = 0dB  Step = 1dB "
		::= { iqmux61CmdEntry 3363 }


	iqmux61Mixer2Mix2Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source1
					Mix2 Source1  cmdID= 3444
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3444 }


	iqmux61MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1
					Min = -71dB  Max = 0dB  Step = 1dB "
		::= { iqmux61CmdEntry 3364 }


	iqmux61Mixer2Mix2Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source2
					Mix2 Source2  cmdID= 3445
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3445 }


	iqmux61MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1
					Min = -71dB  Max = 0dB  Step = 1dB "
		::= { iqmux61CmdEntry 3365 }


	iqmux61Mixer2Mix2Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source3
					Mix2 Source3  cmdID= 3446
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3446 }


	iqmux61MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1
					Min = -71dB  Max = 0dB  Step = 1dB "
		::= { iqmux61CmdEntry 3366 }


	iqmux61Mixer2Mix2Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 2- Mix2 Source4
					Mix2 Source4  cmdID= 3447
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3447 }


	iqmux61MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1
					Min = -71dB  Max = 0dB  Step = 1dB "
		::= { iqmux61CmdEntry 3367 }


	iqmux61Mixer3Mix3Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source1
					Mix3 Source1  cmdID= 3448
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3448 }


	iqmux61MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1
					Min = -71dB  Max = 0dB  Step = 1dB "
		::= { iqmux61CmdEntry 3368 }


	iqmux61Mixer3Mix3Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source2
					Mix3 Source2  cmdID= 3449
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3449 }


	iqmux61MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1
					Min = -71dB  Max = 0dB  Step = 1dB "
		::= { iqmux61CmdEntry 3369 }


	iqmux61Mixer3Mix3Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source3
					Mix3 Source3  cmdID= 3450
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3450 }


	iqmux61MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1
					Min = -71dB  Max = 0dB  Step = 1dB "
		::= { iqmux61CmdEntry 3370 }


	iqmux61Mixer3Mix3Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 3- Mix3 Source4
					Mix3 Source4  cmdID= 3451
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3451 }


	iqmux61MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1
					Min = -71dB  Max = 0dB  Step = 1dB "
		::= { iqmux61CmdEntry 3371 }


	iqmux61Mixer4Mix4Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source1
					Mix4 Source1  cmdID= 3452
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3452 }


	iqmux61MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1
					Min = -71dB  Max = 0dB  Step = 1dB "
		::= { iqmux61CmdEntry 3372 }


	iqmux61Mixer4Mix4Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source2
					Mix4 Source2  cmdID= 3453
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3453 }


	iqmux61MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1
					Min = -71dB  Max = 0dB  Step = 1dB "
		::= { iqmux61CmdEntry 3373 }


	iqmux61Mixer4Mix4Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source3
					Mix4 Source3  cmdID= 3454
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3454 }


	iqmux61MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1
					Min = -71dB  Max = 0dB  Step = 1dB "
		::= { iqmux61CmdEntry 3374 }


	iqmux61Mixer4Mix4Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23)
							}
		MAX-ACCESS		read-write
		STATUS			current
		DESCRIPTION
				"TYPE: - RadiobuttonList
				 PAGE: - Audio- Mix- Mixer 4- Mix4 Source4
					Mix4 Source4  cmdID= 3455
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23  "
		::= { iqmux61CmdEntry 3455 }


	iqmux61MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1
					Min = -71dB  Max = 0dB  Step = 1dB "
		::= { iqmux61CmdEntry 3375 }


	iqmux61BusSourceBusALSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusAL Source
					BusAL Source  cmdID= 3520
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3520 }


	iqmux61BusSourceBusARSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusAR Source
					BusAR Source  cmdID= 3521
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3521 }


	iqmux61BusSourceBusBLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusBL Source
					BusBL Source  cmdID= 3522
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3522 }


	iqmux61BusSourceBusBRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusBR Source
					BusBR Source  cmdID= 3523
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3523 }


	iqmux61BusSourceBusCLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusCL Source
					BusCL Source  cmdID= 3524
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3524 }


	iqmux61BusSourceBusCRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusCR Source
					BusCR Source  cmdID= 3525
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3525 }


	iqmux61BusSourceBusDLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusDL Source
					BusDL Source  cmdID= 3526
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3526 }


	iqmux61BusSourceBusDRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_Analog_1L(20),
							val_Analog_1R(21),
							val_Analog_2L(22),
							val_Analog_2R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusDR Source
					BusDR Source  cmdID= 3527
					deEmbed 1L  value= 0
					deEmbed 1R  value= 1
					deEmbed 2L  value= 2
					deEmbed 2R  value= 3
					deEmbed 3L  value= 4
					deEmbed 3R  value= 5
					deEmbed 4L  value= 6
					deEmbed 4R  value= 7
					deEmbed 5L  value= 8
					deEmbed 5R  value= 9
					deEmbed 6L  value= 10
					deEmbed 6R  value= 11
					deEmbed 7L  value= 12
					deEmbed 7R  value= 13
					deEmbed 8L  value= 14
					deEmbed 8R  value= 15
					aES 1L  value= 16
					aES 1R  value= 17
					aES 2L  value= 18
					aES 2R  value= 19
					analog 1L  value= 20
					analog 1R  value= 21
					analog 2L  value= 22
					analog 2R  value= 23
					mIX 1  value= 24
					mIX 2  value= 25
					mIX 3  value= 26
					mIX 4  value= 27  "
		::= { iqmux61CmdEntry 3527 }


	iqmux61BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqmux61CmdEntry 3320 }


	iqmux61BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10
					Min = -18.0dB  Max = 18.0dB  Step = 0.1dB "
		::= { iqmux61CmdEntry 3080 }


	iqmux61BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqmux61CmdEntry 3160 }


	iqmux61BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqmux61CmdEntry 3240 }


	iqmux61BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10
					Min = -18.0dB  Max = 18.0dB  Step = 0.1dB "
		::= { iqmux61CmdEntry 3081 }


	iqmux61BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqmux61CmdEntry 3161 }


	iqmux61BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqmux61CmdEntry 3241 }


	iqmux61BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqmux61CmdEntry 3321 }


	iqmux61BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10
					Min = -18.0dB  Max = 18.0dB  Step = 0.1dB "
		::= { iqmux61CmdEntry 3082 }


	iqmux61BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqmux61CmdEntry 3162 }


	iqmux61BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqmux61CmdEntry 3242 }


	iqmux61BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10
					Min = -18.0dB  Max = 18.0dB  Step = 0.1dB "
		::= { iqmux61CmdEntry 3083 }


	iqmux61BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqmux61CmdEntry 3163 }


	iqmux61BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqmux61CmdEntry 3243 }


	iqmux61BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqmux61CmdEntry 3322 }


	iqmux61BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10
					Min = -18.0dB  Max = 18.0dB  Step = 0.1dB "
		::= { iqmux61CmdEntry 3084 }


	iqmux61BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqmux61CmdEntry 3164 }


	iqmux61BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqmux61CmdEntry 3244 }


	iqmux61BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10
					Min = -18.0dB  Max = 18.0dB  Step = 0.1dB "
		::= { iqmux61CmdEntry 3085 }


	iqmux61BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqmux61CmdEntry 3165 }


	iqmux61BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqmux61CmdEntry 3245 }


	iqmux61BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqmux61CmdEntry 3323 }


	iqmux61BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10
					Min = -18.0dB  Max = 18.0dB  Step = 0.1dB "
		::= { iqmux61CmdEntry 3086 }


	iqmux61BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqmux61CmdEntry 3166 }


	iqmux61BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqmux61CmdEntry 3246 }


	iqmux61BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10
					Min = -18.0dB  Max = 18.0dB  Step = 0.1dB "
		::= { iqmux61CmdEntry 3087 }


	iqmux61BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqmux61CmdEntry 3167 }


	iqmux61BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqmux61CmdEntry 3247 }


	iqmux61AudioDelayAESInput1Delay OBJECT-TYPE
		SYNTAX		INTEGER
		MAX-ACCESS		read-write
		STATUS			current
		DESCRIPTION
				"TYPE: - Number
				 PAGE: - Audio- Delay
					AES Input 1 Delay  cmdID= 2928  min= 0  max= 1500  step= 1  format= %0.0f ms  div_scale= 1
					Min = 0 ms  Max = 1500 ms  Step = 1 ms "
		::= { iqmux61CmdEntry 2928 }


	iqmux61AudioDelayAESInput2Delay OBJECT-TYPE
		SYNTAX		INTEGER
		MAX-ACCESS		read-write
		STATUS			current
		DESCRIPTION
				"TYPE: - Number
				 PAGE: - Audio- Delay
					AES Input 2 Delay  cmdID= 2929  min= 0  max= 1500  step= 1  format= %0.0f ms  div_scale= 1
					Min = 0 ms  Max = 1500 ms  Step = 1 ms "
		::= { iqmux61CmdEntry 2929 }


	iqmux61AudioDelayAnalogIn1Delay OBJECT-TYPE
		SYNTAX		INTEGER
		MAX-ACCESS		read-write
		STATUS			current
		DESCRIPTION
				"TYPE: - Number
				 PAGE: - Audio- Delay
					Analog In 1 Delay  cmdID= 2930  min= 0  max= 1500  step= 1  format= %0.0f ms  div_scale= 1
					Min = 0 ms  Max = 1500 ms  Step = 1 ms "
		::= { iqmux61CmdEntry 2930 }


	iqmux61AudioDelayAnalogIn2Delay OBJECT-TYPE
		SYNTAX		INTEGER
		MAX-ACCESS		read-write
		STATUS			current
		DESCRIPTION
				"TYPE: - Number
				 PAGE: - Audio- Delay
					Analog In 2 Delay  cmdID= 2931  min= 0  max= 1500  step= 1  format= %0.0f ms  div_scale= 1
					Min = 0 ms  Max = 1500 ms  Step = 1 ms "
		::= { iqmux61CmdEntry 2931 }


	iqmux61DelayDelaySelectInternal OBJECT-TYPE
		SYNTAX		INTEGER { disable(0), enable(1) }
		MAX-ACCESS		read-write
		STATUS			current
		DESCRIPTION
				"TYPE: - Checkbox
				 PAGE: - Audio- Delay
					Internal  cmdID= 2567 "
		::= { iqmux61CmdEntry 2567 }


	iqmux61DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqmux61CmdEntry 2568 }


	iqmux61DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqmux61CmdEntry 2569 }


	iqmux61DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqmux61CmdEntry 2570 }


	iqmux61DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqmux61CmdEntry 2571 }


	iqmux61DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqmux61CmdEntry 2572 }


	iqmux61DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqmux61CmdEntry 3051 }


	iqmux61DelayDelayStatusManual OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1
					Manual  cmdID= 2573  format=
					Min = -40 ms  Max = 1500 ms  Step =   1 ms "
		::= { iqmux61CmdEntry 2573 }


	iqmux61DelayDelayStatusInternal OBJECT-TYPE
		SYNTAX		RollCallString
		MAX-ACCESS		read-only
		STATUS			current
		DESCRIPTION
				"TYPE: - Display
				 PAGE: - Audio- Delay
					Internal  cmdID= 2574  format=   "
		::= { iqmux61CmdEntry 2574 }


	iqmux61DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqmux61CmdEntry 14 }


	iqmux61DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqmux61CmdEntry 15 }


	iqmux61DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqmux61CmdEntry 16 }


	iqmux61DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqmux61CmdEntry 17 }


	iqmux61DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqmux61CmdEntry 3052 }


	iqmux61DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqmux61CmdEntry 2979 }


	iqmux61AudioMonitorSilenceLevel OBJECT-TYPE
		SYNTAX		INTEGER
		MAX-ACCESS		read-write
		STATUS			current
		DESCRIPTION
				"TYPE: - Number
				 PAGE: - Audio- Monitor
					Silence Level  cmdID= 3056  min= -80  max= 0  step= 1  format= %1.1f dB  div_scale= 1
					Min = -80.0 dB  Max = 0.0 dB  Step = 1.0 dB "
		::= { iqmux61CmdEntry 3056 }


	iqmux61AudioMonitorLowLevel OBJECT-TYPE
		SYNTAX		INTEGER
		MAX-ACCESS		read-write
		STATUS			current
		DESCRIPTION
				"TYPE: - Number
				 PAGE: - Audio- Monitor
					Low Level  cmdID= 2517  min= -80  max= 0  step= 1  format= %1.1f dB  div_scale= 1
					Min = -80.0 dB  Max = 0.0 dB  Step = 1.0 dB "
		::= { iqmux61CmdEntry 2517 }


	iqmux61AudioMonitorHighLevel OBJECT-TYPE
		SYNTAX		INTEGER
		MAX-ACCESS		read-write
		STATUS			current
		DESCRIPTION
				"TYPE: - Number
				 PAGE: - Audio- Monitor
					High Level  cmdID= 3057  min= -80  max= 0  step= 1  format= %1.1f dB  div_scale= 1
					Min = -80.0 dB  Max = 0.0 dB  Step = 1.0 dB "
		::= { iqmux61CmdEntry 3057 }


	iqmux61AudioMonitorOverloadLevel OBJECT-TYPE
		SYNTAX		INTEGER
		MAX-ACCESS		read-write
		STATUS			current
		DESCRIPTION
				"TYPE: - Number
				 PAGE: - Audio- Monitor
					Overload Level  cmdID= 3058  min= -80  max= 0  step= 1  format= %1.1f dB  div_scale= 1
					Min = -80.0 dB  Max = 0.0 dB  Step = 1.0 dB "
		::= { iqmux61CmdEntry 3058 }


	iqmux61AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1
					Min = 1 sec  Max = 20 sec  Step = 1 sec "
		::= { iqmux61CmdEntry 2518 }


	iqmux61Freeze OBJECT-TYPE
		SYNTAX		INTEGER { disable(0), enable(1) }
		MAX-ACCESS		read-write
		STATUS			current
		DESCRIPTION
				"TYPE: - Checkbox
					Freeze  cmdID= 1208 "
		::= { iqmux61CmdEntry 1208 }


	iqmux61VideoDelay OBJECT-TYPE
		SYNTAX		INTEGER {
							val_0_Frame_Delay(0),
							val_1_Frame_Delay(1),
							val_2_Frame_Delay(2)
							}
		MAX-ACCESS		read-write
		STATUS			current
		DESCRIPTION
				"TYPE: - Button
				 PAGE: - Video Delay
					0 Frame Delay  cmdID= 2973  value= 0
					1 Frame Delay  cmdID= 2973  value= 1
					2 Frame Delay  cmdID= 2973  value= 2  "
		::= { iqmux61CmdEntry 2973 }


	iqmux61VideoDelayDelayPhase625HPhase OBJECT-TYPE
		SYNTAX		INTEGER
		MAX-ACCESS		read-write
		STATUS			current
		DESCRIPTION
				"TYPE: - Number
				 PAGE: - Video Delay
					625 H Phase  cmdID= 2974  min= 0  max= 63962899  step= -28499  format=  %.0fns  div_scale= 1000
					Min =  0ns  Max =  63963ns  Step =  -28ns "
		::= { iqmux61CmdEntry 2974 }


	iqmux61VideoDelayDelayPhase625VPhase OBJECT-TYPE
		SYNTAX		INTEGER
		MAX-ACCESS		read-write
		STATUS			current
		DESCRIPTION
				"TYPE: - Number
				 PAGE: - Video Delay
					625 V Phase  cmdID= 2975  min= 0  max= 624  step= 1  format=  %.0flines  div_scale= 1
					Min =  0lines  Max =  624lines  Step =  1lines "
		::= { iqmux61CmdEntry 2975 }


	iqmux61VideoDelayDelayPhase525HPhase OBJECT-TYPE
		SYNTAX		INTEGER
		MAX-ACCESS		read-write
		STATUS			current
		DESCRIPTION
				"TYPE: - Number
				 PAGE: - Video Delay
					525 H Phase  cmdID= 2976  min= 0  max= 63518455  step= -28499  format=  %.0fns  div_scale= 1000
					Min =  0ns  Max =  63518ns  Step =  -28ns "
		::= { iqmux61CmdEntry 2976 }


	iqmux61VideoDelayDelayPhase525VPhase OBJECT-TYPE
		SYNTAX		INTEGER
		MAX-ACCESS		read-write
		STATUS			current
		DESCRIPTION
				"TYPE: - Number
				 PAGE: - Video Delay
					525 V Phase  cmdID= 2977  min= 0  max= 524  step= 1  format=  %.0flines  div_scale= 1
					Min =  0lines  Max =  524lines  Step =  1lines "
		::= { iqmux61CmdEntry 2977 }


	iqmux61UserMemMemory1Save1 OBJECT-TYPE
		SYNTAX		INTEGER { noAction(0),save_1(1) }
		MAX-ACCESS		read-write
		STATUS			current
		DESCRIPTION
				"TYPE: - Button
				 PAGE: - User Mem
					save 1  cmdID= 1600  value= 1  "
		::= { iqmux61CmdEntry 1600 }


	iqmux61UserMemMemory1Recall1 OBJECT-TYPE
		SYNTAX		INTEGER { noAction(0),recall_1(1) }
		MAX-ACCESS		read-write
		STATUS			current
		DESCRIPTION
				"TYPE: - Button
				 PAGE: - User Mem
					recall 1  cmdID= 1601  value= 1  "
		::= { iqmux61CmdEntry 1601 }


	iqmux61UserMemMemory1Clear1 OBJECT-TYPE
		SYNTAX		INTEGER { noAction(0),clear_1(1) }
		MAX-ACCESS		read-write
		STATUS			current
		DESCRIPTION
				"TYPE: - Button
				 PAGE: - User Mem
					clear 1  cmdID= 1602  value= 1  "
		::= { iqmux61CmdEntry 1602 }


	iqmux61UserMemMemory1Name1 OBJECT-TYPE
		SYNTAX		RollCallString
		MAX-ACCESS		read-write
		STATUS			current
		DESCRIPTION
				"TYPE: - Editstring
				 PAGE: - User Mem
					Name 1  cmdID= 1603  "
		::= { iqmux61CmdEntry 1603 }


	iqmux61UserMemMemory2Save2 OBJECT-TYPE
		SYNTAX		INTEGER { noAction(0),save_2(1) }
		MAX-ACCESS		read-write
		STATUS			current
		DESCRIPTION
				"TYPE: - Button
				 PAGE: - User Mem
					save 2  cmdID= 1604  value= 1  "
		::= { iqmux61CmdEntry 1604 }


	iqmux61UserMemMemory2Recall2 OBJECT-TYPE
		SYNTAX		INTEGER { noAction(0),recall_2(1) }
		MAX-ACCESS		read-write
		STATUS			current
		DESCRIPTION
				"TYPE: - Button
				 PAGE: - User Mem
					recall 2  cmdID= 1605  value= 1  "
		::= { iqmux61CmdEntry 1605 }


	iqmux61UserMemMemory2Clear2 OBJECT-TYPE
		SYNTAX		INTEGER { noAction(0),clear_2(1) }
		MAX-ACCESS		read-write
		STATUS			current
		DESCRIPTION
				"TYPE: - Button
				 PAGE: - User Mem
					clear 2  cmdID= 1606  value= 1  "
		::= { iqmux61CmdEntry 1606 }


	iqmux61UserMemMemory2Name2 OBJECT-TYPE
		SYNTAX		RollCallString
		MAX-ACCESS		read-write
		STATUS			current
		DESCRIPTION
				"TYPE: - Editstring
				 PAGE: - User Mem
					Name 2  cmdID= 1607  "
		::= { iqmux61CmdEntry 1607 }


	iqmux61UserMemMemory3Save3 OBJECT-TYPE
		SYNTAX		INTEGER { noAction(0),save_3(1) }
		MAX-ACCESS		read-write
		STATUS			current
		DESCRIPTION
				"TYPE: - Button
				 PAGE: - User Mem
					save 3  cmdID= 1608  value= 1  "
		::= { iqmux61CmdEntry 1608 }


	iqmux61UserMemMemory3Recall3 OBJECT-TYPE
		SYNTAX		INTEGER { noAction(0),recall_3(1) }
		MAX-ACCESS		read-write
		STATUS			current
		DESCRIPTION
				"TYPE: - Button
				 PAGE: - User Mem
					recall 3  cmdID= 1609  value= 1  "
		::= { iqmux61CmdEntry 1609 }


	iqmux61UserMemMemory3Clear3 OBJECT-TYPE
		SYNTAX		INTEGER { noAction(0),clear_3(1) }
		MAX-ACCESS		read-write
		STATUS			current
		DESCRIPTION
				"TYPE: - Button
				 PAGE: - User Mem
					clear 3  cmdID= 1610  value= 1  "
		::= { iqmux61CmdEntry 1610 }


	iqmux61UserMemMemory3Name3 OBJECT-TYPE
		SYNTAX		RollCallString
		MAX-ACCESS		read-write
		STATUS			current
		DESCRIPTION
				"TYPE: - Editstring
				 PAGE: - User Mem
					Name 3  cmdID= 1611  "
		::= { iqmux61CmdEntry 1611 }


	iqmux61UserMemMemory4Save4 OBJECT-TYPE
		SYNTAX		INTEGER { noAction(0),save_4(1) }
		MAX-ACCESS		read-write
		STATUS			current
		DESCRIPTION
				"TYPE: - Button
				 PAGE: - User Mem
					save 4  cmdID= 1612  value= 1  "
		::= { iqmux61CmdEntry 1612 }


	iqmux61UserMemMemory4Recall4 OBJECT-TYPE
		SYNTAX		INTEGER { noAction(0),recall_4(1) }
		MAX-ACCESS		read-write
		STATUS			current
		DESCRIPTION
				"TYPE: - Button
				 PAGE: - User Mem
					recall 4  cmdID= 1613  value= 1  "
		::= { iqmux61CmdEntry 1613 }


	iqmux61UserMemMemory4Clear4 OBJECT-TYPE
		SYNTAX		INTEGER { noAction(0),clear_4(1) }
		MAX-ACCESS		read-write
		STATUS			current
		DESCRIPTION
				"TYPE: - Button
				 PAGE: - User Mem
					clear 4  cmdID= 1614  value= 1  "
		::= { iqmux61CmdEntry 1614 }


	iqmux61UserMemMemory4Name4 OBJECT-TYPE
		SYNTAX		RollCallString
		MAX-ACCESS		read-write
		STATUS			current
		DESCRIPTION
				"TYPE: - Editstring
				 PAGE: - User Mem
					Name 4  cmdID= 1615  "
		::= { iqmux61CmdEntry 1615 }


	iqmux61UserMemMemory5Save5 OBJECT-TYPE
		SYNTAX		INTEGER { noAction(0),save_5(1) }
		MAX-ACCESS		read-write
		STATUS			current
		DESCRIPTION
				"TYPE: - Button
				 PAGE: - User Mem
					save 5  cmdID= 1616  value= 1  "
		::= { iqmux61CmdEntry 1616 }


	iqmux61UserMemMemory5Recall5 OBJECT-TYPE
		SYNTAX		INTEGER { noAction(0),recall_5(1) }
		MAX-ACCESS		read-write
		STATUS			current
		DESCRIPTION
				"TYPE: - Button
				 PAGE: - User Mem
					recall 5  cmdID= 1617  value= 1  "
		::= { iqmux61CmdEntry 1617 }


	iqmux61UserMemMemory5Clear5 OBJECT-TYPE
		SYNTAX		INTEGER { noAction(0),clear_5(1) }
		MAX-ACCESS		read-write
		STATUS			current
		DESCRIPTION
				"TYPE: - Button
				 PAGE: - User Mem
					clear 5  cmdID= 1618  value= 1  "
		::= { iqmux61CmdEntry 1618 }


	iqmux61UserMemMemory5Name5 OBJECT-TYPE
		SYNTAX		RollCallString
		MAX-ACCESS		read-write
		STATUS			current
		DESCRIPTION
				"TYPE: - Editstring
				 PAGE: - User Mem
					Name 5  cmdID= 1619  "
		::= { iqmux61CmdEntry 1619 }


	iqmux61UserMemMemory6Save6 OBJECT-TYPE
		SYNTAX		INTEGER { noAction(0),save_6(1) }
		MAX-ACCESS		read-write
		STATUS			current
		DESCRIPTION
				"TYPE: - Button
				 PAGE: - User Mem
					save 6  cmdID= 1620  value= 1  "
		::= { iqmux61CmdEntry 1620 }


	iqmux61UserMemMemory6Recall6 OBJECT-TYPE
		SYNTAX		INTEGER { noAction(0),recall_6(1) }
		MAX-ACCESS		read-write
		STATUS			current
		DESCRIPTION
				"TYPE: - Button
				 PAGE: - User Mem
					recall 6  cmdID= 1621  value= 1  "
		::= { iqmux61CmdEntry 1621 }


	iqmux61UserMemMemory6Clear6 OBJECT-TYPE
		SYNTAX		INTEGER { noAction(0),clear_6(1) }
		MAX-ACCESS		read-write
		STATUS			current
		DESCRIPTION
				"TYPE: - Button
				 PAGE: - User Mem
					clear 6  cmdID= 1622  value= 1  "
		::= { iqmux61CmdEntry 1622 }


	iqmux61UserMemMemory6Name6 OBJECT-TYPE
		SYNTAX		RollCallString
		MAX-ACCESS		read-write
		STATUS			current
		DESCRIPTION
				"TYPE: - Editstring
				 PAGE: - User Mem
					Name 6  cmdID= 1623  "
		::= { iqmux61CmdEntry 1623 }


	iqmux61UserMemMemory7Save7 OBJECT-TYPE
		SYNTAX		INTEGER { noAction(0),save_7(1) }
		MAX-ACCESS		read-write
		STATUS			current
		DESCRIPTION
				"TYPE: - Button
				 PAGE: - User Mem
					save 7  cmdID= 1624  value= 1  "
		::= { iqmux61CmdEntry 1624 }


	iqmux61UserMemMemory7Recall7 OBJECT-TYPE
		SYNTAX		INTEGER { noAction(0),recall_7(1) }
		MAX-ACCESS		read-write
		STATUS			current
		DESCRIPTION
				"TYPE: - Button
				 PAGE: - User Mem
					recall 7  cmdID= 1625  value= 1  "
		::= { iqmux61CmdEntry 1625 }


	iqmux61UserMemMemory7Clear7 OBJECT-TYPE
		SYNTAX		INTEGER { noAction(0),clear_7(1) }
		MAX-ACCESS		read-write
		STATUS			current
		DESCRIPTION
				"TYPE: - Button
				 PAGE: - User Mem
					clear 7  cmdID= 1626  value= 1  "
		::= { iqmux61CmdEntry 1626 }


	iqmux61UserMemMemory7Name7 OBJECT-TYPE
		SYNTAX		RollCallString
		MAX-ACCESS		read-write
		STATUS			current
		DESCRIPTION
				"TYPE: - Editstring
				 PAGE: - User Mem
					Name 7  cmdID= 1627  "
		::= { iqmux61CmdEntry 1627 }


	iqmux61UserMemMemory8Save8 OBJECT-TYPE
		SYNTAX		INTEGER { noAction(0),save_8(1) }
		MAX-ACCESS		read-write
		STATUS			current
		DESCRIPTION
				"TYPE: - Button
				 PAGE: - User Mem
					save 8  cmdID= 1628  value= 1  "
		::= { iqmux61CmdEntry 1628 }


	iqmux61UserMemMemory8Recall8 OBJECT-TYPE
		SYNTAX		INTEGER { noAction(0),recall_8(1) }
		MAX-ACCESS		read-write
		STATUS			current
		DESCRIPTION
				"TYPE: - Button
				 PAGE: - User Mem
					recall 8  cmdID= 1629  value= 1  "
		::= { iqmux61CmdEntry 1629 }


	iqmux61UserMemMemory8Clear8 OBJECT-TYPE
		SYNTAX		INTEGER { noAction(0),clear_8(1) }
		MAX-ACCESS		read-write
		STATUS			current
		DESCRIPTION
				"TYPE: - Button
				 PAGE: - User Mem
					clear 8  cmdID= 1630  value= 1  "
		::= { iqmux61CmdEntry 1630 }


	iqmux61UserMemMemory8Name8 OBJECT-TYPE
		SYNTAX		RollCallString
		MAX-ACCESS		read-write
		STATUS			current
		DESCRIPTION
				"TYPE: - Editstring
				 PAGE: - User Mem
					Name 8  cmdID= 1631  "
		::= { iqmux61CmdEntry 1631 }


	iqmux61SetupPatternAnimatedPattern OBJECT-TYPE
		SYNTAX		INTEGER { disable(0), enable(1) }
		MAX-ACCESS		read-write
		STATUS			current
		DESCRIPTION
				"TYPE: - Checkbox
				 PAGE: - Setup- Pattern
					Animated Pattern  cmdID= 2940 "
		::= { iqmux61CmdEntry 2940 }


	iqmux61SetupPatternEnablePattern OBJECT-TYPE
		SYNTAX		INTEGER { disable(0), enable(1) }
		MAX-ACCESS		read-write
		STATUS			current
		DESCRIPTION
				"TYPE: - Checkbox
				 PAGE: - Setup- Pattern
					Enable Pattern  cmdID= 1035 "
		::= { iqmux61CmdEntry 1035 }


	iqmux61SetupPattern OBJECT-TYPE
		SYNTAX		INTEGER {
							val_Black(0),
							val_EBU_Colour_Bars(1),
							val_Val_100_Colour_Bars(2),
							val_Ramp(3),
							val_Multiburst(4),
							val_Pulse_Bar(5)
							}
		MAX-ACCESS		read-write
		STATUS			current
		DESCRIPTION
				"TYPE: - Button
				 PAGE: - Setup- Pattern
					black  cmdID= 1036  value= 0
					eBU Colour Bars  cmdID= 1036  value= 1
					100% Colour Bars  cmdID= 1036  value= 2
					ramp  cmdID= 1036  value= 3
					multiburst  cmdID= 1036  value= 4
					pulse & Bar  cmdID= 1036  value= 5  "
		::= { iqmux61CmdEntry 1036 }


	iqmux61SetupCaptionEditCaption OBJECT-TYPE
		SYNTAX		RollCallString
		MAX-ACCESS		read-write
		STATUS			current
		DESCRIPTION
				"TYPE: - Editstring
				 PAGE: - Setup- Caption
					Edit Caption  cmdID= 1041  "
		::= { iqmux61CmdEntry 1041 }


	iqmux61SetupCaption OBJECT-TYPE
		SYNTAX		INTEGER {
							val_Caption_Off(0),
							val_Caption_On(1)
							}
		MAX-ACCESS		read-write
		STATUS			current
		DESCRIPTION
				"TYPE: - Button
				 PAGE: - Setup- Caption
					caption Off  cmdID= 1037  value= 0
					caption On  cmdID= 1037  value= 1  "
		::= { iqmux61CmdEntry 1037 }


	iqmux61BlankingVIPass525BlankAll OBJECT-TYPE
		SYNTAX		INTEGER { noAction(0),blank_All(1) }
		MAX-ACCESS		read-write
		STATUS			current
		DESCRIPTION
				"TYPE: - Button
				 PAGE: - Setup- Blanking
					blank All  cmdID= 1298  value= 1  "
		::= { iqmux61CmdEntry 1298 }


	iqmux61BlankingVIPass525PassAll OBJECT-TYPE
		SYNTAX		INTEGER { noAction(0),pass_All(1) }
		MAX-ACCESS		read-write
		STATUS			current
		DESCRIPTION
				"TYPE: - Button
				 PAGE: - Setup- Blanking
					pass All  cmdID= 1297  value= 1  "
		::= { iqmux61CmdEntry 1297 }


	iqmux61BlankingVIPass525Line11 OBJECT-TYPE
		SYNTAX		INTEGER { disable(0), enable(1) }
		MAX-ACCESS		read-write
		STATUS			current
		DESCRIPTION
				"TYPE: - Checkbox
				 PAGE: - Setup- Blanking
					Line 11  cmdID= 1211 "
		::= { iqmux61CmdEntry 1211 }


	iqmux61BlankingVIPass525Line274 OBJECT-TYPE
		SYNTAX		INTEGER { disable(0), enable(1) }
		MAX-ACCESS		read-write
		STATUS			current
		DESCRIPTION
				"TYPE: - Checkbox
				 PAGE: - Setup- Blanking
					Line 274  cmdID= 1231 "
		::= { iqmux61CmdEntry 1231 }


	iqmux61BlankingVIPass525Line12 OBJECT-TYPE
		SYNTAX		INTEGER { disable(0), enable(1) }
		MAX-ACCESS		read-write
		STATUS			current
		DESCRIPTION
				"TYPE: - Checkbox
				 PAGE: - Setup- Blanking
					Line 12  cmdID= 1212 "
		::= { iqmux61CmdEntry 1212 }


	iqmux61BlankingVIPass525Line275 OBJECT-TYPE
		SYNTAX		INTEGER { disable(0), enable(1) }
		MAX-ACCESS		read-write
		STATUS			current
		DESCRIPTION
				"TYPE: - Checkbox
				 PAGE: - Setup- Blanking
					Line 275  cmdID= 1232 "
		::= { iqmux61CmdEntry 1232 }


	iqmux61BlankingVIPass525Line13 OBJECT-TYPE
		SYNTAX		INTEGER { disable(0), enable(1) }
		MAX-ACCESS		read-write
		STATUS			current
		DESCRIPTION
				"TYPE: - Checkbox
				 PAGE: - Setup- Blanking
					Line 13  cmdID= 1213 "
		::= { iqmux61CmdEntry 1213 }


	iqmux61BlankingVIPass525Line276 OBJECT-TYPE
		SYNTAX		INTEGER { disable(0), enable(1) }
		MAX-ACCESS		read-write
		STATUS			current
		DESCRIPTION
				"TYPE: - Checkbox
				 PAGE: - Setup- Blanking
					Line 276  cmdID= 1233 "
		::= { iqmux61CmdEntry 1233 }


	iqmux61BlankingVIPass525Line14 OBJECT-TYPE
		SYNTAX		INTEGER { disable(0), enable(1) }
		MAX-ACCESS		read-write
		STATUS			current
		DESCRIPTION
				"TYPE: - Checkbox
				 PAGE: - Setup- Blanking
					Line 14  cmdID= 1214 "
		::= { iqmux61CmdEntry 1214 }


	iqmux61BlankingVIPass525Line277 OBJECT-TYPE
		SYNTAX		INTEGER { disable(0), enable(1) }
		MAX-ACCESS		read-write
		STATUS			current
		DESCRIPTION
				"TYPE: - Checkbox
				 PAGE: - Setup- Blanking
					Line 277  cmdID= 1234 "
		::= { iqmux61CmdEntry 1234 }


	iqmux61BlankingVIPass525Line15 OBJECT-TYPE
		SYNTAX		INTEGER { disable(0), enable(1) }
		MAX-ACCESS		read-write
		STATUS			current
		DESCRIPTION
				"TYPE: - Checkbox
				 PAGE: - Setup- Blanking
					Line 15  cmdID= 1215 "
		::= { iqmux61CmdEntry 1215 }


	iqmux61BlankingVIPass525Line278 OBJECT-TYPE
		SYNTAX		INTEGER { disable(0), enable(1) }
		MAX-ACCESS		read-write
		STATUS			current
		DESCRIPTION
				"TYPE: - Checkbox
				 PAGE: - Setup- Blanking
					Line 278  cmdID= 1235 "
		::= { iqmux61CmdEntry 1235 }


	iqmux61BlankingVIPass525Line16 OBJECT-TYPE
		SYNTAX		INTEGER { disable(0), enable(1) }
		MAX-ACCESS		read-write
		STATUS			current
		DESCRIPTION
				"TYPE: - Checkbox
				 PAGE: - Setup- Blanking
					Line 16  cmdID= 1216 "
		::= { iqmux61CmdEntry 1216 }


	iqmux61BlankingVIPass525Line279 OBJECT-TYPE
		SYNTAX		INTEGER { disable(0), enable(1) }
		MAX-ACCESS		read-write
		STATUS			current
		DESCRIPTION
				"TYPE: - Checkbox
				 PAGE: - Setup- Blanking
					Line 279  cmdID= 1236 "
		::= { iqmux61CmdEntry 1236 }


	iqmux61BlankingVIPass525Line17 OBJECT-TYPE
		SYNTAX		INTEGER { disable(0), enable(1) }
		MAX-ACCESS		read-write
		STATUS			current
		DESCRIPTION
				"TYPE: - Checkbox
				 PAGE: - Setup- Blanking
					Line 17  cmdID= 1217 "
		::= { iqmux61CmdEntry 1217 }


	iqmux61BlankingVIPass525Line280 OBJECT-TYPE
		SYNTAX		INTEGER { disable(0), enable(1) }
		MAX-ACCESS		read-write
		STATUS			current
		DESCRIPTION
				"TYPE: - Checkbox
				 PAGE: - Setup- Blanking
					Line 280  cmdID= 1237 "
		::= { iqmux61CmdEntry 1237 }


	iqmux61BlankingVIPass525Line18 OBJECT-TYPE
		SYNTAX		INTEGER { disable(0), enable(1) }
		MAX-ACCESS		read-write
		STATUS			current
		DESCRIPTION
				"TYPE: - Checkbox
				 PAGE: - Setup- Blanking
					Line 18  cmdID= 1218 "
		::= { iqmux61CmdEntry 1218 }


	iqmux61BlankingVIPass525Line281 OBJECT-TYPE
		SYNTAX		INTEGER { disable(0), enable(1) }
		MAX-ACCESS		read-write
		STATUS			current
		DESCRIPTION
				"TYPE: - Checkbox
				 PAGE: - Setup- Blanking
					Line 281  cmdID= 1238 "
		::= { iqmux61CmdEntry 1238 }


	iqmux61BlankingVIPass525Line19 OBJECT-TYPE
		SYNTAX		INTEGER { disable(0), enable(1) }
		MAX-ACCESS		read-write
		STATUS			current
		DESCRIPTION
				"TYPE: - Checkbox
				 PAGE: - Setup- Blanking
					Line 19  cmdID= 1219 "
		::= { iqmux61CmdEntry 1219 }


	iqmux61BlankingVIPass525Line282 OBJECT-TYPE
		SYNTAX		INTEGER { disable(0), enable(1) }
		MAX-ACCESS		read-write
		STATUS			current
		DESCRIPTION
				"TYPE: - Checkbox
				 PAGE: - Setup- Blanking
					Line 282  cmdID= 1239 "
		::= { iqmux61CmdEntry 1239 }


	iqmux61BlankingVIPass525Line20 OBJECT-TYPE
		SYNTAX		INTEGER { disable(0), enable(1) }
		MAX-ACCESS		read-write
		STATUS			current
		DESCRIPTION
				"TYPE: - Checkbox
				 PAGE: - Setup- Blanking
					Line 20  cmdID= 1220 "
		::= { iqmux61CmdEntry 1220 }


	iqmux61BlankingVIPass525Line283 OBJECT-TYPE
		SYNTAX		INTEGER { disable(0), enable(1) }
		MAX-ACCESS		read-write
		STATUS			current
		DESCRIPTION
				"TYPE: - Checkbox
				 PAGE: - Setup- Blanking
					Line 283  cmdID= 1240 "
		::= { iqmux61CmdEntry 1240 }


	iqmux61BlankingVIPass525Line21 OBJECT-TYPE
		SYNTAX		INTEGER { disable(0), enable(1) }
		MAX-ACCESS		read-write
		STATUS			current
		DESCRIPTION
				"TYPE: - Checkbox
				 PAGE: - Setup- Blanking
					Line 21  cmdID= 1221 "
		::= { iqmux61CmdEntry 1221 }


	iqmux61BlankingVIPass625BlankAll OBJECT-TYPE
		SYNTAX		INTEGER { noAction(0),blank_All(1) }
		MAX-ACCESS		read-write
		STATUS			current
		DESCRIPTION
				"TYPE: - Button
				 PAGE: - Setup- Blanking
					blank All  cmdID= 1296  value= 1  "
		::= { iqmux61CmdEntry 1296 }


	iqmux61BlankingVIPass625PassAll OBJECT-TYPE
		SYNTAX		INTEGER { noAction(0),pass_All(1) }
		MAX-ACCESS		read-write
		STATUS			current
		DESCRIPTION
				"TYPE: - Button
				 PAGE: - Setup- Blanking
					pass All  cmdID= 1295  value= 1  "
		::= { iqmux61CmdEntry 1295 }


	iqmux61BlankingVIPass625Line7 OBJECT-TYPE
		SYNTAX		INTEGER { disable(0), enable(1) }
		MAX-ACCESS		read-write
		STATUS			current
		DESCRIPTION
				"TYPE: - Checkbox
				 PAGE: - Setup- Blanking
					Line 7  cmdID= 1251 "
		::= { iqmux61CmdEntry 1251 }


	iqmux61BlankingVIPass625Line320 OBJECT-TYPE
		SYNTAX		INTEGER { disable(0), enable(1) }
		MAX-ACCESS		read-write
		STATUS			current
		DESCRIPTION
				"TYPE: - Checkbox
				 PAGE: - Setup- Blanking
					Line 320  cmdID= 1272 "
		::= { iqmux61CmdEntry 1272 }


	iqmux61BlankingVIPass625Line8 OBJECT-TYPE
		SYNTAX		INTEGER { disable(0), enable(1) }
		MAX-ACCESS		read-write
		STATUS			current
		DESCRIPTION
				"TYPE: - Checkbox
				 PAGE: - Setup- Blanking
					Line 8  cmdID= 1252 "
		::= { iqmux61CmdEntry 1252 }


	iqmux61BlankingVIPass625Line321 OBJECT-TYPE
		SYNTAX		INTEGER { disable(0), enable(1) }
		MAX-ACCESS		read-write
		STATUS			current
		DESCRIPTION
				"TYPE: - Checkbox
				 PAGE: - Setup- Blanking
					Line 321  cmdID= 1273 "
		::= { iqmux61CmdEntry 1273 }


	iqmux61BlankingVIPass625Line9 OBJECT-TYPE
		SYNTAX		INTEGER { disable(0), enable(1) }
		MAX-ACCESS		read-write
		STATUS			current
		DESCRIPTION
				"TYPE: - Checkbox
				 PAGE: - Setup- Blanking
					Line 9  cmdID= 1253 "
		::= { iqmux61CmdEntry 1253 }


	iqmux61BlankingVIPass625Line322 OBJECT-TYPE
		SYNTAX		INTEGER { disable(0), enable(1) }
		MAX-ACCESS		read-write
		STATUS			current
		DESCRIPTION
				"TYPE: - Checkbox
				 PAGE: - Setup- Blanking
					Line 322  cmdID= 1274 "
		::= { iqmux61CmdEntry 1274 }


	iqmux61BlankingVIPass625Line10 OBJECT-TYPE
		SYNTAX		INTEGER { disable(0), enable(1) }
		MAX-ACCESS		read-write
		STATUS			current
		DESCRIPTION
				"TYPE: - Checkbox
				 PAGE: - Setup- Blanking
					Line 10  cmdID= 1254 "
		::= { iqmux61CmdEntry 1254 }


	iqmux61BlankingVIPass625Line323 OBJECT-TYPE
		SYNTAX		INTEGER { disable(0), enable(1) }
		MAX-ACCESS		read-write
		STATUS			current
		DESCRIPTION
				"TYPE: - Checkbox
				 PAGE: - Setup- Blanking
					Line 323  cmdID= 1275 "
		::= { iqmux61CmdEntry 1275 }


	iqmux61BlankingVIPass625Line11 OBJECT-TYPE
		SYNTAX		INTEGER { disable(0), enable(1) }
		MAX-ACCESS		read-write
		STATUS			current
		DESCRIPTION
				"TYPE: - Checkbox
				 PAGE: - Setup- Blanking
					Line 11  cmdID= 1255 "
		::= { iqmux61CmdEntry 1255 }


	iqmux61BlankingVIPass625Line324 OBJECT-TYPE
		SYNTAX		INTEGER { disable(0), enable(1) }
		MAX-ACCESS		read-write
		STATUS			current
		DESCRIPTION
				"TYPE: - Checkbox
				 PAGE: - Setup- Blanking
					Line 324  cmdID= 1276 "
		::= { iqmux61CmdEntry 1276 }


	iqmux61BlankingVIPass625Line12 OBJECT-TYPE
		SYNTAX		INTEGER { disable(0), enable(1) }
		MAX-ACCESS		read-write
		STATUS			current
		DESCRIPTION
				"TYPE: - Checkbox
				 PAGE: - Setup- Blanking
					Line 12  cmdID= 1256 "
		::= { iqmux61CmdEntry 1256 }


	iqmux61BlankingVIPass625Line325 OBJECT-TYPE
		SYNTAX		INTEGER { disable(0), enable(1) }
		MAX-ACCESS		read-write
		STATUS			current
		DESCRIPTION
				"TYPE: - Checkbox
				 PAGE: - Setup- Blanking
					Line 325  cmdID= 1277 "
		::= { iqmux61CmdEntry 1277 }


	iqmux61BlankingVIPass625Line13 OBJECT-TYPE
		SYNTAX		INTEGER { disable(0), enable(1) }
		MAX-ACCESS		read-write
		STATUS			current
		DESCRIPTION
				"TYPE: - Checkbox
				 PAGE: - Setup- Blanking
					Line 13  cmdID= 1257 "
		::= { iqmux61CmdEntry 1257 }


	iqmux61BlankingVIPass625Line326 OBJECT-TYPE
		SYNTAX		INTEGER { disable(0), enable(1) }
		MAX-ACCESS		read-write
		STATUS			current
		DESCRIPTION
				"TYPE: - Checkbox
				 PAGE: - Setup- Blanking
					Line 326  cmdID= 1278 "
		::= { iqmux61CmdEntry 1278 }


	iqmux61BlankingVIPass625Line14 OBJECT-TYPE
		SYNTAX		INTEGER { disable(0), enable(1) }
		MAX-ACCESS		read-write
		STATUS			current
		DESCRIPTION
				"TYPE: - Checkbox
				 PAGE: - Setup- Blanking
					Line 14  cmdID= 1258 "
		::= { iqmux61CmdEntry 1258 }


	iqmux61BlankingVIPass625Line327 OBJECT-TYPE
		SYNTAX		INTEGER { disable(0), enable(1) }
		MAX-ACCESS		read-write
		STATUS			current
		DESCRIPTION
				"TYPE: - Checkbox
				 PAGE: - Setup- Blanking
					Line 327  cmdID= 1279 "
		::= { iqmux61CmdEntry 1279 }


	iqmux61BlankingVIPass625Line15 OBJECT-TYPE
		SYNTAX		INTEGER { disable(0), enable(1) }
		MAX-ACCESS		read-write
		STATUS			current
		DESCRIPTION
				"TYPE: - Checkbox
				 PAGE: - Setup- Blanking
					Line 15  cmdID= 1259 "
		::= { iqmux61CmdEntry 1259 }


	iqmux61BlankingVIPass625Line328 OBJECT-TYPE
		SYNTAX		INTEGER { disable(0), enable(1) }
		MAX-ACCESS		read-write
		STATUS			current
		DESCRIPTION
				"TYPE: - Checkbox
				 PAGE: - Setup- Blanking
					Line 328  cmdID= 1280 "
		::= { iqmux61CmdEntry 1280 }


	iqmux61BlankingVIPass625Line16 OBJECT-TYPE
		SYNTAX		INTEGER { disable(0), enable(1) }
		MAX-ACCESS		read-write
		STATUS			current
		DESCRIPTION
				"TYPE: - Checkbox
				 PAGE: - Setup- Blanking
					Line 16  cmdID= 1260 "
		::= { iqmux61CmdEntry 1260 }


	iqmux61BlankingVIPass625Line329 OBJECT-TYPE
		SYNTAX		INTEGER { disable(0), enable(1) }
		MAX-ACCESS		read-write
		STATUS			current
		DESCRIPTION
				"TYPE: - Checkbox
				 PAGE: - Setup- Blanking
					Line 329  cmdID= 1281 "
		::= { iqmux61CmdEntry 1281 }


	iqmux61BlankingVIPass625Line17 OBJECT-TYPE
		SYNTAX		INTEGER { disable(0), enable(1) }
		MAX-ACCESS		read-write
		STATUS			current
		DESCRIPTION
				"TYPE: - Checkbox
				 PAGE: - Setup- Blanking
					Line 17  cmdID= 1261 "
		::= { iqmux61CmdEntry 1261 }


	iqmux61BlankingVIPass625Line330 OBJECT-TYPE
		SYNTAX		INTEGER { disable(0), enable(1) }
		MAX-ACCESS		read-write
		STATUS			current
		DESCRIPTION
				"TYPE: - Checkbox
				 PAGE: - Setup- Blanking
					Line 330  cmdID= 1282 "
		::= { iqmux61CmdEntry 1282 }


	iqmux61BlankingVIPass625Line18 OBJECT-TYPE
		SYNTAX		INTEGER { disable(0), enable(1) }
		MAX-ACCESS		read-write
		STATUS			current
		DESCRIPTION
				"TYPE: - Checkbox
				 PAGE: - Setup- Blanking
					Line 18  cmdID= 1262 "
		::= { iqmux61CmdEntry 1262 }


	iqmux61BlankingVIPass625Line331 OBJECT-TYPE
		SYNTAX		INTEGER { disable(0), enable(1) }
		MAX-ACCESS		read-write
		STATUS			current
		DESCRIPTION
				"TYPE: - Checkbox
				 PAGE: - Setup- Blanking
					Line 331  cmdID= 1283 "
		::= { iqmux61CmdEntry 1283 }


	iqmux61BlankingVIPass625Line19 OBJECT-TYPE
		SYNTAX		INTEGER { disable(0), enable(1) }
		MAX-ACCESS		read-write
		STATUS			current
		DESCRIPTION
				"TYPE: - Checkbox
				 PAGE: - Setup- Blanking
					Line 19  cmdID= 1263 "
		::= { iqmux61CmdEntry 1263 }


	iqmux61BlankingVIPass625Line332 OBJECT-TYPE
		SYNTAX		INTEGER { disable(0), enable(1) }
		MAX-ACCESS		read-write
		STATUS			current
		DESCRIPTION
				"TYPE: - Checkbox
				 PAGE: - Setup- Blanking
					Line 332  cmdID= 1284 "
		::= { iqmux61CmdEntry 1284 }


	iqmux61BlankingVIPass625Line20 OBJECT-TYPE
		SYNTAX		INTEGER { disable(0), enable(1) }
		MAX-ACCESS		read-write
		STATUS			current
		DESCRIPTION
				"TYPE: - Checkbox
				 PAGE: - Setup- Blanking
					Line 20  cmdID= 1264 "
		::= { iqmux61CmdEntry 1264 }


	iqmux61BlankingVIPass625Line333 OBJECT-TYPE
		SYNTAX		INTEGER { disable(0), enable(1) }
		MAX-ACCESS		read-write
		STATUS			current
		DESCRIPTION
				"TYPE: - Checkbox
				 PAGE: - Setup- Blanking
					Line 333  cmdID= 1285 "
		::= { iqmux61CmdEntry 1285 }


	iqmux61BlankingVIPass625Line21 OBJECT-TYPE
		SYNTAX		INTEGER { disable(0), enable(1) }
		MAX-ACCESS		read-write
		STATUS			current
		DESCRIPTION
				"TYPE: - Checkbox
				 PAGE: - Setup- Blanking
					Line 21  cmdID= 1265 "
		::= { iqmux61CmdEntry 1265 }


	iqmux61BlankingVIPass625Line334 OBJECT-TYPE
		SYNTAX		INTEGER { disable(0), enable(1) }
		MAX-ACCESS		read-write
		STATUS			current
		DESCRIPTION
				"TYPE: - Checkbox
				 PAGE: - Setup- Blanking
					Line 334  cmdID= 1286 "
		::= { iqmux61CmdEntry 1286 }


	iqmux61BlankingVIPass625Line22 OBJECT-TYPE
		SYNTAX		INTEGER { disable(0), enable(1) }
		MAX-ACCESS		read-write
		STATUS			current
		DESCRIPTION
				"TYPE: - Checkbox
				 PAGE: - Setup- Blanking
					Line 22  cmdID= 1266 "
		::= { iqmux61CmdEntry 1266 }


	iqmux61BlankingVIPass625Line335 OBJECT-TYPE
		SYNTAX		INTEGER { disable(0), enable(1) }
		MAX-ACCESS		read-write
		STATUS			current
		DESCRIPTION
				"TYPE: - Checkbox
				 PAGE: - Setup- Blanking
					Line 335  cmdID= 1287 "
		::= { iqmux61CmdEntry 1287 }


	iqmux61BlankingVIPass625Line23 OBJECT-TYPE
		SYNTAX		INTEGER { disable(0), enable(1) }
		MAX-ACCESS		read-write
		STATUS			current
		DESCRIPTION
				"TYPE: - Checkbox
				 PAGE: - Setup- Blanking
					Line 23  cmdID= 1267 "
		::= { iqmux61CmdEntry 1267 }


	iqmux61SetupBlankingHancBlank OBJECT-TYPE
		SYNTAX		INTEGER { disable(0), enable(1) }
		MAX-ACCESS		read-write
		STATUS			current
		DESCRIPTION
				"TYPE: - Checkbox
				 PAGE: - Setup- Blanking
					Hanc Blank  cmdID= 2971 "
		::= { iqmux61CmdEntry 2971 }


	iqmux61SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqmux61CmdEntry 2489 }


	iqmux61SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1
					Min = 100.0 Hz  Max = 15000.0 Hz  Step = 100.0 Hz "
		::= { iqmux61CmdEntry 2487 }


	iqmux61SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1
					Min = 100.0 Hz  Max = 15000.0 Hz  Step = 100.0 Hz "
		::= { iqmux61CmdEntry 2488 }


	iqmux61SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1
					Min = 4.0 dB  Max = 24.0 dB  Step = 1.0 dB "
		::= { iqmux61CmdEntry 3055 }


	iqmux61SetupAudioToneADCLineUp OBJECT-TYPE
		SYNTAX		INTEGER
		MAX-ACCESS		read-write
		STATUS			current
		DESCRIPTION
				"TYPE: - Number
				 PAGE: - Setup- Audio Tone
					ADC Line Up  cmdID= 3545  min= -200  max= 200  step= 10  format= %2.0f dBu  div_scale= 10
					Min = -20 dBu  Max = 20 dBu  Step =  1 dBu "
		::= { iqmux61CmdEntry 3545 }


	iqmux61SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972
					instant  value= 0
					fast  value= 1
					medium  value= 2
					slow  value= 3
					slowest  value= 4  "
		::= { iqmux61CmdEntry 2972 }


	iqmux61SetupChannelStatus OBJECT-TYPE
		SYNTAX		RollCallString
		MAX-ACCESS		read-write
		STATUS			current
		DESCRIPTION
				"TYPE: - Editstring
				 PAGE: - Setup
					Channel Status  cmdID= 3060  "
		::= { iqmux61CmdEntry 3060 }


	iqmux61GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqmux61CmdEntry 2605 }


	iqmux61GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqmux61CmdEntry 3053 }


	iqmux61GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqmux61CmdEntry 3054 }


	iqmux61GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 12  step= 1  format= %.0f  div_scale= 1
					Min = -1  Max = 12  Step = 1 "
		::= { iqmux61CmdEntry 2011 }


	iqmux61GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqmux61CmdEntry 2048 }


	iqmux61GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqmux61CmdEntry 3540 }


	iqmux61GPIIOGPIOutputOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2013
					input Present  value= 0
					standard 625  value= 1
					video Delay  value= 2
					unused  value= 3  "
		::= { iqmux61CmdEntry 2013 }


	iqmux61GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqmux61CmdEntry 2049 }


	iqmux61GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqmux61CmdEntry 2014 }


	iqmux61SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 12  step= 1  format= %.0f  div_scale= 1
					Min = -1  Max = 12  Step = 1 "
		::= { iqmux61CmdEntry 2875 }


	iqmux61SetupGPIIOOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2877
					input Present  value= 0
					standard 625  value= 1
					video Delay  value= 2
					unused  value= 3  "
		::= { iqmux61CmdEntry 2877 }


	iqmux61SetupRollTrackRollTrackIndex OBJECT-TYPE
		SYNTAX		INTEGER
		MAX-ACCESS		read-write
		STATUS			current
		DESCRIPTION
				"TYPE: - Number
				 PAGE: - Setup- RollTrack
					RollTrack Index  cmdID= 1495  min= 0  max= 49  step= 1  format= %.0f  div_scale= 1
					Min = 0  Max = 49  Step = 1 "
		::= { iqmux61CmdEntry 1495 }


	iqmux61SetupRollTrackRollTrackSource OBJECT-TYPE
		SYNTAX		INTEGER
		MAX-ACCESS		read-write
		STATUS			current
		DESCRIPTION
				"TYPE: - Number
				 PAGE: - Setup- RollTrack
					RollTrack Source  cmdID= 1496  min= -1  max= 36  step= 1  format= %.0f  div_scale= 1
					Min = -1  Max = 36  Step = 1 "
		::= { iqmux61CmdEntry 1496 }


	iqmux61SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqmux61CmdEntry 1513 }


	iqmux61SetupRollTrackRollTrackAddress OBJECT-TYPE
		SYNTAX		RollCallString
		MAX-ACCESS		read-write
		STATUS			current
		DESCRIPTION
				"TYPE: - Editstring
				 PAGE: - Setup- RollTrack
					RollTrack Address  cmdID= 1497  "
		::= { iqmux61CmdEntry 1497 }


	iqmux61SetupRollTrackRollTrackCommand OBJECT-TYPE
		SYNTAX		RollCallString
		MAX-ACCESS		read-write
		STATUS			current
		DESCRIPTION
				"TYPE: - Editstring
				 PAGE: - Setup- RollTrack
					RollTrack Command  cmdID= 1498  "
		::= { iqmux61CmdEntry 1498 }


	iqmux61SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqmux61CmdEntry 1514 }


	iqmux61SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqmux61CmdEntry 1511 }


	iqmux61SetupRollTrackRollTrackIndexExt OBJECT-TYPE
		SYNTAX		INTEGER
		MAX-ACCESS		read-write
		STATUS			current
		DESCRIPTION
				"TYPE: - Number
				 PAGE: - Setup- RollTrack
					RollTrack Index  cmdID= 2870  min= 0  max= 49  step= 1  format= %.0f  div_scale= 1
					Min = 0  Max = 49  Step = 1 "
		::= { iqmux61CmdEntry 2870 }


	iqmux61SetupRollTrackRollTrackSourceExt OBJECT-TYPE
		SYNTAX		INTEGER
		MAX-ACCESS		read-write
		STATUS			current
		DESCRIPTION
				"TYPE: - Number
				 PAGE: - Setup- RollTrack
					RollTrack Source  cmdID= 2871  min= -1  max= 36  step= 1  format= %.0f  div_scale= 1
					Min = -1  Max = 36  Step = 1 "
		::= { iqmux61CmdEntry 2871 }


	iqmux61SetupRollTrackRollTrackAddressExt OBJECT-TYPE
		SYNTAX		RollCallString
		MAX-ACCESS		read-write
		STATUS			current
		DESCRIPTION
				"TYPE: - Editstring
				 PAGE: - Setup- RollTrack
					RollTrack Address  cmdID= 2872  "
		::= { iqmux61CmdEntry 2872 }


	iqmux61SetupRollTrackRollTrackCommandExt OBJECT-TYPE
		SYNTAX		RollCallString
		MAX-ACCESS		read-write
		STATUS			current
		DESCRIPTION
				"TYPE: - Editstring
				 PAGE: - Setup- RollTrack
					RollTrack Command  cmdID= 2873  "
		::= { iqmux61CmdEntry 2873 }


	iqmux61SetupLoggingInput OBJECT-TYPE
		SYNTAX		INTEGER { disable(0), enable(1) }
		MAX-ACCESS		read-write
		STATUS			current
		DESCRIPTION
				"TYPE: - Checkbox
				 PAGE: - Setup- Logging
					Input  cmdID= 1060 "
		::= { iqmux61CmdEntry 1060 }


	iqmux61SetupLoggingStd OBJECT-TYPE
		SYNTAX		INTEGER { disable(0), enable(1) }
		MAX-ACCESS		read-write
		STATUS			current
		DESCRIPTION
				"TYPE: - Checkbox
				 PAGE: - Setup- Logging
					Std  cmdID= 1061 "
		::= { iqmux61CmdEntry 1061 }


	iqmux61SetupLoggingInput1 OBJECT-TYPE
		SYNTAX		INTEGER { disable(0), enable(1) }
		MAX-ACCESS		read-write
		STATUS			current
		DESCRIPTION
				"TYPE: - Checkbox
				 PAGE: - Setup- Logging
					Input1  cmdID= 1094 "
		::= { iqmux61CmdEntry 1094 }


	iqmux61SetupLoggingStd1 OBJECT-TYPE
		SYNTAX		INTEGER { disable(0), enable(1) }
		MAX-ACCESS		read-write
		STATUS			current
		DESCRIPTION
				"TYPE: - Checkbox
				 PAGE: - Setup- Logging
					Std1  cmdID= 1097 "
		::= { iqmux61CmdEntry 1097 }


	iqmux61SetupLoggingInput2 OBJECT-TYPE
		SYNTAX		INTEGER { disable(0), enable(1) }
		MAX-ACCESS		read-write
		STATUS			current
		DESCRIPTION
				"TYPE: - Checkbox
				 PAGE: - Setup- Logging
					Input2  cmdID= 1095 "
		::= { iqmux61CmdEntry 1095 }


	iqmux61SetupLoggingStd2 OBJECT-TYPE
		SYNTAX		INTEGER { disable(0), enable(1) }
		MAX-ACCESS		read-write
		STATUS			current
		DESCRIPTION
				"TYPE: - Checkbox
				 PAGE: - Setup- Logging
					Std2  cmdID= 1098 "
		::= { iqmux61CmdEntry 1098 }


	iqmux61SetupLoggingEDH OBJECT-TYPE
		SYNTAX		INTEGER { disable(0), enable(1) }
		MAX-ACCESS		read-write
		STATUS			current
		DESCRIPTION
				"TYPE: - Checkbox
				 PAGE: - Setup- Logging
					EDH  cmdID= 1064 "
		::= { iqmux61CmdEntry 1064 }


	iqmux61SetupLoggingEDHErrors OBJECT-TYPE
		SYNTAX		INTEGER { disable(0), enable(1) }
		MAX-ACCESS		read-write
		STATUS			current
		DESCRIPTION
				"TYPE: - Checkbox
				 PAGE: - Setup- Logging
					EDH Errors  cmdID= 1070 "
		::= { iqmux61CmdEntry 1070 }


	iqmux61SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqmux61CmdEntry 1106 }


	iqmux61SetupLoggingDeembed1 OBJECT-TYPE
		SYNTAX		INTEGER { disable(0), enable(1) }
		MAX-ACCESS		read-write
		STATUS			current
		DESCRIPTION
				"TYPE: - Checkbox
				 PAGE: - Setup- Logging
					De-embed 1  cmdID= 1120 "
		::= { iqmux61CmdEntry 1120 }


	iqmux61SetupLoggingDeembed2 OBJECT-TYPE
		SYNTAX		INTEGER { disable(0), enable(1) }
		MAX-ACCESS		read-write
		STATUS			current
		DESCRIPTION
				"TYPE: - Checkbox
				 PAGE: - Setup- Logging
					De-embed 2  cmdID= 1121 "
		::= { iqmux61CmdEntry 1121 }


	iqmux61SetupLoggingDeembed3 OBJECT-TYPE
		SYNTAX		INTEGER { disable(0), enable(1) }
		MAX-ACCESS		read-write
		STATUS			current
		DESCRIPTION
				"TYPE: - Checkbox
				 PAGE: - Setup- Logging
					De-embed 3  cmdID= 1122 "
		::= { iqmux61CmdEntry 1122 }


	iqmux61SetupLoggingDeembed4 OBJECT-TYPE
		SYNTAX		INTEGER { disable(0), enable(1) }
		MAX-ACCESS		read-write
		STATUS			current
		DESCRIPTION
				"TYPE: - Checkbox
				 PAGE: - Setup- Logging
					De-embed 4  cmdID= 1123 "
		::= { iqmux61CmdEntry 1123 }


	iqmux61SetupLoggingDeembed5 OBJECT-TYPE
		SYNTAX		INTEGER { disable(0), enable(1) }
		MAX-ACCESS		read-write
		STATUS			current
		DESCRIPTION
				"TYPE: - Checkbox
				 PAGE: - Setup- Logging
					De-embed 5  cmdID= 1124 "
		::= { iqmux61CmdEntry 1124 }


	iqmux61SetupLoggingDeembed6 OBJECT-TYPE
		SYNTAX		INTEGER { disable(0), enable(1) }
		MAX-ACCESS		read-write
		STATUS			current
		DESCRIPTION
				"TYPE: - Checkbox
				 PAGE: - Setup- Logging
					De-embed 6  cmdID= 1125 "
		::= { iqmux61CmdEntry 1125 }


	iqmux61SetupLoggingDeembed7 OBJECT-TYPE
		SYNTAX		INTEGER { disable(0), enable(1) }
		MAX-ACCESS		read-write
		STATUS			current
		DESCRIPTION
				"TYPE: - Checkbox
				 PAGE: - Setup- Logging
					De-embed 7  cmdID= 1126 "
		::= { iqmux61CmdEntry 1126 }


	iqmux61SetupLoggingDeembed8 OBJECT-TYPE
		SYNTAX		INTEGER { disable(0), enable(1) }
		MAX-ACCESS		read-write
		STATUS			current
		DESCRIPTION
				"TYPE: - Checkbox
				 PAGE: - Setup- Logging
					De-embed 8  cmdID= 1127 "
		::= { iqmux61CmdEntry 1127 }


	iqmux61SetupLoggingnPCM1 OBJECT-TYPE
		SYNTAX		INTEGER { disable(0), enable(1) }
		MAX-ACCESS		read-write
		STATUS			current
		DESCRIPTION
				"TYPE: - Checkbox
				 PAGE: - Setup- Logging
					nPCM 1  cmdID= 1128 "
		::= { iqmux61CmdEntry 1128 }


	iqmux61SetupLoggingnPCM2 OBJECT-TYPE
		SYNTAX		INTEGER { disable(0), enable(1) }
		MAX-ACCESS		read-write
		STATUS			current
		DESCRIPTION
				"TYPE: - Checkbox
				 PAGE: - Setup- Logging
					nPCM 2  cmdID= 1129 "
		::= { iqmux61CmdEntry 1129 }


	iqmux61SetupLoggingnPCM3 OBJECT-TYPE
		SYNTAX		INTEGER { disable(0), enable(1) }
		MAX-ACCESS		read-write
		STATUS			current
		DESCRIPTION
				"TYPE: - Checkbox
				 PAGE: - Setup- Logging
					nPCM 3  cmdID= 1130 "
		::= { iqmux61CmdEntry 1130 }


	iqmux61SetupLoggingnPCM4 OBJECT-TYPE
		SYNTAX		INTEGER { disable(0), enable(1) }
		MAX-ACCESS		read-write
		STATUS			current
		DESCRIPTION
				"TYPE: - Checkbox
				 PAGE: - Setup- Logging
					nPCM 4  cmdID= 1131 "
		::= { iqmux61CmdEntry 1131 }


	iqmux61SetupLoggingnPCM5 OBJECT-TYPE
		SYNTAX		INTEGER { disable(0), enable(1) }
		MAX-ACCESS		read-write
		STATUS			current
		DESCRIPTION
				"TYPE: - Checkbox
				 PAGE: - Setup- Logging
					nPCM 5  cmdID= 1132 "
		::= { iqmux61CmdEntry 1132 }


	iqmux61SetupLoggingnPCM6 OBJECT-TYPE
		SYNTAX		INTEGER { disable(0), enable(1) }
		MAX-ACCESS		read-write
		STATUS			current
		DESCRIPTION
				"TYPE: - Checkbox
				 PAGE: - Setup- Logging
					nPCM 6  cmdID= 1133 "
		::= { iqmux61CmdEntry 1133 }


	iqmux61SetupLoggingnPCM7 OBJECT-TYPE
		SYNTAX		INTEGER { disable(0), enable(1) }
		MAX-ACCESS		read-write
		STATUS			current
		DESCRIPTION
				"TYPE: - Checkbox
				 PAGE: - Setup- Logging
					nPCM 7  cmdID= 1134 "
		::= { iqmux61CmdEntry 1134 }


	iqmux61SetupLoggingnPCM8 OBJECT-TYPE
		SYNTAX		INTEGER { disable(0), enable(1) }
		MAX-ACCESS		read-write
		STATUS			current
		DESCRIPTION
				"TYPE: - Checkbox
				 PAGE: - Setup- Logging
					nPCM 8  cmdID= 1135 "
		::= { iqmux61CmdEntry 1135 }


	iqmux61SetupLoggingAES1 OBJECT-TYPE
		SYNTAX		INTEGER { disable(0), enable(1) }
		MAX-ACCESS		read-write
		STATUS			current
		DESCRIPTION
				"TYPE: - Checkbox
				 PAGE: - Setup- Logging
					AES 1  cmdID= 1108 "
		::= { iqmux61CmdEntry 1108 }


	iqmux61SetupLoggingAES2 OBJECT-TYPE
		SYNTAX		INTEGER { disable(0), enable(1) }
		MAX-ACCESS		read-write
		STATUS			current
		DESCRIPTION
				"TYPE: - Checkbox
				 PAGE: - Setup- Logging
					AES 2  cmdID= 1109 "
		::= { iqmux61CmdEntry 1109 }


	iqmux61SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqmux61CmdEntry 1112 }


	iqmux61SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqmux61CmdEntry 1113 }


	iqmux61SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqmux61CmdEntry 1114 }


	iqmux61SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqmux61CmdEntry 1115 }


	iqmux61SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqmux61CmdEntry 1116 }


	iqmux61SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqmux61CmdEntry 1117 }


	iqmux61SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqmux61CmdEntry 1118 }


	iqmux61SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqmux61CmdEntry 1119 }


	iqmux61SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqmux61CmdEntry 1069 }


	iqmux61SetupLoggingStatusINPUT OBJECT-TYPE
		SYNTAX		RollCallString
		MAX-ACCESS		read-only
		STATUS			current
		DESCRIPTION
				"TYPE: - Display
				 PAGE: - Setup- Logging Status
					INPUT=  cmdID= 2980  format=   "
		::= { iqmux61CmdEntry 2980 }


	iqmux61SetupLoggingStatusSTD OBJECT-TYPE
		SYNTAX		RollCallString
		MAX-ACCESS		read-only
		STATUS			current
		DESCRIPTION
				"TYPE: - Display
				 PAGE: - Setup- Logging Status
					STD=  cmdID= 2981  format=   "
		::= { iqmux61CmdEntry 2981 }


	iqmux61SetupLoggingStatusINPUT1 OBJECT-TYPE
		SYNTAX		RollCallString
		MAX-ACCESS		read-only
		STATUS			current
		DESCRIPTION
				"TYPE: - Display
				 PAGE: - Setup- Logging Status
					INPUT1=  cmdID= 2982  format=   "
		::= { iqmux61CmdEntry 2982 }


	iqmux61SetupLoggingStatusSTD1 OBJECT-TYPE
		SYNTAX		RollCallString
		MAX-ACCESS		read-only
		STATUS			current
		DESCRIPTION
				"TYPE: - Display
				 PAGE: - Setup- Logging Status
					STD1=  cmdID= 2983  format=   "
		::= { iqmux61CmdEntry 2983 }


	iqmux61SetupLoggingStatusINPUT2 OBJECT-TYPE
		SYNTAX		RollCallString
		MAX-ACCESS		read-only
		STATUS			current
		DESCRIPTION
				"TYPE: - Display
				 PAGE: - Setup- Logging Status
					INPUT2=  cmdID= 2984  format=   "
		::= { iqmux61CmdEntry 2984 }


	iqmux61SetupLoggingStatusSTD2 OBJECT-TYPE
		SYNTAX		RollCallString
		MAX-ACCESS		read-only
		STATUS			current
		DESCRIPTION
				"TYPE: - Display
				 PAGE: - Setup- Logging Status
					STD2=  cmdID= 2985  format=   "
		::= { iqmux61CmdEntry 2985 }


	iqmux61SetupLoggingStatusEDH OBJECT-TYPE
		SYNTAX		RollCallString
		MAX-ACCESS		read-only
		STATUS			current
		DESCRIPTION
				"TYPE: - Display
				 PAGE: - Setup- Logging Status
					EDH=  cmdID= 2987  format=   "
		::= { iqmux61CmdEntry 2987 }


	iqmux61SetupLoggingStatusERRSEC OBJECT-TYPE
		SYNTAX		RollCallString
		MAX-ACCESS		read-only
		STATUS			current
		DESCRIPTION
				"TYPE: - Display
				 PAGE: - Setup- Logging Status
					ERRSEC=  cmdID= 2988  format=   "
		::= { iqmux61CmdEntry 2988 }


	iqmux61SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqmux61CmdEntry 2989 }


	iqmux61SetupLoggingStatusDEEMBED1 OBJECT-TYPE
		SYNTAX		RollCallString
		MAX-ACCESS		read-only
		STATUS			current
		DESCRIPTION
				"TYPE: - Display
				 PAGE: - Setup- Logging Status
					DEEMBED1=  cmdID= 3014  format=   "
		::= { iqmux61CmdEntry 3014 }


	iqmux61SetupLoggingStatusDEEMBED2 OBJECT-TYPE
		SYNTAX		RollCallString
		MAX-ACCESS		read-only
		STATUS			current
		DESCRIPTION
				"TYPE: - Display
				 PAGE: - Setup- Logging Status
					DEEMBED2=  cmdID= 3015  format=   "
		::= { iqmux61CmdEntry 3015 }


	iqmux61SetupLoggingStatusDEEMBED3 OBJECT-TYPE
		SYNTAX		RollCallString
		MAX-ACCESS		read-only
		STATUS			current
		DESCRIPTION
				"TYPE: - Display
				 PAGE: - Setup- Logging Status
					DEEMBED3=  cmdID= 3016  format=   "
		::= { iqmux61CmdEntry 3016 }


	iqmux61SetupLoggingStatusDEEMBED4 OBJECT-TYPE
		SYNTAX		RollCallString
		MAX-ACCESS		read-only
		STATUS			current
		DESCRIPTION
				"TYPE: - Display
				 PAGE: - Setup- Logging Status
					DEEMBED4=  cmdID= 3017  format=   "
		::= { iqmux61CmdEntry 3017 }


	iqmux61SetupLoggingStatusDEEMBED5 OBJECT-TYPE
		SYNTAX		RollCallString
		MAX-ACCESS		read-only
		STATUS			current
		DESCRIPTION
				"TYPE: - Display
				 PAGE: - Setup- Logging Status
					DEEMBED5=  cmdID= 3018  format=   "
		::= { iqmux61CmdEntry 3018 }


	iqmux61SetupLoggingStatusDEEMBED6 OBJECT-TYPE
		SYNTAX		RollCallString
		MAX-ACCESS		read-only
		STATUS			current
		DESCRIPTION
				"TYPE: - Display
				 PAGE: - Setup- Logging Status
					DEEMBED6=  cmdID= 3019  format=   "
		::= { iqmux61CmdEntry 3019 }


	iqmux61SetupLoggingStatusDEEMBED7 OBJECT-TYPE
		SYNTAX		RollCallString
		MAX-ACCESS		read-only
		STATUS			current
		DESCRIPTION
				"TYPE: - Display
				 PAGE: - Setup- Logging Status
					DEEMBED7=  cmdID= 3020  format=   "
		::= { iqmux61CmdEntry 3020 }


	iqmux61SetupLoggingStatusDEEMBED8 OBJECT-TYPE
		SYNTAX		RollCallString
		MAX-ACCESS		read-only
		STATUS			current
		DESCRIPTION
				"TYPE: - Display
				 PAGE: - Setup- Logging Status
					DEEMBED8=  cmdID= 3021  format=   "
		::= { iqmux61CmdEntry 3021 }


	iqmux61SetupLoggingStatusNPCM1 OBJECT-TYPE
		SYNTAX		RollCallString
		MAX-ACCESS		read-only
		STATUS			current
		DESCRIPTION
				"TYPE: - Display
				 PAGE: - Setup- Logging Status
					NPCM1=  cmdID= 3022  format=   "
		::= { iqmux61CmdEntry 3022 }


	iqmux61SetupLoggingStatusNPCM2 OBJECT-TYPE
		SYNTAX		RollCallString
		MAX-ACCESS		read-only
		STATUS			current
		DESCRIPTION
				"TYPE: - Display
				 PAGE: - Setup- Logging Status
					NPCM2=  cmdID= 3023  format=   "
		::= { iqmux61CmdEntry 3023 }


	iqmux61SetupLoggingStatusNPCM3 OBJECT-TYPE
		SYNTAX		RollCallString
		MAX-ACCESS		read-only
		STATUS			current
		DESCRIPTION
				"TYPE: - Display
				 PAGE: - Setup- Logging Status
					NPCM3=  cmdID= 3024  format=   "
		::= { iqmux61CmdEntry 3024 }


	iqmux61SetupLoggingStatusNPCM4 OBJECT-TYPE
		SYNTAX		RollCallString
		MAX-ACCESS		read-only
		STATUS			current
		DESCRIPTION
				"TYPE: - Display
				 PAGE: - Setup- Logging Status
					NPCM4=  cmdID= 3025  format=   "
		::= { iqmux61CmdEntry 3025 }


	iqmux61SetupLoggingStatusNPCM5 OBJECT-TYPE
		SYNTAX		RollCallString
		MAX-ACCESS		read-only
		STATUS			current
		DESCRIPTION
				"TYPE: - Display
				 PAGE: - Setup- Logging Status
					NPCM5=  cmdID= 3026  format=   "
		::= { iqmux61CmdEntry 3026 }


	iqmux61SetupLoggingStatusNPCM6 OBJECT-TYPE
		SYNTAX		RollCallString
		MAX-ACCESS		read-only
		STATUS			current
		DESCRIPTION
				"TYPE: - Display
				 PAGE: - Setup- Logging Status
					NPCM6=  cmdID= 3027  format=   "
		::= { iqmux61CmdEntry 3027 }


	iqmux61SetupLoggingStatusNPCM7 OBJECT-TYPE
		SYNTAX		RollCallString
		MAX-ACCESS		read-only
		STATUS			current
		DESCRIPTION
				"TYPE: - Display
				 PAGE: - Setup- Logging Status
					NPCM7=  cmdID= 3028  format=   "
		::= { iqmux61CmdEntry 3028 }


	iqmux61SetupLoggingStatusNPCM8 OBJECT-TYPE
		SYNTAX		RollCallString
		MAX-ACCESS		read-only
		STATUS			current
		DESCRIPTION
				"TYPE: - Display
				 PAGE: - Setup- Logging Status
					NPCM8=  cmdID= 3029  format=   "
		::= { iqmux61CmdEntry 3029 }


	iqmux61SetupLoggingStatusAES1 OBJECT-TYPE
		SYNTAX		RollCallString
		MAX-ACCESS		read-only
		STATUS			current
		DESCRIPTION
				"TYPE: - Display
				 PAGE: - Setup- Logging Status
					AES1=  cmdID= 2994  format=   "
		::= { iqmux61CmdEntry 2994 }


	iqmux61SetupLoggingStatusAES2 OBJECT-TYPE
		SYNTAX		RollCallString
		MAX-ACCESS		read-only
		STATUS			current
		DESCRIPTION
				"TYPE: - Display
				 PAGE: - Setup- Logging Status
					AES2=  cmdID= 2995  format=   "
		::= { iqmux61CmdEntry 2995 }


	iqmux61SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqmux61CmdEntry 2998 }


	iqmux61SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqmux61CmdEntry 2999 }


	iqmux61SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqmux61CmdEntry 3000 }


	iqmux61SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqmux61CmdEntry 3001 }


	iqmux61SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqmux61CmdEntry 3002 }


	iqmux61SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqmux61CmdEntry 3003 }


	iqmux61SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqmux61CmdEntry 3004 }


	iqmux61SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqmux61CmdEntry 3005 }


	iqmux61SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqmux61CmdEntry 2990 }


	iqmux61SetupInformationWindow OBJECT-TYPE
		SYNTAX		INTEGER {
							val_Input_Status(0),
							val_EDH_ANC_Status(1),
							val_Audio_Input_Status(2)
							}
		MAX-ACCESS		read-write
		STATUS			current
		DESCRIPTION
				"TYPE: - Button
				 PAGE: - Setup- Information Window
					input Status  cmdID= 1915  value= 0
					eDH & ANC Status  cmdID= 1915  value= 1
					audio Input Status  cmdID= 1915  value= 2  "
		::= { iqmux61CmdEntry 1915 }


	iqmux61SetupInformationWindowResetErrors OBJECT-TYPE
		SYNTAX		INTEGER { noAction(0),reset_Errors(1) }
		MAX-ACCESS		read-write
		STATUS			current
		DESCRIPTION
				"TYPE: - Button
				 PAGE: - Setup- Information Window
					reset Errors  cmdID= 2978  value= 1  "
		::= { iqmux61CmdEntry 2978 }


	iqmux61SetupDefaultOutput OBJECT-TYPE
		SYNTAX		INTEGER {
							val_Video(1),
							val_Freeze(2),
							val_Pattern(3)
							}
		MAX-ACCESS		read-write
		STATUS			current
		DESCRIPTION
				"TYPE: - Button
				 PAGE: - Setup- Default Output
					video  cmdID= 1202  value= 1
					freeze  cmdID= 1202  value= 2
					pattern  cmdID= 1202  value= 3  "
		::= { iqmux61CmdEntry 1202 }


	iqmux61SetupDefaultPattern OBJECT-TYPE
		SYNTAX		INTEGER {
							val_Black(0),
							val_EBU_Colour_Bars(1),
							val_Val_100_Colour_Bars(2),
							val_Ramp(3),
							val_Multiburst(4),
							val_Pulse_Bar(5)
							}
		MAX-ACCESS		read-write
		STATUS			current
		DESCRIPTION
				"TYPE: - Button
				 PAGE: - Setup- Default Output
					black  cmdID= 1038  value= 0
					eBU Colour Bars  cmdID= 1038  value= 1
					100% Colour Bars  cmdID= 1038  value= 2
					ramp  cmdID= 1038  value= 3
					multiburst  cmdID= 1038  value= 4
					pulse & Bar  cmdID= 1038  value= 5  "
		::= { iqmux61CmdEntry 1038 }


	iqmux61SetupUnitSoftwareVersion OBJECT-TYPE
		SYNTAX		RollCallString
		MAX-ACCESS		read-only
		STATUS			current
		DESCRIPTION
				"TYPE: - Display
				 PAGE: - Setup- Unit
					Software Version  cmdID= 2  format=   "
		::= { iqmux61CmdEntry 2 }


	iqmux61SetupUnitSerialNo OBJECT-TYPE
		SYNTAX		RollCallString
		MAX-ACCESS		read-only
		STATUS			current
		DESCRIPTION
				"TYPE: - Display
				 PAGE: - Setup- Unit
					Serial No  cmdID= 1  format=   "
		::= { iqmux61CmdEntry 1 }


	iqmux61SetupUnitPresetUnit OBJECT-TYPE
		SYNTAX		INTEGER { noAction(0),preset_Unit(1) }
		MAX-ACCESS		read-write
		STATUS			current
		DESCRIPTION
				"TYPE: - Button
				 PAGE: - Setup- Unit
					preset Unit  cmdID= 3  value= 1  "
		::= { iqmux61CmdEntry 3 }


	iqmux61SetupUnitRestart OBJECT-TYPE
		SYNTAX		INTEGER { noAction(0),restart(1) }
		MAX-ACCESS		read-write
		STATUS			current
		DESCRIPTION
				"TYPE: - Button
				 PAGE: - Setup- Unit
					restart  cmdID= 4  value= 1  "
		::= { iqmux61CmdEntry 4 }


	iqmux61SetupUnitBuildNo OBJECT-TYPE
		SYNTAX		RollCallString
		MAX-ACCESS		read-only
		STATUS			current
		DESCRIPTION
				"TYPE: - Display
				 PAGE: - Setup- Unit
					Build No  cmdID= 5  format=   "
		::= { iqmux61CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S12345678
--				:
-- Comments		: Serial Number of module
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE              The unit is not locked to the input signal
--				: FAIL              EDH errors have been found on the input signal
--              : OK                No EDH errors found on the input signal
--              : RESET             EDH statistics have been reset
-- Comments		:
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: STDERR            Input signal standard not recognized or no signal
--				: UNKNOWN           Not a selected input standard
--              : 525               Input standard 525
--              : 625               Input standard 625
-- Comments		:
--
---------------------------------------------------------------------------------------------------
-- Header		: STD1
--
-- MIB ref		: swCardEventLogSlotXX       .4.83.84.68.49
-- absolute OID	: 1.3.6.1.4.1.7995.2.6.1.1.XX.4.83.84.68.49
-- Vary			: YES
--
-- Value(s)		: ERR               Not a selected input standard Input 1
--				: 525               Input 1 standard 525
--              : 625               Input 1 standard 625
-- Comments		:
--
---------------------------------------------------------------------------------------------------
-- Header		: STD2
--
-- MIB ref		: swCardEventLogSlotXX       .4.83.84.68.50
-- absolute OID	: 1.3.6.1.4.1.7995.2.6.1.1.XX.4.83.84.68.50
-- Vary			: YES
--
-- Value(s)		: ERR               Not a selected input standard Input 1
--				: 525               Input 1 standard 525
--              : 625               Input 1 standard 625
-- Comments		:
--
---------------------------------------------------------------------------------------------------
-- Header		: AES_1
--
-- MIB ref		: swCardEventLogSlotXX       .5.65.69.83.95.49
-- absolute OID	: 1.3.6.1.4.1.7995.2.6.1.1.XX.5.65.69.83.95.49
-- Vary			: YES
--
-- Value(s)		: NONPCM            Non-PCM signal present on AES input 1
--				: OK                Valid signal present on AES input 1
--              : LOST              Signal not present at AES input 1
-- Comments		:
--
---------------------------------------------------------------------------------------------------
-- Header		: AES_2
--
-- MIB ref		: swCardEventLogSlotXX       .5.65.69.83.95.50
-- absolute OID	: 1.3.6.1.4.1.7995.2.6.1.1.XX.5.65.69.83.95.50
-- Vary			: YES
--
-- Value(s)		: NONPCM            Non-PCM signal present on AES input 1
--				: OK                Valid signal present on AES input 1
--              : LOST              Signal not present at AES input 1
-- Comments		:
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE              No Internal errors detected
--				: FAIL              Internal error detected
--              : FAIL.FPGA_LOAD    Fpga load failure detected
-- Comments		:
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: OK                Valid input signal
--				: ERR               Invalid input signal
--              : LOST              Input signal lost
-- Comments		:
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
--
-- Value(s)		: 0s                Number or Errored Seconds
--				:
-- Comments		: Runtime string
--
---------------------------------------------------------------------------------------------------
-- Header		: INPUT1
--
-- MIB ref		: swCardEventLogSlotXX       .6.73.78.80.85.84.49
-- absolute OID	: 1.3.6.1.4.1.7995.2.6.1.1.XX.6.73.78.80.85.84.49
-- Vary			: YES
--
-- Value(s)		: OK                Valid input 1 signal
--				: ERR               Invalid input 1 signal
--              : LOST              Input 1 signal lost
-- Comments		:
--
---------------------------------------------------------------------------------------------------
-- Header		: INPUT2
--
-- MIB ref		: swCardEventLogSlotXX       .6.73.78.80.85.84.50
-- absolute OID	: 1.3.6.1.4.1.7995.2.6.1.1.XX.6.73.78.80.85.84.50
-- Vary			: YES
--
-- Value(s)		: OK                Valid input 1 signal
--				: ERR               Invalid input 1 signal
--              : LOST              Input 1 signal lost
-- Comments		:
--
---------------------------------------------------------------------------------------------------
-- Header		: NPCM_1
--
-- MIB ref		: swCardEventLogSlotXX       .6.78.80.67.77.95.49
-- absolute OID	: 1.3.6.1.4.1.7995.2.6.1.1.XX.6.78.80.67.77.95.49
-- Vary			: YES
--
-- Value(s)		: NONE              Non-PCM not present on pair 1 of selected SDI input
--				: OK                Non-PCM present on pair 1 of selected SDI input
-- Comments		:
--
---------------------------------------------------------------------------------------------------
-- Header		: NPCM_2
--
-- MIB ref		: swCardEventLogSlotXX       .6.78.80.67.77.95.50
-- absolute OID	: 1.3.6.1.4.1.7995.2.6.1.1.XX.6.78.80.67.77.95.50
-- Vary			: YES
--
-- Value(s)		: NONE              Non-PCM not present on pair 1 of selected SDI input
--				: OK                Non-PCM present on pair 1 of selected SDI input
-- Comments		:
--
---------------------------------------------------------------------------------------------------
-- Header		: NPCM_3
--
-- MIB ref		: swCardEventLogSlotXX       .6.78.80.67.77.95.51
-- absolute OID	: 1.3.6.1.4.1.7995.2.6.1.1.XX.6.78.80.67.77.95.51
-- Vary			: YES
--
-- Value(s)		: NONE              Non-PCM not present on pair 1 of selected SDI input
--				: OK                Non-PCM present on pair 1 of selected SDI input
-- Comments		:
--
---------------------------------------------------------------------------------------------------
-- Header		: NPCM_4
--
-- MIB ref		: swCardEventLogSlotXX       .6.78.80.67.77.95.52
-- absolute OID	: 1.3.6.1.4.1.7995.2.6.1.1.XX.6.78.80.67.77.95.52
-- Vary			: YES
--
-- Value(s)		: NONE              Non-PCM not present on pair 1 of selected SDI input
--				: OK                Non-PCM present on pair 1 of selected SDI input
-- Comments		:
--
---------------------------------------------------------------------------------------------------
-- Header		: NPCM_5
--
-- MIB ref		: swCardEventLogSlotXX       .6.78.80.67.77.95.53
-- absolute OID	: 1.3.6.1.4.1.7995.2.6.1.1.XX.6.78.80.67.77.95.53
-- Vary			: YES
--
-- Value(s)		: NONE              Non-PCM not present on pair 1 of selected SDI input
--				: OK                Non-PCM present on pair 1 of selected SDI input
-- Comments		:
--
---------------------------------------------------------------------------------------------------
-- Header		: NPCM_6
--
-- MIB ref		: swCardEventLogSlotXX       .6.78.80.67.77.95.54
-- absolute OID	: 1.3.6.1.4.1.7995.2.6.1.1.XX.6.78.80.67.77.95.54
-- Vary			: YES
--
-- Value(s)		: NONE              Non-PCM not present on pair 1 of selected SDI input
--				: OK                Non-PCM present on pair 1 of selected SDI input
-- Comments		:
--
---------------------------------------------------------------------------------------------------
-- Header		: NPCM_7
--
-- MIB ref		: swCardEventLogSlotXX       .6.78.80.67.77.95.55
-- absolute OID	: 1.3.6.1.4.1.7995.2.6.1.1.XX.6.78.80.67.77.95.55
-- Vary			: YES
--
-- Value(s)		: NONE              Non-PCM not present on pair 1 of selected SDI input
--				: OK                Non-PCM present on pair 1 of selected SDI input
-- Comments		:
--
---------------------------------------------------------------------------------------------------
-- Header		: NPCM_8
--
-- MIB ref		: swCardEventLogSlotXX       .6.78.80.67.77.95.56
-- absolute OID	: 1.3.6.1.4.1.7995.2.6.1.1.XX.6.78.80.67.77.95.56
-- Vary			: YES
--
-- Value(s)		: NONE              Non-PCM not present on pair 1 of selected SDI input
--				: OK                Non-PCM present on pair 1 of selected SDI input
-- Comments		:
--              :
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number of connected control sessions to this card.
--              : Generated by gateway card.
--
---------------------------------------------------------------------------------------------------
-- Header		: DEEMBED_1
--
-- MIB ref		: swCardEventLogSlotXX       .9.68.69.69.77.66.69.68.95.49
-- absolute OID	: 1.3.6.1.4.1.7995.2.6.1.1.XX.9.68.69.69.77.66.69.68.95.49
-- Vary			: YES
--
-- Value(s)		: NONE              Nothing present on pair 1
--				: OK                Embedded pair 1 present on selected SDI input
-- Comments		:
--
---------------------------------------------------------------------------------------------------
-- Header		: DEEMBED_2
--
-- MIB ref		: swCardEventLogSlotXX       .9.68.69.69.77.66.69.68.95.50
-- absolute OID	: 1.3.6.1.4.1.7995.2.6.1.1.XX.9.68.69.69.77.66.69.68.95.50
-- Vary			: YES
--
-- Value(s)		: NONE              Nothing present on pair 2
--				: OK                Embedded pair 2 present on selected SDI input
-- Comments		:
--
---------------------------------------------------------------------------------------------------
-- Header		: DEEMBED_3
--
-- MIB ref		: swCardEventLogSlotXX       .9.68.69.69.77.66.69.68.95.51
-- absolute OID	: 1.3.6.1.4.1.7995.2.6.1.1.XX.9.68.69.69.77.66.69.68.95.51
-- Vary			: YES
--
-- Value(s)		: NONE              Nothing present on pair 3
--				: OK                Embedded pair 3 present on selected SDI input
-- Comments		:
--
---------------------------------------------------------------------------------------------------
-- Header		: DEEMBED_4
--
-- MIB ref		: swCardEventLogSlotXX       .9.68.69.69.77.66.69.68.95.52
-- absolute OID	: 1.3.6.1.4.1.7995.2.6.1.1.XX.9.68.69.69.77.66.69.68.95.52
-- Vary			: YES
--
-- Value(s)		: NONE              Nothing present on pair 4
--				: OK                Embedded pair 4 present on selected SDI input
-- Comments		:
--
---------------------------------------------------------------------------------------------------
-- Header		: DEEMBED_5
--
-- MIB ref		: swCardEventLogSlotXX       .9.68.69.69.77.66.69.68.95.53
-- absolute OID	: 1.3.6.1.4.1.7995.2.6.1.1.XX.9.68.69.69.77.66.69.68.95.53
-- Vary			: YES
--
-- Value(s)		: NONE              Nothing present on pair 5
--				: OK                Embedded pair 5 present on selected SDI input
-- Comments		:
--
---------------------------------------------------------------------------------------------------
-- Header		: DEEMBED_6
--
-- MIB ref		: swCardEventLogSlotXX       .9.68.69.69.77.66.69.68.95.54
-- absolute OID	: 1.3.6.1.4.1.7995.2.6.1.1.XX.9.68.69.69.77.66.69.68.95.54
-- Vary			: YES
--
-- Value(s)		: NONE              Nothing present on pair 6
--				: OK                Embedded pair 6 present on selected SDI input
-- Comments		:
--
---------------------------------------------------------------------------------------------------
-- Header		: DEEMBED_7
--
-- MIB ref		: swCardEventLogSlotXX       .9.68.69.69.77.66.69.68.95.55
-- absolute OID	: 1.3.6.1.4.1.7995.2.6.1.1.XX.9.68.69.69.77.66.69.68.95.55
-- Vary			: YES
--
-- Value(s)		: NONE              Nothing present on pair 7
--				: OK                Embedded pair 7 present on selected SDI input
-- Comments		:
--
---------------------------------------------------------------------------------------------------
-- Header		: DEEMBED_8
--
-- MIB ref		: swCardEventLogSlotXX       .9.68.69.69.77.66.69.68.95.56
-- absolute OID	: 1.3.6.1.4.1.7995.2.6.1.1.XX.9.68.69.69.77.66.69.68.95.56
-- Vary			: YES
--
-- Value(s)		: NONE              Nothing present on pair 8
--				: OK                Embedded pair 8 present on selected SDI input
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK                RollTrack message sent and received OK
--				: FAIL              RollTrack message not acknowledged
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2006-07-13T16:18:10Z
--				: -
-- Comments		: Last known restart time of module, generated by gateway
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2006-07-13T16:23:36Z
--				:
-- Comments		: Time of last control update. Generated by gateway
--
---------------------------------------------------------------------------------------------------
