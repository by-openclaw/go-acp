-- ************************************************************************************
-- Snell&Wilcox Card:IQBADX
--        Module Id#:111
--       Command Set:7
--          Filename:SNELL-IQBADX-CMD-MIB.mib
--            Author:Jonathan Riches
--              Date:29/06/2005
--              Time:11:00
-- Last Modification:Logging comments added
--   Version Control:CVS $Id: SNELL-IQBADX-CMD-MIB.mib 226 2006-12-21 17:55:54Z nikolaoskatsampekis $
-- Copyright (c) 2006 Snell & Wilcox Ltd
-- All rights reserved.
--
-- ************************************************************************************

SNELL-IQBADX-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQBADX,
    moduleIQBADXMIB
        FROM SNELL-WILCOX-PRODUCT-REG;

 moduleIQBADXCmdMi MODULE-IDENTITY
    LAST-UPDATED "0506291100Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQBADXMIB 1 }




--********************************************************************************
--*
--*  Snell Wilcox Card:
--*  command set:
--*  list commands/menus:
--*
--******************************************************************************
	iqbadxCmdTable OBJECT-TYPE
		SYNTAX			SEQUENCE OF IqbadxCmdEntry
		MAX-ACCESS		not-accessible
		STATUS			current
		DESCRIPTION
				"Note the instance of this table is relected in the command set Version"
		::= { moduleIQBADX 1 }

	iqbadxCmdEntry OBJECT-TYPE
		SYNTAX		IqbadxCmdEntry
		MAX-ACCESS		not-accessible
		STATUS			current
		DESCRIPTION
				"Entry in command table."
		INDEX	{ iqbadxSlotIndex }
		::= { iqbadxCmdTable 1 }

	IqbadxCmdEntry ::=
		SEQUENCE {
			iqbadxSlotIndex
				Unsigned32,
			iqbadxOutputsAnalogueAESOutA
				INTEGER,
			iqbadxOutputsAnalogueAESOutB
				INTEGER,
			iqbadxOutputsAESOutputC
				INTEGER,
			iqbadxOutputsAESOutputD
				INTEGER,
			iqbadxDisplay
				INTEGER,
			iqbadxExtractAnalogueAESOutAInvertL
				INTEGER,
			iqbadxExtractAnalogueAESOutAInvertR
				INTEGER,
			iqbadxExtractAnalogueAESOutAExtract
				INTEGER,
			iqbadxExtractAnalogueAESOutBInvertL
				INTEGER,
			iqbadxExtractAnalogueAESOutBInvertR
				INTEGER,
			iqbadxExtractAnalogueAESOutBExtract
				INTEGER,
			iqbadxExtractAESOutputCInvertL
				INTEGER,
			iqbadxExtractAESOutputCInvertR
				INTEGER,
			iqbadxExtractAESOutputCExtract
				INTEGER,
			iqbadxExtractAESOutputDInvertL
				INTEGER,
			iqbadxExtractAESOutputDInvertR
				INTEGER,
			iqbadxExtractAESOutputDExtract
				INTEGER,
			iqbadxEDHShowStats
				INTEGER,
			iqbadxEDHResetStats
				INTEGER,
			iqbadxMemoryReadMemory
				INTEGER,
			iqbadxMemorySaveMemory
				INTEGER,
			iqbadxMemoryNameUserMemoryMemory1
				RollCallString,
			iqbadxMemoryNameUserMemoryMemory2
				RollCallString,
			iqbadxMemoryNameUserMemoryMemory3
				RollCallString,
			iqbadxMemoryNameUserMemoryMemory4
				RollCallString,
			iqbadxMemoryClearUserMemory
				INTEGER,
			iqbadxSetupLockToRef
				INTEGER,
			iqbadxSetupGPIGPITriggerSetup
				INTEGER,
			iqbadxSetupGPIGPIFunction
				INTEGER,
			iqbadxSetupSetDefaultOutput
				INTEGER,
			iqbadxSetupToneOutputsToneOutputA
				INTEGER,
			iqbadxSetupToneOutputsToneOutputB
				INTEGER,
			iqbadxSetupToneOutputsToneOutputC
				INTEGER,
			iqbadxSetupToneOutputsToneOutputD
				INTEGER,
			iqbadxNamesOutputNamesOutputA
				RollCallString,
			iqbadxNamesOutputNamesOutputB
				RollCallString,
			iqbadxNamesOutputNamesOutputC
				RollCallString,
			iqbadxNamesOutputNamesOutputD
				RollCallString,
			iqbadxNamesInputNamesGroup1Pair1
				RollCallString,
			iqbadxNamesInputNamesGroup1Pair2
				RollCallString,
			iqbadxNamesInputNamesGroup2Pair1
				RollCallString,
			iqbadxNamesInputNamesGroup2Pair2
				RollCallString,
			iqbadxNamesInputNamesGroup3Pair1
				RollCallString,
			iqbadxNamesInputNamesGroup3Pair2
				RollCallString,
			iqbadxNamesInputNamesGroup4Pair1
				RollCallString,
			iqbadxNamesInputNamesGroup4Pair2
				RollCallString,
			iqbadxSetupNamesPresetNames
				INTEGER,
			iqbadxSetupLoggingVideoInputChange
				INTEGER,
			iqbadxSetupLoggingD1AudioChange
				INTEGER,
			iqbadxSetupLoggingEDHErrors
				INTEGER,
			iqbadxSetupLoggingAESRefChange
				INTEGER,
			iqbadxSetupPresetUnit
				INTEGER,
			iqbadxSetupSoftwareVersion
				RollCallString,
			iqbadxSetupSerialNo
				RollCallString
		}

	iqbadxSlotIndex OBJECT-TYPE
		SYNTAX		Unsigned32
		MAX-ACCESS		not-accessible
		STATUS			current
		DESCRIPTION
				"The unique Index value for each slot.  Its value
					ranges between 1 and the value of slotNumber."
		::= { iqbadxCmdEntry 0 }


	iqbadxOutputsAnalogueAESOutA OBJECT-TYPE
		SYNTAX		INTEGER {
							val_1_Group1_Pair_1(0),
							val_2_Group1_Pair_2(1),
							val_3_Group2_Pair_1(2),
							val_4_Group2_Pair_2(3),
							val_5_Group3_Pair_1(4),
							val_6_Group3_Pair_2(5),
							val_7_Group4_Pair_1(6),
							val_8_Group4_Pair_2(7),
							val_Tone(8),
							val_Silence(9)
							}
		MAX-ACCESS		read-write
		STATUS			current
		DESCRIPTION
				"TYPE: - RadiobuttonList
					Analogue/AES_Out_A  cmdID= 38
					1:Group1_Pair_1  value= 0
					2:Group1_Pair_2  value= 1
					3:Group2_Pair_1  value= 2
					4:Group2_Pair_2  value= 3
					5:Group3_Pair_1  value= 4
					6:Group3_Pair_2  value= 5
					7:Group4_Pair_1  value= 6
					8:Group4_Pair_2  value= 7
					Tone  value= 8
					Silence  value= 9  "
		::= { iqbadxCmdEntry 38 }


	iqbadxOutputsAnalogueAESOutB OBJECT-TYPE
		SYNTAX		INTEGER {
							val_1_Group1_Pair_1(0),
							val_2_Group1_Pair_2(1),
							val_3_Group2_Pair_1(2),
							val_4_Group2_Pair_2(3),
							val_5_Group3_Pair_1(4),
							val_6_Group3_Pair_2(5),
							val_7_Group4_Pair_1(6),
							val_8_Group4_Pair_2(7),
							val_Tone(8),
							val_Silence(9)
							}
		MAX-ACCESS		read-write
		STATUS			current
		DESCRIPTION
				"TYPE: - RadiobuttonList
					Analogue/AES_Out_B  cmdID= 39
					1:Group1_Pair_1  value= 0
					2:Group1_Pair_2  value= 1
					3:Group2_Pair_1  value= 2
					4:Group2_Pair_2  value= 3
					5:Group3_Pair_1  value= 4
					6:Group3_Pair_2  value= 5
					7:Group4_Pair_1  value= 6
					8:Group4_Pair_2  value= 7
					Tone  value= 8
					Silence  value= 9  "
		::= { iqbadxCmdEntry 39 }


	iqbadxOutputsAESOutputC OBJECT-TYPE
		SYNTAX		INTEGER {
							val_1_Group1_Pair_1(0),
							val_2_Group1_Pair_2(1),
							val_3_Group2_Pair_1(2),
							val_4_Group2_Pair_2(3),
							val_5_Group3_Pair_1(4),
							val_6_Group3_Pair_2(5),
							val_7_Group4_Pair_1(6),
							val_8_Group4_Pair_2(7),
							val_Tone(8),
							val_Silence(9)
							}
		MAX-ACCESS		read-write
		STATUS			current
		DESCRIPTION
				"TYPE: - RadiobuttonList
					AES_Output_C  cmdID= 40
					1:Group1_Pair_1  value= 0
					2:Group1_Pair_2  value= 1
					3:Group2_Pair_1  value= 2
					4:Group2_Pair_2  value= 3
					5:Group3_Pair_1  value= 4
					6:Group3_Pair_2  value= 5
					7:Group4_Pair_1  value= 6
					8:Group4_Pair_2  value= 7
					Tone  value= 8
					Silence  value= 9  "
		::= { iqbadxCmdEntry 40 }


	iqbadxOutputsAESOutputD OBJECT-TYPE
		SYNTAX		INTEGER {
							val_1_Group1_Pair_1(0),
							val_2_Group1_Pair_2(1),
							val_3_Group2_Pair_1(2),
							val_4_Group2_Pair_2(3),
							val_5_Group3_Pair_1(4),
							val_6_Group3_Pair_2(5),
							val_7_Group4_Pair_1(6),
							val_8_Group4_Pair_2(7),
							val_Tone(8),
							val_Silence(9)
							}
		MAX-ACCESS		read-write
		STATUS			current
		DESCRIPTION
				"TYPE: - RadiobuttonList
					AES_Output_D  cmdID= 41
					1:Group1_Pair_1  value= 0
					2:Group1_Pair_2  value= 1
					3:Group2_Pair_1  value= 2
					4:Group2_Pair_2  value= 3
					5:Group3_Pair_1  value= 4
					6:Group3_Pair_2  value= 5
					7:Group4_Pair_1  value= 6
					8:Group4_Pair_2  value= 7
					Tone  value= 8
					Silence  value= 9  "
		::= { iqbadxCmdEntry 41 }


	iqbadxDisplay OBJECT-TYPE
		SYNTAX		INTEGER {
							val_Embedded_D1(0),
							val_Audio_Outputs(1)
							}
		MAX-ACCESS		read-write
		STATUS			current
		DESCRIPTION
				"TYPE: - RadiobuttonList
					Display  cmdID= 6
					Embedded_D1  value= 0
					Audio_Outputs  value= 1  "
		::= { iqbadxCmdEntry 6 }


	iqbadxExtractAnalogueAESOutAInvertL OBJECT-TYPE
		SYNTAX		INTEGER { disable(0), enable(1) }
		MAX-ACCESS		read-write
		STATUS			current
		DESCRIPTION
				"TYPE: - Checkbox
					Invert_L  cmdID= 50 "
		::= { iqbadxCmdEntry 50 }


	iqbadxExtractAnalogueAESOutAInvertR OBJECT-TYPE
		SYNTAX		INTEGER { disable(0), enable(1) }
		MAX-ACCESS		read-write
		STATUS			current
		DESCRIPTION
				"TYPE: - Checkbox
					Invert_R  cmdID= 51 "
		::= { iqbadxCmdEntry 51 }


	iqbadxExtractAnalogueAESOutAExtract OBJECT-TYPE
		SYNTAX		INTEGER {
							val_Out_A_Left_Right(0),
							val_Out_A_Right_Left(1),
							val_Out_A_Left_Left(2),
							val_Out_A_Right_Right(3)
							}
		MAX-ACCESS		read-write
		STATUS			current
		DESCRIPTION
				"TYPE: - RadiobuttonList
					Extract  cmdID= 27
					Out_A_Left/Right  value= 0
					Out_A_Right/Left  value= 1
					Out_A_Left/Left  value= 2
					Out_A_Right/Right  value= 3  "
		::= { iqbadxCmdEntry 27 }


	iqbadxExtractAnalogueAESOutBInvertL OBJECT-TYPE
		SYNTAX		INTEGER { disable(0), enable(1) }
		MAX-ACCESS		read-write
		STATUS			current
		DESCRIPTION
				"TYPE: - Checkbox
					Invert_L  cmdID= 52 "
		::= { iqbadxCmdEntry 52 }


	iqbadxExtractAnalogueAESOutBInvertR OBJECT-TYPE
		SYNTAX		INTEGER { disable(0), enable(1) }
		MAX-ACCESS		read-write
		STATUS			current
		DESCRIPTION
				"TYPE: - Checkbox
					Invert_R  cmdID= 53 "
		::= { iqbadxCmdEntry 53 }


	iqbadxExtractAnalogueAESOutBExtract OBJECT-TYPE
		SYNTAX		INTEGER {
							val_Out_B_Left_Right(0),
							val_Out_B_Right_Left(1),
							val_Out_B_Left_Left(2),
							val_Out_B_Right_Right(3)
							}
		MAX-ACCESS		read-write
		STATUS			current
		DESCRIPTION
				"TYPE: - RadiobuttonList
					Extract  cmdID= 28
					Out_B_Left/Right  value= 0
					Out_B_Right/Left  value= 1
					Out_B_Left/Left  value= 2
					Out_B_Right/Right  value= 3  "
		::= { iqbadxCmdEntry 28 }


	iqbadxExtractAESOutputCInvertL OBJECT-TYPE
		SYNTAX		INTEGER { disable(0), enable(1) }
		MAX-ACCESS		read-write
		STATUS			current
		DESCRIPTION
				"TYPE: - Checkbox
					Invert_L  cmdID= 54 "
		::= { iqbadxCmdEntry 54 }


	iqbadxExtractAESOutputCInvertR OBJECT-TYPE
		SYNTAX		INTEGER { disable(0), enable(1) }
		MAX-ACCESS		read-write
		STATUS			current
		DESCRIPTION
				"TYPE: - Checkbox
					Invert_R  cmdID= 55 "
		::= { iqbadxCmdEntry 55 }


	iqbadxExtractAESOutputCExtract OBJECT-TYPE
		SYNTAX		INTEGER {
							val_Out_C_Left_Right(0),
							val_Out_C_Right_Left(1),
							val_Out_C_Left_Left(2),
							val_Out_C_Right_Right(3)
							}
		MAX-ACCESS		read-write
		STATUS			current
		DESCRIPTION
				"TYPE: - RadiobuttonList
					Extract  cmdID= 29
					Out_C_Left/Right  value= 0
					Out_C_Right/Left  value= 1
					Out_C_Left/Left  value= 2
					Out_C_Right/Right  value= 3  "
		::= { iqbadxCmdEntry 29 }


	iqbadxExtractAESOutputDInvertL OBJECT-TYPE
		SYNTAX		INTEGER { disable(0), enable(1) }
		MAX-ACCESS		read-write
		STATUS			current
		DESCRIPTION
				"TYPE: - Checkbox
					Invert_L  cmdID= 56 "
		::= { iqbadxCmdEntry 56 }


	iqbadxExtractAESOutputDInvertR OBJECT-TYPE
		SYNTAX		INTEGER { disable(0), enable(1) }
		MAX-ACCESS		read-write
		STATUS			current
		DESCRIPTION
				"TYPE: - Checkbox
					Invert_R  cmdID= 57 "
		::= { iqbadxCmdEntry 57 }


	iqbadxExtractAESOutputDExtract OBJECT-TYPE
		SYNTAX		INTEGER {
							val_Out_D_Left_Right(0),
							val_Out_D_Right_Left(1),
							val_Out_D_Left_Left(2),
							val_Out_D_Right_Right(3)
							}
		MAX-ACCESS		read-write
		STATUS			current
		DESCRIPTION
				"TYPE: - RadiobuttonList
					Extract  cmdID= 30
					Out_D_Left/Right  value= 0
					Out_D_Right/Left  value= 1
					Out_D_Left/Left  value= 2
					Out_D_Right/Right  value= 3  "
		::= { iqbadxCmdEntry 30 }


	iqbadxEDHShowStats OBJECT-TYPE
		SYNTAX		INTEGER { disable(0), enable(1) }
		MAX-ACCESS		read-write
		STATUS			current
		DESCRIPTION
				"TYPE: - Checkbox
					Show_Stats  cmdID= 5 "
		::= { iqbadxCmdEntry 5 }


	iqbadxEDHResetStats OBJECT-TYPE
		SYNTAX		INTEGER { noAction(0),val_Reset_Stats(1) }
		MAX-ACCESS		read-write
		STATUS			current
		DESCRIPTION
				"TYPE: - Button
					Reset_Stats  cmdID= 7  value= 1  "
		::= { iqbadxCmdEntry 7 }


	iqbadxMemoryReadMemory OBJECT-TYPE
		SYNTAX		INTEGER {
							val_Memory_1(0),
							val_Memory_2(1),
							val_Memory_3(2),
							val_Memory_4(3)
							}
		MAX-ACCESS		read-write
		STATUS			current
		DESCRIPTION
				"TYPE: - RadiobuttonList
					Read_Memory  cmdID= 35
					Memory_1  value= 0
					Memory_2  value= 1
					Memory_3  value= 2
					Memory_4  value= 3  "
		::= { iqbadxCmdEntry 35 }


	iqbadxMemorySaveMemory OBJECT-TYPE
		SYNTAX		INTEGER {
							val_Memory_1(0),
							val_Memory_2(1),
							val_Memory_3(2),
							val_Memory_4(3)
							}
		MAX-ACCESS		read-write
		STATUS			current
		DESCRIPTION
				"TYPE: - RadiobuttonList
					Save_Memory  cmdID= 36
					Memory_1  value= 0
					Memory_2  value= 1
					Memory_3  value= 2
					Memory_4  value= 3  "
		::= { iqbadxCmdEntry 36 }


	iqbadxMemoryNameUserMemoryMemory1 OBJECT-TYPE
		SYNTAX		RollCallString
		MAX-ACCESS		read-write
		STATUS			current
		DESCRIPTION
				"TYPE: - Editstring
					Memory_1  cmdID= 16  "
		::= { iqbadxCmdEntry 16 }


	iqbadxMemoryNameUserMemoryMemory2 OBJECT-TYPE
		SYNTAX		RollCallString
		MAX-ACCESS		read-write
		STATUS			current
		DESCRIPTION
				"TYPE: - Editstring
					Memory_2  cmdID= 17  "
		::= { iqbadxCmdEntry 17 }


	iqbadxMemoryNameUserMemoryMemory3 OBJECT-TYPE
		SYNTAX		RollCallString
		MAX-ACCESS		read-write
		STATUS			current
		DESCRIPTION
				"TYPE: - Editstring
					Memory_3  cmdID= 18  "
		::= { iqbadxCmdEntry 18 }


	iqbadxMemoryNameUserMemoryMemory4 OBJECT-TYPE
		SYNTAX		RollCallString
		MAX-ACCESS		read-write
		STATUS			current
		DESCRIPTION
				"TYPE: - Editstring
					Memory_4  cmdID= 19  "
		::= { iqbadxCmdEntry 19 }


	iqbadxMemoryClearUserMemory OBJECT-TYPE
		SYNTAX		INTEGER {
							val_Memory_1(0),
							val_Memory_2(1),
							val_Memory_3(2),
							val_Memory_4(3)
							}
		MAX-ACCESS		read-write
		STATUS			current
		DESCRIPTION
				"TYPE: - RadiobuttonList
					Clear_User_Memory  cmdID= 37
					Memory_1  value= 0
					Memory_2  value= 1
					Memory_3  value= 2
					Memory_4  value= 3  "
		::= { iqbadxCmdEntry 37 }


	iqbadxSetupLockToRef OBJECT-TYPE
		SYNTAX		INTEGER { disable(0), enable(1) }
		MAX-ACCESS		read-write
		STATUS			current
		DESCRIPTION
				"TYPE: - Checkbox
					Lock_To_Ref  cmdID= 26 "
		::= { iqbadxCmdEntry 26 }


	iqbadxSetupGPIGPITriggerSetup OBJECT-TYPE
		SYNTAX		INTEGER {
							val_Off(0),
							val_Latch(2),
							val_Edge(1)
							}
		MAX-ACCESS		read-write
		STATUS			current
		DESCRIPTION
				"TYPE: - RadiobuttonList
					GPI_Trigger_Setup  cmdID= 46
					Off  value= 0
					Latch  value= 2
					Edge  value= 1  "
		::= { iqbadxCmdEntry 46 }


	iqbadxSetupGPIGPIFunction OBJECT-TYPE
		SYNTAX		INTEGER {
							val_Output_A_Silence(0),
							val_Output_B_Silence(1),
							val_Output_C_Silence(2),
							val_Output_D_Silence(3),
							val_Output_A_Tone(4),
							val_Output_B_Tone(5),
							val_Output_C_Tone(6),
							val_Output_D_Tone(7),
							val_Trigger_Memory_1(8),
							val_Trigger_Memory_2(9),
							val_Trigger_Memory_3(10),
							val_Trigger_Memory_4(11)
							}
		MAX-ACCESS		read-write
		STATUS			current
		DESCRIPTION
				"TYPE: - RadiobuttonList
					GPI_Function  cmdID= 47
					Output_A_Silence  value= 0
					Output_B_Silence  value= 1
					Output_C_Silence  value= 2
					Output_D_Silence  value= 3
					Output_A_Tone  value= 4
					Output_B_Tone  value= 5
					Output_C_Tone  value= 6
					Output_D_Tone  value= 7
					Trigger_Memory_1  value= 8
					Trigger_Memory_2  value= 9
					Trigger_Memory_3  value= 10
					Trigger_Memory_4  value= 11  "
		::= { iqbadxCmdEntry 47 }


	iqbadxSetupSetDefaultOutput OBJECT-TYPE
		SYNTAX		INTEGER
		MAX-ACCESS		read-write
		STATUS			current
		DESCRIPTION
				"TYPE: - Number
					Set_Default_Output  cmdID= 25  min= 0  max= 7  step= 1  format= %f  div_scale= 1
					Min = 0.000000  Max = 7.000000  Step = 1.000000 "
		::= { iqbadxCmdEntry 25 }


	iqbadxSetupToneOutputsToneOutputA OBJECT-TYPE
		SYNTAX		INTEGER
		MAX-ACCESS		read-write
		STATUS			current
		DESCRIPTION
				"TYPE: - Number
					Tone_Output_A  cmdID= 42  min= 1  max= 7  step= 1  format= %f  div_scale= 1
					Min = 1.000000  Max = 7.000000  Step = 1.000000 "
		::= { iqbadxCmdEntry 42 }


	iqbadxSetupToneOutputsToneOutputB OBJECT-TYPE
		SYNTAX		INTEGER
		MAX-ACCESS		read-write
		STATUS			current
		DESCRIPTION
				"TYPE: - Number
					Tone_Output_B  cmdID= 43  min= 1  max= 7  step= 1  format= %f  div_scale= 1
					Min = 1.000000  Max = 7.000000  Step = 1.000000 "
		::= { iqbadxCmdEntry 43 }


	iqbadxSetupToneOutputsToneOutputC OBJECT-TYPE
		SYNTAX		INTEGER
		MAX-ACCESS		read-write
		STATUS			current
		DESCRIPTION
				"TYPE: - Number
					Tone_Output_C  cmdID= 44  min= 1  max= 7  step= 1  format= %f  div_scale= 1
					Min = 1.000000  Max = 7.000000  Step = 1.000000 "
		::= { iqbadxCmdEntry 44 }


	iqbadxSetupToneOutputsToneOutputD OBJECT-TYPE
		SYNTAX		INTEGER
		MAX-ACCESS		read-write
		STATUS			current
		DESCRIPTION
				"TYPE: - Number
					Tone_Output_D  cmdID= 45  min= 1  max= 7  step= 1  format= %f  div_scale= 1
					Min = 1.000000  Max = 7.000000  Step = 1.000000 "
		::= { iqbadxCmdEntry 45 }


	iqbadxNamesOutputNamesOutputA OBJECT-TYPE
		SYNTAX		RollCallString
		MAX-ACCESS		read-write
		STATUS			current
		DESCRIPTION
				"TYPE: - Editstring
					Output_A  cmdID= 20  "
		::= { iqbadxCmdEntry 20 }


	iqbadxNamesOutputNamesOutputB OBJECT-TYPE
		SYNTAX		RollCallString
		MAX-ACCESS		read-write
		STATUS			current
		DESCRIPTION
				"TYPE: - Editstring
					Output_B  cmdID= 21  "
		::= { iqbadxCmdEntry 21 }


	iqbadxNamesOutputNamesOutputC OBJECT-TYPE
		SYNTAX		RollCallString
		MAX-ACCESS		read-write
		STATUS			current
		DESCRIPTION
				"TYPE: - Editstring
					Output_C  cmdID= 22  "
		::= { iqbadxCmdEntry 22 }


	iqbadxNamesOutputNamesOutputD OBJECT-TYPE
		SYNTAX		RollCallString
		MAX-ACCESS		read-write
		STATUS			current
		DESCRIPTION
				"TYPE: - Editstring
					Output_D  cmdID= 23  "
		::= { iqbadxCmdEntry 23 }


	iqbadxNamesInputNamesGroup1Pair1 OBJECT-TYPE
		SYNTAX		RollCallString
		MAX-ACCESS		read-write
		STATUS			current
		DESCRIPTION
				"TYPE: - Editstring
					Group1_Pair_1  cmdID= 8  "
		::= { iqbadxCmdEntry 8 }


	iqbadxNamesInputNamesGroup1Pair2 OBJECT-TYPE
		SYNTAX		RollCallString
		MAX-ACCESS		read-write
		STATUS			current
		DESCRIPTION
				"TYPE: - Editstring
					Group1_Pair_2  cmdID= 9  "
		::= { iqbadxCmdEntry 9 }


	iqbadxNamesInputNamesGroup2Pair1 OBJECT-TYPE
		SYNTAX		RollCallString
		MAX-ACCESS		read-write
		STATUS			current
		DESCRIPTION
				"TYPE: - Editstring
					Group2_Pair_1  cmdID= 10  "
		::= { iqbadxCmdEntry 10 }


	iqbadxNamesInputNamesGroup2Pair2 OBJECT-TYPE
		SYNTAX		RollCallString
		MAX-ACCESS		read-write
		STATUS			current
		DESCRIPTION
				"TYPE: - Editstring
					Group2_Pair_2  cmdID= 11  "
		::= { iqbadxCmdEntry 11 }


	iqbadxNamesInputNamesGroup3Pair1 OBJECT-TYPE
		SYNTAX		RollCallString
		MAX-ACCESS		read-write
		STATUS			current
		DESCRIPTION
				"TYPE: - Editstring
					Group3_Pair_1  cmdID= 12  "
		::= { iqbadxCmdEntry 12 }


	iqbadxNamesInputNamesGroup3Pair2 OBJECT-TYPE
		SYNTAX		RollCallString
		MAX-ACCESS		read-write
		STATUS			current
		DESCRIPTION
				"TYPE: - Editstring
					Group3_Pair_2  cmdID= 13  "
		::= { iqbadxCmdEntry 13 }


	iqbadxNamesInputNamesGroup4Pair1 OBJECT-TYPE
		SYNTAX		RollCallString
		MAX-ACCESS		read-write
		STATUS			current
		DESCRIPTION
				"TYPE: - Editstring
					Group4_Pair_1  cmdID= 14  "
		::= { iqbadxCmdEntry 14 }


	iqbadxNamesInputNamesGroup4Pair2 OBJECT-TYPE
		SYNTAX		RollCallString
		MAX-ACCESS		read-write
		STATUS			current
		DESCRIPTION
				"TYPE: - Editstring
					Group4_Pair_2  cmdID= 15  "
		::= { iqbadxCmdEntry 15 }


	iqbadxSetupNamesPresetNames OBJECT-TYPE
		SYNTAX		INTEGER {
							val_Preset_Names(1)
							}
		MAX-ACCESS		read-write
		STATUS			current
		DESCRIPTION
				"TYPE: - RadiobuttonList
					Preset_Names  cmdID= 24
					Preset_Names  value= 1  "
		::= { iqbadxCmdEntry 24 }


	iqbadxSetupLoggingVideoInputChange OBJECT-TYPE
		SYNTAX		INTEGER { disable(0), enable(1) }
		MAX-ACCESS		read-write
		STATUS			current
		DESCRIPTION
				"TYPE: - Checkbox
					Video_Input_Change  cmdID= 31 "
		::= { iqbadxCmdEntry 31 }


	iqbadxSetupLoggingD1AudioChange OBJECT-TYPE
		SYNTAX		INTEGER { disable(0), enable(1) }
		MAX-ACCESS		read-write
		STATUS			current
		DESCRIPTION
				"TYPE: - Checkbox
					D1_Audio_Change  cmdID= 34 "
		::= { iqbadxCmdEntry 34 }


	iqbadxSetupLoggingEDHErrors OBJECT-TYPE
		SYNTAX		INTEGER { disable(0), enable(1) }
		MAX-ACCESS		read-write
		STATUS			current
		DESCRIPTION
				"TYPE: - Checkbox
					EDH_Errors  cmdID= 32 "
		::= { iqbadxCmdEntry 32 }


	iqbadxSetupLoggingAESRefChange OBJECT-TYPE
		SYNTAX		INTEGER { disable(0), enable(1) }
		MAX-ACCESS		read-write
		STATUS			current
		DESCRIPTION
				"TYPE: - Checkbox
					AES_Ref_Change  cmdID= 33 "
		::= { iqbadxCmdEntry 33 }


	iqbadxSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqbadxCmdEntry 3 }


	iqbadxSetupSoftwareVersion OBJECT-TYPE
		SYNTAX		RollCallString
		MAX-ACCESS		read-only
		STATUS			current
		DESCRIPTION
				"TYPE: - Display
					Software_Version  cmdID= 2  format=   "
		::= { iqbadxCmdEntry 2 }


	iqbadxSetupSerialNo OBJECT-TYPE
		SYNTAX		RollCallString
		MAX-ACCESS		read-only
		STATUS			current
		DESCRIPTION
				"TYPE: - Display
					Serial_No  cmdID= 1  format=   "
		::= { iqbadxCmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		:
--				:
-- Comments		: This log field shows the unique S&W serial number for this
--				: board instance. 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: This log field shows the EDH status of the SDI
--				: input.
--				: EDH (Error Detection Handling) as specified by
--				: SMPTE RP 165-1994 and by the ITU standard ITU-R BT.1304.
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: This log field shows whether the IQ frame gateway card
--				: can communicate with this module.
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: 625
--				: 525
-- Comments		: This log field shows the detected video standard of the detected SDI input.
--
---------------------------------------------------------------------------------------------------
-- Header		: AUDIO
--
-- MIB ref		: swCardEventLogSlotXX       .5.65.85.68.73.79
-- absolute OID	: 1.3.6.1.4.1.7995.2.6.1.1.XX.5.65.85.68.73.79
-- Vary			: YES
--
-- Value(s)		: ----------------
--				: --------------8-
--				: ------------7---
--				: ------------7-8-
--				: ----------6-----
--				: ----------6---8-
--				: ----------6-7---
--				: ----------6-7-8-
--				: --------5-------
--				: --------5-----8-
--				: --------5---7---
--				: --------5---7-8-
--				: --------5-6-----
--				: --------5-6---8-
--				: --------5-6-7---
--				: --------5-6-7-8-
--				: ------4---------
--				: ------4-------8-
--				: ------4-----7---
--				: ------4-----7-8-
--				: ------4---6-----
--				: ------4---6---8-
--				: ------4---6-7---
--				: ------4---6-7-8-
--				: ------4-5-------
--				: ------4-5-----8-
--				: ------4-5---7---
--				: ------4-5---7-8-
--				: ------4-5-6-----
--				: ------4-5-6---8-
--				: ------4-5-6-7---
--				: ------4-5-6-7-8-
--				: ----3-----------
--				: ----3---------8-
--				: ----3-------7---
--				: ----3-------7-8-
--				: ----3-----6-----
--				: ----3-----6---8-
--				: ----3-----6-7---
--				: ----3-----6-7-8-
--				: ----3---5-------
--				: ----3---5-----8-
--				: ----3---5---7---
--				: ----3---5---7-8-
--				: ----3---5-6-----
--				: ----3---5-6---8-
--				: ----3---5-6-7---
--				: ----3---5-6-7-8-
--				: ----3-4---------
--				: ----3-4-------8-
--				: ----3-4-----7---
--				: ----3-4-----7-8-
--				: ----3-4---6-----
--				: ----3-4---6---8-
--				: ----3-4---6-7---
--				: ----3-4---6-7-8-
--				: ----3-4-5-------
--				: ----3-4-5-----8-
--				: ----3-4-5---7---
--				: ----3-4-5---7-8-
--				: ----3-4-5-6-----
--				: ----3-4-5-6---8-
--				: ----3-4-5-6-7---
--				: ----3-4-5-6-7-8-
--				: --2-------------
--				: --2-----------8-
--				: --2---------7---
--				: --2---------7-8-
--				: --2-------6-----
--				: --2-------6---8-
--				: --2-------6-7---
--				: --2-------6-7-8-
--				: --2-----5-------
--				: --2-----5-----8-
--				: --2-----5---7---
--				: --2-----5---7-8-
--				: --2-----5-6-----
--				: --2-----5-6---8-
--				: --2-----5-6-7---
--				: --2-----5-6-7-8-
--				: --2---4---------
--				: --2---4-------8-
--				: --2---4-----7---
--				: --2---4-----7-8-
--				: --2---4---6-----
--				: --2---4---6---8-
--				: --2---4---6-7---
--				: --2---4---6-7-8-
--				: --2---4-5-------
--				: --2---4-5-----8-
--				: --2---4-5---7---
--				: --2---4-5---7-8-
--				: --2---4-5-6-----
--				: --2---4-5-6---8-
--				: --2---4-5-6-7---
--				: --2---4-5-6-7-8-
--				: --2-3-----------
--				: --2-3---------8-
--				: --2-3-------7---
--				: --2-3-------7-8-
--				: --2-3-----6-----
--				: --2-3-----6---8-
--				: --2-3-----6-7---
--				: --2-3-----6-7-8-
--				: --2-3---5-------
--				: --2-3---5-----8-
--				: --2-3---5---7---
--				: --2-3---5---7-8-
--				: --2-3---5-6-----
--				: --2-3---5-6---8-
--				: --2-3---5-6-7---
--				: --2-3---5-6-7-8-
--				: --2-3-4---------
--				: --2-3-4-------8-
--				: --2-3-4-----7---
--				: --2-3-4-----7-8-
--				: --2-3-4---6-----
--				: --2-3-4---6---8-
--				: --2-3-4---6-7---
--				: --2-3-4---6-7-8-
--				: --2-3-4-5-------
--				: --2-3-4-5-----8-
--				: --2-3-4-5---7---
--				: --2-3-4-5---7-8-
--				: --2-3-4-5-6-----
--				: --2-3-4-5-6---8-
--				: --2-3-4-5-6-7---
--				: --2-3-4-5-6-7-8-
--				: 1---------------
--				: 1-------------8-
--				: 1-----------7---
--				: 1-----------7-8-
--				: 1---------6-----
--				: 1---------6---8-
--				: 1---------6-7---
--				: 1---------6-7-8-
--				: 1-------5-------
--				: 1-------5-----8-
--				: 1-------5---7---
--				: 1-------5---7-8-
--				: 1-------5-6-----
--				: 1-------5-6---8-
--				: 1-------5-6-7---
--				: 1-------5-6-7-8-
--				: 1-----4---------
--				: 1-----4-------8-
--				: 1-----4-----7---
--				: 1-----4-----7-8-
--				: 1-----4---6-----
--				: 1-----4---6---8-
--				: 1-----4---6-7---
--				: 1-----4---6-7-8-
--				: 1-----4-5-------
--				: 1-----4-5-----8-
--				: 1-----4-5---7---
--				: 1-----4-5---7-8-
--				: 1-----4-5-6-----
--				: 1-----4-5-6---8-
--				: 1-----4-5-6-7---
--				: 1-----4-5-6-7-8-
--				: 1---3-----------
--				: 1---3---------8-
--				: 1---3-------7---
--				: 1---3-------7-8-
--				: 1---3-----6-----
--				: 1---3-----6---8-
--				: 1---3-----6-7---
--				: 1---3-----6-7-8-
--				: 1---3---5-------
--				: 1---3---5-----8-
--				: 1---3---5---7---
--				: 1---3---5---7-8-
--				: 1---3---5-6-----
--				: 1---3---5-6---8-
--				: 1---3---5-6-7---
--				: 1---3---5-6-7-8-
--				: 1---3-4---------
--				: 1---3-4-------8-
--				: 1---3-4-----7---
--				: 1---3-4-----7-8-
--				: 1---3-4---6-----
--				: 1---3-4---6---8-
--				: 1---3-4---6-7---
--				: 1---3-4---6-7-8-
--				: 1---3-4-5-------
--				: 1---3-4-5-----8-
--				: 1---3-4-5---7---
--				: 1---3-4-5---7-8-
--				: 1---3-4-5-6-----
--				: 1---3-4-5-6---8-
--				: 1---3-4-5-6-7---
--				: 1---3-4-5-6-7-8-
--				: 1-2-------------
--				: 1-2-----------8-
--				: 1-2---------7---
--				: 1-2---------7-8-
--				: 1-2-------6-----
--				: 1-2-------6---8-
--				: 1-2-------6-7---
--				: 1-2-------6-7-8-
--				: 1-2-----5-------
--				: 1-2-----5-----8-
--				: 1-2-----5---7---
--				: 1-2-----5---7-8-
--				: 1-2-----5-6-----
--				: 1-2-----5-6---8-
--				: 1-2-----5-6-7---
--				: 1-2-----5-6-7-8-
--				: 1-2---4---------
--				: 1-2---4-------8-
--				: 1-2---4-----7---
--				: 1-2---4-----7-8-
--				: 1-2---4---6-----
--				: 1-2---4---6---8-
--				: 1-2---4---6-7---
--				: 1-2---4---6-7-8-
--				: 1-2---4-5-------
--				: 1-2---4-5-----8-
--				: 1-2---4-5---7---
--				: 1-2---4-5---7-8-
--				: 1-2---4-5-6-----
--				: 1-2---4-5-6---8-
--				: 1-2---4-5-6-7---
--				: 1-2---4-5-6-7-8-
--				: 1-2-3-----------
--				: 1-2-3---------8-
--				: 1-2-3-------7---
--				: 1-2-3-------7-8-
--				: 1-2-3-----6-----
--				: 1-2-3-----6---8-
--				: 1-2-3-----6-7---
--				: 1-2-3-----6-7-8-
--				: 1-2-3---5-------
--				: 1-2-3---5-----8-
--				: 1-2-3---5---7---
--				: 1-2-3---5---7-8-
--				: 1-2-3---5-6-----
--				: 1-2-3---5-6---8-
--				: 1-2-3---5-6-7---
--				: 1-2-3---5-6-7-8-
--				: 1-2-3-4---------
--				: 1-2-3-4-------8-
--				: 1-2-3-4-----7---
--				: 1-2-3-4-----7-8-
--				: 1-2-3-4---6-----
--				: 1-2-3-4---6---8-
--				: 1-2-3-4---6-7---
--				: 1-2-3-4---6-7-8-
--				: 1-2-3-4-5-------
--				: 1-2-3-4-5-----8-
--				: 1-2-3-4-5---7---
--				: 1-2-3-4-5---7-8-
--				: 1-2-3-4-5-6-----
--				: 1-2-3-4-5-6---8-
--				: 1-2-3-4-5-6-7---
--				: 1-2-3-4-5-6-7-8-
-- Comments		: This log field reports the detected state of embedded audio pairs in the input SDI stream.
--				: Each digit represents presence of that pair and a ( - ) the absence of that pair.
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: This log field shows the detected state of the SDI input signal.
--				: LOST indicates no input detected. 
--				: ERROR indicates that the detected input is not valid. 
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary Number  : YES
-- Value(s)		:
--				:
-- Comments		: The number of EDH errors raised since initialization or the last EDH stats reset.
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: LOST
--				: OK
--				: N/A
-- Comments		: This log field shows the status of the reference.
--				: OK indicates that the card is locked to the selected input.
--				: N/A indicates no valid reference signal available.
--				: LOST indicates that the reference signal has been Lost.
--
---------------------------------------------------------------------------------------------------
