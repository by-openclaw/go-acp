-- ************************************************************************************
-- Snell&Wilcox Card:IQDNRS
--        Module Id#:128
--       Command Set:9
--          Filename:SNELL-IQDNRS-CMD-MIB.mib
--            Author:Jonathan Riches
--              Date:30/06/2005
--              Time:14:46
--
-- Copyright (c) 2005 Snell & Wilcox Ltd
-- All rights reserved.
--
-- ************************************************************************************

SNELL-IQDNRS-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDNRS,
    moduleIQDNRSMIB
        FROM SNELL-WILCOX-PRODUCT-REG;

 moduleIQDNRSCmdMi MODULE-IDENTITY
    LAST-UPDATED "0506301446Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDNRSMIB 1 }




--********************************************************************************
--*
--*  Snell Wilcox Card:
--*  command set:
--*  list commands/menus:
--*
--******************************************************************************
	iqdnrsCmdTable OBJECT-TYPE
		SYNTAX			SEQUENCE OF IqdnrsCmdEntry
		MAX-ACCESS		not-accessible
		STATUS			current
		DESCRIPTION
				"Note the instance of this table is relected in the command set Version"
		::= { moduleIQDNRS 1 }

	iqdnrsCmdEntry OBJECT-TYPE
		SYNTAX		IqdnrsCmdEntry
		MAX-ACCESS		not-accessible
		STATUS			current
		DESCRIPTION
				"Entry in command table."
		INDEX	{ iqdnrsSlotIndex }
		::= { iqdnrsCmdTable 1 }

	IqdnrsCmdEntry ::=
		SEQUENCE {
			iqdnrsSlotIndex
				Unsigned32,
			iqdnrsNoiseReduceRecursiveC
				INTEGER,
			iqdnrsNoiseReduceRecursiveY
				INTEGER,
			iqdnrsNoiseReduceSparkleFilter
				INTEGER,
			iqdnrsNoiseReduceAdaptiveLowPass
				INTEGER,
			iqdnrsNoiseReduceSetupRecursiveThreshold
				INTEGER,
			iqdnrsNoiseReduceSetupSparkleSensitivity
				INTEGER,
			iqdnrsNoiseReduceSetupMedianFilter
				INTEGER,
			iqdnrsNoiseReduceSetupDropOutFilter
				INTEGER,
			iqdnrsNoiseReduceSetupSparkleMotionProc
				INTEGER,
			iqdnrsNoiseReduceSetupSparkleTrailProc
				INTEGER,
			iqdnrsEnhanceHHighFrequencyLevel
				INTEGER,
			iqdnrsEnhanceHHighFrequency
				INTEGER,
			iqdnrsEnhanceHMidFrequencyLevel
				INTEGER,
			iqdnrsEnhanceHMidFrequency
				INTEGER,
			iqdnrsEnhanceVertical
				INTEGER,
			iqdnrsBypass
				INTEGER,
			iqdnrsProcAmpYGain
				INTEGER,
			iqdnrsProcAmpFreeze
				INTEGER,
			iqdnrsProcAmpCGain
				INTEGER,
			iqdnrsProcAmpPicturePos
				INTEGER,
			iqdnrsProcAmpBlackLevel
				INTEGER,
			iqdnrsProcAmpYCDelay
				INTEGER,
			iqdnrsProcAmpLimiter
				INTEGER,
			iqdnrsHandsFree
				INTEGER,
			iqdnrsUserMemoryRead
				INTEGER,
			iqdnrsUserMemorySave
				INTEGER,
			iqdnrsUserMemoryClear
				INTEGER,
			iqdnrsUserMemoryNameMemory1
				RollCallString,
			iqdnrsUserMemoryNameMemory2
				RollCallString,
			iqdnrsUserMemoryNameMemory3
				RollCallString,
			iqdnrsUserMemoryNameMemory4
				RollCallString,
			iqdnrsUserMemoryNameMemory5
				RollCallString,
			iqdnrsUserMemoryNameMemory6
				RollCallString,
			iqdnrsUserMemoryNameMemory7
				RollCallString,
			iqdnrsUserMemoryNameMemory8
				RollCallString,
			iqdnrsUserMemoryNameMemory9
				RollCallString,
			iqdnrsUserMemoryNameMemory10
				RollCallString,
			iqdnrsUserMemoryNameMemory11
				RollCallString,
			iqdnrsUserMemoryNameMemory12
				RollCallString,
			iqdnrsUserMemoryNameMemory13
				RollCallString,
			iqdnrsUserMemoryNameMemory14
				RollCallString,
			iqdnrsUserMemoryNameMemory15
				RollCallString,
			iqdnrsUserMemoryNameMemory16
				RollCallString,
			iqdnrsUserMemoryNameMemory17
				RollCallString,
			iqdnrsUserMemoryNameMemory18
				RollCallString,
			iqdnrsUserMemoryNameMemory19
				RollCallString,
			iqdnrsUserMemoryNameMemory20
				RollCallString,
			iqdnrsUserMemoryNameMemory21
				RollCallString,
			iqdnrsUserMemoryNameMemory22
				RollCallString,
			iqdnrsUserMemoryNameMemory23
				RollCallString,
			iqdnrsUserMemoryNameMemory24
				RollCallString,
			iqdnrsUserMemoryNamePresetAllNames
				INTEGER,
			iqdnrsSetupSplitScreen
				INTEGER,
			iqdnrsSetupOutputStandard
				INTEGER,
			iqdnrsSetupDefaultOutputAutoFreeze
				INTEGER,
			iqdnrsSetupDefaultOutput
				INTEGER,
			iqdnrsSetupPatternsPatternOn
				INTEGER,
			iqdnrsSetupPatterns
				INTEGER,
			iqdnrsSetupEDHShowStats
				INTEGER,
			iqdnrsSetupEDHResetStats
				INTEGER,
			iqdnrsSetupGPIInputsGPI1
				INTEGER,
			iqdnrsSetupGPIInputsGPI1GPI1Function
				INTEGER,
			iqdnrsSetupGPIInputsGPI2
				INTEGER,
			iqdnrsSetupGPIInputsGPI2GPI2Function
				INTEGER,
			iqdnrsSetupGPIInputsGPI3
				INTEGER,
			iqdnrsSetupGPIInputsGPI3GPI3Function
				INTEGER,
			iqdnrsSetupLoggingInputChange
				INTEGER,
			iqdnrsSetupLoggingEDHErrors
				INTEGER,
			iqdnrsSetupPresetUnit
				INTEGER,
			iqdnrsSetupSoftwareVersion
				RollCallString,
			iqdnrsSetupSerialNo
				RollCallString,
			iqdnrsSetupRestart
				INTEGER
		}

	iqdnrsSlotIndex OBJECT-TYPE
		SYNTAX		Unsigned32
		MAX-ACCESS		not-accessible
		STATUS			current
		DESCRIPTION
				"The unique Index value for each slot.  Its value
					ranges between 1 and the value of slotNumber."
		::= { iqdnrsCmdEntry 0 }


	iqdnrsNoiseReduceRecursiveC OBJECT-TYPE
		SYNTAX		INTEGER {
							val_C_Off(0),
							val_C_Low(1),
							val_C_Medium(2),
							val_C_High(3)
							}
		MAX-ACCESS		read-write
		STATUS			current
		DESCRIPTION
				"TYPE: - Button
					C_Off  cmdID= 6  value= 0  
					C_Low  cmdID= 6  value= 1  
					C_Medium  cmdID= 6  value= 2  
					C_High  cmdID= 6  value= 3  "
		::= { iqdnrsCmdEntry 6 }


	iqdnrsNoiseReduceRecursiveY OBJECT-TYPE
		SYNTAX		INTEGER {
							val_Y_Off(0),
							val_Y_Low(1),
							val_Y_Medium(2),
							val_Y_High(3)
							}
		MAX-ACCESS		read-write
		STATUS			current
		DESCRIPTION
				"TYPE: - Button
					Y_Off  cmdID= 5  value= 0  
					Y_Low  cmdID= 5  value= 1  
					Y_Medium  cmdID= 5  value= 2  
					Y_High  cmdID= 5  value= 3  "
		::= { iqdnrsCmdEntry 5 }


	iqdnrsNoiseReduceSparkleFilter OBJECT-TYPE
		SYNTAX		INTEGER { disable(0), enable(1) }
		MAX-ACCESS		read-write
		STATUS			current
		DESCRIPTION
				"TYPE: - Checkbox
					Sparkle_Filter  cmdID= 62 "
		::= { iqdnrsCmdEntry 62 }


	iqdnrsNoiseReduceAdaptiveLowPass OBJECT-TYPE
		SYNTAX		INTEGER { disable(0), enable(1) }
		MAX-ACCESS		read-write
		STATUS			current
		DESCRIPTION
				"TYPE: - Checkbox
					Adaptive_Low_Pass  cmdID= 8 "
		::= { iqdnrsCmdEntry 8 }


	iqdnrsNoiseReduceSetupRecursiveThreshold OBJECT-TYPE
		SYNTAX		INTEGER
		MAX-ACCESS		read-write
		STATUS			current
		DESCRIPTION
				"TYPE: - Number
					Recursive_Threshold  cmdID= 7  min= 0  max= 8  step= 1  format= %1.0f  div_scale= 1 
					Min = 0  Max = 8  Step = 1 "
		::= { iqdnrsCmdEntry 7 }


	iqdnrsNoiseReduceSetupSparkleSensitivity OBJECT-TYPE
		SYNTAX		INTEGER
		MAX-ACCESS		read-write
		STATUS			current
		DESCRIPTION
				"TYPE: - Number
					Sparkle_Sensitivity  cmdID= 61  min= 1  max= 4  step= 1  format= %1.0f  div_scale= 1 
					Min = 1  Max = 4  Step = 1 "
		::= { iqdnrsCmdEntry 61 }


	iqdnrsNoiseReduceSetupMedianFilter OBJECT-TYPE
		SYNTAX		INTEGER { disable(0), enable(1) }
		MAX-ACCESS		read-write
		STATUS			current
		DESCRIPTION
				"TYPE: - Checkbox
					Median_Filter  cmdID= 69 "
		::= { iqdnrsCmdEntry 69 }


	iqdnrsNoiseReduceSetupDropOutFilter OBJECT-TYPE
		SYNTAX		INTEGER { disable(0), enable(1) }
		MAX-ACCESS		read-write
		STATUS			current
		DESCRIPTION
				"TYPE: - Checkbox
					Drop_Out_Filter  cmdID= 63 "
		::= { iqdnrsCmdEntry 63 }


	iqdnrsNoiseReduceSetupSparkleMotionProc OBJECT-TYPE
		SYNTAX		INTEGER { disable(0), enable(1) }
		MAX-ACCESS		read-write
		STATUS			current
		DESCRIPTION
				"TYPE: - Checkbox
					Sparkle_Motion_Proc  cmdID= 64 "
		::= { iqdnrsCmdEntry 64 }


	iqdnrsNoiseReduceSetupSparkleTrailProc OBJECT-TYPE
		SYNTAX		INTEGER { disable(0), enable(1) }
		MAX-ACCESS		read-write
		STATUS			current
		DESCRIPTION
				"TYPE: - Checkbox
					Sparkle_Trail_Proc  cmdID= 65 "
		::= { iqdnrsCmdEntry 65 }


	iqdnrsEnhanceHHighFrequencyLevel OBJECT-TYPE
		SYNTAX		INTEGER {
							val_Off(0),
							val_Low(1),
							val_Medium(2),
							val_High(3)
							}
		MAX-ACCESS		read-write
		STATUS			current
		DESCRIPTION
				"TYPE: - Button
					Off  cmdID= 10  value= 0  
					Low  cmdID= 10  value= 1  
					Medium  cmdID= 10  value= 2  
					High  cmdID= 10  value= 3  "
		::= { iqdnrsCmdEntry 10 }


	iqdnrsEnhanceHHighFrequency OBJECT-TYPE
		SYNTAX		INTEGER {
							val_Normal(0),
							val_De_Enhance(2),
							val_Noise_Suppress(1)
							}
		MAX-ACCESS		read-write
		STATUS			current
		DESCRIPTION
				"TYPE: - Button
					Normal  cmdID= 12  value= 0  
					De-Enhance  cmdID= 12  value= 2  
					Noise_Suppress  cmdID= 12  value= 1  "
		::= { iqdnrsCmdEntry 12 }


	iqdnrsEnhanceHMidFrequencyLevel OBJECT-TYPE
		SYNTAX		INTEGER {
							val_Off(0),
							val_Low(1),
							val_Medium(2),
							val_High(3)
							}
		MAX-ACCESS		read-write
		STATUS			current
		DESCRIPTION
				"TYPE: - Button
					Off  cmdID= 11  value= 0  
					Low  cmdID= 11  value= 1  
					Medium  cmdID= 11  value= 2  
					High  cmdID= 11  value= 3  "
		::= { iqdnrsCmdEntry 11 }


	iqdnrsEnhanceHMidFrequency OBJECT-TYPE
		SYNTAX		INTEGER {
							val_Normal(0),
							val_De_Enhance(2),
							val_Noise_Suppress(1)
							}
		MAX-ACCESS		read-write
		STATUS			current
		DESCRIPTION
				"TYPE: - Button
					Normal  cmdID= 13  value= 0  
					De-Enhance  cmdID= 13  value= 2  
					Noise_Suppress  cmdID= 13  value= 1  "
		::= { iqdnrsCmdEntry 13 }


	iqdnrsEnhanceVertical OBJECT-TYPE
		SYNTAX		INTEGER {
							val_Vertical_Off(0),
							val_Vertical_Low(1),
							val_Vertical_Medium(2),
							val_Vertical_High(3)
							}
		MAX-ACCESS		read-write
		STATUS			current
		DESCRIPTION
				"TYPE: - RadiobuttonList
					Vertical  cmdID= 9 
					Vertical_Off  value= 0  
					Vertical_Low  value= 1  
					Vertical_Medium  value= 2  
					Vertical_High  value= 3  "
		::= { iqdnrsCmdEntry 9 }


	iqdnrsBypass OBJECT-TYPE
		SYNTAX		INTEGER { disable(0), enable(1) }
		MAX-ACCESS		read-write
		STATUS			current
		DESCRIPTION
				"TYPE: - Checkbox
					Bypass  cmdID= 60 "
		::= { iqdnrsCmdEntry 60 }


	iqdnrsProcAmpYGain OBJECT-TYPE
		SYNTAX		INTEGER
		MAX-ACCESS		read-write
		STATUS			current
		DESCRIPTION
				"TYPE: - Number
					Y_Gain  cmdID= 14  min= -60  max= 60  step= 1  format= %1.1f dB  div_scale= 10 
					Min = -6.0 dB  Max = 6.0 dB  Step = 0.1 dB "
		::= { iqdnrsCmdEntry 14 }


	iqdnrsProcAmpFreeze OBJECT-TYPE
		SYNTAX		INTEGER { disable(0), enable(1) }
		MAX-ACCESS		read-write
		STATUS			current
		DESCRIPTION
				"TYPE: - Checkbox
					Freeze  cmdID= 20 "
		::= { iqdnrsCmdEntry 20 }


	iqdnrsProcAmpCGain OBJECT-TYPE
		SYNTAX		INTEGER
		MAX-ACCESS		read-write
		STATUS			current
		DESCRIPTION
				"TYPE: - Number
					C_Gain  cmdID= 15  min= -60  max= 60  step= 1  format= %1.1f dB  div_scale= 10 
					Min = -6.0 dB  Max = 6.0 dB  Step = 0.1 dB "
		::= { iqdnrsCmdEntry 15 }


	iqdnrsProcAmpPicturePos OBJECT-TYPE
		SYNTAX		INTEGER
		MAX-ACCESS		read-write
		STATUS			current
		DESCRIPTION
				"TYPE: - Number
					Picture_Pos  cmdID= 18  min= -592  max= 592  step= 148  format= %1.0f ns  div_scale= 1 
					Min = -592 ns  Max = 592 ns  Step = 148 ns "
		::= { iqdnrsCmdEntry 18 }


	iqdnrsProcAmpBlackLevel OBJECT-TYPE
		SYNTAX		INTEGER
		MAX-ACCESS		read-write
		STATUS			current
		DESCRIPTION
				"TYPE: - Number
					Black_Level  cmdID= 16  min= -1000  max= 1000  step= 8  format= %1.1f mV  div_scale= 10 
					Min = -100.0 mV  Max = 100.0 mV  Step = 0.8 mV "
		::= { iqdnrsCmdEntry 16 }


	iqdnrsProcAmpYCDelay OBJECT-TYPE
		SYNTAX		INTEGER
		MAX-ACCESS		read-write
		STATUS			current
		DESCRIPTION
				"TYPE: - Number
					YC_Delay  cmdID= 17  min= -444  max= 444  step= 148  format= %1.0f ns  div_scale= 1 
					Min = -444 ns  Max = 444 ns  Step = 148 ns "
		::= { iqdnrsCmdEntry 17 }


	iqdnrsProcAmpLimiter OBJECT-TYPE
		SYNTAX		INTEGER { disable(0), enable(1) }
		MAX-ACCESS		read-write
		STATUS			current
		DESCRIPTION
				"TYPE: - Checkbox
					Limiter  cmdID= 19 "
		::= { iqdnrsCmdEntry 19 }


	iqdnrsHandsFree OBJECT-TYPE
		SYNTAX		INTEGER { disable(0), enable(1) }
		MAX-ACCESS		read-write
		STATUS			current
		DESCRIPTION
				"TYPE: - Checkbox
					Hands_Free  cmdID= 29 "
		::= { iqdnrsCmdEntry 29 }


	iqdnrsUserMemoryRead OBJECT-TYPE
		SYNTAX		INTEGER {
							val_Ohitus(0),
							val_Asetus_1(1),
							val_Memory_3(2),
							val_Memory_4(3),
							val_Memory_5(4),
							val_Memory_6(5),
							val_Memory_7(6),
							val_Memory_8(7),
							val_Memory_9(8),
							val_Memory_10(9),
							val_Memory_11(10),
							val_Memory_12(11),
							val_Memory_13(12),
							val_Memory_14(13),
							val_Memory_15(14),
							val_Memory_16(15),
							val_Memory_17(16),
							val_Memory_18(17),
							val_Memory_19(18),
							val_Memory_20(19),
							val_Memory_21(20),
							val_Memory_22(21),
							val_Memory_23(22),
							val_Memory_24(23)
							}
		MAX-ACCESS		read-write
		STATUS			current
		DESCRIPTION
				"TYPE: - RadiobuttonList
				 PAGE: - User_Memory
					Read  cmdID= 30 
					Ohitus__  value= 0  
					Asetus_1  value= 1  
					Memory_3  value= 2  
					Memory_4  value= 3  
					Memory_5  value= 4  
					Memory_6  value= 5  
					Memory_7  value= 6  
					Memory_8  value= 7  
					Memory_9  value= 8  
					Memory_10  value= 9  
					Memory_11  value= 10  
					Memory_12  value= 11  
					Memory_13  value= 12  
					Memory_14  value= 13  
					Memory_15  value= 14  
					Memory_16  value= 15  
					Memory_17  value= 16  
					Memory_18  value= 17  
					Memory_19  value= 18  
					Memory_20  value= 19  
					Memory_21  value= 20  
					Memory_22  value= 21  
					Memory_23  value= 22  
					Memory_24  value= 23  "
		::= { iqdnrsCmdEntry 30 }


	iqdnrsUserMemorySave OBJECT-TYPE
		SYNTAX		INTEGER {
							val_Ohitus(0),
							val_Asetus_1(1),
							val_Memory_3(2),
							val_Memory_4(3),
							val_Memory_5(4),
							val_Memory_6(5),
							val_Memory_7(6),
							val_Memory_8(7),
							val_Memory_9(8),
							val_Memory_10(9),
							val_Memory_11(10),
							val_Memory_12(11),
							val_Memory_13(12),
							val_Memory_14(13),
							val_Memory_15(14),
							val_Memory_16(15),
							val_Memory_17(16),
							val_Memory_18(17),
							val_Memory_19(18),
							val_Memory_20(19),
							val_Memory_21(20),
							val_Memory_22(21),
							val_Memory_23(22),
							val_Memory_24(23)
							}
		MAX-ACCESS		read-write
		STATUS			current
		DESCRIPTION
				"TYPE: - RadiobuttonList
				 PAGE: - User_Memory
					Save  cmdID= 31 
					Ohitus__  value= 0  
					Asetus_1  value= 1  
					Memory_3  value= 2  
					Memory_4  value= 3  
					Memory_5  value= 4  
					Memory_6  value= 5  
					Memory_7  value= 6  
					Memory_8  value= 7  
					Memory_9  value= 8  
					Memory_10  value= 9  
					Memory_11  value= 10  
					Memory_12  value= 11  
					Memory_13  value= 12  
					Memory_14  value= 13  
					Memory_15  value= 14  
					Memory_16  value= 15  
					Memory_17  value= 16  
					Memory_18  value= 17  
					Memory_19  value= 18  
					Memory_20  value= 19  
					Memory_21  value= 20  
					Memory_22  value= 21  
					Memory_23  value= 22  
					Memory_24  value= 23  "
		::= { iqdnrsCmdEntry 31 }


	iqdnrsUserMemoryClear OBJECT-TYPE
		SYNTAX		INTEGER {
							val_Ohitus(0),
							val_Asetus_1(1),
							val_Memory_3(2),
							val_Memory_4(3),
							val_Memory_5(4),
							val_Memory_6(5),
							val_Memory_7(6),
							val_Memory_8(7),
							val_Memory_9(8),
							val_Memory_10(9),
							val_Memory_11(10),
							val_Memory_12(11),
							val_Memory_13(12),
							val_Memory_14(13),
							val_Memory_15(14),
							val_Memory_16(15),
							val_Memory_17(16),
							val_Memory_18(17),
							val_Memory_19(18),
							val_Memory_20(19),
							val_Memory_21(20),
							val_Memory_22(21),
							val_Memory_23(22),
							val_Memory_24(23)
							}
		MAX-ACCESS		read-write
		STATUS			current
		DESCRIPTION
				"TYPE: - RadiobuttonList
				 PAGE: - User_Memory
					Clear  cmdID= 32 
					Ohitus__  value= 0  
					Asetus_1  value= 1  
					Memory_3  value= 2  
					Memory_4  value= 3  
					Memory_5  value= 4  
					Memory_6  value= 5  
					Memory_7  value= 6  
					Memory_8  value= 7  
					Memory_9  value= 8  
					Memory_10  value= 9  
					Memory_11  value= 10  
					Memory_12  value= 11  
					Memory_13  value= 12  
					Memory_14  value= 13  
					Memory_15  value= 14  
					Memory_16  value= 15  
					Memory_17  value= 16  
					Memory_18  value= 17  
					Memory_19  value= 18  
					Memory_20  value= 19  
					Memory_21  value= 20  
					Memory_22  value= 21  
					Memory_23  value= 22  
					Memory_24  value= 23  "
		::= { iqdnrsCmdEntry 32 }


	iqdnrsUserMemoryNameMemory1 OBJECT-TYPE
		SYNTAX		RollCallString
		MAX-ACCESS		read-write
		STATUS			current
		DESCRIPTION
				"TYPE: - Editstring
				 PAGE: - User_Memory
					Memory_1  cmdID= 34  "
		::= { iqdnrsCmdEntry 34 }


	iqdnrsUserMemoryNameMemory2 OBJECT-TYPE
		SYNTAX		RollCallString
		MAX-ACCESS		read-write
		STATUS			current
		DESCRIPTION
				"TYPE: - Editstring
				 PAGE: - User_Memory
					Memory_2  cmdID= 35  "
		::= { iqdnrsCmdEntry 35 }


	iqdnrsUserMemoryNameMemory3 OBJECT-TYPE
		SYNTAX		RollCallString
		MAX-ACCESS		read-write
		STATUS			current
		DESCRIPTION
				"TYPE: - Editstring
				 PAGE: - User_Memory
					Memory_3  cmdID= 36  "
		::= { iqdnrsCmdEntry 36 }


	iqdnrsUserMemoryNameMemory4 OBJECT-TYPE
		SYNTAX		RollCallString
		MAX-ACCESS		read-write
		STATUS			current
		DESCRIPTION
				"TYPE: - Editstring
				 PAGE: - User_Memory
					Memory_4  cmdID= 37  "
		::= { iqdnrsCmdEntry 37 }


	iqdnrsUserMemoryNameMemory5 OBJECT-TYPE
		SYNTAX		RollCallString
		MAX-ACCESS		read-write
		STATUS			current
		DESCRIPTION
				"TYPE: - Editstring
				 PAGE: - User_Memory
					Memory_5  cmdID= 38  "
		::= { iqdnrsCmdEntry 38 }


	iqdnrsUserMemoryNameMemory6 OBJECT-TYPE
		SYNTAX		RollCallString
		MAX-ACCESS		read-write
		STATUS			current
		DESCRIPTION
				"TYPE: - Editstring
				 PAGE: - User_Memory
					Memory_6  cmdID= 39  "
		::= { iqdnrsCmdEntry 39 }


	iqdnrsUserMemoryNameMemory7 OBJECT-TYPE
		SYNTAX		RollCallString
		MAX-ACCESS		read-write
		STATUS			current
		DESCRIPTION
				"TYPE: - Editstring
				 PAGE: - User_Memory
					Memory_7  cmdID= 40  "
		::= { iqdnrsCmdEntry 40 }


	iqdnrsUserMemoryNameMemory8 OBJECT-TYPE
		SYNTAX		RollCallString
		MAX-ACCESS		read-write
		STATUS			current
		DESCRIPTION
				"TYPE: - Editstring
				 PAGE: - User_Memory
					Memory_8  cmdID= 41  "
		::= { iqdnrsCmdEntry 41 }


	iqdnrsUserMemoryNameMemory9 OBJECT-TYPE
		SYNTAX		RollCallString
		MAX-ACCESS		read-write
		STATUS			current
		DESCRIPTION
				"TYPE: - Editstring
				 PAGE: - User_Memory
					Memory_9  cmdID= 42  "
		::= { iqdnrsCmdEntry 42 }


	iqdnrsUserMemoryNameMemory10 OBJECT-TYPE
		SYNTAX		RollCallString
		MAX-ACCESS		read-write
		STATUS			current
		DESCRIPTION
				"TYPE: - Editstring
				 PAGE: - User_Memory
					Memory_10  cmdID= 43  "
		::= { iqdnrsCmdEntry 43 }


	iqdnrsUserMemoryNameMemory11 OBJECT-TYPE
		SYNTAX		RollCallString
		MAX-ACCESS		read-write
		STATUS			current
		DESCRIPTION
				"TYPE: - Editstring
				 PAGE: - User_Memory
					Memory_11  cmdID= 44  "
		::= { iqdnrsCmdEntry 44 }


	iqdnrsUserMemoryNameMemory12 OBJECT-TYPE
		SYNTAX		RollCallString
		MAX-ACCESS		read-write
		STATUS			current
		DESCRIPTION
				"TYPE: - Editstring
				 PAGE: - User_Memory
					Memory_12  cmdID= 45  "
		::= { iqdnrsCmdEntry 45 }


	iqdnrsUserMemoryNameMemory13 OBJECT-TYPE
		SYNTAX		RollCallString
		MAX-ACCESS		read-write
		STATUS			current
		DESCRIPTION
				"TYPE: - Editstring
				 PAGE: - User_Memory
					Memory_13  cmdID= 46  "
		::= { iqdnrsCmdEntry 46 }


	iqdnrsUserMemoryNameMemory14 OBJECT-TYPE
		SYNTAX		RollCallString
		MAX-ACCESS		read-write
		STATUS			current
		DESCRIPTION
				"TYPE: - Editstring
				 PAGE: - User_Memory
					Memory_14  cmdID= 47  "
		::= { iqdnrsCmdEntry 47 }


	iqdnrsUserMemoryNameMemory15 OBJECT-TYPE
		SYNTAX		RollCallString
		MAX-ACCESS		read-write
		STATUS			current
		DESCRIPTION
				"TYPE: - Editstring
				 PAGE: - User_Memory
					Memory_15  cmdID= 48  "
		::= { iqdnrsCmdEntry 48 }


	iqdnrsUserMemoryNameMemory16 OBJECT-TYPE
		SYNTAX		RollCallString
		MAX-ACCESS		read-write
		STATUS			current
		DESCRIPTION
				"TYPE: - Editstring
				 PAGE: - User_Memory
					Memory_16  cmdID= 49  "
		::= { iqdnrsCmdEntry 49 }


	iqdnrsUserMemoryNameMemory17 OBJECT-TYPE
		SYNTAX		RollCallString
		MAX-ACCESS		read-write
		STATUS			current
		DESCRIPTION
				"TYPE: - Editstring
				 PAGE: - User_Memory
					Memory_17  cmdID= 50  "
		::= { iqdnrsCmdEntry 50 }


	iqdnrsUserMemoryNameMemory18 OBJECT-TYPE
		SYNTAX		RollCallString
		MAX-ACCESS		read-write
		STATUS			current
		DESCRIPTION
				"TYPE: - Editstring
				 PAGE: - User_Memory
					Memory_18  cmdID= 51  "
		::= { iqdnrsCmdEntry 51 }


	iqdnrsUserMemoryNameMemory19 OBJECT-TYPE
		SYNTAX		RollCallString
		MAX-ACCESS		read-write
		STATUS			current
		DESCRIPTION
				"TYPE: - Editstring
				 PAGE: - User_Memory
					Memory_19  cmdID= 52  "
		::= { iqdnrsCmdEntry 52 }


	iqdnrsUserMemoryNameMemory20 OBJECT-TYPE
		SYNTAX		RollCallString
		MAX-ACCESS		read-write
		STATUS			current
		DESCRIPTION
				"TYPE: - Editstring
				 PAGE: - User_Memory
					Memory_20  cmdID= 53  "
		::= { iqdnrsCmdEntry 53 }


	iqdnrsUserMemoryNameMemory21 OBJECT-TYPE
		SYNTAX		RollCallString
		MAX-ACCESS		read-write
		STATUS			current
		DESCRIPTION
				"TYPE: - Editstring
				 PAGE: - User_Memory
					Memory_21  cmdID= 54  "
		::= { iqdnrsCmdEntry 54 }


	iqdnrsUserMemoryNameMemory22 OBJECT-TYPE
		SYNTAX		RollCallString
		MAX-ACCESS		read-write
		STATUS			current
		DESCRIPTION
				"TYPE: - Editstring
				 PAGE: - User_Memory
					Memory_22  cmdID= 55  "
		::= { iqdnrsCmdEntry 55 }


	iqdnrsUserMemoryNameMemory23 OBJECT-TYPE
		SYNTAX		RollCallString
		MAX-ACCESS		read-write
		STATUS			current
		DESCRIPTION
				"TYPE: - Editstring
				 PAGE: - User_Memory
					Memory_23  cmdID= 56  "
		::= { iqdnrsCmdEntry 56 }


	iqdnrsUserMemoryNameMemory24 OBJECT-TYPE
		SYNTAX		RollCallString
		MAX-ACCESS		read-write
		STATUS			current
		DESCRIPTION
				"TYPE: - Editstring
				 PAGE: - User_Memory
					Memory_24  cmdID= 57  "
		::= { iqdnrsCmdEntry 57 }


	iqdnrsUserMemoryNamePresetAllNames OBJECT-TYPE
		SYNTAX		INTEGER {
							val_Preset_All_Names(1)
							}
		MAX-ACCESS		read-write
		STATUS			current
		DESCRIPTION
				"TYPE: - RadiobuttonList
				 PAGE: - User_Memory
					Preset_All_Names  cmdID= 33 
					Preset_All_Names  value= 1  "
		::= { iqdnrsCmdEntry 33 }


	iqdnrsSetupSplitScreen OBJECT-TYPE
		SYNTAX		INTEGER {
							val_None(0),
							val_Left_Right(1),
							val_Top_Bottom(2)
							}
		MAX-ACCESS		read-write
		STATUS			current
		DESCRIPTION
				"TYPE: - RadiobuttonList
					Split_Screen  cmdID= 21 
					None  value= 0  
					Left/Right  value= 1  
					Top/Bottom  value= 2  "
		::= { iqdnrsCmdEntry 21 }


	iqdnrsSetupOutputStandard OBJECT-TYPE
		SYNTAX		INTEGER {
							val_Auto(0),
							val_625(1),
							val_525(2)
							}
		MAX-ACCESS		read-write
		STATUS			current
		DESCRIPTION
				"TYPE: - RadiobuttonList
					Output_Standard  cmdID= 22 
					Auto  value= 0  
					625  value= 1  
					525  value= 2  "
		::= { iqdnrsCmdEntry 22 }


	iqdnrsSetupDefaultOutputAutoFreeze OBJECT-TYPE
		SYNTAX		INTEGER { disable(0), enable(1) }
		MAX-ACCESS		read-write
		STATUS			current
		DESCRIPTION
				"TYPE: - Checkbox
					Auto_Freeze  cmdID= 26 "
		::= { iqdnrsCmdEntry 26 }


	iqdnrsSetupDefaultOutput OBJECT-TYPE
		SYNTAX		INTEGER {
							val_Black(0),
							val_EBU_Bars(3),
							val_100_Bars(2),
							val_Valid_Ramp(1),
							val_Multi_Burst(4),
							val_Pulse_and_Bar(5)
							}
		MAX-ACCESS		read-write
		STATUS			current
		DESCRIPTION
				"TYPE: - Button
					Black  cmdID= 25  value= 0  
					EBU_Bars  cmdID= 25  value= 3  
					100%_Bars  cmdID= 25  value= 2  
					Valid_Ramp  cmdID= 25  value= 1  
					Multi_Burst  cmdID= 25  value= 4  
					Pulse_and_Bar  cmdID= 25  value= 5  "
		::= { iqdnrsCmdEntry 25 }


	iqdnrsSetupPatternsPatternOn OBJECT-TYPE
		SYNTAX		INTEGER { disable(0), enable(1) }
		MAX-ACCESS		read-write
		STATUS			current
		DESCRIPTION
				"TYPE: - Checkbox
					Pattern_On  cmdID= 23 "
		::= { iqdnrsCmdEntry 23 }


	iqdnrsSetupPatterns OBJECT-TYPE
		SYNTAX		INTEGER {
							val_Black(0),
							val_EBU_Bars(3),
							val_100_Bars(2),
							val_Valid_Ramp(1),
							val_Multi_Burst(4),
							val_Pulse_and_Bar(5)
							}
		MAX-ACCESS		read-write
		STATUS			current
		DESCRIPTION
				"TYPE: - Button
					Black  cmdID= 24  value= 0  
					EBU_Bars  cmdID= 24  value= 3  
					100%_Bars  cmdID= 24  value= 2  
					Valid_Ramp  cmdID= 24  value= 1  
					Multi_Burst  cmdID= 24  value= 4  
					Pulse_and_Bar  cmdID= 24  value= 5  "
		::= { iqdnrsCmdEntry 24 }


	iqdnrsSetupEDHShowStats OBJECT-TYPE
		SYNTAX		INTEGER { disable(0), enable(1) }
		MAX-ACCESS		read-write
		STATUS			current
		DESCRIPTION
				"TYPE: - Checkbox
					Show_Stats  cmdID= 27 "
		::= { iqdnrsCmdEntry 27 }


	iqdnrsSetupEDHResetStats OBJECT-TYPE
		SYNTAX		INTEGER { noAction(0),val_Reset_Stats(1) }
		MAX-ACCESS		read-write
		STATUS			current
		DESCRIPTION
				"TYPE: - Button
					Reset_Stats  cmdID= 28  value= 1  "
		::= { iqdnrsCmdEntry 28 }


	iqdnrsSetupGPIInputsGPI1 OBJECT-TYPE
		SYNTAX		INTEGER {
							val_Off(2),
							val_Latch(0),
							val_Edge(1)
							}
		MAX-ACCESS		read-write
		STATUS			current
		DESCRIPTION
				"TYPE: - Button
				 PAGE: - Setup_GPI_Inputs
					Off  cmdID= 66  value= 2  
					Latch  cmdID= 66  value= 0  
					Edge  cmdID= 66  value= 1  "
		::= { iqdnrsCmdEntry 66 }


	iqdnrsSetupGPIInputsGPI1GPI1Function OBJECT-TYPE
		SYNTAX		INTEGER {
							val_ByPass(0),
							val_Hands_Free(1),
							val_Low_Pass(2),
							val_Freeze(3),
							val_Pattern(4),
							val_Memory_1(5),
							val_Memory_2(6),
							val_Memory_3(7),
							val_Memory_4(8),
							val_Memory_5(9),
							val_Memory_6(10),
							val_Memory_7(11),
							val_Memory_8(12),
							val_Memory_9(13),
							val_Memory_10(14),
							val_Memory_11(15),
							val_Memory_12(16),
							val_Memory_13(17),
							val_Memory_14(18),
							val_Memory_15(19),
							val_Memory_16(20),
							val_Memory_17(21),
							val_Memory_18(22),
							val_Memory_19(23),
							val_Memory_20(24),
							val_Memory_21(25),
							val_Memory_22(26),
							val_Memory_23(27),
							val_Memory_24(28)
							}
		MAX-ACCESS		read-write
		STATUS			current
		DESCRIPTION
				"TYPE: - RadiobuttonList
				 PAGE: - Setup_GPI_Inputs
					GPI_1_Function  cmdID= 70 
					ByPass  value= 0  
					Hands_Free  value= 1  
					Low_Pass  value= 2  
					Freeze  value= 3  
					Pattern  value= 4  
					Memory_1  value= 5  
					Memory_2  value= 6  
					Memory_3  value= 7  
					Memory_4  value= 8  
					Memory_5  value= 9  
					Memory_6  value= 10  
					Memory_7  value= 11  
					Memory_8  value= 12  
					Memory_9  value= 13  
					Memory_10  value= 14  
					Memory_11  value= 15  
					Memory_12  value= 16  
					Memory_13  value= 17  
					Memory_14  value= 18  
					Memory_15  value= 19  
					Memory_16  value= 20  
					Memory_17  value= 21  
					Memory_18  value= 22  
					Memory_19  value= 23  
					Memory_20  value= 24  
					Memory_21  value= 25  
					Memory_22  value= 26  
					Memory_23  value= 27  
					Memory_24  value= 28  "
		::= { iqdnrsCmdEntry 70 }


	iqdnrsSetupGPIInputsGPI2 OBJECT-TYPE
		SYNTAX		INTEGER {
							val_Off(2),
							val_Latch(0),
							val_Edge(1)
							}
		MAX-ACCESS		read-write
		STATUS			current
		DESCRIPTION
				"TYPE: - Button
				 PAGE: - Setup_GPI_Inputs
					Off  cmdID= 67  value= 2  
					Latch  cmdID= 67  value= 0  
					Edge  cmdID= 67  value= 1  "
		::= { iqdnrsCmdEntry 67 }


	iqdnrsSetupGPIInputsGPI2GPI2Function OBJECT-TYPE
		SYNTAX		INTEGER {
							val_ByPass(0),
							val_Hands_Free(1),
							val_Low_Pass(2),
							val_Freeze(3),
							val_Pattern(4),
							val_Memory_1(5),
							val_Memory_2(6),
							val_Memory_3(7),
							val_Memory_4(8),
							val_Memory_5(9),
							val_Memory_6(10),
							val_Memory_7(11),
							val_Memory_8(12),
							val_Memory_9(13),
							val_Memory_10(14),
							val_Memory_11(15),
							val_Memory_12(16),
							val_Memory_13(17),
							val_Memory_14(18),
							val_Memory_15(19),
							val_Memory_16(20),
							val_Memory_17(21),
							val_Memory_18(22),
							val_Memory_19(23),
							val_Memory_20(24),
							val_Memory_21(25),
							val_Memory_22(26),
							val_Memory_23(27),
							val_Memory_24(28)
							}
		MAX-ACCESS		read-write
		STATUS			current
		DESCRIPTION
				"TYPE: - RadiobuttonList
				 PAGE: - Setup_GPI_Inputs
					GPI_2_Function  cmdID= 71 
					ByPass  value= 0  
					Hands_Free  value= 1  
					Low_Pass  value= 2  
					Freeze  value= 3  
					Pattern  value= 4  
					Memory_1  value= 5  
					Memory_2  value= 6  
					Memory_3  value= 7  
					Memory_4  value= 8  
					Memory_5  value= 9  
					Memory_6  value= 10  
					Memory_7  value= 11  
					Memory_8  value= 12  
					Memory_9  value= 13  
					Memory_10  value= 14  
					Memory_11  value= 15  
					Memory_12  value= 16  
					Memory_13  value= 17  
					Memory_14  value= 18  
					Memory_15  value= 19  
					Memory_16  value= 20  
					Memory_17  value= 21  
					Memory_18  value= 22  
					Memory_19  value= 23  
					Memory_20  value= 24  
					Memory_21  value= 25  
					Memory_22  value= 26  
					Memory_23  value= 27  
					Memory_24  value= 28  "
		::= { iqdnrsCmdEntry 71 }


	iqdnrsSetupGPIInputsGPI3 OBJECT-TYPE
		SYNTAX		INTEGER {
							val_Off(2),
							val_Latch(0),
							val_Edge(1)
							}
		MAX-ACCESS		read-write
		STATUS			current
		DESCRIPTION
				"TYPE: - Button
				 PAGE: - Setup_GPI_Inputs
					Off  cmdID= 68  value= 2  
					Latch  cmdID= 68  value= 0  
					Edge  cmdID= 68  value= 1  "
		::= { iqdnrsCmdEntry 68 }


	iqdnrsSetupGPIInputsGPI3GPI3Function OBJECT-TYPE
		SYNTAX		INTEGER {
							val_ByPass(0),
							val_Hands_Free(1),
							val_Low_Pass(2),
							val_Freeze(3),
							val_Pattern(4),
							val_Memory_1(5),
							val_Memory_2(6),
							val_Memory_3(7),
							val_Memory_4(8),
							val_Memory_5(9),
							val_Memory_6(10),
							val_Memory_7(11),
							val_Memory_8(12),
							val_Memory_9(13),
							val_Memory_10(14),
							val_Memory_11(15),
							val_Memory_12(16),
							val_Memory_13(17),
							val_Memory_14(18),
							val_Memory_15(19),
							val_Memory_16(20),
							val_Memory_17(21),
							val_Memory_18(22),
							val_Memory_19(23),
							val_Memory_20(24),
							val_Memory_21(25),
							val_Memory_22(26),
							val_Memory_23(27),
							val_Memory_24(28)
							}
		MAX-ACCESS		read-write
		STATUS			current
		DESCRIPTION
				"TYPE: - RadiobuttonList
				 PAGE: - Setup_GPI_Inputs
					GPI_3_Function  cmdID= 72 
					ByPass  value= 0  
					Hands_Free  value= 1  
					Low_Pass  value= 2  
					Freeze  value= 3  
					Pattern  value= 4  
					Memory_1  value= 5  
					Memory_2  value= 6  
					Memory_3  value= 7  
					Memory_4  value= 8  
					Memory_5  value= 9  
					Memory_6  value= 10  
					Memory_7  value= 11  
					Memory_8  value= 12  
					Memory_9  value= 13  
					Memory_10  value= 14  
					Memory_11  value= 15  
					Memory_12  value= 16  
					Memory_13  value= 17  
					Memory_14  value= 18  
					Memory_15  value= 19  
					Memory_16  value= 20  
					Memory_17  value= 21  
					Memory_18  value= 22  
					Memory_19  value= 23  
					Memory_20  value= 24  
					Memory_21  value= 25  
					Memory_22  value= 26  
					Memory_23  value= 27  
					Memory_24  value= 28  "
		::= { iqdnrsCmdEntry 72 }


	iqdnrsSetupLoggingInputChange OBJECT-TYPE
		SYNTAX		INTEGER { disable(0), enable(1) }
		MAX-ACCESS		read-write
		STATUS			current
		DESCRIPTION
				"TYPE: - Checkbox
					Input_Change  cmdID= 58 "
		::= { iqdnrsCmdEntry 58 }


	iqdnrsSetupLoggingEDHErrors OBJECT-TYPE
		SYNTAX		INTEGER { disable(0), enable(1) }
		MAX-ACCESS		read-write
		STATUS			current
		DESCRIPTION
				"TYPE: - Checkbox
					EDH_Errors  cmdID= 59 "
		::= { iqdnrsCmdEntry 59 }


	iqdnrsSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdnrsCmdEntry 3 }


	iqdnrsSetupSoftwareVersion OBJECT-TYPE
		SYNTAX		RollCallString
		MAX-ACCESS		read-only
		STATUS			current
		DESCRIPTION
				"TYPE: - Display
					Software_Version  cmdID= 2  format=   "
		::= { iqdnrsCmdEntry 2 }


	iqdnrsSetupSerialNo OBJECT-TYPE
		SYNTAX		RollCallString
		MAX-ACCESS		read-only
		STATUS			current
		DESCRIPTION
				"TYPE: - Display
					Serial_No  cmdID= 1  format=   "
		::= { iqdnrsCmdEntry 1 }


	iqdnrsSetupRestart OBJECT-TYPE
		SYNTAX		INTEGER { noAction(0),val_Restart(1) }
		MAX-ACCESS		read-write
		STATUS			current
		DESCRIPTION
				"TYPE: - Button
					Restart  cmdID= 4  value= 1  "
		::= { iqdnrsCmdEntry 4 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: 625
--				: 525
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: ERR
--				: OK
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary Number  : YES
-- Value(s)		: 
--				: 
-- Comments		: 
--
---------------------------------------------------------------------------------------------------
