-- ************************************************************************************
--        Snell Card:IQHCO30
--        Module Id#:574
--       Command Set:20
--          Filename:SNELL-IQHCO30-CMD-MIB.mib
--            Author:N Hewer
--              Date:13/11/2014
--              Time:14:56
--
-- Copyright (c) 2010 Snell Ltd
-- All rights reserved.
--
-- ************************************************************************************

SNELL-IQHCO30-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQHCO30,
    moduleIQHCO30MIB
        FROM SNELL-WILCOX-PRODUCT-REG;

 moduleIQHCO30CmdMi MODULE-IDENTITY
    LAST-UPDATED "1411131456Z"
    ORGANIZATION "Snell Ltd"
    CONTACT-INFO
        "Primary Author:N Hewer

         postal:    Southleigh Park House
                    Eastleigh Road
                    Havant, Hants
                    PO9 2PE
         phone:     +44 (0)23 92489000
         email:     snmp.support@snellgroup.com"
    DESCRIPTION
        "This file defines the Snell card, command set  translations."
    ::= { moduleIQHCO30MIB 1 }




--********************************************************************************
--*
--*  Snell Card:
--*  command set:
--*  list commands/menus:
--*
--******************************************************************************
	iqhco30CmdTable OBJECT-TYPE
		SYNTAX			SEQUENCE OF Iqhco30CmdEntry
		MAX-ACCESS		not-accessible
		STATUS			current
		DESCRIPTION
				"Note the instance of this table is relected in the command set Version"
		::= { moduleIQHCO30 1 }

	iqhco30CmdEntry OBJECT-TYPE
		SYNTAX		Iqhco30CmdEntry
		MAX-ACCESS		not-accessible
		STATUS			current
		DESCRIPTION
				"Entry in command table."
		INDEX	{ iqhco30SlotIndex }
		::= { iqhco30CmdTable 1 }

	Iqhco30CmdEntry ::=
		SEQUENCE {
			iqhco30SlotIndex
				Unsigned32,
			iqhco30MasterValidValidInputStds108050pB
				INTEGER,
			iqhco30MasterValidValidInputStds108059pB
				INTEGER,
			iqhco30MasterValidValidInputStds108050pA
				INTEGER,
			iqhco30MasterValidValidInputStds108059pA
				INTEGER,
			iqhco30MasterValidValidInputStds108029i
				INTEGER,
			iqhco30MasterValidValidInputStds108025i
				INTEGER,
			iqhco30MasterValidValidInputStds72059p
				INTEGER,
			iqhco30MasterValidValidInputStds72050p
				INTEGER,
			iqhco30MasterValidValidInputStds52529i
				INTEGER,
			iqhco30MasterValidValidInputStds62525i
				INTEGER,
			iqhco30MasterValidCRCEDHErroredsecErrSecEnable
				INTEGER,
			iqhco30MasterValidCRCEDHErroredsecErrSecDecision
				RollCallString,
			iqhco30MasterValidCRCEDHErroredsecCarrierDecision
				RollCallString,
			iqhco30MasterValidCRCEDHErroredsecStdDecision
				RollCallString,
			iqhco30MasterValidCRCEDHErroredsecInputStd
				RollCallString,
			iqhco30MasterValidCRCEDHErroredsecFreezeEnable
				INTEGER,
			iqhco30MasterValidCRCEDHErroredsecFreezeDecision
				RollCallString,
			iqhco30MasterValidCRCEDHErroredsecBlackEnable
				INTEGER,
			iqhco30MasterValidCRCEDHErroredsecBlackDecision
				RollCallString,
			iqhco30MasterValidCRCEDHErroredsecBlackThreshold
				INTEGER,
			iqhco30MasterValidVideoValidTimersBlackFailDelay
				INTEGER,
			iqhco30MasterValidVideoValidTimersBlackRecoverDelay
				INTEGER,
			iqhco30MasterValidVideoValidTimersFreezeFailDelay
				INTEGER,
			iqhco30MasterValidVideoValidTimersFreezeRecoverDela
				INTEGER,
			iqhco30MasterValidVideoValidTimersErrsecFailDelay
				INTEGER,
			iqhco30MasterValidVideoValidTimersErrsecRecoverDela
				INTEGER,
			iqhco30MasterValidVideoValidTimersValidFailDelay
				INTEGER,
			iqhco30MasterValidVideoValidTimersValidRecoverDelay
				INTEGER,
			iqhco30MasterValidValidAudioDecision
				RollCallString,
			iqhco30ValidAudioMasterPair1Decision
				RollCallString,
			iqhco30ValidAudioMasterPair1CurrentType
				RollCallString,
			iqhco30ValidAudioMasterPair1
				INTEGER,
			iqhco30ValidAudioMasterPair1Ch1State
				RollCallString,
			iqhco30ValidAudioMasterPair1Ch2State
				RollCallString,
			iqhco30ValidAudioMasterPair1Mute
				INTEGER,
			iqhco30ValidAudioMasterPair1Lowlevel
				INTEGER,
			iqhco30ValidAudioMasterPair1Overload
				INTEGER,
			iqhco30ValidAudioMasterPair2Decision
				RollCallString,
			iqhco30ValidAudioMasterPair2CurrentType
				RollCallString,
			iqhco30ValidAudioMasterPair2
				INTEGER,
			iqhco30ValidAudioMasterPair2Ch1State
				RollCallString,
			iqhco30ValidAudioMasterPair2Ch2State
				RollCallString,
			iqhco30ValidAudioMasterPair2Mute
				INTEGER,
			iqhco30ValidAudioMasterPair2Lowlevel
				INTEGER,
			iqhco30ValidAudioMasterPair2Overload
				INTEGER,
			iqhco30ValidAudioMasterPair3Decision
				RollCallString,
			iqhco30ValidAudioMasterPair3CurrentType
				RollCallString,
			iqhco30ValidAudioMasterPair3
				INTEGER,
			iqhco30ValidAudioMasterPair3Ch1State
				RollCallString,
			iqhco30ValidAudioMasterPair3Ch2State
				RollCallString,
			iqhco30ValidAudioMasterPair3Mute
				INTEGER,
			iqhco30ValidAudioMasterPair3Lowlevel
				INTEGER,
			iqhco30ValidAudioMasterPair3Overload
				INTEGER,
			iqhco30ValidAudioMasterPair4Decision
				RollCallString,
			iqhco30ValidAudioMasterPair4CurrentType
				RollCallString,
			iqhco30ValidAudioMasterPair4
				INTEGER,
			iqhco30ValidAudioMasterPair4Ch1State
				RollCallString,
			iqhco30ValidAudioMasterPair4Ch2State
				RollCallString,
			iqhco30ValidAudioMasterPair4Mute
				INTEGER,
			iqhco30ValidAudioMasterPair4Lowlevel
				INTEGER,
			iqhco30ValidAudioMasterPair4Overload
				INTEGER,
			iqhco30ValidAudioMasterPair5Decision
				RollCallString,
			iqhco30ValidAudioMasterPair5CurrentType
				RollCallString,
			iqhco30ValidAudioMasterPair5
				INTEGER,
			iqhco30ValidAudioMasterPair5Ch1State
				RollCallString,
			iqhco30ValidAudioMasterPair5Ch2State
				RollCallString,
			iqhco30ValidAudioMasterPair5Mute
				INTEGER,
			iqhco30ValidAudioMasterPair5Lowlevel
				INTEGER,
			iqhco30ValidAudioMasterPair5Overload
				INTEGER,
			iqhco30ValidAudioMasterPair6Decision
				RollCallString,
			iqhco30ValidAudioMasterPair6CurrentType
				RollCallString,
			iqhco30ValidAudioMasterPair6
				INTEGER,
			iqhco30ValidAudioMasterPair6Ch1State
				RollCallString,
			iqhco30ValidAudioMasterPair6Ch2State
				RollCallString,
			iqhco30ValidAudioMasterPair6Mute
				INTEGER,
			iqhco30ValidAudioMasterPair6Lowlevel
				INTEGER,
			iqhco30ValidAudioMasterPair6Overload
				INTEGER,
			iqhco30ValidAudioMasterPair7Decision
				RollCallString,
			iqhco30ValidAudioMasterPair7CurrentType
				RollCallString,
			iqhco30ValidAudioMasterPair7
				INTEGER,
			iqhco30ValidAudioMasterPair7Ch1State
				RollCallString,
			iqhco30ValidAudioMasterPair7Ch2State
				RollCallString,
			iqhco30ValidAudioMasterPair7Mute
				INTEGER,
			iqhco30ValidAudioMasterPair7Lowlevel
				INTEGER,
			iqhco30ValidAudioMasterPair7Overload
				INTEGER,
			iqhco30ValidAudioMasterPair8Decision
				RollCallString,
			iqhco30ValidAudioMasterPair8CurrentType
				RollCallString,
			iqhco30ValidAudioMasterPair8
				INTEGER,
			iqhco30ValidAudioMasterPair8Ch1State
				RollCallString,
			iqhco30ValidAudioMasterPair8Ch2State
				RollCallString,
			iqhco30ValidAudioMasterPair8Mute
				INTEGER,
			iqhco30ValidAudioMasterPair8Lowlevel
				INTEGER,
			iqhco30ValidAudioMasterPair8Overload
				INTEGER,
			iqhco30MasterValidValidAudioLowlevel
				INTEGER,
			iqhco30MasterValidValidAudioOverloadLevel
				INTEGER,
			iqhco30MasterValidValidAudioTypeFailTimer
				INTEGER,
			iqhco30MasterValidValidAudioTypeRecoverTimer
				INTEGER,
			iqhco30MasterValidValidAudioMuteFailTimer
				INTEGER,
			iqhco30MasterValidValidAudioMuteRecoverTimer
				INTEGER,
			iqhco30MasterValidValidAudioLowFailTimer
				INTEGER,
			iqhco30MasterValidValidAudioLowRecoverTimer
				INTEGER,
			iqhco30MasterValidValidAudioOverFailTimer
				INTEGER,
			iqhco30MasterValidValidAudioOverRecoverTimer
				INTEGER,
			iqhco30VideoMasterCaption
				INTEGER,
			iqhco30VideoMasterCaptionEditCaption
				RollCallString,
			iqhco30MasterVideoMasterPattern
				INTEGER,
			iqhco30BackupValidValidInputStds108050pB
				INTEGER,
			iqhco30BackupValidValidInputStds108059pB
				INTEGER,
			iqhco30BackupValidValidInputStds108050pA
				INTEGER,
			iqhco30BackupValidValidInputStds108059pA
				INTEGER,
			iqhco30BackupValidValidInputStds108029i
				INTEGER,
			iqhco30BackupValidValidInputStds108025i
				INTEGER,
			iqhco30BackupValidValidInputStds72059p
				INTEGER,
			iqhco30BackupValidValidInputStds72050p
				INTEGER,
			iqhco30BackupValidValidInputStds52529i
				INTEGER,
			iqhco30BackupValidValidInputStds62525i
				INTEGER,
			iqhco30BackupValidCRCEDHErroredsecErrSecEnable
				INTEGER,
			iqhco30BackupValidCRCEDHErroredsecErrSecDecision
				RollCallString,
			iqhco30BackupValidCRCEDHErroredsecCarrierDecision
				RollCallString,
			iqhco30BackupValidCRCEDHErroredsecStdDecision
				RollCallString,
			iqhco30BackupValidCRCEDHErroredsecInputStd
				RollCallString,
			iqhco30BackupValidCRCEDHErroredsecFreezeEnable
				INTEGER,
			iqhco30BackupValidCRCEDHErroredsecFreezeDecision
				RollCallString,
			iqhco30BackupValidCRCEDHErroredsecBlackEnable
				INTEGER,
			iqhco30BackupValidCRCEDHErroredsecBlackDecision
				RollCallString,
			iqhco30BackupValidCRCEDHErroredsecBlackThreshold
				INTEGER,
			iqhco30BackupValidVideoValidTimersBlackFailDelay
				INTEGER,
			iqhco30BackupValidVideoValidTimersBlackRecoverDelay
				INTEGER,
			iqhco30BackupValidVideoValidTimersFreezeFailDelay
				INTEGER,
			iqhco30BackupValidVideoValidTimersFreezeRecoverDela
				INTEGER,
			iqhco30BackupValidVideoValidTimersErrsecFailDelay
				INTEGER,
			iqhco30BackupValidVideoValidTimersErrsecRecoverDela
				INTEGER,
			iqhco30BackupValidVideoValidTimersValidFailDelay
				INTEGER,
			iqhco30BackupValidVideoValidTimersValidRecoverDelay
				INTEGER,
			iqhco30BackupValidValidAudioDecision
				RollCallString,
			iqhco30ValidAudioBackupPair1Decision
				RollCallString,
			iqhco30ValidAudioBackupPair1CurrentType
				RollCallString,
			iqhco30ValidAudioBackupPair1
				INTEGER,
			iqhco30ValidAudioBackupPair1Ch1State
				RollCallString,
			iqhco30ValidAudioBackupPair1Ch2State
				RollCallString,
			iqhco30ValidAudioBackupPair1Mute
				INTEGER,
			iqhco30ValidAudioBackupPair1Lowlevel
				INTEGER,
			iqhco30ValidAudioBackupPair1Overload
				INTEGER,
			iqhco30ValidAudioBackupPair2Decision
				RollCallString,
			iqhco30ValidAudioBackupPair2CurrentType
				RollCallString,
			iqhco30ValidAudioBackupPair2
				INTEGER,
			iqhco30ValidAudioBackupPair2Ch1State
				RollCallString,
			iqhco30ValidAudioBackupPair2Ch2State
				RollCallString,
			iqhco30ValidAudioBackupPair2Mute
				INTEGER,
			iqhco30ValidAudioBackupPair2Lowlevel
				INTEGER,
			iqhco30ValidAudioBackupPair2Overload
				INTEGER,
			iqhco30ValidAudioBackupPair3Decision
				RollCallString,
			iqhco30ValidAudioBackupPair3CurrentType
				RollCallString,
			iqhco30ValidAudioBackupPair3
				INTEGER,
			iqhco30ValidAudioBackupPair3Ch1State
				RollCallString,
			iqhco30ValidAudioBackupPair3Ch2State
				RollCallString,
			iqhco30ValidAudioBackupPair3Mute
				INTEGER,
			iqhco30ValidAudioBackupPair3Lowlevel
				INTEGER,
			iqhco30ValidAudioBackupPair3Overload
				INTEGER,
			iqhco30ValidAudioBackupPair4Decision
				RollCallString,
			iqhco30ValidAudioBackupPair4CurrentType
				RollCallString,
			iqhco30ValidAudioBackupPair4
				INTEGER,
			iqhco30ValidAudioBackupPair4Ch1State
				RollCallString,
			iqhco30ValidAudioBackupPair4Ch2State
				RollCallString,
			iqhco30ValidAudioBackupPair4Mute
				INTEGER,
			iqhco30ValidAudioBackupPair4Lowlevel
				INTEGER,
			iqhco30ValidAudioBackupPair4Overload
				INTEGER,
			iqhco30ValidAudioBackupPair5Decision
				RollCallString,
			iqhco30ValidAudioBackupPair5CurrentType
				RollCallString,
			iqhco30ValidAudioBackupPair5
				INTEGER,
			iqhco30ValidAudioBackupPair5Ch1State
				RollCallString,
			iqhco30ValidAudioBackupPair5Ch2State
				RollCallString,
			iqhco30ValidAudioBackupPair5Mute
				INTEGER,
			iqhco30ValidAudioBackupPair5Lowlevel
				INTEGER,
			iqhco30ValidAudioBackupPair5Overload
				INTEGER,
			iqhco30ValidAudioBackupPair6Decision
				RollCallString,
			iqhco30ValidAudioBackupPair6CurrentType
				RollCallString,
			iqhco30ValidAudioBackupPair6
				INTEGER,
			iqhco30ValidAudioBackupPair6Ch1State
				RollCallString,
			iqhco30ValidAudioBackupPair6Ch2State
				RollCallString,
			iqhco30ValidAudioBackupPair6Mute
				INTEGER,
			iqhco30ValidAudioBackupPair6Lowlevel
				INTEGER,
			iqhco30ValidAudioBackupPair6Overload
				INTEGER,
			iqhco30ValidAudioBackupPair7Decision
				RollCallString,
			iqhco30ValidAudioBackupPair7CurrentType
				RollCallString,
			iqhco30ValidAudioBackupPair7
				INTEGER,
			iqhco30ValidAudioBackupPair7Ch1State
				RollCallString,
			iqhco30ValidAudioBackupPair7Ch2State
				RollCallString,
			iqhco30ValidAudioBackupPair7Mute
				INTEGER,
			iqhco30ValidAudioBackupPair7Lowlevel
				INTEGER,
			iqhco30ValidAudioBackupPair7Overload
				INTEGER,
			iqhco30ValidAudioBackupPair8Decision
				RollCallString,
			iqhco30ValidAudioBackupPair8CurrentType
				RollCallString,
			iqhco30ValidAudioBackupPair8
				INTEGER,
			iqhco30ValidAudioBackupPair8Ch1State
				RollCallString,
			iqhco30ValidAudioBackupPair8Ch2State
				RollCallString,
			iqhco30ValidAudioBackupPair8Mute
				INTEGER,
			iqhco30ValidAudioBackupPair8Lowlevel
				INTEGER,
			iqhco30ValidAudioBackupPair8Overload
				INTEGER,
			iqhco30BackupValidValidAudioLowlevel
				INTEGER,
			iqhco30BackupValidValidAudioOverloadLevel
				INTEGER,
			iqhco30BackupValidValidAudioTypeFailTimer
				INTEGER,
			iqhco30BackupValidValidAudioTypeRecoverTimer
				INTEGER,
			iqhco30BackupValidValidAudioMuteFailTimer
				INTEGER,
			iqhco30BackupValidValidAudioMuteRecoverTimer
				INTEGER,
			iqhco30BackupValidValidAudioLowFailTimer
				INTEGER,
			iqhco30BackupValidValidAudioLowRecoverTimer
				INTEGER,
			iqhco30BackupValidValidAudioOverFailTimer
				INTEGER,
			iqhco30BackupValidValidAudioOverRecoverTimer
				INTEGER,
			iqhco30VideoBackupCaption
				INTEGER,
			iqhco30VideoBackupCaptionEditCaption
				RollCallString,
			iqhco30BackupVideoBackupPattern
				INTEGER,
			iqhco30RulesRulesVideoMasterCurrentOutput
				RollCallString,
			iqhco30RulesRulesVideoMasterSwitchtoMaster
				INTEGER,
			iqhco30RulesRulesVideoMasterActive
				RollCallString,
			iqhco30RulesRulesVideoMaster5602
				INTEGER,
			iqhco30RulesRulesVideoMaster5603
				INTEGER,
			iqhco30RulesRulesVideoMaster5604
				INTEGER,
			iqhco30RulesRulesVideoMaster5605
				INTEGER,
			iqhco30RulesRulesVideoMaster5606
				INTEGER,
			iqhco30RulesRulesVideoMaster5607
				INTEGER,
			iqhco30RulesRulesVideoMaster5608
				INTEGER,
			iqhco30RulesRulesVideoMaster5609
				INTEGER,
			iqhco30RulesRulesVideoMaster5610
				INTEGER,
			iqhco30RulesRulesVideoMaster5611
				INTEGER,
			iqhco30RulesRulesVideoBackupSwitchtoBackup
				INTEGER,
			iqhco30RulesRulesVideoBackupActive
				RollCallString,
			iqhco30RulesRulesVideoBackup5622
				INTEGER,
			iqhco30RulesRulesVideoBackup5623
				INTEGER,
			iqhco30RulesRulesVideoBackup5624
				INTEGER,
			iqhco30RulesRulesVideoBackup5625
				INTEGER,
			iqhco30RulesRulesVideoBackup5626
				INTEGER,
			iqhco30RulesRulesVideoBackup5627
				INTEGER,
			iqhco30RulesRulesVideoBackup5628
				INTEGER,
			iqhco30RulesRulesVideoBackup5629
				INTEGER,
			iqhco30RulesRulesVideoBackup5630
				INTEGER,
			iqhco30RulesRulesVideoBackup5631
				INTEGER,
			iqhco30GPIEnableGPIO1GPIO1State
				RollCallString,
			iqhco30GPIEnableGPIO1
				INTEGER,
			iqhco30GPIEnableGPIO1GPO1Invert
				INTEGER,
			iqhco30GPIEnableGPIO2GPIO2State
				RollCallString,
			iqhco30GPIEnableGPIO2
				INTEGER,
			iqhco30GPIEnableGPIO2GPO2Invert
				INTEGER,
			iqhco30GPIEnableGPIO3GPIO3State
				RollCallString,
			iqhco30GPIEnableGPIO3
				INTEGER,
			iqhco30GPIEnableGPIO3GPO3Invert
				INTEGER,
			iqhco30GPIEnableGPIO4GPIO4State
				RollCallString,
			iqhco30GPIEnableGPIO4
				INTEGER,
			iqhco30GPIEnableGPIO4GPO4Invert
				INTEGER,
			iqhco30RulesGPIEnableNoGPIsonRear
				RollCallString,
			iqhco30RulesRulesGPI1outActive
				RollCallString,
			iqhco30RulesRulesGPI1out5672
				INTEGER,
			iqhco30RulesRulesGPI1out5662
				INTEGER,
			iqhco30RulesRulesGPI1out5663
				INTEGER,
			iqhco30RulesRulesGPI1out5664
				INTEGER,
			iqhco30RulesRulesGPI1out5665
				INTEGER,
			iqhco30RulesRulesGPI1out5666
				INTEGER,
			iqhco30RulesRulesGPI1out5667
				INTEGER,
			iqhco30RulesRulesGPI1out5668
				INTEGER,
			iqhco30RulesRulesGPI1out5669
				INTEGER,
			iqhco30RulesRulesGPI1out5670
				INTEGER,
			iqhco30RulesRulesGPI1out
				INTEGER,
			iqhco30RulesRulesGPI2outActive
				RollCallString,
			iqhco30RulesRulesGPI2out5692
				INTEGER,
			iqhco30RulesRulesGPI2out5682
				INTEGER,
			iqhco30RulesRulesGPI2out5683
				INTEGER,
			iqhco30RulesRulesGPI2out5684
				INTEGER,
			iqhco30RulesRulesGPI2out5685
				INTEGER,
			iqhco30RulesRulesGPI2out5686
				INTEGER,
			iqhco30RulesRulesGPI2out5687
				INTEGER,
			iqhco30RulesRulesGPI2out5688
				INTEGER,
			iqhco30RulesRulesGPI2out5689
				INTEGER,
			iqhco30RulesRulesGPI2out5690
				INTEGER,
			iqhco30RulesRulesGPI2out
				INTEGER,
			iqhco30RulesRulesGPI3outActive
				RollCallString,
			iqhco30RulesRulesGPI3out5712
				INTEGER,
			iqhco30RulesRulesGPI3out5702
				INTEGER,
			iqhco30RulesRulesGPI3out5703
				INTEGER,
			iqhco30RulesRulesGPI3out5704
				INTEGER,
			iqhco30RulesRulesGPI3out5705
				INTEGER,
			iqhco30RulesRulesGPI3out5706
				INTEGER,
			iqhco30RulesRulesGPI3out5707
				INTEGER,
			iqhco30RulesRulesGPI3out5708
				INTEGER,
			iqhco30RulesRulesGPI3out5709
				INTEGER,
			iqhco30RulesRulesGPI3out5710
				INTEGER,
			iqhco30RulesRulesGPI3out
				INTEGER,
			iqhco30RulesRulesGPI4outActive
				RollCallString,
			iqhco30RulesRulesGPI4out5732
				INTEGER,
			iqhco30RulesRulesGPI4out5722
				INTEGER,
			iqhco30RulesRulesGPI4out5723
				INTEGER,
			iqhco30RulesRulesGPI4out5724
				INTEGER,
			iqhco30RulesRulesGPI4out5725
				INTEGER,
			iqhco30RulesRulesGPI4out5726
				INTEGER,
			iqhco30RulesRulesGPI4out5727
				INTEGER,
			iqhco30RulesRulesGPI4out5728
				INTEGER,
			iqhco30RulesRulesGPI4out5729
				INTEGER,
			iqhco30RulesRulesGPI4out5730
				INTEGER,
			iqhco30RulesRulesGPI4out
				INTEGER,
			iqhco30RulesRollTrackEnableEnable6649
				INTEGER,
			iqhco30RulesRollTrackEnableEnable6651
				INTEGER,
			iqhco30RulesRollTrackEnableEnable6653
				INTEGER,
			iqhco30RulesRollTrackEnableEnable6655
				INTEGER,
			iqhco30RulesRollTrackEnableState6648
				RollCallString,
			iqhco30RulesRollTrackEnableState6650
				RollCallString,
			iqhco30RulesRollTrackEnableState6652
				RollCallString,
			iqhco30RulesRollTrackEnableState6654
				RollCallString,
			iqhco30RulesRulesRollTack101Active
				RollCallString,
			iqhco30RulesRulesRollTack1015752
				INTEGER,
			iqhco30RulesRulesRollTack1015742
				INTEGER,
			iqhco30RulesRulesRollTack1015743
				INTEGER,
			iqhco30RulesRulesRollTack1015744
				INTEGER,
			iqhco30RulesRulesRollTack1015745
				INTEGER,
			iqhco30RulesRulesRollTack1015746
				INTEGER,
			iqhco30RulesRulesRollTack1015747
				INTEGER,
			iqhco30RulesRulesRollTack1015748
				INTEGER,
			iqhco30RulesRulesRollTack1015749
				INTEGER,
			iqhco30RulesRulesRollTack1015750
				INTEGER,
			iqhco30RulesRulesRollTack101
				INTEGER,
			iqhco30RulesRulesRollTack102Active
				RollCallString,
			iqhco30RulesRulesRollTack1025772
				INTEGER,
			iqhco30RulesRulesRollTack1025762
				INTEGER,
			iqhco30RulesRulesRollTack1025763
				INTEGER,
			iqhco30RulesRulesRollTack1025764
				INTEGER,
			iqhco30RulesRulesRollTack1025765
				INTEGER,
			iqhco30RulesRulesRollTack1025766
				INTEGER,
			iqhco30RulesRulesRollTack1025767
				INTEGER,
			iqhco30RulesRulesRollTack1025768
				INTEGER,
			iqhco30RulesRulesRollTack1025769
				INTEGER,
			iqhco30RulesRulesRollTack1025770
				INTEGER,
			iqhco30RulesRulesRollTack102
				INTEGER,
			iqhco30RulesRulesRollTack103Active
				RollCallString,
			iqhco30RulesRulesRollTack1035792
				INTEGER,
			iqhco30RulesRulesRollTack1035782
				INTEGER,
			iqhco30RulesRulesRollTack1035783
				INTEGER,
			iqhco30RulesRulesRollTack1035784
				INTEGER,
			iqhco30RulesRulesRollTack1035785
				INTEGER,
			iqhco30RulesRulesRollTack1035786
				INTEGER,
			iqhco30RulesRulesRollTack1035787
				INTEGER,
			iqhco30RulesRulesRollTack1035788
				INTEGER,
			iqhco30RulesRulesRollTack1035789
				INTEGER,
			iqhco30RulesRulesRollTack1035790
				INTEGER,
			iqhco30RulesRulesRollTack103
				INTEGER,
			iqhco30RulesRulesRollTack104Active
				RollCallString,
			iqhco30RulesRulesRollTack1045812
				INTEGER,
			iqhco30RulesRulesRollTack1045802
				INTEGER,
			iqhco30RulesRulesRollTack1045803
				INTEGER,
			iqhco30RulesRulesRollTack1045804
				INTEGER,
			iqhco30RulesRulesRollTack1045805
				INTEGER,
			iqhco30RulesRulesRollTack1045806
				INTEGER,
			iqhco30RulesRulesRollTack1045807
				INTEGER,
			iqhco30RulesRulesRollTack1045808
				INTEGER,
			iqhco30RulesRulesRollTack1045809
				INTEGER,
			iqhco30RulesRulesRollTack1045810
				INTEGER,
			iqhco30RulesRulesRollTack104
				INTEGER,
			iqhco30RulesPresetsPriorityMaster6660
				INTEGER,
			iqhco30RulesPresetsPriorityBackup6661
				INTEGER,
			iqhco30RulesPresetsNoPriority6662
				INTEGER,
			iqhco30RulesPresetsPriorityMaster6663
				INTEGER,
			iqhco30RulesPresetsPriorityBackup6664
				INTEGER,
			iqhco30RulesPresetsNoPriority6665
				INTEGER,
			iqhco30RulesPresetsPriorityMaster
				INTEGER,
			iqhco30RulesPresetsPriorityBackup
				INTEGER,
			iqhco30RulesPresetsNoPriority
				INTEGER,
			iqhco30OutputsMasterSelect
				INTEGER,
			iqhco30OutputsMonitorSelect
				INTEGER,
			iqhco30OutputsRulesSelection
				INTEGER,
			iqhco30AESOut12AESOut1SourceLR
				INTEGER,
			iqhco30AESOut12AESOut2SourceLR
				INTEGER,
			iqhco30OutputsToneFrequency
				INTEGER,
			iqhco30OutputsToneChannelident
				INTEGER,
			iqhco30CommonDefFormat
				INTEGER,
			iqhco30CommonMemoriesSelMemory
				INTEGER,
			iqhco30CommonMemoriesSetMemName
				RollCallString,
			iqhco30CommonMemoriesRecallMemory
				INTEGER,
			iqhco30CommonMemoriesSaveMemory
				INTEGER,
			iqhco30CommonMemoriesLastUserMemory
				RollCallString,
			iqhco30CommonMemoriesClearMemory
				INTEGER,
			iqhco30MemoriesMemoryNamesMemory1Name
				RollCallString,
			iqhco30MemoriesMemoryNamesMemory2Name
				RollCallString,
			iqhco30MemoriesMemoryNamesMemory3Name
				RollCallString,
			iqhco30MemoriesMemoryNamesMemory4Name
				RollCallString,
			iqhco30MemoriesMemoryNamesMemory5Name
				RollCallString,
			iqhco30MemoriesMemoryNamesMemory6Name
				RollCallString,
			iqhco30MemoriesMemoryNamesMemory7Name
				RollCallString,
			iqhco30MemoriesMemoryNamesMemory8Name
				RollCallString,
			iqhco30MemoriesMemoryNamesMemory9Name
				RollCallString,
			iqhco30MemoriesMemoryNamesMemory10Name
				RollCallString,
			iqhco30MemoriesMemoryNamesMemory11Name
				RollCallString,
			iqhco30MemoriesMemoryNamesMemory12Name
				RollCallString,
			iqhco30MemoriesMemoryNamesMemory13Name
				RollCallString,
			iqhco30MemoriesMemoryNamesMemory14Name
				RollCallString,
			iqhco30MemoriesMemoryNamesMemory15Name
				RollCallString,
			iqhco30MemoriesMemoryNamesMemory16Name
				RollCallString,
			iqhco30LoggingLogMiscSlotStarten
				INTEGER,
			iqhco30LoggingLogMiscSlotStart
				RollCallString,
			iqhco30LoggingLogMiscSlotWidthen
				INTEGER,
			iqhco30LoggingLogMiscSlotWidth
				RollCallString,
			iqhco30LoggingLogMiscRearStatusen
				INTEGER,
			iqhco30LoggingLogMiscRearStatus
				RollCallString,
			iqhco30LoggingLogMiscRearIDen
				INTEGER,
			iqhco30LoggingLogMiscRearID
				RollCallString,
			iqhco30LoggingLogMiscFirmwareVersionen
				INTEGER,
			iqhco30LoggingLogMiscFirmwareVersion
				RollCallString,
			iqhco30LoggingLogMiscLicensedOptionsen
				INTEGER,
			iqhco30LoggingLogMiscLicensedOptions
				RollCallString,
			iqhco30LoggingLogMiscBuildNumberen
				INTEGER,
			iqhco30LoggingLogMiscBuildNumber
				RollCallString,
			iqhco30LoggingLogMiscOSVersionen
				INTEGER,
			iqhco30LoggingLogMiscOSVersion
				RollCallString,
			iqhco30LoggingLogMiscHardwareVersionen
				INTEGER,
			iqhco30LoggingLogMiscHardwareVersion
				RollCallString,
			iqhco30LoggingLogMiscUptimeen
				INTEGER,
			iqhco30LoggingLogMiscUptime
				RollCallString,
			iqhco30LoggingLogMiscSerialNumberen
				INTEGER,
			iqhco30LoggingLogMiscSerialNumber
				RollCallString,
			iqhco30LoggingLogVideoInput1Input1en
				INTEGER,
			iqhco30LoggingLogVideoInput1Input1
				RollCallString,
			iqhco30LoggingLogVideoInput1Input1Standarden
				INTEGER,
			iqhco30LoggingLogVideoInput1Input1Standard
				RollCallString,
			iqhco30LoggingLogVideoInput1In1SDIERRSen
				INTEGER,
			iqhco30LoggingLogVideoInput1In1SDIERRS
				RollCallString,
			iqhco30LoggingLogVideoInput1In1SDIANCERRSen
				INTEGER,
			iqhco30LoggingLogVideoInput1In1SDIANCERRS
				RollCallString,
			iqhco30LoggingLogVideoInput1Input1Typeen
				INTEGER,
			iqhco30LoggingLogVideoInput1Input1Type
				RollCallString,
			iqhco30LoggingLogVideoInput1Input1Identen
				INTEGER,
			iqhco30LoggingLogVideoInput1Input1Ident
				RollCallString,
			iqhco30LoggingLogVideoInput1In1BlackERRSen
				INTEGER,
			iqhco30LoggingLogVideoInput1In1BlackERRS
				RollCallString,
			iqhco30LoggingLogVideoInput1In1FreezeERRSen
				INTEGER,
			iqhco30LoggingLogVideoInput1In1FreezeERRS
				RollCallString,
			iqhco30LoggingLogVideoInput2Input2en
				INTEGER,
			iqhco30LoggingLogVideoInput2Input2
				RollCallString,
			iqhco30LoggingLogVideoInput2Input2Standarden
				INTEGER,
			iqhco30LoggingLogVideoInput2Input2Standard
				RollCallString,
			iqhco30LoggingLogVideoInput2In2SDIERRSen
				INTEGER,
			iqhco30LoggingLogVideoInput2In2SDIERRS
				RollCallString,
			iqhco30LoggingLogVideoInput2In2SDIANCERRSen
				INTEGER,
			iqhco30LoggingLogVideoInput2In2SDIANCERRS
				RollCallString,
			iqhco30LoggingLogVideoInput2Input2Typeen
				INTEGER,
			iqhco30LoggingLogVideoInput2Input2Type
				RollCallString,
			iqhco30LoggingLogVideoInput2Input2Identen
				INTEGER,
			iqhco30LoggingLogVideoInput2Input2Ident
				RollCallString,
			iqhco30LoggingLogVideoInput2In2BlackERRSen
				INTEGER,
			iqhco30LoggingLogVideoInput2In2BlackERRS
				RollCallString,
			iqhco30LoggingLogVideoInput2In2FreezeERRSen
				INTEGER,
			iqhco30LoggingLogVideoInput2In2FreezeERRS
				RollCallString,
			iqhco30LoggingLogAudioInput1Input1Audio11en
				INTEGER,
			iqhco30LoggingLogAudioInput1Input1Audio11
				RollCallString,
			iqhco30LoggingLogAudioInput1Input1Audio12en
				INTEGER,
			iqhco30LoggingLogAudioInput1Input1Audio12
				RollCallString,
			iqhco30LoggingLogAudioInput1Input1Audio21en
				INTEGER,
			iqhco30LoggingLogAudioInput1Input1Audio21
				RollCallString,
			iqhco30LoggingLogAudioInput1Input1Audio22en
				INTEGER,
			iqhco30LoggingLogAudioInput1Input1Audio22
				RollCallString,
			iqhco30LoggingLogAudioInput1Input1Audio31en
				INTEGER,
			iqhco30LoggingLogAudioInput1Input1Audio31
				RollCallString,
			iqhco30LoggingLogAudioInput1Input1Audio32en
				INTEGER,
			iqhco30LoggingLogAudioInput1Input1Audio32
				RollCallString,
			iqhco30LoggingLogAudioInput1Input1Audio41en
				INTEGER,
			iqhco30LoggingLogAudioInput1Input1Audio41
				RollCallString,
			iqhco30LoggingLogAudioInput1Input1Audio42en
				INTEGER,
			iqhco30LoggingLogAudioInput1Input1Audio42
				RollCallString,
			iqhco30LoggingLogAudioInput1Input1Audio51en
				INTEGER,
			iqhco30LoggingLogAudioInput1Input1Audio51
				RollCallString,
			iqhco30LoggingLogAudioInput1Input1Audio52en
				INTEGER,
			iqhco30LoggingLogAudioInput1Input1Audio52
				RollCallString,
			iqhco30LoggingLogAudioInput1Input1Audio61en
				INTEGER,
			iqhco30LoggingLogAudioInput1Input1Audio61
				RollCallString,
			iqhco30LoggingLogAudioInput1Input1Audio62en
				INTEGER,
			iqhco30LoggingLogAudioInput1Input1Audio62
				RollCallString,
			iqhco30LoggingLogAudioInput1Input1Audio71en
				INTEGER,
			iqhco30LoggingLogAudioInput1Input1Audio71
				RollCallString,
			iqhco30LoggingLogAudioInput1Input1Audio72en
				INTEGER,
			iqhco30LoggingLogAudioInput1Input1Audio72
				RollCallString,
			iqhco30LoggingLogAudioInput1Input1Audio81en
				INTEGER,
			iqhco30LoggingLogAudioInput1Input1Audio81
				RollCallString,
			iqhco30LoggingLogAudioInput1Input1Audio82en
				INTEGER,
			iqhco30LoggingLogAudioInput1Input1Audio82
				RollCallString,
			iqhco30LoggingLogAudioInput2Input2Audio11en
				INTEGER,
			iqhco30LoggingLogAudioInput2Input2Audio11
				RollCallString,
			iqhco30LoggingLogAudioInput2Input2Audio12en
				INTEGER,
			iqhco30LoggingLogAudioInput2Input2Audio12
				RollCallString,
			iqhco30LoggingLogAudioInput2Input2Audio21en
				INTEGER,
			iqhco30LoggingLogAudioInput2Input2Audio21
				RollCallString,
			iqhco30LoggingLogAudioInput2Input2Audio22en
				INTEGER,
			iqhco30LoggingLogAudioInput2Input2Audio22
				RollCallString,
			iqhco30LoggingLogAudioInput2Input2Audio31en
				INTEGER,
			iqhco30LoggingLogAudioInput2Input2Audio31
				RollCallString,
			iqhco30LoggingLogAudioInput2Input2Audio32en
				INTEGER,
			iqhco30LoggingLogAudioInput2Input2Audio32
				RollCallString,
			iqhco30LoggingLogAudioInput2Input2Audio41en
				INTEGER,
			iqhco30LoggingLogAudioInput2Input2Audio41
				RollCallString,
			iqhco30LoggingLogAudioInput2Input2Audio42en
				INTEGER,
			iqhco30LoggingLogAudioInput2Input2Audio42
				RollCallString,
			iqhco30LoggingLogAudioInput2Input2Audio51en
				INTEGER,
			iqhco30LoggingLogAudioInput2Input2Audio51
				RollCallString,
			iqhco30LoggingLogAudioInput2Input2Audio52en
				INTEGER,
			iqhco30LoggingLogAudioInput2Input2Audio52
				RollCallString,
			iqhco30LoggingLogAudioInput2Input2Audio61en
				INTEGER,
			iqhco30LoggingLogAudioInput2Input2Audio61
				RollCallString,
			iqhco30LoggingLogAudioInput2Input2Audio62en
				INTEGER,
			iqhco30LoggingLogAudioInput2Input2Audio62
				RollCallString,
			iqhco30LoggingLogAudioInput2Input2Audio71en
				INTEGER,
			iqhco30LoggingLogAudioInput2Input2Audio71
				RollCallString,
			iqhco30LoggingLogAudioInput2Input2Audio72en
				INTEGER,
			iqhco30LoggingLogAudioInput2Input2Audio72
				RollCallString,
			iqhco30LoggingLogAudioInput2Input2Audio81en
				INTEGER,
			iqhco30LoggingLogAudioInput2Input2Audio81
				RollCallString,
			iqhco30LoggingLogAudioInput2Input2Audio82en
				INTEGER,
			iqhco30LoggingLogAudioInput2Input2Audio82
				RollCallString,
			iqhco30LoggingLogVideoOutputOutput1Typeen
				INTEGER,
			iqhco30LoggingLogVideoOutputOutput1Type
				RollCallString,
			iqhco30LoggingLogVideoOutputOutput1Stateen
				INTEGER,
			iqhco30LoggingLogVideoOutputOutput1State
				RollCallString,
			iqhco30LoggingLogVideoOutputOutput1Stden
				INTEGER,
			iqhco30LoggingLogVideoOutputOutput1Std
				RollCallString,
			iqhco30LoggingLogVideoOutputOutput1en
				INTEGER,
			iqhco30LoggingLogVideoOutputOutput1
				RollCallString,
			iqhco30LoggingLogChangeoverMasterStateen
				INTEGER,
			iqhco30LoggingLogChangeoverMasterState
				RollCallString,
			iqhco30LoggingLogChangeoverBackupStateen
				INTEGER,
			iqhco30LoggingLogChangeoverBackupState
				RollCallString,
			iqhco30LoggingLogChangeoverRulesStateen
				INTEGER,
			iqhco30LoggingLogChangeoverRulesState
				RollCallString,
			iqhco30LoggingLogChangeoverGpi1Stateen
				INTEGER,
			iqhco30LoggingLogChangeoverGpi1State
				RollCallString,
			iqhco30LoggingLogChangeoverGpi2Stateen
				INTEGER,
			iqhco30LoggingLogChangeoverGpi2State
				RollCallString,
			iqhco30LoggingLogChangeoverGpi3Stateen
				INTEGER,
			iqhco30LoggingLogChangeoverGpi3State
				RollCallString,
			iqhco30LoggingLogChangeoverGpi4Stateen
				INTEGER,
			iqhco30LoggingLogChangeoverGpi4State
				RollCallString,
			iqhco30LoggingLogChangeoverRollCall101State4420
				INTEGER,
			iqhco30LoggingLogChangeoverRollCall101State4421
				RollCallString,
			iqhco30LoggingLogChangeoverRollCall102State4424
				INTEGER,
			iqhco30LoggingLogChangeoverRollCall102State4425
				RollCallString,
			iqhco30LoggingLogChangeoverRollCall103State4428
				INTEGER,
			iqhco30LoggingLogChangeoverRollCall103State4429
				RollCallString,
			iqhco30LoggingLogChangeoverRollCall104State4432
				INTEGER,
			iqhco30LoggingLogChangeoverRollCall104State4433
				RollCallString,
			iqhco30LoggingLogChangeoverRollTrkOut1State4436
				INTEGER,
			iqhco30LoggingLogChangeoverRollTrkOut1State4437
				RollCallString,
			iqhco30LoggingLogChangeoverRollTrkOut2State4440
				INTEGER,
			iqhco30LoggingLogChangeoverRollTrkOut2State4441
				RollCallString,
			iqhco30LoggingLogChangeoverRollTrkOut3State4444
				INTEGER,
			iqhco30LoggingLogChangeoverRollTrkOut3State4445
				RollCallString,
			iqhco30LoggingLogChangeoverRollTrkOut4State4448
				INTEGER,
			iqhco30LoggingLogChangeoverRollTrkOut4State4449
				RollCallString,
			iqhco30SetupRollTracksRollTrackIndex1495
				INTEGER,
			iqhco30SetupRollTracksRollTrackSource1496
				INTEGER,
			iqhco30SetupRollTracksRollTrackDisable
				INTEGER,
			iqhco30SetupRollTracksRollTrackAddress1497
				RollCallString,
			iqhco30SetupRollTracksRollTrackCommand1498
				RollCallString,
			iqhco30SetupRollTracksRollTrackSending
				RollCallString,
			iqhco30SetupRollTracksRollTrackStatus
				RollCallString,
			iqhco30SetupRollTracksRollTrackIndex2870
				INTEGER,
			iqhco30SetupRollTracksRollTrackSource2871
				INTEGER,
			iqhco30SetupRollTracksRollTrackAddress2872
				RollCallString,
			iqhco30SetupRollTracksRollTrackCommand2873
				RollCallString,
			iqhco30CommonStatusStatusDisplay
				INTEGER,
			iqhco30CommonStatusProduct
				RollCallString,
			iqhco30CommonStatusSoftwareVersion
				RollCallString,
			iqhco30CommonStatusSerialNo
				RollCallString,
			iqhco30CommonStatusFactoryDefaults
				INTEGER,
			iqhco30CommonStatusDefaultSetting
				INTEGER,
			iqhco30CommonStatusRestart
				INTEGER,
			iqhco30CommonStatusBuild
				RollCallString,
			iqhco30CommonStatusPCB
				RollCallString,
			iqhco30CommonStatusKOSVersion
				RollCallString,
			iqhco30CommonStatusFirmwareVersion
				RollCallString,
			iqhco30CommonStatusUpTime
				RollCallString
		}

	iqhco30SlotIndex OBJECT-TYPE
		SYNTAX		Unsigned32
		MAX-ACCESS		not-accessible
		STATUS			current
		DESCRIPTION
				"The unique Index value for each slot.  Its value
					ranges between 1 and the value of slotNumber."
		::= { iqhco30CmdEntry 0 }


	iqhco30MasterValidValidInputStds108050pB OBJECT-TYPE
		SYNTAX		INTEGER { disable(0), enable(1) }
		MAX-ACCESS		read-write
		STATUS			current
		DESCRIPTION
				"TYPE: - Checkbox
				 PAGE: - Master- Video Master- Master Valid
					1080/50p-B  cmdID= 5225 "
		::= { iqhco30CmdEntry 5225 }


	iqhco30MasterValidValidInputStds108059pB OBJECT-TYPE
		SYNTAX		INTEGER { disable(0), enable(1) }
		MAX-ACCESS		read-write
		STATUS			current
		DESCRIPTION
				"TYPE: - Checkbox
				 PAGE: - Master- Video Master- Master Valid
					1080/59p-B  cmdID= 5226 "
		::= { iqhco30CmdEntry 5226 }


	iqhco30MasterValidValidInputStds108050pA OBJECT-TYPE
		SYNTAX		INTEGER { disable(0), enable(1) }
		MAX-ACCESS		read-write
		STATUS			current
		DESCRIPTION
				"TYPE: - Checkbox
				 PAGE: - Master- Video Master- Master Valid
					1080/50p-A  cmdID= 5222 "
		::= { iqhco30CmdEntry 5222 }


	iqhco30MasterValidValidInputStds108059pA OBJECT-TYPE
		SYNTAX		INTEGER { disable(0), enable(1) }
		MAX-ACCESS		read-write
		STATUS			current
		DESCRIPTION
				"TYPE: - Checkbox
				 PAGE: - Master- Video Master- Master Valid
					1080/59p-A  cmdID= 5223 "
		::= { iqhco30CmdEntry 5223 }


	iqhco30MasterValidValidInputStds108029i OBJECT-TYPE
		SYNTAX		INTEGER { disable(0), enable(1) }
		MAX-ACCESS		read-write
		STATUS			current
		DESCRIPTION
				"TYPE: - Checkbox
				 PAGE: - Master- Video Master- Master Valid
					1080/29i  cmdID= 5218 "
		::= { iqhco30CmdEntry 5218 }


	iqhco30MasterValidValidInputStds108025i OBJECT-TYPE
		SYNTAX		INTEGER { disable(0), enable(1) }
		MAX-ACCESS		read-write
		STATUS			current
		DESCRIPTION
				"TYPE: - Checkbox
				 PAGE: - Master- Video Master- Master Valid
					1080/25i  cmdID= 5217 "
		::= { iqhco30CmdEntry 5217 }


	iqhco30MasterValidValidInputStds72059p OBJECT-TYPE
		SYNTAX		INTEGER { disable(0), enable(1) }
		MAX-ACCESS		read-write
		STATUS			current
		DESCRIPTION
				"TYPE: - Checkbox
				 PAGE: - Master- Video Master- Master Valid
					720/59p  cmdID= 5210 "
		::= { iqhco30CmdEntry 5210 }


	iqhco30MasterValidValidInputStds72050p OBJECT-TYPE
		SYNTAX		INTEGER { disable(0), enable(1) }
		MAX-ACCESS		read-write
		STATUS			current
		DESCRIPTION
				"TYPE: - Checkbox
				 PAGE: - Master- Video Master- Master Valid
					720/50p  cmdID= 5209 "
		::= { iqhco30CmdEntry 5209 }


	iqhco30MasterValidValidInputStds52529i OBJECT-TYPE
		SYNTAX		INTEGER { disable(0), enable(1) }
		MAX-ACCESS		read-write
		STATUS			current
		DESCRIPTION
				"TYPE: - Checkbox
				 PAGE: - Master- Video Master- Master Valid
					525/29i  cmdID= 5203 "
		::= { iqhco30CmdEntry 5203 }


	iqhco30MasterValidValidInputStds62525i OBJECT-TYPE
		SYNTAX		INTEGER { disable(0), enable(1) }
		MAX-ACCESS		read-write
		STATUS			current
		DESCRIPTION
				"TYPE: - Checkbox
				 PAGE: - Master- Video Master- Master Valid
					625/25i  cmdID= 5202 "
		::= { iqhco30CmdEntry 5202 }


	iqhco30MasterValidCRCEDHErroredsecErrSecEnable OBJECT-TYPE
		SYNTAX		INTEGER { disable(0), enable(1) }
		MAX-ACCESS		read-write
		STATUS			current
		DESCRIPTION
				"TYPE: - Checkbox
				 PAGE: - Master- Video Master- Master Valid
					ErrSec Enable  cmdID= 5354 "
		::= { iqhco30CmdEntry 5354 }


	iqhco30MasterValidCRCEDHErroredsecErrSecDecision OBJECT-TYPE
		SYNTAX		RollCallString
		MAX-ACCESS		read-only
		STATUS			current
		DESCRIPTION
				"TYPE: - Display
				 PAGE: - Master- Video Master- Master Valid
					ErrSec Decision  cmdID= 5353  format=   "
		::= { iqhco30CmdEntry 5353 }


	iqhco30MasterValidCRCEDHErroredsecCarrierDecision OBJECT-TYPE
		SYNTAX		RollCallString
		MAX-ACCESS		read-only
		STATUS			current
		DESCRIPTION
				"TYPE: - Display
				 PAGE: - Master- Video Master- Master Valid
					Carrier Decision  cmdID= 5351  format=   "
		::= { iqhco30CmdEntry 5351 }


	iqhco30MasterValidCRCEDHErroredsecStdDecision OBJECT-TYPE
		SYNTAX		RollCallString
		MAX-ACCESS		read-only
		STATUS			current
		DESCRIPTION
				"TYPE: - Display
				 PAGE: - Master- Video Master- Master Valid
					Std Decision  cmdID= 5352  format=   "
		::= { iqhco30CmdEntry 5352 }


	iqhco30MasterValidCRCEDHErroredsecInputStd OBJECT-TYPE
		SYNTAX		RollCallString
		MAX-ACCESS		read-only
		STATUS			current
		DESCRIPTION
				"TYPE: - Display
				 PAGE: - Master- Video Master- Master Valid
					Input Std  cmdID= 5399  format=   "
		::= { iqhco30CmdEntry 5399 }


	iqhco30MasterValidCRCEDHErroredsecFreezeEnable OBJECT-TYPE
		SYNTAX		INTEGER { disable(0), enable(1) }
		MAX-ACCESS		read-write
		STATUS			current
		DESCRIPTION
				"TYPE: - Checkbox
				 PAGE: - Master- Video Master- Master Valid
					Freeze Enable  cmdID= 5356 "
		::= { iqhco30CmdEntry 5356 }


	iqhco30MasterValidCRCEDHErroredsecFreezeDecision OBJECT-TYPE
		SYNTAX		RollCallString
		MAX-ACCESS		read-only
		STATUS			current
		DESCRIPTION
				"TYPE: - Display
				 PAGE: - Master- Video Master- Master Valid
					Freeze Decision  cmdID= 5355  format=   "
		::= { iqhco30CmdEntry 5355 }


	iqhco30MasterValidCRCEDHErroredsecBlackEnable OBJECT-TYPE
		SYNTAX		INTEGER { disable(0), enable(1) }
		MAX-ACCESS		read-write
		STATUS			current
		DESCRIPTION
				"TYPE: - Checkbox
				 PAGE: - Master- Video Master- Master Valid
					Black Enable  cmdID= 5358 "
		::= { iqhco30CmdEntry 5358 }


	iqhco30MasterValidCRCEDHErroredsecBlackDecision OBJECT-TYPE
		SYNTAX		RollCallString
		MAX-ACCESS		read-only
		STATUS			current
		DESCRIPTION
				"TYPE: - Display
				 PAGE: - Master- Video Master- Master Valid
					Black Decision  cmdID= 5357  format=   "
		::= { iqhco30CmdEntry 5357 }


	iqhco30MasterValidCRCEDHErroredsecBlackThreshold OBJECT-TYPE
		SYNTAX		INTEGER
		MAX-ACCESS		read-write
		STATUS			current
		DESCRIPTION
				"TYPE: - Number
				 PAGE: - Master- Video Master- Master Valid
					Black Threshold  cmdID= 5578  min= 0  max= 153  step= 1  format= %.0f mV  div_scale= 1 
					Min = 0 mV  Max = 153 mV  Step = 1 mV "
		::= { iqhco30CmdEntry 5578 }


	iqhco30MasterValidVideoValidTimersBlackFailDelay OBJECT-TYPE
		SYNTAX		INTEGER
		MAX-ACCESS		read-write
		STATUS			current
		DESCRIPTION
				"TYPE: - Number
				 PAGE: - Master- Video Master- Master Valid
					Black Fail Delay  cmdID= 5550  min= 2  max= 100  step= 1  format= %.1f s  div_scale= 10 
					Min = 0.2 s  Max = 10.0 s  Step = 0.1 s "
		::= { iqhco30CmdEntry 5550 }


	iqhco30MasterValidVideoValidTimersBlackRecoverDelay OBJECT-TYPE
		SYNTAX		INTEGER
		MAX-ACCESS		read-write
		STATUS			current
		DESCRIPTION
				"TYPE: - Number
				 PAGE: - Master- Video Master- Master Valid
					Black Recover Delay  cmdID= 5551  min= 2  max= 100  step= 1  format= %.1f s  div_scale= 10 
					Min = 0.2 s  Max = 10.0 s  Step = 0.1 s "
		::= { iqhco30CmdEntry 5551 }


	iqhco30MasterValidVideoValidTimersFreezeFailDelay OBJECT-TYPE
		SYNTAX		INTEGER
		MAX-ACCESS		read-write
		STATUS			current
		DESCRIPTION
				"TYPE: - Number
				 PAGE: - Master- Video Master- Master Valid
					Freeze Fail Delay  cmdID= 5552  min= 2  max= 100  step= 1  format= %.1f s  div_scale= 10 
					Min = 0.2 s  Max = 10.0 s  Step = 0.1 s "
		::= { iqhco30CmdEntry 5552 }


	iqhco30MasterValidVideoValidTimersFreezeRecoverDela OBJECT-TYPE
		SYNTAX		INTEGER
		MAX-ACCESS		read-write
		STATUS			current
		DESCRIPTION
				"TYPE: - Number
				 PAGE: - Master- Video Master- Master Valid
					Freeze Recover Dela  cmdID= 5553  min= 2  max= 100  step= 1  format= %.1f s  div_scale= 10 
					Min = 0.2 s  Max = 10.0 s  Step = 0.1 s "
		::= { iqhco30CmdEntry 5553 }


	iqhco30MasterValidVideoValidTimersErrsecFailDelay OBJECT-TYPE
		SYNTAX		INTEGER
		MAX-ACCESS		read-write
		STATUS			current
		DESCRIPTION
				"TYPE: - Number
				 PAGE: - Master- Video Master- Master Valid
					Errsec Fail Delay  cmdID= 5554  min= 0  max= 10  step= 1  format= %.0f s  div_scale= 1 
					Min = 0 s  Max = 10 s  Step = 1 s "
		::= { iqhco30CmdEntry 5554 }


	iqhco30MasterValidVideoValidTimersErrsecRecoverDela OBJECT-TYPE
		SYNTAX		INTEGER
		MAX-ACCESS		read-write
		STATUS			current
		DESCRIPTION
				"TYPE: - Number
				 PAGE: - Master- Video Master- Master Valid
					Errsec Recover Dela  cmdID= 5555  min= 0  max= 10  step= 1  format= %.0f s  div_scale= 1 
					Min = 0 s  Max = 10 s  Step = 1 s "
		::= { iqhco30CmdEntry 5555 }


	iqhco30MasterValidVideoValidTimersValidFailDelay OBJECT-TYPE
		SYNTAX		INTEGER
		MAX-ACCESS		read-write
		STATUS			current
		DESCRIPTION
				"TYPE: - Number
				 PAGE: - Master- Video Master- Master Valid
					Valid Fail Delay  cmdID= 5562  min= 0  max= 100  step= 1  format= %.1f s  div_scale= 10 
					Min = 0.0 s  Max = 10.0 s  Step = 0.1 s "
		::= { iqhco30CmdEntry 5562 }


	iqhco30MasterValidVideoValidTimersValidRecoverDelay OBJECT-TYPE
		SYNTAX		INTEGER
		MAX-ACCESS		read-write
		STATUS			current
		DESCRIPTION
				"TYPE: - Number
				 PAGE: - Master- Video Master- Master Valid
					Valid Recover Delay  cmdID= 5563  min= 2  max= 100  step= 1  format= %.1f s  div_scale= 10 
					Min = 0.2 s  Max = 10.0 s  Step = 0.1 s "
		::= { iqhco30CmdEntry 5563 }


	iqhco30MasterValidValidAudioDecision OBJECT-TYPE
		SYNTAX		RollCallString
		MAX-ACCESS		read-only
		STATUS			current
		DESCRIPTION
				"TYPE: - Display
				 PAGE: - Master- Video Master- Master Valid- Valid Audio
					Decision  cmdID= 5350  format=   "
		::= { iqhco30CmdEntry 5350 }


	iqhco30ValidAudioMasterPair1Decision OBJECT-TYPE
		SYNTAX		RollCallString
		MAX-ACCESS		read-only
		STATUS			current
		DESCRIPTION
				"TYPE: - Display
				 PAGE: - Master- Video Master- Master Valid- Valid Audio
					Decision  cmdID= 5359  format=   "
		::= { iqhco30CmdEntry 5359 }


	iqhco30ValidAudioMasterPair1CurrentType OBJECT-TYPE
		SYNTAX		RollCallString
		MAX-ACCESS		read-only
		STATUS			current
		DESCRIPTION
				"TYPE: - Display
				 PAGE: - Master- Video Master- Master Valid- Valid Audio
					Current Type  cmdID= 5360  format=   "
		::= { iqhco30CmdEntry 5360 }


	iqhco30ValidAudioMasterPair1 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5361  value= 0  
					DolbyE  cmdID= 5361  value= 1  
					Data  cmdID= 5361  value= 2  
					None  cmdID= 5361  value= 3  
					Any  cmdID= 5361  value= 4  
					Ignored  cmdID= 5361  value= 5  "
		::= { iqhco30CmdEntry 5361 }


	iqhco30ValidAudioMasterPair1Ch1State OBJECT-TYPE
		SYNTAX		RollCallString
		MAX-ACCESS		read-only
		STATUS			current
		DESCRIPTION
				"TYPE: - Display
				 PAGE: - Master- Video Master- Master Valid- Valid Audio
					Ch1 State  cmdID= 7008  format=   "
		::= { iqhco30CmdEntry 7008 }


	iqhco30ValidAudioMasterPair1Ch2State OBJECT-TYPE
		SYNTAX		RollCallString
		MAX-ACCESS		read-only
		STATUS			current
		DESCRIPTION
				"TYPE: - Display
				 PAGE: - Master- Video Master- Master Valid- Valid Audio
					Ch2 State  cmdID= 7009  format=   "
		::= { iqhco30CmdEntry 7009 }


	iqhco30ValidAudioMasterPair1Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5450 "
		::= { iqhco30CmdEntry 5450 }


	iqhco30ValidAudioMasterPair1Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5362 "
		::= { iqhco30CmdEntry 5362 }


	iqhco30ValidAudioMasterPair1Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5363 "
		::= { iqhco30CmdEntry 5363 }


	iqhco30ValidAudioMasterPair2Decision OBJECT-TYPE
		SYNTAX		RollCallString
		MAX-ACCESS		read-only
		STATUS			current
		DESCRIPTION
				"TYPE: - Display
				 PAGE: - Master- Video Master- Master Valid- Valid Audio
					Decision  cmdID= 5364  format=   "
		::= { iqhco30CmdEntry 5364 }


	iqhco30ValidAudioMasterPair2CurrentType OBJECT-TYPE
		SYNTAX		RollCallString
		MAX-ACCESS		read-only
		STATUS			current
		DESCRIPTION
				"TYPE: - Display
				 PAGE: - Master- Video Master- Master Valid- Valid Audio
					Current Type  cmdID= 5365  format=   "
		::= { iqhco30CmdEntry 5365 }


	iqhco30ValidAudioMasterPair2 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5366  value= 0  
					DolbyE  cmdID= 5366  value= 1  
					Data  cmdID= 5366  value= 2  
					None  cmdID= 5366  value= 3  
					Any  cmdID= 5366  value= 4  
					Ignored  cmdID= 5366  value= 5  "
		::= { iqhco30CmdEntry 5366 }


	iqhco30ValidAudioMasterPair2Ch1State OBJECT-TYPE
		SYNTAX		RollCallString
		MAX-ACCESS		read-only
		STATUS			current
		DESCRIPTION
				"TYPE: - Display
				 PAGE: - Master- Video Master- Master Valid- Valid Audio
					Ch1 State  cmdID= 7010  format=   "
		::= { iqhco30CmdEntry 7010 }


	iqhco30ValidAudioMasterPair2Ch2State OBJECT-TYPE
		SYNTAX		RollCallString
		MAX-ACCESS		read-only
		STATUS			current
		DESCRIPTION
				"TYPE: - Display
				 PAGE: - Master- Video Master- Master Valid- Valid Audio
					Ch2 State  cmdID= 7011  format=   "
		::= { iqhco30CmdEntry 7011 }


	iqhco30ValidAudioMasterPair2Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5451 "
		::= { iqhco30CmdEntry 5451 }


	iqhco30ValidAudioMasterPair2Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5367 "
		::= { iqhco30CmdEntry 5367 }


	iqhco30ValidAudioMasterPair2Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5368 "
		::= { iqhco30CmdEntry 5368 }


	iqhco30ValidAudioMasterPair3Decision OBJECT-TYPE
		SYNTAX		RollCallString
		MAX-ACCESS		read-only
		STATUS			current
		DESCRIPTION
				"TYPE: - Display
				 PAGE: - Master- Video Master- Master Valid- Valid Audio
					Decision  cmdID= 5369  format=   "
		::= { iqhco30CmdEntry 5369 }


	iqhco30ValidAudioMasterPair3CurrentType OBJECT-TYPE
		SYNTAX		RollCallString
		MAX-ACCESS		read-only
		STATUS			current
		DESCRIPTION
				"TYPE: - Display
				 PAGE: - Master- Video Master- Master Valid- Valid Audio
					Current Type  cmdID= 5370  format=   "
		::= { iqhco30CmdEntry 5370 }


	iqhco30ValidAudioMasterPair3 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5371  value= 0  
					DolbyE  cmdID= 5371  value= 1  
					Data  cmdID= 5371  value= 2  
					None  cmdID= 5371  value= 3  
					Any  cmdID= 5371  value= 4  
					Ignored  cmdID= 5371  value= 5  "
		::= { iqhco30CmdEntry 5371 }


	iqhco30ValidAudioMasterPair3Ch1State OBJECT-TYPE
		SYNTAX		RollCallString
		MAX-ACCESS		read-only
		STATUS			current
		DESCRIPTION
				"TYPE: - Display
				 PAGE: - Master- Video Master- Master Valid- Valid Audio
					Ch1 State  cmdID= 7012  format=   "
		::= { iqhco30CmdEntry 7012 }


	iqhco30ValidAudioMasterPair3Ch2State OBJECT-TYPE
		SYNTAX		RollCallString
		MAX-ACCESS		read-only
		STATUS			current
		DESCRIPTION
				"TYPE: - Display
				 PAGE: - Master- Video Master- Master Valid- Valid Audio
					Ch2 State  cmdID= 7013  format=   "
		::= { iqhco30CmdEntry 7013 }


	iqhco30ValidAudioMasterPair3Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5452 "
		::= { iqhco30CmdEntry 5452 }


	iqhco30ValidAudioMasterPair3Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5372 "
		::= { iqhco30CmdEntry 5372 }


	iqhco30ValidAudioMasterPair3Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5373 "
		::= { iqhco30CmdEntry 5373 }


	iqhco30ValidAudioMasterPair4Decision OBJECT-TYPE
		SYNTAX		RollCallString
		MAX-ACCESS		read-only
		STATUS			current
		DESCRIPTION
				"TYPE: - Display
				 PAGE: - Master- Video Master- Master Valid- Valid Audio
					Decision  cmdID= 5374  format=   "
		::= { iqhco30CmdEntry 5374 }


	iqhco30ValidAudioMasterPair4CurrentType OBJECT-TYPE
		SYNTAX		RollCallString
		MAX-ACCESS		read-only
		STATUS			current
		DESCRIPTION
				"TYPE: - Display
				 PAGE: - Master- Video Master- Master Valid- Valid Audio
					Current Type  cmdID= 5375  format=   "
		::= { iqhco30CmdEntry 5375 }


	iqhco30ValidAudioMasterPair4 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5376  value= 0  
					DolbyE  cmdID= 5376  value= 1  
					Data  cmdID= 5376  value= 2  
					None  cmdID= 5376  value= 3  
					Any  cmdID= 5376  value= 4  
					Ignored  cmdID= 5376  value= 5  "
		::= { iqhco30CmdEntry 5376 }


	iqhco30ValidAudioMasterPair4Ch1State OBJECT-TYPE
		SYNTAX		RollCallString
		MAX-ACCESS		read-only
		STATUS			current
		DESCRIPTION
				"TYPE: - Display
				 PAGE: - Master- Video Master- Master Valid- Valid Audio
					Ch1 State  cmdID= 7014  format=   "
		::= { iqhco30CmdEntry 7014 }


	iqhco30ValidAudioMasterPair4Ch2State OBJECT-TYPE
		SYNTAX		RollCallString
		MAX-ACCESS		read-only
		STATUS			current
		DESCRIPTION
				"TYPE: - Display
				 PAGE: - Master- Video Master- Master Valid- Valid Audio
					Ch2 State  cmdID= 7015  format=   "
		::= { iqhco30CmdEntry 7015 }


	iqhco30ValidAudioMasterPair4Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5453 "
		::= { iqhco30CmdEntry 5453 }


	iqhco30ValidAudioMasterPair4Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5377 "
		::= { iqhco30CmdEntry 5377 }


	iqhco30ValidAudioMasterPair4Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5378 "
		::= { iqhco30CmdEntry 5378 }


	iqhco30ValidAudioMasterPair5Decision OBJECT-TYPE
		SYNTAX		RollCallString
		MAX-ACCESS		read-only
		STATUS			current
		DESCRIPTION
				"TYPE: - Display
				 PAGE: - Master- Video Master- Master Valid- Valid Audio
					Decision  cmdID= 5379  format=   "
		::= { iqhco30CmdEntry 5379 }


	iqhco30ValidAudioMasterPair5CurrentType OBJECT-TYPE
		SYNTAX		RollCallString
		MAX-ACCESS		read-only
		STATUS			current
		DESCRIPTION
				"TYPE: - Display
				 PAGE: - Master- Video Master- Master Valid- Valid Audio
					Current Type  cmdID= 5380  format=   "
		::= { iqhco30CmdEntry 5380 }


	iqhco30ValidAudioMasterPair5 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5381  value= 0  
					DolbyE  cmdID= 5381  value= 1  
					Data  cmdID= 5381  value= 2  
					None  cmdID= 5381  value= 3  
					Any  cmdID= 5381  value= 4  
					Ignored  cmdID= 5381  value= 5  "
		::= { iqhco30CmdEntry 5381 }


	iqhco30ValidAudioMasterPair5Ch1State OBJECT-TYPE
		SYNTAX		RollCallString
		MAX-ACCESS		read-only
		STATUS			current
		DESCRIPTION
				"TYPE: - Display
				 PAGE: - Master- Video Master- Master Valid- Valid Audio
					Ch1 State  cmdID= 7016  format=   "
		::= { iqhco30CmdEntry 7016 }


	iqhco30ValidAudioMasterPair5Ch2State OBJECT-TYPE
		SYNTAX		RollCallString
		MAX-ACCESS		read-only
		STATUS			current
		DESCRIPTION
				"TYPE: - Display
				 PAGE: - Master- Video Master- Master Valid- Valid Audio
					Ch2 State  cmdID= 7017  format=   "
		::= { iqhco30CmdEntry 7017 }


	iqhco30ValidAudioMasterPair5Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5454 "
		::= { iqhco30CmdEntry 5454 }


	iqhco30ValidAudioMasterPair5Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5382 "
		::= { iqhco30CmdEntry 5382 }


	iqhco30ValidAudioMasterPair5Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5383 "
		::= { iqhco30CmdEntry 5383 }


	iqhco30ValidAudioMasterPair6Decision OBJECT-TYPE
		SYNTAX		RollCallString
		MAX-ACCESS		read-only
		STATUS			current
		DESCRIPTION
				"TYPE: - Display
				 PAGE: - Master- Video Master- Master Valid- Valid Audio
					Decision  cmdID= 5384  format=   "
		::= { iqhco30CmdEntry 5384 }


	iqhco30ValidAudioMasterPair6CurrentType OBJECT-TYPE
		SYNTAX		RollCallString
		MAX-ACCESS		read-only
		STATUS			current
		DESCRIPTION
				"TYPE: - Display
				 PAGE: - Master- Video Master- Master Valid- Valid Audio
					Current Type  cmdID= 5385  format=   "
		::= { iqhco30CmdEntry 5385 }


	iqhco30ValidAudioMasterPair6 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5386  value= 0  
					DolbyE  cmdID= 5386  value= 1  
					Data  cmdID= 5386  value= 2  
					None  cmdID= 5386  value= 3  
					Any  cmdID= 5386  value= 4  
					Ignored  cmdID= 5386  value= 5  "
		::= { iqhco30CmdEntry 5386 }


	iqhco30ValidAudioMasterPair6Ch1State OBJECT-TYPE
		SYNTAX		RollCallString
		MAX-ACCESS		read-only
		STATUS			current
		DESCRIPTION
				"TYPE: - Display
				 PAGE: - Master- Video Master- Master Valid- Valid Audio
					Ch1 State  cmdID= 7018  format=   "
		::= { iqhco30CmdEntry 7018 }


	iqhco30ValidAudioMasterPair6Ch2State OBJECT-TYPE
		SYNTAX		RollCallString
		MAX-ACCESS		read-only
		STATUS			current
		DESCRIPTION
				"TYPE: - Display
				 PAGE: - Master- Video Master- Master Valid- Valid Audio
					Ch2 State  cmdID= 7019  format=   "
		::= { iqhco30CmdEntry 7019 }


	iqhco30ValidAudioMasterPair6Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5455 "
		::= { iqhco30CmdEntry 5455 }


	iqhco30ValidAudioMasterPair6Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5387 "
		::= { iqhco30CmdEntry 5387 }


	iqhco30ValidAudioMasterPair6Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5388 "
		::= { iqhco30CmdEntry 5388 }


	iqhco30ValidAudioMasterPair7Decision OBJECT-TYPE
		SYNTAX		RollCallString
		MAX-ACCESS		read-only
		STATUS			current
		DESCRIPTION
				"TYPE: - Display
				 PAGE: - Master- Video Master- Master Valid- Valid Audio
					Decision  cmdID= 5389  format=   "
		::= { iqhco30CmdEntry 5389 }


	iqhco30ValidAudioMasterPair7CurrentType OBJECT-TYPE
		SYNTAX		RollCallString
		MAX-ACCESS		read-only
		STATUS			current
		DESCRIPTION
				"TYPE: - Display
				 PAGE: - Master- Video Master- Master Valid- Valid Audio
					Current Type  cmdID= 5390  format=   "
		::= { iqhco30CmdEntry 5390 }


	iqhco30ValidAudioMasterPair7 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5391  value= 0  
					DolbyE  cmdID= 5391  value= 1  
					Data  cmdID= 5391  value= 2  
					None  cmdID= 5391  value= 3  
					Any  cmdID= 5391  value= 4  
					Ignored  cmdID= 5391  value= 5  "
		::= { iqhco30CmdEntry 5391 }


	iqhco30ValidAudioMasterPair7Ch1State OBJECT-TYPE
		SYNTAX		RollCallString
		MAX-ACCESS		read-only
		STATUS			current
		DESCRIPTION
				"TYPE: - Display
				 PAGE: - Master- Video Master- Master Valid- Valid Audio
					Ch1 State  cmdID= 7020  format=   "
		::= { iqhco30CmdEntry 7020 }


	iqhco30ValidAudioMasterPair7Ch2State OBJECT-TYPE
		SYNTAX		RollCallString
		MAX-ACCESS		read-only
		STATUS			current
		DESCRIPTION
				"TYPE: - Display
				 PAGE: - Master- Video Master- Master Valid- Valid Audio
					Ch2 State  cmdID= 7021  format=   "
		::= { iqhco30CmdEntry 7021 }


	iqhco30ValidAudioMasterPair7Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5456 "
		::= { iqhco30CmdEntry 5456 }


	iqhco30ValidAudioMasterPair7Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5392 "
		::= { iqhco30CmdEntry 5392 }


	iqhco30ValidAudioMasterPair7Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5393 "
		::= { iqhco30CmdEntry 5393 }


	iqhco30ValidAudioMasterPair8Decision OBJECT-TYPE
		SYNTAX		RollCallString
		MAX-ACCESS		read-only
		STATUS			current
		DESCRIPTION
				"TYPE: - Display
				 PAGE: - Master- Video Master- Master Valid- Valid Audio
					Decision  cmdID= 5394  format=   "
		::= { iqhco30CmdEntry 5394 }


	iqhco30ValidAudioMasterPair8CurrentType OBJECT-TYPE
		SYNTAX		RollCallString
		MAX-ACCESS		read-only
		STATUS			current
		DESCRIPTION
				"TYPE: - Display
				 PAGE: - Master- Video Master- Master Valid- Valid Audio
					Current Type  cmdID= 5395  format=   "
		::= { iqhco30CmdEntry 5395 }


	iqhco30ValidAudioMasterPair8 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Master- Video Master- Master Valid- Valid Audio
					PCM  cmdID= 5396  value= 0  
					DolbyE  cmdID= 5396  value= 1  
					Data  cmdID= 5396  value= 2  
					None  cmdID= 5396  value= 3  
					Any  cmdID= 5396  value= 4  
					Ignored  cmdID= 5396  value= 5  "
		::= { iqhco30CmdEntry 5396 }


	iqhco30ValidAudioMasterPair8Ch1State OBJECT-TYPE
		SYNTAX		RollCallString
		MAX-ACCESS		read-only
		STATUS			current
		DESCRIPTION
				"TYPE: - Display
				 PAGE: - Master- Video Master- Master Valid- Valid Audio
					Ch1 State  cmdID= 7022  format=   "
		::= { iqhco30CmdEntry 7022 }


	iqhco30ValidAudioMasterPair8Ch2State OBJECT-TYPE
		SYNTAX		RollCallString
		MAX-ACCESS		read-only
		STATUS			current
		DESCRIPTION
				"TYPE: - Display
				 PAGE: - Master- Video Master- Master Valid- Valid Audio
					Ch2 State  cmdID= 7023  format=   "
		::= { iqhco30CmdEntry 7023 }


	iqhco30ValidAudioMasterPair8Mute OBJECT-TYPE
		SYNTAX		INTEGER { disable(0), enable(1) }
		MAX-ACCESS		read-write
		STATUS			current
		DESCRIPTION
				"TYPE: - Checkbox
				 PAGE: - Master- Video Master- Master Valid- Valid Audio
					Mute  cmdID= 5457 "
		::= { iqhco30CmdEntry 5457 }


	iqhco30ValidAudioMasterPair8Lowlevel OBJECT-TYPE
		SYNTAX		INTEGER { disable(0), enable(1) }
		MAX-ACCESS		read-write
		STATUS			current
		DESCRIPTION
				"TYPE: - Checkbox
				 PAGE: - Master- Video Master- Master Valid- Valid Audio
					Low-level  cmdID= 5397 "
		::= { iqhco30CmdEntry 5397 }


	iqhco30ValidAudioMasterPair8Overload OBJECT-TYPE
		SYNTAX		INTEGER { disable(0), enable(1) }
		MAX-ACCESS		read-write
		STATUS			current
		DESCRIPTION
				"TYPE: - Checkbox
				 PAGE: - Master- Video Master- Master Valid- Valid Audio
					Overload  cmdID= 5398 "
		::= { iqhco30CmdEntry 5398 }


	iqhco30MasterValidValidAudioLowlevel OBJECT-TYPE
		SYNTAX		INTEGER
		MAX-ACCESS		read-write
		STATUS			current
		DESCRIPTION
				"TYPE: - Number
				 PAGE: - Master- Video Master- Master Valid- Valid Audio
					Low-level  cmdID= 3061  min= -80  max= 0  step= 1  format= %1.0f dB  div_scale= 1 
					Min = -80 dB  Max = 0 dB  Step = 1 dB "
		::= { iqhco30CmdEntry 3061 }


	iqhco30MasterValidValidAudioOverloadLevel OBJECT-TYPE
		SYNTAX		INTEGER
		MAX-ACCESS		read-write
		STATUS			current
		DESCRIPTION
				"TYPE: - Number
				 PAGE: - Master- Video Master- Master Valid- Valid Audio
					Overload Level  cmdID= 3064  min= -80  max= 0  step= 1  format= %1.0f dB  div_scale= 1 
					Min = -80 dB  Max = 0 dB  Step = 1 dB "
		::= { iqhco30CmdEntry 3064 }


	iqhco30MasterValidValidAudioTypeFailTimer OBJECT-TYPE
		SYNTAX		INTEGER
		MAX-ACCESS		read-write
		STATUS			current
		DESCRIPTION
				"TYPE: - Number
				 PAGE: - Master- Video Master- Master Valid- Valid Audio
					Type Fail Timer  cmdID= 5556  min= 0  max= 10  step= 1  format= %1.0f sec  div_scale= 1 
					Min = 0 sec  Max = 10 sec  Step = 1 sec "
		::= { iqhco30CmdEntry 5556 }


	iqhco30MasterValidValidAudioTypeRecoverTimer OBJECT-TYPE
		SYNTAX		INTEGER
		MAX-ACCESS		read-write
		STATUS			current
		DESCRIPTION
				"TYPE: - Number
				 PAGE: - Master- Video Master- Master Valid- Valid Audio
					Type Recover Timer  cmdID= 5557  min= 0  max= 10  step= 1  format= %1.0f sec  div_scale= 1 
					Min = 0 sec  Max = 10 sec  Step = 1 sec "
		::= { iqhco30CmdEntry 5557 }


	iqhco30MasterValidValidAudioMuteFailTimer OBJECT-TYPE
		SYNTAX		INTEGER
		MAX-ACCESS		read-write
		STATUS			current
		DESCRIPTION
				"TYPE: - Number
				 PAGE: - Master- Video Master- Master Valid- Valid Audio
					Mute Fail Timer  cmdID= 5580  min= 0  max= 120  step= 1  format= %1.0f sec  div_scale= 1 
					Min = 0 sec  Max = 120 sec  Step = 1 sec "
		::= { iqhco30CmdEntry 5580 }


	iqhco30MasterValidValidAudioMuteRecoverTimer OBJECT-TYPE
		SYNTAX		INTEGER
		MAX-ACCESS		read-write
		STATUS			current
		DESCRIPTION
				"TYPE: - Number
				 PAGE: - Master- Video Master- Master Valid- Valid Audio
					Mute Recover Timer  cmdID= 5581  min= 0  max= 120  step= 1  format= %1.0f sec  div_scale= 1 
					Min = 0 sec  Max = 120 sec  Step = 1 sec "
		::= { iqhco30CmdEntry 5581 }


	iqhco30MasterValidValidAudioLowFailTimer OBJECT-TYPE
		SYNTAX		INTEGER
		MAX-ACCESS		read-write
		STATUS			current
		DESCRIPTION
				"TYPE: - Number
				 PAGE: - Master- Video Master- Master Valid- Valid Audio
					Low Fail Timer  cmdID= 5558  min= 0  max= 120  step= 1  format= %1.0f sec  div_scale= 1 
					Min = 0 sec  Max = 120 sec  Step = 1 sec "
		::= { iqhco30CmdEntry 5558 }


	iqhco30MasterValidValidAudioLowRecoverTimer OBJECT-TYPE
		SYNTAX		INTEGER
		MAX-ACCESS		read-write
		STATUS			current
		DESCRIPTION
				"TYPE: - Number
				 PAGE: - Master- Video Master- Master Valid- Valid Audio
					Low Recover Timer  cmdID= 5559  min= 0  max= 120  step= 1  format= %1.0f sec  div_scale= 1 
					Min = 0 sec  Max = 120 sec  Step = 1 sec "
		::= { iqhco30CmdEntry 5559 }


	iqhco30MasterValidValidAudioOverFailTimer OBJECT-TYPE
		SYNTAX		INTEGER
		MAX-ACCESS		read-write
		STATUS			current
		DESCRIPTION
				"TYPE: - Number
				 PAGE: - Master- Video Master- Master Valid- Valid Audio
					Over Fail Timer  cmdID= 5560  min= 0  max= 120  step= 1  format= %1.0f sec  div_scale= 1 
					Min = 0 sec  Max = 120 sec  Step = 1 sec "
		::= { iqhco30CmdEntry 5560 }


	iqhco30MasterValidValidAudioOverRecoverTimer OBJECT-TYPE
		SYNTAX		INTEGER
		MAX-ACCESS		read-write
		STATUS			current
		DESCRIPTION
				"TYPE: - Number
				 PAGE: - Master- Video Master- Master Valid- Valid Audio
					Over Recover Timer  cmdID= 5561  min= 0  max= 120  step= 1  format= %1.0f sec  div_scale= 1 
					Min = 0 sec  Max = 120 sec  Step = 1 sec "
		::= { iqhco30CmdEntry 5561 }


	iqhco30VideoMasterCaption OBJECT-TYPE
		SYNTAX		INTEGER {
							val-Animated-Off(0),
							val-Animated-Slow(1),
							val-Animated-Medium(2),
							val-Animated-Fast(3)
							}
		MAX-ACCESS		read-write
		STATUS			current
		DESCRIPTION
				"TYPE: - Button
				 PAGE: - Master- Video Master
					Animated Off  cmdID= 1037  value= 0  
					Animated Slow  cmdID= 1037  value= 1  
					Animated Medium  cmdID= 1037  value= 2  
					Animated Fast  cmdID= 1037  value= 3  "
		::= { iqhco30CmdEntry 1037 }


	iqhco30VideoMasterCaptionEditCaption OBJECT-TYPE
		SYNTAX		RollCallString
		MAX-ACCESS		read-write
		STATUS			current
		DESCRIPTION
				"TYPE: - Editstring
				 PAGE: - Master- Video Master
					Edit Caption  cmdID= 1041  "
		::= { iqhco30CmdEntry 1041 }


	iqhco30MasterVideoMasterPattern OBJECT-TYPE
		SYNTAX		INTEGER {
							val-Black(1),
							val-Bars(2)
							}
		MAX-ACCESS		read-write
		STATUS			current
		DESCRIPTION
				"TYPE: - RadiobuttonList
				 PAGE: - Master- Video Master
					Pattern  cmdID= 2624 
					Black  value= 1  
					Bars  value= 2  "
		::= { iqhco30CmdEntry 2624 }


	iqhco30BackupValidValidInputStds108050pB OBJECT-TYPE
		SYNTAX		INTEGER { disable(0), enable(1) }
		MAX-ACCESS		read-write
		STATUS			current
		DESCRIPTION
				"TYPE: - Checkbox
				 PAGE: - Backup- Video Backup- Backup Valid
					1080/50p-B  cmdID= 5275 "
		::= { iqhco30CmdEntry 5275 }


	iqhco30BackupValidValidInputStds108059pB OBJECT-TYPE
		SYNTAX		INTEGER { disable(0), enable(1) }
		MAX-ACCESS		read-write
		STATUS			current
		DESCRIPTION
				"TYPE: - Checkbox
				 PAGE: - Backup- Video Backup- Backup Valid
					1080/59p-B  cmdID= 5276 "
		::= { iqhco30CmdEntry 5276 }


	iqhco30BackupValidValidInputStds108050pA OBJECT-TYPE
		SYNTAX		INTEGER { disable(0), enable(1) }
		MAX-ACCESS		read-write
		STATUS			current
		DESCRIPTION
				"TYPE: - Checkbox
				 PAGE: - Backup- Video Backup- Backup Valid
					1080/50p-A  cmdID= 5272 "
		::= { iqhco30CmdEntry 5272 }


	iqhco30BackupValidValidInputStds108059pA OBJECT-TYPE
		SYNTAX		INTEGER { disable(0), enable(1) }
		MAX-ACCESS		read-write
		STATUS			current
		DESCRIPTION
				"TYPE: - Checkbox
				 PAGE: - Backup- Video Backup- Backup Valid
					1080/59p-A  cmdID= 5273 "
		::= { iqhco30CmdEntry 5273 }


	iqhco30BackupValidValidInputStds108029i OBJECT-TYPE
		SYNTAX		INTEGER { disable(0), enable(1) }
		MAX-ACCESS		read-write
		STATUS			current
		DESCRIPTION
				"TYPE: - Checkbox
				 PAGE: - Backup- Video Backup- Backup Valid
					1080/29i  cmdID= 5268 "
		::= { iqhco30CmdEntry 5268 }


	iqhco30BackupValidValidInputStds108025i OBJECT-TYPE
		SYNTAX		INTEGER { disable(0), enable(1) }
		MAX-ACCESS		read-write
		STATUS			current
		DESCRIPTION
				"TYPE: - Checkbox
				 PAGE: - Backup- Video Backup- Backup Valid
					1080/25i  cmdID= 5267 "
		::= { iqhco30CmdEntry 5267 }


	iqhco30BackupValidValidInputStds72059p OBJECT-TYPE
		SYNTAX		INTEGER { disable(0), enable(1) }
		MAX-ACCESS		read-write
		STATUS			current
		DESCRIPTION
				"TYPE: - Checkbox
				 PAGE: - Backup- Video Backup- Backup Valid
					720/59p  cmdID= 5260 "
		::= { iqhco30CmdEntry 5260 }


	iqhco30BackupValidValidInputStds72050p OBJECT-TYPE
		SYNTAX		INTEGER { disable(0), enable(1) }
		MAX-ACCESS		read-write
		STATUS			current
		DESCRIPTION
				"TYPE: - Checkbox
				 PAGE: - Backup- Video Backup- Backup Valid
					720/50p  cmdID= 5259 "
		::= { iqhco30CmdEntry 5259 }


	iqhco30BackupValidValidInputStds52529i OBJECT-TYPE
		SYNTAX		INTEGER { disable(0), enable(1) }
		MAX-ACCESS		read-write
		STATUS			current
		DESCRIPTION
				"TYPE: - Checkbox
				 PAGE: - Backup- Video Backup- Backup Valid
					525/29i  cmdID= 5253 "
		::= { iqhco30CmdEntry 5253 }


	iqhco30BackupValidValidInputStds62525i OBJECT-TYPE
		SYNTAX		INTEGER { disable(0), enable(1) }
		MAX-ACCESS		read-write
		STATUS			current
		DESCRIPTION
				"TYPE: - Checkbox
				 PAGE: - Backup- Video Backup- Backup Valid
					625/25i  cmdID= 5252 "
		::= { iqhco30CmdEntry 5252 }


	iqhco30BackupValidCRCEDHErroredsecErrSecEnable OBJECT-TYPE
		SYNTAX		INTEGER { disable(0), enable(1) }
		MAX-ACCESS		read-write
		STATUS			current
		DESCRIPTION
				"TYPE: - Checkbox
				 PAGE: - Backup- Video Backup- Backup Valid
					ErrSec Enable  cmdID= 5404 "
		::= { iqhco30CmdEntry 5404 }


	iqhco30BackupValidCRCEDHErroredsecErrSecDecision OBJECT-TYPE
		SYNTAX		RollCallString
		MAX-ACCESS		read-only
		STATUS			current
		DESCRIPTION
				"TYPE: - Display
				 PAGE: - Backup- Video Backup- Backup Valid
					ErrSec Decision  cmdID= 5403  format=   "
		::= { iqhco30CmdEntry 5403 }


	iqhco30BackupValidCRCEDHErroredsecCarrierDecision OBJECT-TYPE
		SYNTAX		RollCallString
		MAX-ACCESS		read-only
		STATUS			current
		DESCRIPTION
				"TYPE: - Display
				 PAGE: - Backup- Video Backup- Backup Valid
					Carrier Decision  cmdID= 5401  format=   "
		::= { iqhco30CmdEntry 5401 }


	iqhco30BackupValidCRCEDHErroredsecStdDecision OBJECT-TYPE
		SYNTAX		RollCallString
		MAX-ACCESS		read-only
		STATUS			current
		DESCRIPTION
				"TYPE: - Display
				 PAGE: - Backup- Video Backup- Backup Valid
					Std Decision  cmdID= 5402  format=   "
		::= { iqhco30CmdEntry 5402 }


	iqhco30BackupValidCRCEDHErroredsecInputStd OBJECT-TYPE
		SYNTAX		RollCallString
		MAX-ACCESS		read-only
		STATUS			current
		DESCRIPTION
				"TYPE: - Display
				 PAGE: - Backup- Video Backup- Backup Valid
					Input Std  cmdID= 5449  format=   "
		::= { iqhco30CmdEntry 5449 }


	iqhco30BackupValidCRCEDHErroredsecFreezeEnable OBJECT-TYPE
		SYNTAX		INTEGER { disable(0), enable(1) }
		MAX-ACCESS		read-write
		STATUS			current
		DESCRIPTION
				"TYPE: - Checkbox
				 PAGE: - Backup- Video Backup- Backup Valid
					Freeze Enable  cmdID= 5406 "
		::= { iqhco30CmdEntry 5406 }


	iqhco30BackupValidCRCEDHErroredsecFreezeDecision OBJECT-TYPE
		SYNTAX		RollCallString
		MAX-ACCESS		read-only
		STATUS			current
		DESCRIPTION
				"TYPE: - Display
				 PAGE: - Backup- Video Backup- Backup Valid
					Freeze Decision  cmdID= 5405  format=   "
		::= { iqhco30CmdEntry 5405 }


	iqhco30BackupValidCRCEDHErroredsecBlackEnable OBJECT-TYPE
		SYNTAX		INTEGER { disable(0), enable(1) }
		MAX-ACCESS		read-write
		STATUS			current
		DESCRIPTION
				"TYPE: - Checkbox
				 PAGE: - Backup- Video Backup- Backup Valid
					Black Enable  cmdID= 5408 "
		::= { iqhco30CmdEntry 5408 }


	iqhco30BackupValidCRCEDHErroredsecBlackDecision OBJECT-TYPE
		SYNTAX		RollCallString
		MAX-ACCESS		read-only
		STATUS			current
		DESCRIPTION
				"TYPE: - Display
				 PAGE: - Backup- Video Backup- Backup Valid
					Black Decision  cmdID= 5407  format=   "
		::= { iqhco30CmdEntry 5407 }


	iqhco30BackupValidCRCEDHErroredsecBlackThreshold OBJECT-TYPE
		SYNTAX		INTEGER
		MAX-ACCESS		read-write
		STATUS			current
		DESCRIPTION
				"TYPE: - Number
				 PAGE: - Backup- Video Backup- Backup Valid
					Black Threshold  cmdID= 5579  min= 0  max= 153  step= 1  format= %.0f mV  div_scale= 1 
					Min = 0 mV  Max = 153 mV  Step = 1 mV "
		::= { iqhco30CmdEntry 5579 }


	iqhco30BackupValidVideoValidTimersBlackFailDelay OBJECT-TYPE
		SYNTAX		INTEGER
		MAX-ACCESS		read-write
		STATUS			current
		DESCRIPTION
				"TYPE: - Number
				 PAGE: - Backup- Video Backup- Backup Valid
					Black Fail Delay  cmdID= 5564  min= 2  max= 100  step= 1  format= %.1f s  div_scale= 10 
					Min = 0.2 s  Max = 10.0 s  Step = 0.1 s "
		::= { iqhco30CmdEntry 5564 }


	iqhco30BackupValidVideoValidTimersBlackRecoverDelay OBJECT-TYPE
		SYNTAX		INTEGER
		MAX-ACCESS		read-write
		STATUS			current
		DESCRIPTION
				"TYPE: - Number
				 PAGE: - Backup- Video Backup- Backup Valid
					Black Recover Delay  cmdID= 5565  min= 2  max= 100  step= 1  format= %.1f s  div_scale= 10 
					Min = 0.2 s  Max = 10.0 s  Step = 0.1 s "
		::= { iqhco30CmdEntry 5565 }


	iqhco30BackupValidVideoValidTimersFreezeFailDelay OBJECT-TYPE
		SYNTAX		INTEGER
		MAX-ACCESS		read-write
		STATUS			current
		DESCRIPTION
				"TYPE: - Number
				 PAGE: - Backup- Video Backup- Backup Valid
					Freeze Fail Delay  cmdID= 5566  min= 2  max= 100  step= 1  format= %.1f s  div_scale= 10 
					Min = 0.2 s  Max = 10.0 s  Step = 0.1 s "
		::= { iqhco30CmdEntry 5566 }


	iqhco30BackupValidVideoValidTimersFreezeRecoverDela OBJECT-TYPE
		SYNTAX		INTEGER
		MAX-ACCESS		read-write
		STATUS			current
		DESCRIPTION
				"TYPE: - Number
				 PAGE: - Backup- Video Backup- Backup Valid
					Freeze Recover Dela  cmdID= 5567  min= 2  max= 100  step= 1  format= %.1f s  div_scale= 10 
					Min = 0.2 s  Max = 10.0 s  Step = 0.1 s "
		::= { iqhco30CmdEntry 5567 }


	iqhco30BackupValidVideoValidTimersErrsecFailDelay OBJECT-TYPE
		SYNTAX		INTEGER
		MAX-ACCESS		read-write
		STATUS			current
		DESCRIPTION
				"TYPE: - Number
				 PAGE: - Backup- Video Backup- Backup Valid
					Errsec Fail Delay  cmdID= 5568  min= 0  max= 10  step= 1  format= %.0f s  div_scale= 1 
					Min = 0 s  Max = 10 s  Step = 1 s "
		::= { iqhco30CmdEntry 5568 }


	iqhco30BackupValidVideoValidTimersErrsecRecoverDela OBJECT-TYPE
		SYNTAX		INTEGER
		MAX-ACCESS		read-write
		STATUS			current
		DESCRIPTION
				"TYPE: - Number
				 PAGE: - Backup- Video Backup- Backup Valid
					Errsec Recover Dela  cmdID= 5569  min= 0  max= 10  step= 1  format= %.0f s  div_scale= 1 
					Min = 0 s  Max = 10 s  Step = 1 s "
		::= { iqhco30CmdEntry 5569 }


	iqhco30BackupValidVideoValidTimersValidFailDelay OBJECT-TYPE
		SYNTAX		INTEGER
		MAX-ACCESS		read-write
		STATUS			current
		DESCRIPTION
				"TYPE: - Number
				 PAGE: - Backup- Video Backup- Backup Valid
					Valid Fail Delay  cmdID= 5576  min= 0  max= 100  step= 1  format= %.1f s  div_scale= 10 
					Min = 0.0 s  Max = 10.0 s  Step = 0.1 s "
		::= { iqhco30CmdEntry 5576 }


	iqhco30BackupValidVideoValidTimersValidRecoverDelay OBJECT-TYPE
		SYNTAX		INTEGER
		MAX-ACCESS		read-write
		STATUS			current
		DESCRIPTION
				"TYPE: - Number
				 PAGE: - Backup- Video Backup- Backup Valid
					Valid Recover Delay  cmdID= 5577  min= 2  max= 100  step= 1  format= %.1f s  div_scale= 10 
					Min = 0.2 s  Max = 10.0 s  Step = 0.1 s "
		::= { iqhco30CmdEntry 5577 }


	iqhco30BackupValidValidAudioDecision OBJECT-TYPE
		SYNTAX		RollCallString
		MAX-ACCESS		read-only
		STATUS			current
		DESCRIPTION
				"TYPE: - Display
				 PAGE: - Backup- Video Backup- Backup Valid- Valid Audio
					Decision  cmdID= 5400  format=   "
		::= { iqhco30CmdEntry 5400 }


	iqhco30ValidAudioBackupPair1Decision OBJECT-TYPE
		SYNTAX		RollCallString
		MAX-ACCESS		read-only
		STATUS			current
		DESCRIPTION
				"TYPE: - Display
				 PAGE: - Backup- Video Backup- Backup Valid- Valid Audio
					Decision  cmdID= 5409  format=   "
		::= { iqhco30CmdEntry 5409 }


	iqhco30ValidAudioBackupPair1CurrentType OBJECT-TYPE
		SYNTAX		RollCallString
		MAX-ACCESS		read-only
		STATUS			current
		DESCRIPTION
				"TYPE: - Display
				 PAGE: - Backup- Video Backup- Backup Valid- Valid Audio
					Current Type  cmdID= 5410  format=   "
		::= { iqhco30CmdEntry 5410 }


	iqhco30ValidAudioBackupPair1 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5411  value= 0  
					DolbyE  cmdID= 5411  value= 1  
					Data  cmdID= 5411  value= 2  
					None  cmdID= 5411  value= 3  
					Any  cmdID= 5411  value= 4  
					Ignored  cmdID= 5411  value= 5  "
		::= { iqhco30CmdEntry 5411 }


	iqhco30ValidAudioBackupPair1Ch1State OBJECT-TYPE
		SYNTAX		RollCallString
		MAX-ACCESS		read-only
		STATUS			current
		DESCRIPTION
				"TYPE: - Display
				 PAGE: - Backup- Video Backup- Backup Valid- Valid Audio
					Ch1 State  cmdID= 7024  format=   "
		::= { iqhco30CmdEntry 7024 }


	iqhco30ValidAudioBackupPair1Ch2State OBJECT-TYPE
		SYNTAX		RollCallString
		MAX-ACCESS		read-only
		STATUS			current
		DESCRIPTION
				"TYPE: - Display
				 PAGE: - Backup- Video Backup- Backup Valid- Valid Audio
					Ch2 State  cmdID= 7025  format=   "
		::= { iqhco30CmdEntry 7025 }


	iqhco30ValidAudioBackupPair1Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5458 "
		::= { iqhco30CmdEntry 5458 }


	iqhco30ValidAudioBackupPair1Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5412 "
		::= { iqhco30CmdEntry 5412 }


	iqhco30ValidAudioBackupPair1Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5413 "
		::= { iqhco30CmdEntry 5413 }


	iqhco30ValidAudioBackupPair2Decision OBJECT-TYPE
		SYNTAX		RollCallString
		MAX-ACCESS		read-only
		STATUS			current
		DESCRIPTION
				"TYPE: - Display
				 PAGE: - Backup- Video Backup- Backup Valid- Valid Audio
					Decision  cmdID= 5414  format=   "
		::= { iqhco30CmdEntry 5414 }


	iqhco30ValidAudioBackupPair2CurrentType OBJECT-TYPE
		SYNTAX		RollCallString
		MAX-ACCESS		read-only
		STATUS			current
		DESCRIPTION
				"TYPE: - Display
				 PAGE: - Backup- Video Backup- Backup Valid- Valid Audio
					Current Type  cmdID= 5415  format=   "
		::= { iqhco30CmdEntry 5415 }


	iqhco30ValidAudioBackupPair2 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5416  value= 0  
					DolbyE  cmdID= 5416  value= 1  
					Data  cmdID= 5416  value= 2  
					None  cmdID= 5416  value= 3  
					Any  cmdID= 5416  value= 4  
					Ignored  cmdID= 5416  value= 5  "
		::= { iqhco30CmdEntry 5416 }


	iqhco30ValidAudioBackupPair2Ch1State OBJECT-TYPE
		SYNTAX		RollCallString
		MAX-ACCESS		read-only
		STATUS			current
		DESCRIPTION
				"TYPE: - Display
				 PAGE: - Backup- Video Backup- Backup Valid- Valid Audio
					Ch1 State  cmdID= 7026  format=   "
		::= { iqhco30CmdEntry 7026 }


	iqhco30ValidAudioBackupPair2Ch2State OBJECT-TYPE
		SYNTAX		RollCallString
		MAX-ACCESS		read-only
		STATUS			current
		DESCRIPTION
				"TYPE: - Display
				 PAGE: - Backup- Video Backup- Backup Valid- Valid Audio
					Ch2 State  cmdID= 7027  format=   "
		::= { iqhco30CmdEntry 7027 }


	iqhco30ValidAudioBackupPair2Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5459 "
		::= { iqhco30CmdEntry 5459 }


	iqhco30ValidAudioBackupPair2Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5417 "
		::= { iqhco30CmdEntry 5417 }


	iqhco30ValidAudioBackupPair2Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5418 "
		::= { iqhco30CmdEntry 5418 }


	iqhco30ValidAudioBackupPair3Decision OBJECT-TYPE
		SYNTAX		RollCallString
		MAX-ACCESS		read-only
		STATUS			current
		DESCRIPTION
				"TYPE: - Display
				 PAGE: - Backup- Video Backup- Backup Valid- Valid Audio
					Decision  cmdID= 5419  format=   "
		::= { iqhco30CmdEntry 5419 }


	iqhco30ValidAudioBackupPair3CurrentType OBJECT-TYPE
		SYNTAX		RollCallString
		MAX-ACCESS		read-only
		STATUS			current
		DESCRIPTION
				"TYPE: - Display
				 PAGE: - Backup- Video Backup- Backup Valid- Valid Audio
					Current Type  cmdID= 5420  format=   "
		::= { iqhco30CmdEntry 5420 }


	iqhco30ValidAudioBackupPair3 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5421  value= 0  
					DolbyE  cmdID= 5421  value= 1  
					Data  cmdID= 5421  value= 2  
					None  cmdID= 5421  value= 3  
					Any  cmdID= 5421  value= 4  
					Ignored  cmdID= 5421  value= 5  "
		::= { iqhco30CmdEntry 5421 }


	iqhco30ValidAudioBackupPair3Ch1State OBJECT-TYPE
		SYNTAX		RollCallString
		MAX-ACCESS		read-only
		STATUS			current
		DESCRIPTION
				"TYPE: - Display
				 PAGE: - Backup- Video Backup- Backup Valid- Valid Audio
					Ch1 State  cmdID= 7028  format=   "
		::= { iqhco30CmdEntry 7028 }


	iqhco30ValidAudioBackupPair3Ch2State OBJECT-TYPE
		SYNTAX		RollCallString
		MAX-ACCESS		read-only
		STATUS			current
		DESCRIPTION
				"TYPE: - Display
				 PAGE: - Backup- Video Backup- Backup Valid- Valid Audio
					Ch2 State  cmdID= 7029  format=   "
		::= { iqhco30CmdEntry 7029 }


	iqhco30ValidAudioBackupPair3Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5460 "
		::= { iqhco30CmdEntry 5460 }


	iqhco30ValidAudioBackupPair3Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5422 "
		::= { iqhco30CmdEntry 5422 }


	iqhco30ValidAudioBackupPair3Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5423 "
		::= { iqhco30CmdEntry 5423 }


	iqhco30ValidAudioBackupPair4Decision OBJECT-TYPE
		SYNTAX		RollCallString
		MAX-ACCESS		read-only
		STATUS			current
		DESCRIPTION
				"TYPE: - Display
				 PAGE: - Backup- Video Backup- Backup Valid- Valid Audio
					Decision  cmdID= 5424  format=   "
		::= { iqhco30CmdEntry 5424 }


	iqhco30ValidAudioBackupPair4CurrentType OBJECT-TYPE
		SYNTAX		RollCallString
		MAX-ACCESS		read-only
		STATUS			current
		DESCRIPTION
				"TYPE: - Display
				 PAGE: - Backup- Video Backup- Backup Valid- Valid Audio
					Current Type  cmdID= 5425  format=   "
		::= { iqhco30CmdEntry 5425 }


	iqhco30ValidAudioBackupPair4 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5426  value= 0  
					DolbyE  cmdID= 5426  value= 1  
					Data  cmdID= 5426  value= 2  
					None  cmdID= 5426  value= 3  
					Any  cmdID= 5426  value= 4  
					Ignored  cmdID= 5426  value= 5  "
		::= { iqhco30CmdEntry 5426 }


	iqhco30ValidAudioBackupPair4Ch1State OBJECT-TYPE
		SYNTAX		RollCallString
		MAX-ACCESS		read-only
		STATUS			current
		DESCRIPTION
				"TYPE: - Display
				 PAGE: - Backup- Video Backup- Backup Valid- Valid Audio
					Ch1 State  cmdID= 7030  format=   "
		::= { iqhco30CmdEntry 7030 }


	iqhco30ValidAudioBackupPair4Ch2State OBJECT-TYPE
		SYNTAX		RollCallString
		MAX-ACCESS		read-only
		STATUS			current
		DESCRIPTION
				"TYPE: - Display
				 PAGE: - Backup- Video Backup- Backup Valid- Valid Audio
					Ch2 State  cmdID= 7031  format=   "
		::= { iqhco30CmdEntry 7031 }


	iqhco30ValidAudioBackupPair4Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5461 "
		::= { iqhco30CmdEntry 5461 }


	iqhco30ValidAudioBackupPair4Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5427 "
		::= { iqhco30CmdEntry 5427 }


	iqhco30ValidAudioBackupPair4Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5428 "
		::= { iqhco30CmdEntry 5428 }


	iqhco30ValidAudioBackupPair5Decision OBJECT-TYPE
		SYNTAX		RollCallString
		MAX-ACCESS		read-only
		STATUS			current
		DESCRIPTION
				"TYPE: - Display
				 PAGE: - Backup- Video Backup- Backup Valid- Valid Audio
					Decision  cmdID= 5429  format=   "
		::= { iqhco30CmdEntry 5429 }


	iqhco30ValidAudioBackupPair5CurrentType OBJECT-TYPE
		SYNTAX		RollCallString
		MAX-ACCESS		read-only
		STATUS			current
		DESCRIPTION
				"TYPE: - Display
				 PAGE: - Backup- Video Backup- Backup Valid- Valid Audio
					Current Type  cmdID= 5430  format=   "
		::= { iqhco30CmdEntry 5430 }


	iqhco30ValidAudioBackupPair5 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5431  value= 0  
					DolbyE  cmdID= 5431  value= 1  
					Data  cmdID= 5431  value= 2  
					None  cmdID= 5431  value= 3  
					Any  cmdID= 5431  value= 4  
					Ignored  cmdID= 5431  value= 5  "
		::= { iqhco30CmdEntry 5431 }


	iqhco30ValidAudioBackupPair5Ch1State OBJECT-TYPE
		SYNTAX		RollCallString
		MAX-ACCESS		read-only
		STATUS			current
		DESCRIPTION
				"TYPE: - Display
				 PAGE: - Backup- Video Backup- Backup Valid- Valid Audio
					Ch1 State  cmdID= 7032  format=   "
		::= { iqhco30CmdEntry 7032 }


	iqhco30ValidAudioBackupPair5Ch2State OBJECT-TYPE
		SYNTAX		RollCallString
		MAX-ACCESS		read-only
		STATUS			current
		DESCRIPTION
				"TYPE: - Display
				 PAGE: - Backup- Video Backup- Backup Valid- Valid Audio
					Ch2 State  cmdID= 7033  format=   "
		::= { iqhco30CmdEntry 7033 }


	iqhco30ValidAudioBackupPair5Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5462 "
		::= { iqhco30CmdEntry 5462 }


	iqhco30ValidAudioBackupPair5Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5432 "
		::= { iqhco30CmdEntry 5432 }


	iqhco30ValidAudioBackupPair5Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5433 "
		::= { iqhco30CmdEntry 5433 }


	iqhco30ValidAudioBackupPair6Decision OBJECT-TYPE
		SYNTAX		RollCallString
		MAX-ACCESS		read-only
		STATUS			current
		DESCRIPTION
				"TYPE: - Display
				 PAGE: - Backup- Video Backup- Backup Valid- Valid Audio
					Decision  cmdID= 5434  format=   "
		::= { iqhco30CmdEntry 5434 }


	iqhco30ValidAudioBackupPair6CurrentType OBJECT-TYPE
		SYNTAX		RollCallString
		MAX-ACCESS		read-only
		STATUS			current
		DESCRIPTION
				"TYPE: - Display
				 PAGE: - Backup- Video Backup- Backup Valid- Valid Audio
					Current Type  cmdID= 5435  format=   "
		::= { iqhco30CmdEntry 5435 }


	iqhco30ValidAudioBackupPair6 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5436  value= 0  
					DolbyE  cmdID= 5436  value= 1  
					Data  cmdID= 5436  value= 2  
					None  cmdID= 5436  value= 3  
					Any  cmdID= 5436  value= 4  
					Ignored  cmdID= 5436  value= 5  "
		::= { iqhco30CmdEntry 5436 }


	iqhco30ValidAudioBackupPair6Ch1State OBJECT-TYPE
		SYNTAX		RollCallString
		MAX-ACCESS		read-only
		STATUS			current
		DESCRIPTION
				"TYPE: - Display
				 PAGE: - Backup- Video Backup- Backup Valid- Valid Audio
					Ch1 State  cmdID= 7034  format=   "
		::= { iqhco30CmdEntry 7034 }


	iqhco30ValidAudioBackupPair6Ch2State OBJECT-TYPE
		SYNTAX		RollCallString
		MAX-ACCESS		read-only
		STATUS			current
		DESCRIPTION
				"TYPE: - Display
				 PAGE: - Backup- Video Backup- Backup Valid- Valid Audio
					Ch2 State  cmdID= 7035  format=   "
		::= { iqhco30CmdEntry 7035 }


	iqhco30ValidAudioBackupPair6Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5463 "
		::= { iqhco30CmdEntry 5463 }


	iqhco30ValidAudioBackupPair6Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5437 "
		::= { iqhco30CmdEntry 5437 }


	iqhco30ValidAudioBackupPair6Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5438 "
		::= { iqhco30CmdEntry 5438 }


	iqhco30ValidAudioBackupPair7Decision OBJECT-TYPE
		SYNTAX		RollCallString
		MAX-ACCESS		read-only
		STATUS			current
		DESCRIPTION
				"TYPE: - Display
				 PAGE: - Backup- Video Backup- Backup Valid- Valid Audio
					Decision  cmdID= 5439  format=   "
		::= { iqhco30CmdEntry 5439 }


	iqhco30ValidAudioBackupPair7CurrentType OBJECT-TYPE
		SYNTAX		RollCallString
		MAX-ACCESS		read-only
		STATUS			current
		DESCRIPTION
				"TYPE: - Display
				 PAGE: - Backup- Video Backup- Backup Valid- Valid Audio
					Current Type  cmdID= 5440  format=   "
		::= { iqhco30CmdEntry 5440 }


	iqhco30ValidAudioBackupPair7 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5441  value= 0  
					DolbyE  cmdID= 5441  value= 1  
					Data  cmdID= 5441  value= 2  
					None  cmdID= 5441  value= 3  
					Any  cmdID= 5441  value= 4  
					Ignored  cmdID= 5441  value= 5  "
		::= { iqhco30CmdEntry 5441 }


	iqhco30ValidAudioBackupPair7Ch1State OBJECT-TYPE
		SYNTAX		RollCallString
		MAX-ACCESS		read-only
		STATUS			current
		DESCRIPTION
				"TYPE: - Display
				 PAGE: - Backup- Video Backup- Backup Valid- Valid Audio
					Ch1 State  cmdID= 7036  format=   "
		::= { iqhco30CmdEntry 7036 }


	iqhco30ValidAudioBackupPair7Ch2State OBJECT-TYPE
		SYNTAX		RollCallString
		MAX-ACCESS		read-only
		STATUS			current
		DESCRIPTION
				"TYPE: - Display
				 PAGE: - Backup- Video Backup- Backup Valid- Valid Audio
					Ch2 State  cmdID= 7037  format=   "
		::= { iqhco30CmdEntry 7037 }


	iqhco30ValidAudioBackupPair7Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5464 "
		::= { iqhco30CmdEntry 5464 }


	iqhco30ValidAudioBackupPair7Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5442 "
		::= { iqhco30CmdEntry 5442 }


	iqhco30ValidAudioBackupPair7Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5443 "
		::= { iqhco30CmdEntry 5443 }


	iqhco30ValidAudioBackupPair8Decision OBJECT-TYPE
		SYNTAX		RollCallString
		MAX-ACCESS		read-only
		STATUS			current
		DESCRIPTION
				"TYPE: - Display
				 PAGE: - Backup- Video Backup- Backup Valid- Valid Audio
					Decision  cmdID= 5444  format=   "
		::= { iqhco30CmdEntry 5444 }


	iqhco30ValidAudioBackupPair8CurrentType OBJECT-TYPE
		SYNTAX		RollCallString
		MAX-ACCESS		read-only
		STATUS			current
		DESCRIPTION
				"TYPE: - Display
				 PAGE: - Backup- Video Backup- Backup Valid- Valid Audio
					Current Type  cmdID= 5445  format=   "
		::= { iqhco30CmdEntry 5445 }


	iqhco30ValidAudioBackupPair8 OBJECT-TYPE
		SYNTAX		INTEGER {
							val-PCM(0),
							val-DolbyE(1),
							val-Data(2),
							val-None(3),
							val-Any(4),
							val-Ignored(5)
							}
		MAX-ACCESS		read-write
		STATUS			current
		DESCRIPTION
				"TYPE: - Button
				 PAGE: - Backup- Video Backup- Backup Valid- Valid Audio
					PCM  cmdID= 5446  value= 0  
					DolbyE  cmdID= 5446  value= 1  
					Data  cmdID= 5446  value= 2  
					None  cmdID= 5446  value= 3  
					Any  cmdID= 5446  value= 4  
					Ignored  cmdID= 5446  value= 5  "
		::= { iqhco30CmdEntry 5446 }


	iqhco30ValidAudioBackupPair8Ch1State OBJECT-TYPE
		SYNTAX		RollCallString
		MAX-ACCESS		read-only
		STATUS			current
		DESCRIPTION
				"TYPE: - Display
				 PAGE: - Backup- Video Backup- Backup Valid- Valid Audio
					Ch1 State  cmdID= 7038  format=   "
		::= { iqhco30CmdEntry 7038 }


	iqhco30ValidAudioBackupPair8Ch2State OBJECT-TYPE
		SYNTAX		RollCallString
		MAX-ACCESS		read-only
		STATUS			current
		DESCRIPTION
				"TYPE: - Display
				 PAGE: - Backup- Video Backup- Backup Valid- Valid Audio
					Ch2 State  cmdID= 7039  format=   "
		::= { iqhco30CmdEntry 7039 }


	iqhco30ValidAudioBackupPair8Mute OBJECT-TYPE
		SYNTAX		INTEGER { disable(0), enable(1) }
		MAX-ACCESS		read-write
		STATUS			current
		DESCRIPTION
				"TYPE: - Checkbox
				 PAGE: - Backup- Video Backup- Backup Valid- Valid Audio
					Mute  cmdID= 5465 "
		::= { iqhco30CmdEntry 5465 }


	iqhco30ValidAudioBackupPair8Lowlevel OBJECT-TYPE
		SYNTAX		INTEGER { disable(0), enable(1) }
		MAX-ACCESS		read-write
		STATUS			current
		DESCRIPTION
				"TYPE: - Checkbox
				 PAGE: - Backup- Video Backup- Backup Valid- Valid Audio
					Low-level  cmdID= 5447 "
		::= { iqhco30CmdEntry 5447 }


	iqhco30ValidAudioBackupPair8Overload OBJECT-TYPE
		SYNTAX		INTEGER { disable(0), enable(1) }
		MAX-ACCESS		read-write
		STATUS			current
		DESCRIPTION
				"TYPE: - Checkbox
				 PAGE: - Backup- Video Backup- Backup Valid- Valid Audio
					Overload  cmdID= 5448 "
		::= { iqhco30CmdEntry 5448 }


	iqhco30BackupValidValidAudioLowlevel OBJECT-TYPE
		SYNTAX		INTEGER
		MAX-ACCESS		read-write
		STATUS			current
		DESCRIPTION
				"TYPE: - Number
				 PAGE: - Backup- Video Backup- Backup Valid- Valid Audio
					Low-level  cmdID= 3075  min= -80  max= 0  step= 1  format= %1.0f dB  div_scale= 1 
					Min = -80 dB  Max = 0 dB  Step = 1 dB "
		::= { iqhco30CmdEntry 3075 }


	iqhco30BackupValidValidAudioOverloadLevel OBJECT-TYPE
		SYNTAX		INTEGER
		MAX-ACCESS		read-write
		STATUS			current
		DESCRIPTION
				"TYPE: - Number
				 PAGE: - Backup- Video Backup- Backup Valid- Valid Audio
					Overload Level  cmdID= 3078  min= -80  max= 0  step= 1  format= %1.0f dB  div_scale= 1 
					Min = -80 dB  Max = 0 dB  Step = 1 dB "
		::= { iqhco30CmdEntry 3078 }


	iqhco30BackupValidValidAudioTypeFailTimer OBJECT-TYPE
		SYNTAX		INTEGER
		MAX-ACCESS		read-write
		STATUS			current
		DESCRIPTION
				"TYPE: - Number
				 PAGE: - Backup- Video Backup- Backup Valid- Valid Audio
					Type Fail Timer  cmdID= 5570  min= 0  max= 10  step= 1  format= %1.0f sec  div_scale= 1 
					Min = 0 sec  Max = 10 sec  Step = 1 sec "
		::= { iqhco30CmdEntry 5570 }


	iqhco30BackupValidValidAudioTypeRecoverTimer OBJECT-TYPE
		SYNTAX		INTEGER
		MAX-ACCESS		read-write
		STATUS			current
		DESCRIPTION
				"TYPE: - Number
				 PAGE: - Backup- Video Backup- Backup Valid- Valid Audio
					Type Recover Timer  cmdID= 5571  min= 0  max= 10  step= 1  format= %1.0f sec  div_scale= 1 
					Min = 0 sec  Max = 10 sec  Step = 1 sec "
		::= { iqhco30CmdEntry 5571 }


	iqhco30BackupValidValidAudioMuteFailTimer OBJECT-TYPE
		SYNTAX		INTEGER
		MAX-ACCESS		read-write
		STATUS			current
		DESCRIPTION
				"TYPE: - Number
				 PAGE: - Backup- Video Backup- Backup Valid- Valid Audio
					Mute Fail Timer  cmdID= 5582  min= 0  max= 120  step= 1  format= %1.0f sec  div_scale= 1 
					Min = 0 sec  Max = 120 sec  Step = 1 sec "
		::= { iqhco30CmdEntry 5582 }


	iqhco30BackupValidValidAudioMuteRecoverTimer OBJECT-TYPE
		SYNTAX		INTEGER
		MAX-ACCESS		read-write
		STATUS			current
		DESCRIPTION
				"TYPE: - Number
				 PAGE: - Backup- Video Backup- Backup Valid- Valid Audio
					Mute Recover Timer  cmdID= 5583  min= 0  max= 120  step= 1  format= %1.0f sec  div_scale= 1 
					Min = 0 sec  Max = 120 sec  Step = 1 sec "
		::= { iqhco30CmdEntry 5583 }


	iqhco30BackupValidValidAudioLowFailTimer OBJECT-TYPE
		SYNTAX		INTEGER
		MAX-ACCESS		read-write
		STATUS			current
		DESCRIPTION
				"TYPE: - Number
				 PAGE: - Backup- Video Backup- Backup Valid- Valid Audio
					Low Fail Timer  cmdID= 5572  min= 0  max= 120  step= 1  format= %1.0f sec  div_scale= 1 
					Min = 0 sec  Max = 120 sec  Step = 1 sec "
		::= { iqhco30CmdEntry 5572 }


	iqhco30BackupValidValidAudioLowRecoverTimer OBJECT-TYPE
		SYNTAX		INTEGER
		MAX-ACCESS		read-write
		STATUS			current
		DESCRIPTION
				"TYPE: - Number
				 PAGE: - Backup- Video Backup- Backup Valid- Valid Audio
					Low Recover Timer  cmdID= 5573  min= 0  max= 120  step= 1  format= %1.0f sec  div_scale= 1 
					Min = 0 sec  Max = 120 sec  Step = 1 sec "
		::= { iqhco30CmdEntry 5573 }


	iqhco30BackupValidValidAudioOverFailTimer OBJECT-TYPE
		SYNTAX		INTEGER
		MAX-ACCESS		read-write
		STATUS			current
		DESCRIPTION
				"TYPE: - Number
				 PAGE: - Backup- Video Backup- Backup Valid- Valid Audio
					Over Fail Timer  cmdID= 5574  min= 0  max= 120  step= 1  format= %1.0f sec  div_scale= 1 
					Min = 0 sec  Max = 120 sec  Step = 1 sec "
		::= { iqhco30CmdEntry 5574 }


	iqhco30BackupValidValidAudioOverRecoverTimer OBJECT-TYPE
		SYNTAX		INTEGER
		MAX-ACCESS		read-write
		STATUS			current
		DESCRIPTION
				"TYPE: - Number
				 PAGE: - Backup- Video Backup- Backup Valid- Valid Audio
					Over Recover Timer  cmdID= 5575  min= 0  max= 120  step= 1  format= %1.0f sec  div_scale= 1 
					Min = 0 sec  Max = 120 sec  Step = 1 sec "
		::= { iqhco30CmdEntry 5575 }


	iqhco30VideoBackupCaption OBJECT-TYPE
		SYNTAX		INTEGER {
							val-Animated-Off(0),
							val-Animated-Slow(1),
							val-Animated-Medium(2),
							val-Animated-Fast(3)
							}
		MAX-ACCESS		read-write
		STATUS			current
		DESCRIPTION
				"TYPE: - Button
				 PAGE: - Backup- Video Backup
					Animated Off  cmdID= 1039  value= 0  
					Animated Slow  cmdID= 1039  value= 1  
					Animated Medium  cmdID= 1039  value= 2  
					Animated Fast  cmdID= 1039  value= 3  "
		::= { iqhco30CmdEntry 1039 }


	iqhco30VideoBackupCaptionEditCaption OBJECT-TYPE
		SYNTAX		RollCallString
		MAX-ACCESS		read-write
		STATUS			current
		DESCRIPTION
				"TYPE: - Editstring
				 PAGE: - Backup- Video Backup
					Edit Caption  cmdID= 1040  "
		::= { iqhco30CmdEntry 1040 }


	iqhco30BackupVideoBackupPattern OBJECT-TYPE
		SYNTAX		INTEGER {
							val-Black(1),
							val-Bars(2)
							}
		MAX-ACCESS		read-write
		STATUS			current
		DESCRIPTION
				"TYPE: - RadiobuttonList
				 PAGE: - Backup- Video Backup
					Pattern  cmdID= 2629 
					Black  value= 1  
					Bars  value= 2  "
		::= { iqhco30CmdEntry 2629 }


	iqhco30RulesRulesVideoMasterCurrentOutput OBJECT-TYPE
		SYNTAX		RollCallString
		MAX-ACCESS		read-only
		STATUS			current
		DESCRIPTION
				"TYPE: - Display
				 PAGE: - Rules- Rules Video Master
					Current Output  cmdID= 6630  format=   "
		::= { iqhco30CmdEntry 6630 }


	iqhco30RulesRulesVideoMasterSwitchtoMaster OBJECT-TYPE
		SYNTAX		INTEGER { disable(0), enable(1) }
		MAX-ACCESS		read-write
		STATUS			current
		DESCRIPTION
				"TYPE: - Checkbox
				 PAGE: - Rules- Rules Video Master
					Switch to Master  cmdID= 5600 "
		::= { iqhco30CmdEntry 5600 }


	iqhco30RulesRulesVideoMasterActive OBJECT-TYPE
		SYNTAX		RollCallString
		MAX-ACCESS		read-only
		STATUS			current
		DESCRIPTION
				"TYPE: - Display
				 PAGE: - Rules- Rules Video Master
					Active  cmdID= 5601  format=   "
		::= { iqhco30CmdEntry 5601 }


	iqhco30RulesRulesVideoMaster5602 OBJECT-TYPE
		SYNTAX		INTEGER {
							val-or-OK-Master(1),
							val-and-OK-Master(2),
							val-Don-t-use-Master(5)
							}
		MAX-ACCESS		read-write
		STATUS			current
		DESCRIPTION
				"TYPE: - Button
				 PAGE: - Rules- Rules Video Master
					or:OK Master  cmdID= 5602  value= 1  
					and:OK Master  cmdID= 5602  value= 2  
					Don't use Master  cmdID= 5602  value= 5  "
		::= { iqhco30CmdEntry 5602 }


	iqhco30RulesRulesVideoMaster5603 OBJECT-TYPE
		SYNTAX		INTEGER {
							val-or-FAIL-Backup(3),
							val-Don-t-use-Backup(5)
							}
		MAX-ACCESS		read-write
		STATUS			current
		DESCRIPTION
				"TYPE: - Button
				 PAGE: - Rules- Rules Video Master
					or:FAIL Backup  cmdID= 5603  value= 3  
					Don't use Backup  cmdID= 5603  value= 5  "
		::= { iqhco30CmdEntry 5603 }


	iqhco30RulesRulesVideoMaster5604 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules Video Master
					or:GPI1 High  cmdID= 5604  value= 1  
					or:GPI1 Low  cmdID= 5604  value= 3  
					and:GPI1 High  cmdID= 5604  value= 2  
					and:GPI1 Low  cmdID= 5604  value= 4  
					Don't use GPI1  cmdID= 5604  value= 5  "
		::= { iqhco30CmdEntry 5604 }


	iqhco30RulesRulesVideoMaster5605 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules Video Master
					or:GPI2 High  cmdID= 5605  value= 1  
					or:GPI2 Low  cmdID= 5605  value= 3  
					and:GPI2 High  cmdID= 5605  value= 2  
					and:GPI2 Low  cmdID= 5605  value= 4  
					Don't use GPI2  cmdID= 5605  value= 5  "
		::= { iqhco30CmdEntry 5605 }


	iqhco30RulesRulesVideoMaster5606 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules Video Master
					or:GPI3 High  cmdID= 5606  value= 1  
					or:GPI3 Low  cmdID= 5606  value= 3  
					and:GPI3 High  cmdID= 5606  value= 2  
					and:GPI3 Low  cmdID= 5606  value= 4  
					Don't use GPI3  cmdID= 5606  value= 5  "
		::= { iqhco30CmdEntry 5606 }


	iqhco30RulesRulesVideoMaster5607 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules Video Master
					or:GPI4 High  cmdID= 5607  value= 1  
					or:GPI4 Low  cmdID= 5607  value= 3  
					and:GPI4 High  cmdID= 5607  value= 2  
					and:GPI4 Low  cmdID= 5607  value= 4  
					Don't use GPI4  cmdID= 5607  value= 5  "
		::= { iqhco30CmdEntry 5607 }


	iqhco30RulesRulesVideoMaster5608 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules Video Master
					or:RollTrack101=1  cmdID= 5608  value= 1  
					or:RollTrack101=0  cmdID= 5608  value= 3  
					and:RollTrack101=1  cmdID= 5608  value= 2  
					and:RollTrack101=0  cmdID= 5608  value= 4  
					Don't use 101  cmdID= 5608  value= 5  "
		::= { iqhco30CmdEntry 5608 }


	iqhco30RulesRulesVideoMaster5609 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules Video Master
					or:RollTrack102=1  cmdID= 5609  value= 1  
					or:RollTrack102=0  cmdID= 5609  value= 3  
					and:RollTrack102=1  cmdID= 5609  value= 2  
					and:RollTrack102=0  cmdID= 5609  value= 4  
					Don't use 102  cmdID= 5609  value= 5  "
		::= { iqhco30CmdEntry 5609 }


	iqhco30RulesRulesVideoMaster5610 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules Video Master
					or:RollTrack103=1  cmdID= 5610  value= 1  
					or:RollTrack103=0  cmdID= 5610  value= 3  
					and:RollTrack103=1  cmdID= 5610  value= 2  
					and:RollTrack103=0  cmdID= 5610  value= 4  
					Don't use 103  cmdID= 5610  value= 5  "
		::= { iqhco30CmdEntry 5610 }


	iqhco30RulesRulesVideoMaster5611 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules Video Master
					or:RollTrack104=1  cmdID= 5611  value= 1  
					or:RollTrack104=0  cmdID= 5611  value= 3  
					and:RollTrack104=1  cmdID= 5611  value= 2  
					and:RollTrack104=0  cmdID= 5611  value= 4  
					Don't use 104  cmdID= 5611  value= 5  "
		::= { iqhco30CmdEntry 5611 }


	iqhco30RulesRulesVideoBackupSwitchtoBackup OBJECT-TYPE
		SYNTAX		INTEGER { disable(0), enable(1) }
		MAX-ACCESS		read-write
		STATUS			current
		DESCRIPTION
				"TYPE: - Checkbox
				 PAGE: - Rules- Rules Video Backup
					Switch to Backup  cmdID= 5620 "
		::= { iqhco30CmdEntry 5620 }


	iqhco30RulesRulesVideoBackupActive OBJECT-TYPE
		SYNTAX		RollCallString
		MAX-ACCESS		read-only
		STATUS			current
		DESCRIPTION
				"TYPE: - Display
				 PAGE: - Rules- Rules Video Backup
					Active  cmdID= 5621  format=   "
		::= { iqhco30CmdEntry 5621 }


	iqhco30RulesRulesVideoBackup5622 OBJECT-TYPE
		SYNTAX		INTEGER {
							val-or-FAIL-Master(3),
							val-Don-t-use-Master(5)
							}
		MAX-ACCESS		read-write
		STATUS			current
		DESCRIPTION
				"TYPE: - Button
				 PAGE: - Rules- Rules Video Backup
					or:FAIL Master  cmdID= 5622  value= 3  
					Don't use Master  cmdID= 5622  value= 5  "
		::= { iqhco30CmdEntry 5622 }


	iqhco30RulesRulesVideoBackup5623 OBJECT-TYPE
		SYNTAX		INTEGER {
							val-or-OK-Backup(1),
							val-and-OK-Backup(2),
							val-Don-t-use-Backup(5)
							}
		MAX-ACCESS		read-write
		STATUS			current
		DESCRIPTION
				"TYPE: - Button
				 PAGE: - Rules- Rules Video Backup
					or:OK Backup  cmdID= 5623  value= 1  
					and:OK Backup  cmdID= 5623  value= 2  
					Don't use Backup  cmdID= 5623  value= 5  "
		::= { iqhco30CmdEntry 5623 }


	iqhco30RulesRulesVideoBackup5624 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules Video Backup
					or:GPI1 High  cmdID= 5624  value= 1  
					or:GPI1 Low  cmdID= 5624  value= 3  
					and:GPI1 High  cmdID= 5624  value= 2  
					and:GPI1 Low  cmdID= 5624  value= 4  
					Don't use GPI1  cmdID= 5624  value= 5  "
		::= { iqhco30CmdEntry 5624 }


	iqhco30RulesRulesVideoBackup5625 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules Video Backup
					or:GPI2 High  cmdID= 5625  value= 1  
					or:GPI2 Low  cmdID= 5625  value= 3  
					and:GPI2 High  cmdID= 5625  value= 2  
					and:GPI2 Low  cmdID= 5625  value= 4  
					Don't use GPI2  cmdID= 5625  value= 5  "
		::= { iqhco30CmdEntry 5625 }


	iqhco30RulesRulesVideoBackup5626 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules Video Backup
					or:GPI3 High  cmdID= 5626  value= 1  
					or:GPI3 Low  cmdID= 5626  value= 3  
					and:GPI3 High  cmdID= 5626  value= 2  
					and:GPI3 Low  cmdID= 5626  value= 4  
					Don't use GPI3  cmdID= 5626  value= 5  "
		::= { iqhco30CmdEntry 5626 }


	iqhco30RulesRulesVideoBackup5627 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules Video Backup
					or:GPI4 High  cmdID= 5627  value= 1  
					or:GPI4 Low  cmdID= 5627  value= 3  
					and:GPI4 High  cmdID= 5627  value= 2  
					and:GPI4 Low  cmdID= 5627  value= 4  
					Don't use GPI4  cmdID= 5627  value= 5  "
		::= { iqhco30CmdEntry 5627 }


	iqhco30RulesRulesVideoBackup5628 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules Video Backup
					or:RollTrack101=1  cmdID= 5628  value= 1  
					or:RollTrack101=0  cmdID= 5628  value= 3  
					and:RollTrack101=1  cmdID= 5628  value= 2  
					and:RollTrack101=0  cmdID= 5628  value= 4  
					Don't use 101  cmdID= 5628  value= 5  "
		::= { iqhco30CmdEntry 5628 }


	iqhco30RulesRulesVideoBackup5629 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules Video Backup
					or:RollTrack102=1  cmdID= 5629  value= 1  
					or:RollTrack102=0  cmdID= 5629  value= 3  
					and:RollTrack102=1  cmdID= 5629  value= 2  
					and:RollTrack102=0  cmdID= 5629  value= 4  
					Don't use 102  cmdID= 5629  value= 5  "
		::= { iqhco30CmdEntry 5629 }


	iqhco30RulesRulesVideoBackup5630 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules Video Backup
					or:RollTrack103=1  cmdID= 5630  value= 1  
					or:RollTrack103=0  cmdID= 5630  value= 3  
					and:RollTrack103=1  cmdID= 5630  value= 2  
					and:RollTrack103=0  cmdID= 5630  value= 4  
					Don't use 103  cmdID= 5630  value= 5  "
		::= { iqhco30CmdEntry 5630 }


	iqhco30RulesRulesVideoBackup5631 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules Video Backup
					or:RollTrack104=1  cmdID= 5631  value= 1  
					or:RollTrack104=0  cmdID= 5631  value= 3  
					and:RollTrack104=1  cmdID= 5631  value= 2  
					and:RollTrack104=0  cmdID= 5631  value= 4  
					Don't use 104  cmdID= 5631  value= 5  "
		::= { iqhco30CmdEntry 5631 }


	iqhco30GPIEnableGPIO1GPIO1State OBJECT-TYPE
		SYNTAX		RollCallString
		MAX-ACCESS		read-only
		STATUS			current
		DESCRIPTION
				"TYPE: - Display
				 PAGE: - Rules
					GPIO 1 State  cmdID= 6640  format=   "
		::= { iqhco30CmdEntry 6640 }


	iqhco30GPIEnableGPIO1 OBJECT-TYPE
		SYNTAX		INTEGER {
							val-GPIO-1-Input(1),
							val-GPIO-1-Output(0),
							val-GPIO-1-Unused(2)
							}
		MAX-ACCESS		read-write
		STATUS			current
		DESCRIPTION
				"TYPE: - Button
				 PAGE: - Rules
					GPIO 1 Input  cmdID= 6641  value= 1  
					GPIO 1 Output  cmdID= 6641  value= 0  
					GPIO 1 Unused  cmdID= 6641  value= 2  "
		::= { iqhco30CmdEntry 6641 }


	iqhco30GPIEnableGPIO1GPO1Invert OBJECT-TYPE
		SYNTAX		INTEGER { disable(0), enable(1) }
		MAX-ACCESS		read-write
		STATUS			current
		DESCRIPTION
				"TYPE: - Checkbox
				 PAGE: - Rules
					GPO 1 Invert  cmdID= 7071 "
		::= { iqhco30CmdEntry 7071 }


	iqhco30GPIEnableGPIO2GPIO2State OBJECT-TYPE
		SYNTAX		RollCallString
		MAX-ACCESS		read-only
		STATUS			current
		DESCRIPTION
				"TYPE: - Display
				 PAGE: - Rules
					GPIO 2 State  cmdID= 6642  format=   "
		::= { iqhco30CmdEntry 6642 }


	iqhco30GPIEnableGPIO2 OBJECT-TYPE
		SYNTAX		INTEGER {
							val-GPIO-2-Input(1),
							val-GPIO-2-Output(0),
							val-GPIO-2-Unused(2)
							}
		MAX-ACCESS		read-write
		STATUS			current
		DESCRIPTION
				"TYPE: - Button
				 PAGE: - Rules
					GPIO 2 Input  cmdID= 6643  value= 1  
					GPIO 2 Output  cmdID= 6643  value= 0  
					GPIO 2 Unused  cmdID= 6643  value= 2  "
		::= { iqhco30CmdEntry 6643 }


	iqhco30GPIEnableGPIO2GPO2Invert OBJECT-TYPE
		SYNTAX		INTEGER { disable(0), enable(1) }
		MAX-ACCESS		read-write
		STATUS			current
		DESCRIPTION
				"TYPE: - Checkbox
				 PAGE: - Rules
					GPO 2 Invert  cmdID= 7072 "
		::= { iqhco30CmdEntry 7072 }


	iqhco30GPIEnableGPIO3GPIO3State OBJECT-TYPE
		SYNTAX		RollCallString
		MAX-ACCESS		read-only
		STATUS			current
		DESCRIPTION
				"TYPE: - Display
				 PAGE: - Rules
					GPIO 3 State  cmdID= 6644  format=   "
		::= { iqhco30CmdEntry 6644 }


	iqhco30GPIEnableGPIO3 OBJECT-TYPE
		SYNTAX		INTEGER {
							val-GPIO-3-Input(1),
							val-GPIO-3-Output(0),
							val-GPIO-3-Unused(2)
							}
		MAX-ACCESS		read-write
		STATUS			current
		DESCRIPTION
				"TYPE: - Button
				 PAGE: - Rules
					GPIO 3 Input  cmdID= 6645  value= 1  
					GPIO 3 Output  cmdID= 6645  value= 0  
					GPIO 3 Unused  cmdID= 6645  value= 2  "
		::= { iqhco30CmdEntry 6645 }


	iqhco30GPIEnableGPIO3GPO3Invert OBJECT-TYPE
		SYNTAX		INTEGER { disable(0), enable(1) }
		MAX-ACCESS		read-write
		STATUS			current
		DESCRIPTION
				"TYPE: - Checkbox
				 PAGE: - Rules
					GPO 3 Invert  cmdID= 7073 "
		::= { iqhco30CmdEntry 7073 }


	iqhco30GPIEnableGPIO4GPIO4State OBJECT-TYPE
		SYNTAX		RollCallString
		MAX-ACCESS		read-only
		STATUS			current
		DESCRIPTION
				"TYPE: - Display
				 PAGE: - Rules
					GPIO 4 State  cmdID= 6646  format=   "
		::= { iqhco30CmdEntry 6646 }


	iqhco30GPIEnableGPIO4 OBJECT-TYPE
		SYNTAX		INTEGER {
							val-GPIO-4-Input(1),
							val-GPIO-4-Output(0),
							val-GPIO-4-Unused(2)
							}
		MAX-ACCESS		read-write
		STATUS			current
		DESCRIPTION
				"TYPE: - Button
				 PAGE: - Rules
					GPIO 4 Input  cmdID= 6647  value= 1  
					GPIO 4 Output  cmdID= 6647  value= 0  
					GPIO 4 Unused  cmdID= 6647  value= 2  "
		::= { iqhco30CmdEntry 6647 }


	iqhco30GPIEnableGPIO4GPO4Invert OBJECT-TYPE
		SYNTAX		INTEGER { disable(0), enable(1) }
		MAX-ACCESS		read-write
		STATUS			current
		DESCRIPTION
				"TYPE: - Checkbox
				 PAGE: - Rules
					GPO 4 Invert  cmdID= 7074 "
		::= { iqhco30CmdEntry 7074 }


	iqhco30RulesGPIEnableNoGPIsonRear OBJECT-TYPE
		SYNTAX		RollCallString
		MAX-ACCESS		read-only
		STATUS			current
		DESCRIPTION
				"TYPE: - Display
				 PAGE: - Rules
					No GPI's on Rear  cmdID= 7077  format=   "
		::= { iqhco30CmdEntry 7077 }


	iqhco30RulesRulesGPI1outActive OBJECT-TYPE
		SYNTAX		RollCallString
		MAX-ACCESS		read-only
		STATUS			current
		DESCRIPTION
				"TYPE: - Display
				 PAGE: - Rules- Rules GPI 1 out
					Active  cmdID= 5661  format=   "
		::= { iqhco30CmdEntry 5661 }


	iqhco30RulesRulesGPI1out5672 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 1 out
					or:Master Selected  cmdID= 5672  value= 1  
					or:Backup Selected  cmdID= 5672  value= 2  
					Don't Use  cmdID= 5672  value= 3  "
		::= { iqhco30CmdEntry 5672 }


	iqhco30RulesRulesGPI1out5662 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules GPI 1 out
					or:OK Master  cmdID= 5662  value= 1  
					or:FAIL Master  cmdID= 5662  value= 3  
					and:OK Master  cmdID= 5662  value= 2  
					and:FAIL Master  cmdID= 5662  value= 4  
					Don't use Master  cmdID= 5662  value= 5  "
		::= { iqhco30CmdEntry 5662 }


	iqhco30RulesRulesGPI1out5663 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules GPI 1 out
					or:OK Backup  cmdID= 5663  value= 1  
					or:FAIL Backup  cmdID= 5663  value= 3  
					and:OK Backup  cmdID= 5663  value= 2  
					and:FAIL Backup  cmdID= 5663  value= 4  
					Don't use Backup  cmdID= 5663  value= 5  "
		::= { iqhco30CmdEntry 5663 }


	iqhco30RulesRulesGPI1out5664 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 1 out
					or:GPI1 High  cmdID= 5664  value= 1  
					or:GPI1 Low  cmdID= 5664  value= 3  
					and:GPI1 High  cmdID= 5664  value= 2  
					and:GPI1 Low  cmdID= 5664  value= 4  
					Don't use GPI1  cmdID= 5664  value= 5  "
		::= { iqhco30CmdEntry 5664 }


	iqhco30RulesRulesGPI1out5665 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 1 out
					or:GPI2 High  cmdID= 5665  value= 1  
					or:GPI2 Low  cmdID= 5665  value= 3  
					and:GPI2 High  cmdID= 5665  value= 2  
					and:GPI2 Low  cmdID= 5665  value= 4  
					Don't use GPI2  cmdID= 5665  value= 5  "
		::= { iqhco30CmdEntry 5665 }


	iqhco30RulesRulesGPI1out5666 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 1 out
					or:GPI3 High  cmdID= 5666  value= 1  
					or:GPI3 Low  cmdID= 5666  value= 3  
					and:GPI3 High  cmdID= 5666  value= 2  
					and:GPI3 Low  cmdID= 5666  value= 4  
					Don't use GPI3  cmdID= 5666  value= 5  "
		::= { iqhco30CmdEntry 5666 }


	iqhco30RulesRulesGPI1out5667 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 1 out
					or:GPI4 High  cmdID= 5667  value= 1  
					or:GPI4 Low  cmdID= 5667  value= 3  
					and:GPI4 High  cmdID= 5667  value= 2  
					and:GPI4 Low  cmdID= 5667  value= 4  
					Don't use GPI4  cmdID= 5667  value= 5  "
		::= { iqhco30CmdEntry 5667 }


	iqhco30RulesRulesGPI1out5668 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 1 out
					or:RollTrack101=1  cmdID= 5668  value= 1  
					or:RollTrack101=0  cmdID= 5668  value= 3  
					and:RollTrack101=1  cmdID= 5668  value= 2  
					and:RollTrack101=0  cmdID= 5668  value= 4  
					Don't use 101  cmdID= 5668  value= 5  "
		::= { iqhco30CmdEntry 5668 }


	iqhco30RulesRulesGPI1out5669 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules GPI 1 out
					or:RollTrack102=1  cmdID= 5669  value= 1  
					or:RollTrack102=0  cmdID= 5669  value= 3  
					and:RollTrack102=1  cmdID= 5669  value= 2  
					and:RollTrack102=0  cmdID= 5669  value= 4  
					Don't use 102  cmdID= 5669  value= 5  "
		::= { iqhco30CmdEntry 5669 }


	iqhco30RulesRulesGPI1out5670 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 1 out
					or:RollTrack103=1  cmdID= 5670  value= 1  
					or:RollTrack103=0  cmdID= 5670  value= 3  
					and:RollTrack103=1  cmdID= 5670  value= 2  
					and:RollTrack103=0  cmdID= 5670  value= 4  
					Don't use 103  cmdID= 5670  value= 5  "
		::= { iqhco30CmdEntry 5670 }


	iqhco30RulesRulesGPI1out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 1 out
					or:RollTrack104=1  cmdID= 5671  value= 1  
					or:RollTrack104=0  cmdID= 5671  value= 3  
					and:RollTrack104=1  cmdID= 5671  value= 2  
					and:RollTrack104=0  cmdID= 5671  value= 4  
					Don't use 104  cmdID= 5671  value= 5  "
		::= { iqhco30CmdEntry 5671 }


	iqhco30RulesRulesGPI2outActive OBJECT-TYPE
		SYNTAX		RollCallString
		MAX-ACCESS		read-only
		STATUS			current
		DESCRIPTION
				"TYPE: - Display
				 PAGE: - Rules- Rules GPI 2 out
					Active  cmdID= 5681  format=   "
		::= { iqhco30CmdEntry 5681 }


	iqhco30RulesRulesGPI2out5692 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 2 out
					or:Master Selected  cmdID= 5692  value= 1  
					or:Backup Selected  cmdID= 5692  value= 2  
					Don't Use  cmdID= 5692  value= 3  "
		::= { iqhco30CmdEntry 5692 }


	iqhco30RulesRulesGPI2out5682 OBJECT-TYPE
		SYNTAX		INTEGER {
							val-or-OK-Master(1),
							val-or-FAIL-Master(3),
							val-and-OK-Master(2),
							val-and-FAIL-Master(4),
							val-Don-t-use(5)
							}
		MAX-ACCESS		read-write
		STATUS			current
		DESCRIPTION
				"TYPE: - Button
				 PAGE: - Rules- Rules GPI 2 out
					or:OK Master  cmdID= 5682  value= 1  
					or:FAIL Master  cmdID= 5682  value= 3  
					and:OK Master  cmdID= 5682  value= 2  
					and:FAIL Master  cmdID= 5682  value= 4  
					Don't use  cmdID= 5682  value= 5  "
		::= { iqhco30CmdEntry 5682 }


	iqhco30RulesRulesGPI2out5683 OBJECT-TYPE
		SYNTAX		INTEGER {
							val-or-OK-Backup(1),
							val-or-FAIL-Backup(3),
							val-and-OK-Backup(2),
							val-and-FAIL-Backup(4),
							val-Don-t-use(5)
							}
		MAX-ACCESS		read-write
		STATUS			current
		DESCRIPTION
				"TYPE: - Button
				 PAGE: - Rules- Rules GPI 2 out
					or:OK Backup  cmdID= 5683  value= 1  
					or:FAIL Backup  cmdID= 5683  value= 3  
					and:OK Backup  cmdID= 5683  value= 2  
					and:FAIL Backup  cmdID= 5683  value= 4  
					Don't use  cmdID= 5683  value= 5  "
		::= { iqhco30CmdEntry 5683 }


	iqhco30RulesRulesGPI2out5684 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 2 out
					or:GPI1 High  cmdID= 5684  value= 1  
					or:GPI1 Low  cmdID= 5684  value= 3  
					and:GPI1 High  cmdID= 5684  value= 2  
					and:GPI1 Low  cmdID= 5684  value= 4  
					Don't use GPI1  cmdID= 5684  value= 5  "
		::= { iqhco30CmdEntry 5684 }


	iqhco30RulesRulesGPI2out5685 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 2 out
					or:GPI2 High  cmdID= 5685  value= 1  
					or:GPI2 Low  cmdID= 5685  value= 3  
					and:GPI2 High  cmdID= 5685  value= 2  
					and:GPI2 Low  cmdID= 5685  value= 4  
					Don't use GPI2  cmdID= 5685  value= 5  "
		::= { iqhco30CmdEntry 5685 }


	iqhco30RulesRulesGPI2out5686 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 2 out
					or:GPI3 High  cmdID= 5686  value= 1  
					or:GPI3 Low  cmdID= 5686  value= 3  
					and:GPI3 High  cmdID= 5686  value= 2  
					and:GPI3 Low  cmdID= 5686  value= 4  
					Don't use GPI3  cmdID= 5686  value= 5  "
		::= { iqhco30CmdEntry 5686 }


	iqhco30RulesRulesGPI2out5687 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 2 out
					or:GPI4 High  cmdID= 5687  value= 1  
					or:GPI4 Low  cmdID= 5687  value= 3  
					and:GPI4 High  cmdID= 5687  value= 2  
					and:GPI4 Low  cmdID= 5687  value= 4  
					Don't use GPI4  cmdID= 5687  value= 5  "
		::= { iqhco30CmdEntry 5687 }


	iqhco30RulesRulesGPI2out5688 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 2 out
					or:RollTrack101=1  cmdID= 5688  value= 1  
					or:RollTrack101=0  cmdID= 5688  value= 3  
					and:RollTrack101=1  cmdID= 5688  value= 2  
					and:RollTrack101=0  cmdID= 5688  value= 4  
					Don't use 101  cmdID= 5688  value= 5  "
		::= { iqhco30CmdEntry 5688 }


	iqhco30RulesRulesGPI2out5689 OBJECT-TYPE
		SYNTAX		INTEGER {
							val-or-RollTrack102-1(1),
							val-or-RollTrack102-0(3),
							val-and-RollTrack102-1(2),
							val-and-RollTrack102-0(4),
							val-Don-t-use-102(5)
							}
		MAX-ACCESS		read-write
		STATUS			current
		DESCRIPTION
				"TYPE: - Button
				 PAGE: - Rules- Rules GPI 2 out
					or:RollTrack102=1  cmdID= 5689  value= 1  
					or:RollTrack102=0  cmdID= 5689  value= 3  
					and:RollTrack102=1  cmdID= 5689  value= 2  
					and:RollTrack102=0  cmdID= 5689  value= 4  
					Don't use 102  cmdID= 5689  value= 5  "
		::= { iqhco30CmdEntry 5689 }


	iqhco30RulesRulesGPI2out5690 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 2 out
					or:RollTrack103=1  cmdID= 5690  value= 1  
					or:RollTrack103=0  cmdID= 5690  value= 3  
					and:RollTrack103=1  cmdID= 5690  value= 2  
					and:RollTrack103=0  cmdID= 5690  value= 4  
					Don't use 103  cmdID= 5690  value= 5  "
		::= { iqhco30CmdEntry 5690 }


	iqhco30RulesRulesGPI2out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 2 out
					or:RollTrack104=1  cmdID= 5691  value= 1  
					or:RollTrack104=0  cmdID= 5691  value= 3  
					and:RollTrack104=1  cmdID= 5691  value= 2  
					and:RollTrack104=0  cmdID= 5691  value= 4  
					Don't use 104  cmdID= 5691  value= 5  "
		::= { iqhco30CmdEntry 5691 }


	iqhco30RulesRulesGPI3outActive OBJECT-TYPE
		SYNTAX		RollCallString
		MAX-ACCESS		read-only
		STATUS			current
		DESCRIPTION
				"TYPE: - Display
				 PAGE: - Rules- Rules GPI 3 out
					Active  cmdID= 5701  format=   "
		::= { iqhco30CmdEntry 5701 }


	iqhco30RulesRulesGPI3out5712 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 3 out
					or:Master Selected  cmdID= 5712  value= 1  
					or:Backup Selected  cmdID= 5712  value= 2  
					Don't Use  cmdID= 5712  value= 3  "
		::= { iqhco30CmdEntry 5712 }


	iqhco30RulesRulesGPI3out5702 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules GPI 3 out
					or:OK Master  cmdID= 5702  value= 1  
					or:FAIL Master  cmdID= 5702  value= 3  
					and:OK Master  cmdID= 5702  value= 2  
					and:FAIL Master  cmdID= 5702  value= 4  
					Don't use Master  cmdID= 5702  value= 5  "
		::= { iqhco30CmdEntry 5702 }


	iqhco30RulesRulesGPI3out5703 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules GPI 3 out
					or:OK Backup  cmdID= 5703  value= 1  
					or:FAIL Backup  cmdID= 5703  value= 3  
					and:OK Backup  cmdID= 5703  value= 2  
					and:FAIL Backup  cmdID= 5703  value= 4  
					Don't use Backup  cmdID= 5703  value= 5  "
		::= { iqhco30CmdEntry 5703 }


	iqhco30RulesRulesGPI3out5704 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 3 out
					or:GPI1 High  cmdID= 5704  value= 1  
					or:GPI1 Low  cmdID= 5704  value= 3  
					and:GPI1 High  cmdID= 5704  value= 2  
					and:GPI1 Low  cmdID= 5704  value= 4  
					Don't use GPI1  cmdID= 5704  value= 5  "
		::= { iqhco30CmdEntry 5704 }


	iqhco30RulesRulesGPI3out5705 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 3 out
					or:GPI2 High  cmdID= 5705  value= 1  
					or:GPI2 Low  cmdID= 5705  value= 3  
					and:GPI2 High  cmdID= 5705  value= 2  
					and:GPI2 Low  cmdID= 5705  value= 4  
					Don't use GPI2  cmdID= 5705  value= 5  "
		::= { iqhco30CmdEntry 5705 }


	iqhco30RulesRulesGPI3out5706 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 3 out
					or:GPI3 High  cmdID= 5706  value= 1  
					or:GPI3 Low  cmdID= 5706  value= 3  
					and:GPI3 High  cmdID= 5706  value= 2  
					and:GPI3 Low  cmdID= 5706  value= 4  
					Don't use GPI3  cmdID= 5706  value= 5  "
		::= { iqhco30CmdEntry 5706 }


	iqhco30RulesRulesGPI3out5707 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 3 out
					or:GPI4 High  cmdID= 5707  value= 1  
					or:GPI4 Low  cmdID= 5707  value= 3  
					and:GPI4 High  cmdID= 5707  value= 2  
					and:GPI4 Low  cmdID= 5707  value= 4  
					Don't use GPI4  cmdID= 5707  value= 5  "
		::= { iqhco30CmdEntry 5707 }


	iqhco30RulesRulesGPI3out5708 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 3 out
					or:RollTrack101=1  cmdID= 5708  value= 1  
					or:RollTrack101=0  cmdID= 5708  value= 3  
					and:RollTrack101=1  cmdID= 5708  value= 2  
					and:RollTrack101=0  cmdID= 5708  value= 4  
					Don't use 101  cmdID= 5708  value= 5  "
		::= { iqhco30CmdEntry 5708 }


	iqhco30RulesRulesGPI3out5709 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules GPI 3 out
					or:RollTrack102=1  cmdID= 5709  value= 1  
					or:RollTrack102=0  cmdID= 5709  value= 3  
					and:RollTrack101=1  cmdID= 5709  value= 2  
					and:RollTrack102=0  cmdID= 5709  value= 4  
					Don't use 102  cmdID= 5709  value= 5  "
		::= { iqhco30CmdEntry 5709 }


	iqhco30RulesRulesGPI3out5710 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 3 out
					or:RollTrack103=1  cmdID= 5710  value= 1  
					or:RollTrack103=0  cmdID= 5710  value= 3  
					and:RollTrack103=1  cmdID= 5710  value= 2  
					and:RollTrack103=0  cmdID= 5710  value= 4  
					Don't use 103  cmdID= 5710  value= 5  "
		::= { iqhco30CmdEntry 5710 }


	iqhco30RulesRulesGPI3out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 3 out
					or:RollTrack104=1  cmdID= 5711  value= 1  
					or:RollTrack104=0  cmdID= 5711  value= 3  
					and:RollTrack104=1  cmdID= 5711  value= 2  
					and:RollTrack104=0  cmdID= 5711  value= 4  
					Don't use 104  cmdID= 5711  value= 5  "
		::= { iqhco30CmdEntry 5711 }


	iqhco30RulesRulesGPI4outActive OBJECT-TYPE
		SYNTAX		RollCallString
		MAX-ACCESS		read-only
		STATUS			current
		DESCRIPTION
				"TYPE: - Display
				 PAGE: - Rules- Rules GPI 4 out
					Active  cmdID= 5721  format=   "
		::= { iqhco30CmdEntry 5721 }


	iqhco30RulesRulesGPI4out5732 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules GPI 4 out
					or:Master Selected  cmdID= 5732  value= 1  
					or:Backup Selected  cmdID= 5732  value= 2  
					Don't Use  cmdID= 5732  value= 3  "
		::= { iqhco30CmdEntry 5732 }


	iqhco30RulesRulesGPI4out5722 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules GPI 4 out
					or:OK Master  cmdID= 5722  value= 1  
					or:FAIL Master  cmdID= 5722  value= 3  
					and:OK Master  cmdID= 5722  value= 2  
					and:FAIL Master  cmdID= 5722  value= 4  
					Don't use Master  cmdID= 5722  value= 5  "
		::= { iqhco30CmdEntry 5722 }


	iqhco30RulesRulesGPI4out5723 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules GPI 4 out
					or:OK Backup  cmdID= 5723  value= 1  
					or:FAIL Backup  cmdID= 5723  value= 3  
					and:OK Backup  cmdID= 5723  value= 2  
					and:FAIL Backup  cmdID= 5723  value= 4  
					Don't use Backup  cmdID= 5723  value= 5  "
		::= { iqhco30CmdEntry 5723 }


	iqhco30RulesRulesGPI4out5724 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules GPI 4 out
					or:GPI1 High  cmdID= 5724  value= 1  
					or:GPI1 Low  cmdID= 5724  value= 3  
					and:GPI1 High  cmdID= 5724  value= 2  
					and:GPI1 Low  cmdID= 5724  value= 4  
					Don't use GPI1  cmdID= 5724  value= 5  "
		::= { iqhco30CmdEntry 5724 }


	iqhco30RulesRulesGPI4out5725 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules GPI 4 out
					or:GPI2 High  cmdID= 5725  value= 1  
					or:GPI2 Low  cmdID= 5725  value= 3  
					and:GPI2 High  cmdID= 5725  value= 2  
					and:GPI2 Low  cmdID= 5725  value= 4  
					Don't use GPI2  cmdID= 5725  value= 5  "
		::= { iqhco30CmdEntry 5725 }


	iqhco30RulesRulesGPI4out5726 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules GPI 4 out
					or:GPI3 High  cmdID= 5726  value= 1  
					or:GPI3 Low  cmdID= 5726  value= 3  
					and:GPI3 High  cmdID= 5726  value= 2  
					and:GPI3 Low  cmdID= 5726  value= 4  
					Don't use GPI3  cmdID= 5726  value= 5  "
		::= { iqhco30CmdEntry 5726 }


	iqhco30RulesRulesGPI4out5727 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules GPI 4 out
					or:GPI4 High  cmdID= 5727  value= 1  
					or:GPI4 Low  cmdID= 5727  value= 3  
					and:GPI4 High  cmdID= 5727  value= 2  
					and:GPI4 Low  cmdID= 5727  value= 4  
					Don't use GPI4  cmdID= 5727  value= 5  "
		::= { iqhco30CmdEntry 5727 }


	iqhco30RulesRulesGPI4out5728 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules GPI 4 out
					or:RollTrack101=1  cmdID= 5728  value= 1  
					or:RollTrack101=0  cmdID= 5728  value= 3  
					and:RollTrack101=1  cmdID= 5728  value= 2  
					and:RollTrack101=0  cmdID= 5728  value= 4  
					Don't use 101  cmdID= 5728  value= 5  "
		::= { iqhco30CmdEntry 5728 }


	iqhco30RulesRulesGPI4out5729 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules GPI 4 out
					or:RollTrack102=1  cmdID= 5729  value= 1  
					or:RollTrack102=0  cmdID= 5729  value= 3  
					and:RollTrack101=1  cmdID= 5729  value= 2  
					and:RollTrack102=0  cmdID= 5729  value= 4  
					Don't use 102  cmdID= 5729  value= 5  "
		::= { iqhco30CmdEntry 5729 }


	iqhco30RulesRulesGPI4out5730 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules GPI 4 out
					or:RollTrack103=1  cmdID= 5730  value= 1  
					or:RollTrack103=0  cmdID= 5730  value= 3  
					and:RollTrack103=1  cmdID= 5730  value= 2  
					and:RollTrack103=0  cmdID= 5730  value= 4  
					Don't use 103  cmdID= 5730  value= 5  "
		::= { iqhco30CmdEntry 5730 }


	iqhco30RulesRulesGPI4out OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules GPI 4 out
					or:RollTrack104=1  cmdID= 5731  value= 1  
					or:RollTrack104=0  cmdID= 5731  value= 3  
					and:RollTrack104=1  cmdID= 5731  value= 2  
					and:RollTrack104=0  cmdID= 5731  value= 4  
					Don't use 104  cmdID= 5731  value= 5  "
		::= { iqhco30CmdEntry 5731 }


	iqhco30RulesRollTrackEnableEnable6649 OBJECT-TYPE
		SYNTAX		INTEGER { disable(0), enable(1) }
		MAX-ACCESS		read-write
		STATUS			current
		DESCRIPTION
				"TYPE: - Checkbox
				 PAGE: - Rules
					Enable  cmdID= 6649 "
		::= { iqhco30CmdEntry 6649 }


	iqhco30RulesRollTrackEnableEnable6651 OBJECT-TYPE
		SYNTAX		INTEGER { disable(0), enable(1) }
		MAX-ACCESS		read-write
		STATUS			current
		DESCRIPTION
				"TYPE: - Checkbox
				 PAGE: - Rules
					Enable  cmdID= 6651 "
		::= { iqhco30CmdEntry 6651 }


	iqhco30RulesRollTrackEnableEnable6653 OBJECT-TYPE
		SYNTAX		INTEGER { disable(0), enable(1) }
		MAX-ACCESS		read-write
		STATUS			current
		DESCRIPTION
				"TYPE: - Checkbox
				 PAGE: - Rules
					Enable  cmdID= 6653 "
		::= { iqhco30CmdEntry 6653 }


	iqhco30RulesRollTrackEnableEnable6655 OBJECT-TYPE
		SYNTAX		INTEGER { disable(0), enable(1) }
		MAX-ACCESS		read-write
		STATUS			current
		DESCRIPTION
				"TYPE: - Checkbox
				 PAGE: - Rules
					Enable  cmdID= 6655 "
		::= { iqhco30CmdEntry 6655 }


	iqhco30RulesRollTrackEnableState6648 OBJECT-TYPE
		SYNTAX		RollCallString
		MAX-ACCESS		read-only
		STATUS			current
		DESCRIPTION
				"TYPE: - Display
				 PAGE: - Rules
					State  cmdID= 6648  format=   "
		::= { iqhco30CmdEntry 6648 }


	iqhco30RulesRollTrackEnableState6650 OBJECT-TYPE
		SYNTAX		RollCallString
		MAX-ACCESS		read-only
		STATUS			current
		DESCRIPTION
				"TYPE: - Display
				 PAGE: - Rules
					State  cmdID= 6650  format=   "
		::= { iqhco30CmdEntry 6650 }


	iqhco30RulesRollTrackEnableState6652 OBJECT-TYPE
		SYNTAX		RollCallString
		MAX-ACCESS		read-only
		STATUS			current
		DESCRIPTION
				"TYPE: - Display
				 PAGE: - Rules
					State  cmdID= 6652  format=   "
		::= { iqhco30CmdEntry 6652 }


	iqhco30RulesRollTrackEnableState6654 OBJECT-TYPE
		SYNTAX		RollCallString
		MAX-ACCESS		read-only
		STATUS			current
		DESCRIPTION
				"TYPE: - Display
				 PAGE: - Rules
					State  cmdID= 6654  format=   "
		::= { iqhco30CmdEntry 6654 }


	iqhco30RulesRulesRollTack101Active OBJECT-TYPE
		SYNTAX		RollCallString
		MAX-ACCESS		read-only
		STATUS			current
		DESCRIPTION
				"TYPE: - Display
				 PAGE: - Rules- Rules RollTack 101
					Active  cmdID= 5741  format=   "
		::= { iqhco30CmdEntry 5741 }


	iqhco30RulesRulesRollTack1015752 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 101
					or:Master Selected  cmdID= 5752  value= 1  
					or:Backup Selected  cmdID= 5752  value= 2  
					Don't Use  cmdID= 5752  value= 3  "
		::= { iqhco30CmdEntry 5752 }


	iqhco30RulesRulesRollTack1015742 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 101
					or:OK Master  cmdID= 5742  value= 1  
					or:FAIL Master  cmdID= 5742  value= 3  
					and:OK Master  cmdID= 5742  value= 2  
					and:FAIL Master  cmdID= 5742  value= 4  
					Don't use Master  cmdID= 5742  value= 5  "
		::= { iqhco30CmdEntry 5742 }


	iqhco30RulesRulesRollTack1015743 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 101
					or:OK Backup  cmdID= 5743  value= 1  
					or:FAIL Backup  cmdID= 5743  value= 3  
					and:OK Backup  cmdID= 5743  value= 2  
					and:FAIL Backup  cmdID= 5743  value= 4  
					Don't use Backup  cmdID= 5743  value= 5  "
		::= { iqhco30CmdEntry 5743 }


	iqhco30RulesRulesRollTack1015744 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 101
					or:GPI1 High  cmdID= 5744  value= 1  
					or:GPI1 Low  cmdID= 5744  value= 3  
					and:GPI1 High  cmdID= 5744  value= 2  
					and:GPI1 Low  cmdID= 5744  value= 4  
					Don't use GPI1  cmdID= 5744  value= 5  "
		::= { iqhco30CmdEntry 5744 }


	iqhco30RulesRulesRollTack1015745 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 101
					or:GPI2 High  cmdID= 5745  value= 1  
					or:GPI2 Low  cmdID= 5745  value= 3  
					and:GPI2 High  cmdID= 5745  value= 2  
					and:GPI2 Low  cmdID= 5745  value= 4  
					Don't use GPI2  cmdID= 5745  value= 5  "
		::= { iqhco30CmdEntry 5745 }


	iqhco30RulesRulesRollTack1015746 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 101
					or:GPI3 High  cmdID= 5746  value= 1  
					or:GPI3 Low  cmdID= 5746  value= 3  
					and:GPI3 High  cmdID= 5746  value= 2  
					and:GPI3 Low  cmdID= 5746  value= 4  
					Don't use GPI3  cmdID= 5746  value= 5  "
		::= { iqhco30CmdEntry 5746 }


	iqhco30RulesRulesRollTack1015747 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 101
					or:GPI4 High  cmdID= 5747  value= 1  
					or:GPI4 Low  cmdID= 5747  value= 3  
					and:GPI4 High  cmdID= 5747  value= 2  
					and:GPI4 Low  cmdID= 5747  value= 4  
					Don't use GPI4  cmdID= 5747  value= 5  "
		::= { iqhco30CmdEntry 5747 }


	iqhco30RulesRulesRollTack1015748 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 101
					or:RollTrack101=1  cmdID= 5748  value= 1  
					or:RollTrack101=0  cmdID= 5748  value= 3  
					and:RollTrack101=1  cmdID= 5748  value= 2  
					and:RollTrack101=0  cmdID= 5748  value= 4  
					Don't use 101  cmdID= 5748  value= 5  "
		::= { iqhco30CmdEntry 5748 }


	iqhco30RulesRulesRollTack1015749 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 101
					or:RollTrack102=1  cmdID= 5749  value= 1  
					or:RollTrack102=0  cmdID= 5749  value= 3  
					and:RollTrack101=1  cmdID= 5749  value= 2  
					and:RollTrack102=0  cmdID= 5749  value= 4  
					Don't use 102  cmdID= 5749  value= 5  "
		::= { iqhco30CmdEntry 5749 }


	iqhco30RulesRulesRollTack1015750 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 101
					or:RollTrack103=1  cmdID= 5750  value= 1  
					or:RollTrack103=0  cmdID= 5750  value= 3  
					and:RollTrack103=1  cmdID= 5750  value= 2  
					and:RollTrack103=0  cmdID= 5750  value= 4  
					Don't use 103  cmdID= 5750  value= 5  "
		::= { iqhco30CmdEntry 5750 }


	iqhco30RulesRulesRollTack101 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 101
					or:RollTrack104=1  cmdID= 5751  value= 1  
					or:RollTrack104=0  cmdID= 5751  value= 3  
					and:RollTrack104=1  cmdID= 5751  value= 2  
					and:RollTrack104=0  cmdID= 5751  value= 4  
					Don't use 104  cmdID= 5751  value= 5  "
		::= { iqhco30CmdEntry 5751 }


	iqhco30RulesRulesRollTack102Active OBJECT-TYPE
		SYNTAX		RollCallString
		MAX-ACCESS		read-only
		STATUS			current
		DESCRIPTION
				"TYPE: - Display
				 PAGE: - Rules- Rules RollTack 102
					Active  cmdID= 5761  format=   "
		::= { iqhco30CmdEntry 5761 }


	iqhco30RulesRulesRollTack1025772 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 102
					or:Master Selected  cmdID= 5772  value= 1  
					or:Backup Selected  cmdID= 5772  value= 2  
					Don't Use  cmdID= 5772  value= 3  "
		::= { iqhco30CmdEntry 5772 }


	iqhco30RulesRulesRollTack1025762 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 102
					or:OK Master  cmdID= 5762  value= 1  
					or:FAIL Master  cmdID= 5762  value= 3  
					and:OK Master  cmdID= 5762  value= 2  
					and:FAIL Master  cmdID= 5762  value= 4  
					Don't use Master  cmdID= 5762  value= 5  "
		::= { iqhco30CmdEntry 5762 }


	iqhco30RulesRulesRollTack1025763 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 102
					or:OK Backup  cmdID= 5763  value= 1  
					or:FAIL Backup  cmdID= 5763  value= 3  
					and:OK Backup  cmdID= 5763  value= 2  
					and:FAIL Backup  cmdID= 5763  value= 4  
					Don't use Backup  cmdID= 5763  value= 5  "
		::= { iqhco30CmdEntry 5763 }


	iqhco30RulesRulesRollTack1025764 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 102
					or:GPI1 High  cmdID= 5764  value= 1  
					or:GPI1 Low  cmdID= 5764  value= 3  
					and:GPI1 High  cmdID= 5764  value= 2  
					and:GPI1 Low  cmdID= 5764  value= 4  
					Don't use GPI1  cmdID= 5764  value= 5  "
		::= { iqhco30CmdEntry 5764 }


	iqhco30RulesRulesRollTack1025765 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 102
					or:GPI2 High  cmdID= 5765  value= 1  
					or:GPI2 Low  cmdID= 5765  value= 3  
					and:GPI2 High  cmdID= 5765  value= 2  
					and:GPI2 Low  cmdID= 5765  value= 4  
					Don't use GPI2  cmdID= 5765  value= 5  "
		::= { iqhco30CmdEntry 5765 }


	iqhco30RulesRulesRollTack1025766 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 102
					or:GPI3 High  cmdID= 5766  value= 1  
					or:GPI3 Low  cmdID= 5766  value= 3  
					and:GPI3 High  cmdID= 5766  value= 2  
					and:GPI3 Low  cmdID= 5766  value= 4  
					Don't use GPI3  cmdID= 5766  value= 5  "
		::= { iqhco30CmdEntry 5766 }


	iqhco30RulesRulesRollTack1025767 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 102
					or:GPI4 High  cmdID= 5767  value= 1  
					or:GPI4 Low  cmdID= 5767  value= 3  
					and:GPI4 High  cmdID= 5767  value= 2  
					and:GPI4 Low  cmdID= 5767  value= 4  
					Don't use GPI4  cmdID= 5767  value= 5  "
		::= { iqhco30CmdEntry 5767 }


	iqhco30RulesRulesRollTack1025768 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 102
					or:RollTrack101=1  cmdID= 5768  value= 1  
					or:RollTrack101=0  cmdID= 5768  value= 3  
					and:RollTrack101=1  cmdID= 5768  value= 2  
					and:RollTrack101=0  cmdID= 5768  value= 4  
					Don't use 101  cmdID= 5768  value= 5  "
		::= { iqhco30CmdEntry 5768 }


	iqhco30RulesRulesRollTack1025769 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 102
					or:RollTrack102=1  cmdID= 5769  value= 1  
					or:RollTrack102=0  cmdID= 5769  value= 3  
					and:RollTrack101=1  cmdID= 5769  value= 2  
					and:RollTrack102=0  cmdID= 5769  value= 4  
					Don't use 102  cmdID= 5769  value= 5  "
		::= { iqhco30CmdEntry 5769 }


	iqhco30RulesRulesRollTack1025770 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 102
					or:RollTrack103=1  cmdID= 5770  value= 1  
					or:RollTrack103=0  cmdID= 5770  value= 3  
					and:RollTrack103=1  cmdID= 5770  value= 2  
					and:RollTrack103=0  cmdID= 5770  value= 4  
					Don't use 103  cmdID= 5770  value= 5  "
		::= { iqhco30CmdEntry 5770 }


	iqhco30RulesRulesRollTack102 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 102
					or:RollTrack104=1  cmdID= 5771  value= 1  
					or:RollTrack104=0  cmdID= 5771  value= 3  
					and:RollTrack104=1  cmdID= 5771  value= 2  
					and:RollTrack104=0  cmdID= 5771  value= 4  
					Don't use 104  cmdID= 5771  value= 5  "
		::= { iqhco30CmdEntry 5771 }


	iqhco30RulesRulesRollTack103Active OBJECT-TYPE
		SYNTAX		RollCallString
		MAX-ACCESS		read-only
		STATUS			current
		DESCRIPTION
				"TYPE: - Display
				 PAGE: - Rules- Rules RollTack 103
					Active  cmdID= 5781  format=   "
		::= { iqhco30CmdEntry 5781 }


	iqhco30RulesRulesRollTack1035792 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 103
					or:Master Selected  cmdID= 5792  value= 1  
					or:Backup Selected  cmdID= 5792  value= 2  
					Don't Use  cmdID= 5792  value= 3  "
		::= { iqhco30CmdEntry 5792 }


	iqhco30RulesRulesRollTack1035782 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 103
					or:OK Master  cmdID= 5782  value= 1  
					or:FAIL Master  cmdID= 5782  value= 3  
					and:OK Master  cmdID= 5782  value= 2  
					and:FAIL Master  cmdID= 5782  value= 4  
					Don't use Master  cmdID= 5782  value= 5  "
		::= { iqhco30CmdEntry 5782 }


	iqhco30RulesRulesRollTack1035783 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 103
					or:OK Backup  cmdID= 5783  value= 1  
					or:FAIL Backup  cmdID= 5783  value= 3  
					and:OK Backup  cmdID= 5783  value= 2  
					and:FAIL Backup  cmdID= 5783  value= 4  
					Don't use Backup  cmdID= 5783  value= 5  "
		::= { iqhco30CmdEntry 5783 }


	iqhco30RulesRulesRollTack1035784 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 103
					or:GPI1 High  cmdID= 5784  value= 1  
					or:GPI1 Low  cmdID= 5784  value= 3  
					and:GPI1 High  cmdID= 5784  value= 2  
					and:GPI1 Low  cmdID= 5784  value= 4  
					Don't use GPI1  cmdID= 5784  value= 5  "
		::= { iqhco30CmdEntry 5784 }


	iqhco30RulesRulesRollTack1035785 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 103
					or:GPI2 High  cmdID= 5785  value= 1  
					or:GPI2 Low  cmdID= 5785  value= 3  
					and:GPI2 High  cmdID= 5785  value= 2  
					and:GPI2 Low  cmdID= 5785  value= 4  
					Don't use GPI2  cmdID= 5785  value= 5  "
		::= { iqhco30CmdEntry 5785 }


	iqhco30RulesRulesRollTack1035786 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 103
					or:GPI3 High  cmdID= 5786  value= 1  
					or:GPI3 Low  cmdID= 5786  value= 3  
					and:GPI3 High  cmdID= 5786  value= 2  
					and:GPI3 Low  cmdID= 5786  value= 4  
					Don't use GPI3  cmdID= 5786  value= 5  "
		::= { iqhco30CmdEntry 5786 }


	iqhco30RulesRulesRollTack1035787 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 103
					or:GPI4 High  cmdID= 5787  value= 1  
					or:GPI4 Low  cmdID= 5787  value= 3  
					and:GPI4 High  cmdID= 5787  value= 2  
					and:GPI4 Low  cmdID= 5787  value= 4  
					Don't use GPI4  cmdID= 5787  value= 5  "
		::= { iqhco30CmdEntry 5787 }


	iqhco30RulesRulesRollTack1035788 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 103
					or:RollTrack101=1  cmdID= 5788  value= 1  
					or:RollTrack101=0  cmdID= 5788  value= 3  
					and:RollTrack101=1  cmdID= 5788  value= 2  
					and:RollTrack101=0  cmdID= 5788  value= 4  
					Don't use 101  cmdID= 5788  value= 5  "
		::= { iqhco30CmdEntry 5788 }


	iqhco30RulesRulesRollTack1035789 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 103
					or:RollTrack102=1  cmdID= 5789  value= 1  
					or:RollTrack102=0  cmdID= 5789  value= 3  
					and:RollTrack101=1  cmdID= 5789  value= 2  
					and:RollTrack102=0  cmdID= 5789  value= 4  
					Don't use 102  cmdID= 5789  value= 5  "
		::= { iqhco30CmdEntry 5789 }


	iqhco30RulesRulesRollTack1035790 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 103
					or:RollTrack103=1  cmdID= 5790  value= 1  
					or:RollTrack103=0  cmdID= 5790  value= 3  
					and:RollTrack103=1  cmdID= 5790  value= 2  
					and:RollTrack103=0  cmdID= 5790  value= 4  
					Don't use 103  cmdID= 5790  value= 5  "
		::= { iqhco30CmdEntry 5790 }


	iqhco30RulesRulesRollTack103 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 103
					or:RollTrack104=1  cmdID= 5791  value= 1  
					or:RollTrack104=0  cmdID= 5791  value= 3  
					and:RollTrack104=1  cmdID= 5791  value= 2  
					and:RollTrack104=0  cmdID= 5791  value= 4  
					Don't use 104  cmdID= 5791  value= 5  "
		::= { iqhco30CmdEntry 5791 }


	iqhco30RulesRulesRollTack104Active OBJECT-TYPE
		SYNTAX		RollCallString
		MAX-ACCESS		read-only
		STATUS			current
		DESCRIPTION
				"TYPE: - Display
				 PAGE: - Rules- Rules RollTack 104
					Active  cmdID= 5801  format=   "
		::= { iqhco30CmdEntry 5801 }


	iqhco30RulesRulesRollTack1045812 OBJECT-TYPE
		SYNTAX		INTEGER {
							val-or-Master-Selected(1),
							val-or-Backup-Selected(2),
							val-Don-t-Use(3)
							}
		MAX-ACCESS		read-write
		STATUS			current
		DESCRIPTION
				"TYPE: - Button
				 PAGE: - Rules- Rules RollTack 104
					or:Master Selected  cmdID= 5812  value= 1  
					or:Backup Selected  cmdID= 5812  value= 2  
					Don't Use  cmdID= 5812  value= 3  "
		::= { iqhco30CmdEntry 5812 }


	iqhco30RulesRulesRollTack1045802 OBJECT-TYPE
		SYNTAX		INTEGER {
							val-or-OK-Master(1),
							val-or-FAIL-Master(3),
							val-and-OK-Master(2),
							val-and-FAIL-Master(4),
							val-Don-t-use-Master(5)
							}
		MAX-ACCESS		read-write
		STATUS			current
		DESCRIPTION
				"TYPE: - Button
				 PAGE: - Rules- Rules RollTack 104
					or:OK Master  cmdID= 5802  value= 1  
					or:FAIL Master  cmdID= 5802  value= 3  
					and:OK Master  cmdID= 5802  value= 2  
					and:FAIL Master  cmdID= 5802  value= 4  
					Don't use Master  cmdID= 5802  value= 5  "
		::= { iqhco30CmdEntry 5802 }


	iqhco30RulesRulesRollTack1045803 OBJECT-TYPE
		SYNTAX		INTEGER {
							val-or-OK-Backup(1),
							val-or-FAIL-Backup(3),
							val-and-OK-Backup(2),
							val-and-FAIL-Backup(4),
							val-Don-t-use-Backup(5)
							}
		MAX-ACCESS		read-write
		STATUS			current
		DESCRIPTION
				"TYPE: - Button
				 PAGE: - Rules- Rules RollTack 104
					or:OK Backup  cmdID= 5803  value= 1  
					or:FAIL Backup  cmdID= 5803  value= 3  
					and:OK Backup  cmdID= 5803  value= 2  
					and:FAIL Backup  cmdID= 5803  value= 4  
					Don't use Backup  cmdID= 5803  value= 5  "
		::= { iqhco30CmdEntry 5803 }


	iqhco30RulesRulesRollTack1045804 OBJECT-TYPE
		SYNTAX		INTEGER {
							val-or-GPI1-High(1),
							val-or-GPI1-Low(3),
							val-and-GPI1-High(2),
							val-and-GPI1-Low(4),
							val-Don-t-use-GPI1(5)
							}
		MAX-ACCESS		read-write
		STATUS			current
		DESCRIPTION
				"TYPE: - Button
				 PAGE: - Rules- Rules RollTack 104
					or:GPI1 High  cmdID= 5804  value= 1  
					or:GPI1 Low  cmdID= 5804  value= 3  
					and:GPI1 High  cmdID= 5804  value= 2  
					and:GPI1 Low  cmdID= 5804  value= 4  
					Don't use GPI1  cmdID= 5804  value= 5  "
		::= { iqhco30CmdEntry 5804 }


	iqhco30RulesRulesRollTack1045805 OBJECT-TYPE
		SYNTAX		INTEGER {
							val-or-GPI2-High(1),
							val-or-GPI2-Low(3),
							val-and-GPI2-High(2),
							val-and-GPI2-Low(4),
							val-Don-t-use-GPI2(5)
							}
		MAX-ACCESS		read-write
		STATUS			current
		DESCRIPTION
				"TYPE: - Button
				 PAGE: - Rules- Rules RollTack 104
					or:GPI2 High  cmdID= 5805  value= 1  
					or:GPI2 Low  cmdID= 5805  value= 3  
					and:GPI2 High  cmdID= 5805  value= 2  
					and:GPI2 Low  cmdID= 5805  value= 4  
					Don't use GPI2  cmdID= 5805  value= 5  "
		::= { iqhco30CmdEntry 5805 }


	iqhco30RulesRulesRollTack1045806 OBJECT-TYPE
		SYNTAX		INTEGER {
							val-or-GPI3-High(1),
							val-or-GPI3-Low(3),
							val-and-GPI3-High(2),
							val-and-GPI3-Low(4),
							val-Don-t-use-GPI3(5)
							}
		MAX-ACCESS		read-write
		STATUS			current
		DESCRIPTION
				"TYPE: - Button
				 PAGE: - Rules- Rules RollTack 104
					or:GPI3 High  cmdID= 5806  value= 1  
					or:GPI3 Low  cmdID= 5806  value= 3  
					and:GPI3 High  cmdID= 5806  value= 2  
					and:GPI3 Low  cmdID= 5806  value= 4  
					Don't use GPI3  cmdID= 5806  value= 5  "
		::= { iqhco30CmdEntry 5806 }


	iqhco30RulesRulesRollTack1045807 OBJECT-TYPE
		SYNTAX		INTEGER {
							val-or-GPI4-High(1),
							val-or-GPI4-Low(3),
							val-and-GPI4-High(2),
							val-and-GPI4-Low(4),
							val-Don-t-use-GPI4(5)
							}
		MAX-ACCESS		read-write
		STATUS			current
		DESCRIPTION
				"TYPE: - Button
				 PAGE: - Rules- Rules RollTack 104
					or:GPI4 High  cmdID= 5807  value= 1  
					or:GPI4 Low  cmdID= 5807  value= 3  
					and:GPI4 High  cmdID= 5807  value= 2  
					and:GPI4 Low  cmdID= 5807  value= 4  
					Don't use GPI4  cmdID= 5807  value= 5  "
		::= { iqhco30CmdEntry 5807 }


	iqhco30RulesRulesRollTack1045808 OBJECT-TYPE
		SYNTAX		INTEGER {
							val-or-RollTrack101-1(1),
							val-or-RollTrack101-0(3),
							val-and-RollTrack101-1(2),
							val-and-RollTrack101-0(4),
							val-Don-t-use-101(5)
							}
		MAX-ACCESS		read-write
		STATUS			current
		DESCRIPTION
				"TYPE: - Button
				 PAGE: - Rules- Rules RollTack 104
					or:RollTrack101=1  cmdID= 5808  value= 1  
					or:RollTrack101=0  cmdID= 5808  value= 3  
					and:RollTrack101=1  cmdID= 5808  value= 2  
					and:RollTrack101=0  cmdID= 5808  value= 4  
					Don't use 101  cmdID= 5808  value= 5  "
		::= { iqhco30CmdEntry 5808 }


	iqhco30RulesRulesRollTack1045809 OBJECT-TYPE
		SYNTAX		INTEGER {
							val-or-RollTrack102-1(1),
							val-or-RollTrack102-0(3),
							val-and-RollTrack101-1(2),
							val-and-RollTrack102-0(4),
							val-Don-t-use-102(5)
							}
		MAX-ACCESS		read-write
		STATUS			current
		DESCRIPTION
				"TYPE: - Button
				 PAGE: - Rules- Rules RollTack 104
					or:RollTrack102=1  cmdID= 5809  value= 1  
					or:RollTrack102=0  cmdID= 5809  value= 3  
					and:RollTrack101=1  cmdID= 5809  value= 2  
					and:RollTrack102=0  cmdID= 5809  value= 4  
					Don't use 102  cmdID= 5809  value= 5  "
		::= { iqhco30CmdEntry 5809 }


	iqhco30RulesRulesRollTack1045810 OBJECT-TYPE
		SYNTAX		INTEGER {
							val-or-RollTrack103-1(1),
							val-or-RollTrack103-0(3),
							val-and-RollTrack103-1(2),
							val-and-RollTrack103-0(4),
							val-Don-t-use-103(5)
							}
		MAX-ACCESS		read-write
		STATUS			current
		DESCRIPTION
				"TYPE: - Button
				 PAGE: - Rules- Rules RollTack 104
					or:RollTrack103=1  cmdID= 5810  value= 1  
					or:RollTrack103=0  cmdID= 5810  value= 3  
					and:RollTrack103=1  cmdID= 5810  value= 2  
					and:RollTrack103=0  cmdID= 5810  value= 4  
					Don't use 103  cmdID= 5810  value= 5  "
		::= { iqhco30CmdEntry 5810 }


	iqhco30RulesRulesRollTack104 OBJECT-TYPE
		SYNTAX		INTEGER {
							val-or-RollTrack104-1(1),
							val-or-RollTrack104-0(3),
							val-and-RollTrack104-1(2),
							val-and-RollTrack104-0(4),
							val-Don-t-use-104(5)
							}
		MAX-ACCESS		read-write
		STATUS			current
		DESCRIPTION
				"TYPE: - Button
				 PAGE: - Rules- Rules RollTack 104
					or:RollTrack104=1  cmdID= 5811  value= 1  
					or:RollTrack104=0  cmdID= 5811  value= 3  
					and:RollTrack104=1  cmdID= 5811  value= 2  
					and:RollTrack104=0  cmdID= 5811  value= 4  
					Don't use 104  cmdID= 5811  value= 5  "
		::= { iqhco30CmdEntry 5811 }


	iqhco30RulesPresetsPriorityMaster6660 OBJECT-TYPE
		SYNTAX		INTEGER { noAction(0),val-Priority-Master(1) }
		MAX-ACCESS		read-write
		STATUS			current
		DESCRIPTION
				"TYPE: - Button
				 PAGE: - Rules
					Priority Master  cmdID= 6660  value= 1  "
		::= { iqhco30CmdEntry 6660 }


	iqhco30RulesPresetsPriorityBackup6661 OBJECT-TYPE
		SYNTAX		INTEGER { noAction(0),val-Priority-Backup(1) }
		MAX-ACCESS		read-write
		STATUS			current
		DESCRIPTION
				"TYPE: - Button
				 PAGE: - Rules
					Priority Backup  cmdID= 6661  value= 1  "
		::= { iqhco30CmdEntry 6661 }


	iqhco30RulesPresetsNoPriority6662 OBJECT-TYPE
		SYNTAX		INTEGER { noAction(0),val-No-Priority(1) }
		MAX-ACCESS		read-write
		STATUS			current
		DESCRIPTION
				"TYPE: - Button
				 PAGE: - Rules
					No Priority  cmdID= 6662  value= 1  "
		::= { iqhco30CmdEntry 6662 }


	iqhco30RulesPresetsPriorityMaster6663 OBJECT-TYPE
		SYNTAX		INTEGER { noAction(0),val-Priority-Master(1) }
		MAX-ACCESS		read-write
		STATUS			current
		DESCRIPTION
				"TYPE: - Button
				 PAGE: - Rules
					Priority Master.  cmdID= 6663  value= 1  "
		::= { iqhco30CmdEntry 6663 }


	iqhco30RulesPresetsPriorityBackup6664 OBJECT-TYPE
		SYNTAX		INTEGER { noAction(0),val-Priority-Backup(1) }
		MAX-ACCESS		read-write
		STATUS			current
		DESCRIPTION
				"TYPE: - Button
				 PAGE: - Rules
					Priority Backup.  cmdID= 6664  value= 1  "
		::= { iqhco30CmdEntry 6664 }


	iqhco30RulesPresetsNoPriority6665 OBJECT-TYPE
		SYNTAX		INTEGER { noAction(0),val-No-Priority(1) }
		MAX-ACCESS		read-write
		STATUS			current
		DESCRIPTION
				"TYPE: - Button
				 PAGE: - Rules
					No Priority.  cmdID= 6665  value= 1  "
		::= { iqhco30CmdEntry 6665 }


	iqhco30RulesPresetsPriorityMaster OBJECT-TYPE
		SYNTAX		INTEGER { noAction(0),val-Priority-Master(1) }
		MAX-ACCESS		read-write
		STATUS			current
		DESCRIPTION
				"TYPE: - Button
				 PAGE: - Rules
					Priority Master..  cmdID= 6666  value= 1  "
		::= { iqhco30CmdEntry 6666 }


	iqhco30RulesPresetsPriorityBackup OBJECT-TYPE
		SYNTAX		INTEGER { noAction(0),val-Priority-Backup(1) }
		MAX-ACCESS		read-write
		STATUS			current
		DESCRIPTION
				"TYPE: - Button
				 PAGE: - Rules
					Priority Backup..  cmdID= 6667  value= 1  "
		::= { iqhco30CmdEntry 6667 }


	iqhco30RulesPresetsNoPriority OBJECT-TYPE
		SYNTAX		INTEGER { noAction(0),val-No-Priority(1) }
		MAX-ACCESS		read-write
		STATUS			current
		DESCRIPTION
				"TYPE: - Button
				 PAGE: - Rules
					No Priority..  cmdID= 6668  value= 1  "
		::= { iqhco30CmdEntry 6668 }


	iqhco30OutputsMasterSelect OBJECT-TYPE
		SYNTAX		INTEGER {
							val-Rules(4),
							val-Master(0),
							val-Backup(1),
							val-Pattern(2),
							val-Caption(3)
							}
		MAX-ACCESS		read-write
		STATUS			current
		DESCRIPTION
				"TYPE: - RadiobuttonList
				 PAGE: - Outputs
					Master Select  cmdID= 6631 
					Rules  value= 4  
					Master  value= 0  
					Backup  value= 1  
					Pattern  value= 2  
					Caption  value= 3  "
		::= { iqhco30CmdEntry 6631 }


	iqhco30OutputsMonitorSelect OBJECT-TYPE
		SYNTAX		INTEGER {
							val-Follow-Main(5),
							val-Follow-InActive-Inp(6),
							val-Master(0),
							val-Backup(1),
							val-Pattern(2),
							val-Caption(7)
							}
		MAX-ACCESS		read-write
		STATUS			current
		DESCRIPTION
				"TYPE: - RadiobuttonList
				 PAGE: - Outputs
					Monitor Select  cmdID= 6632 
					Follow Main  value= 5  
					Follow InActive Inp  value= 6  
					Master  value= 0  
					Backup  value= 1  
					Pattern  value= 2  
					Caption  value= 7  "
		::= { iqhco30CmdEntry 6632 }


	iqhco30OutputsRulesSelection OBJECT-TYPE
		SYNTAX		INTEGER {
							val-Active-Master(1),
							val-Active-Backup(2)
							}
		MAX-ACCESS		read-write
		STATUS			current
		DESCRIPTION
				"TYPE: - RadiobuttonList
				 PAGE: - Outputs
					Rules Selection  cmdID= 6633 
					Active Master  value= 1  
					Active Backup  value= 2  "
		::= { iqhco30CmdEntry 6633 }


	iqhco30AESOut12AESOut1SourceLR OBJECT-TYPE
		SYNTAX		INTEGER {
							val-Disembed-1(0),
							val-Disembed-2(1),
							val-Disembed-3(2),
							val-Disembed-4(3),
							val-Disembed-5(4),
							val-Disembed-6(5),
							val-Disembed-7(6),
							val-Disembed-8(7),
							val-Tone(8),
							val-Silence(9)
							}
		MAX-ACCESS		read-write
		STATUS			current
		DESCRIPTION
				"TYPE: - RadiobuttonList
				 PAGE: - Outputs- AES Out 1-2- AES Out 1
					Source L+R  cmdID= 2951 
					Disembed 1  value= 0  
					Disembed 2  value= 1  
					Disembed 3  value= 2  
					Disembed 4  value= 3  
					Disembed 5  value= 4  
					Disembed 6  value= 5  
					Disembed 7  value= 6  
					Disembed 8  value= 7  
					Tone  value= 8  
					Silence  value= 9  "
		::= { iqhco30CmdEntry 2951 }


	iqhco30AESOut12AESOut2SourceLR OBJECT-TYPE
		SYNTAX		INTEGER {
							val-Disembed-1(0),
							val-Disembed-2(1),
							val-Disembed-3(2),
							val-Disembed-4(3),
							val-Disembed-5(4),
							val-Disembed-6(5),
							val-Disembed-7(6),
							val-Disembed-8(7),
							val-Tone(8),
							val-Silence(9)
							}
		MAX-ACCESS		read-write
		STATUS			current
		DESCRIPTION
				"TYPE: - RadiobuttonList
				 PAGE: - Outputs- AES Out 1-2- AES Out 2
					Source L+R  cmdID= 2952 
					Disembed 1  value= 0  
					Disembed 2  value= 1  
					Disembed 3  value= 2  
					Disembed 4  value= 3  
					Disembed 5  value= 4  
					Disembed 6  value= 5  
					Disembed 7  value= 6  
					Disembed 8  value= 7  
					Tone  value= 8  
					Silence  value= 9  "
		::= { iqhco30CmdEntry 2952 }


	iqhco30OutputsToneFrequency OBJECT-TYPE
		SYNTAX		INTEGER
		MAX-ACCESS		read-write
		STATUS			current
		DESCRIPTION
				"TYPE: - Number
				 PAGE: - Outputs
					Frequency  cmdID= 2487  min= 100  max= 10000  step= 100  format= %5.0fHz  div_scale= 1 
					Min =   100Hz  Max = 10000Hz  Step =   100Hz "
		::= { iqhco30CmdEntry 2487 }


	iqhco30OutputsToneChannelident OBJECT-TYPE
		SYNTAX		INTEGER { disable(0), enable(1) }
		MAX-ACCESS		read-write
		STATUS			current
		DESCRIPTION
				"TYPE: - Checkbox
				 PAGE: - Outputs
					Channel ident  cmdID= 5030 "
		::= { iqhco30CmdEntry 5030 }


	iqhco30CommonDefFormat OBJECT-TYPE
		SYNTAX		INTEGER {
							val-Last-Known-Good(1),
							val-625-25i(2),
							val-525-29i(3),
							val-720-50p(9),
							val-720-59p(10),
							val-1080-25i(17),
							val-1080-29i(18),
							val-1080-50p-A(22),
							val-1080-59p-A(23),
							val-1080-50p-B(25),
							val-1080-59p-B(26)
							}
		MAX-ACCESS		read-write
		STATUS			current
		DESCRIPTION
				"TYPE: - RadiobuttonList
				 PAGE: - Common
					Def. Format  cmdID= 3793 
					Last Known Good  value= 1  
					625/25i  value= 2  
					525/29i  value= 3  
					720/50p  value= 9  
					720/59p  value= 10  
					1080/25i  value= 17  
					1080/29i  value= 18  
					1080/50p-A  value= 22  
					1080/59p-A  value= 23  
					1080/50p-B  value= 25  
					1080/59p-B  value= 26  "
		::= { iqhco30CmdEntry 3793 }


	iqhco30CommonMemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Common
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqhco30CmdEntry 37101 }


	iqhco30CommonMemoriesSetMemName OBJECT-TYPE
		SYNTAX		RollCallString
		MAX-ACCESS		read-write
		STATUS			current
		DESCRIPTION
				"TYPE: - Editstring
				 PAGE: - Common
					SetMemName  cmdID= 37103  "
		::= { iqhco30CmdEntry 37103 }


	iqhco30CommonMemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Common
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqhco30CmdEntry 37100 }


	iqhco30CommonMemoriesSaveMemory OBJECT-TYPE
		SYNTAX		INTEGER { noAction(0),val-Save-Memory(1) }
		MAX-ACCESS		read-write
		STATUS			current
		DESCRIPTION
				"TYPE: - Button
				 PAGE: - Common
					Save Memory  cmdID= 37102  value= 1  "
		::= { iqhco30CmdEntry 37102 }


	iqhco30CommonMemoriesLastUserMemory OBJECT-TYPE
		SYNTAX		RollCallString
		MAX-ACCESS		read-only
		STATUS			current
		DESCRIPTION
				"TYPE: - Display
				 PAGE: - Common
					Last User Memory  cmdID= 37104  format=   "
		::= { iqhco30CmdEntry 37104 }


	iqhco30CommonMemoriesClearMemory OBJECT-TYPE
		SYNTAX		INTEGER { noAction(0),val-Clear-Memory(1) }
		MAX-ACCESS		read-write
		STATUS			current
		DESCRIPTION
				"TYPE: - Button
				 PAGE: - Common
					Clear Memory  cmdID= 37105  value= 1  "
		::= { iqhco30CmdEntry 37105 }


	iqhco30MemoriesMemoryNamesMemory1Name OBJECT-TYPE
		SYNTAX		RollCallString
		MAX-ACCESS		read-only
		STATUS			current
		DESCRIPTION
				"TYPE: - Display
				 PAGE: - Common
					Memory 1 Name  cmdID= 37106  format=   "
		::= { iqhco30CmdEntry 37106 }


	iqhco30MemoriesMemoryNamesMemory2Name OBJECT-TYPE
		SYNTAX		RollCallString
		MAX-ACCESS		read-only
		STATUS			current
		DESCRIPTION
				"TYPE: - Display
				 PAGE: - Common
					Memory 2 Name  cmdID= 37107  format=   "
		::= { iqhco30CmdEntry 37107 }


	iqhco30MemoriesMemoryNamesMemory3Name OBJECT-TYPE
		SYNTAX		RollCallString
		MAX-ACCESS		read-only
		STATUS			current
		DESCRIPTION
				"TYPE: - Display
				 PAGE: - Common
					Memory 3 Name  cmdID= 37108  format=   "
		::= { iqhco30CmdEntry 37108 }


	iqhco30MemoriesMemoryNamesMemory4Name OBJECT-TYPE
		SYNTAX		RollCallString
		MAX-ACCESS		read-only
		STATUS			current
		DESCRIPTION
				"TYPE: - Display
				 PAGE: - Common
					Memory 4 Name  cmdID= 37109  format=   "
		::= { iqhco30CmdEntry 37109 }


	iqhco30MemoriesMemoryNamesMemory5Name OBJECT-TYPE
		SYNTAX		RollCallString
		MAX-ACCESS		read-only
		STATUS			current
		DESCRIPTION
				"TYPE: - Display
				 PAGE: - Common
					Memory 5 Name  cmdID= 37110  format=   "
		::= { iqhco30CmdEntry 37110 }


	iqhco30MemoriesMemoryNamesMemory6Name OBJECT-TYPE
		SYNTAX		RollCallString
		MAX-ACCESS		read-only
		STATUS			current
		DESCRIPTION
				"TYPE: - Display
				 PAGE: - Common
					Memory 6 Name  cmdID= 37111  format=   "
		::= { iqhco30CmdEntry 37111 }


	iqhco30MemoriesMemoryNamesMemory7Name OBJECT-TYPE
		SYNTAX		RollCallString
		MAX-ACCESS		read-only
		STATUS			current
		DESCRIPTION
				"TYPE: - Display
				 PAGE: - Common
					Memory 7 Name  cmdID= 37112  format=   "
		::= { iqhco30CmdEntry 37112 }


	iqhco30MemoriesMemoryNamesMemory8Name OBJECT-TYPE
		SYNTAX		RollCallString
		MAX-ACCESS		read-only
		STATUS			current
		DESCRIPTION
				"TYPE: - Display
				 PAGE: - Common
					Memory 8 Name  cmdID= 37113  format=   "
		::= { iqhco30CmdEntry 37113 }


	iqhco30MemoriesMemoryNamesMemory9Name OBJECT-TYPE
		SYNTAX		RollCallString
		MAX-ACCESS		read-only
		STATUS			current
		DESCRIPTION
				"TYPE: - Display
				 PAGE: - Common
					Memory 9 Name  cmdID= 37114  format=   "
		::= { iqhco30CmdEntry 37114 }


	iqhco30MemoriesMemoryNamesMemory10Name OBJECT-TYPE
		SYNTAX		RollCallString
		MAX-ACCESS		read-only
		STATUS			current
		DESCRIPTION
				"TYPE: - Display
				 PAGE: - Common
					Memory 10 Name  cmdID= 37115  format=   "
		::= { iqhco30CmdEntry 37115 }


	iqhco30MemoriesMemoryNamesMemory11Name OBJECT-TYPE
		SYNTAX		RollCallString
		MAX-ACCESS		read-only
		STATUS			current
		DESCRIPTION
				"TYPE: - Display
				 PAGE: - Common
					Memory 11 Name  cmdID= 37116  format=   "
		::= { iqhco30CmdEntry 37116 }


	iqhco30MemoriesMemoryNamesMemory12Name OBJECT-TYPE
		SYNTAX		RollCallString
		MAX-ACCESS		read-only
		STATUS			current
		DESCRIPTION
				"TYPE: - Display
				 PAGE: - Common
					Memory 12 Name  cmdID= 37117  format=   "
		::= { iqhco30CmdEntry 37117 }


	iqhco30MemoriesMemoryNamesMemory13Name OBJECT-TYPE
		SYNTAX		RollCallString
		MAX-ACCESS		read-only
		STATUS			current
		DESCRIPTION
				"TYPE: - Display
				 PAGE: - Common
					Memory 13 Name  cmdID= 37118  format=   "
		::= { iqhco30CmdEntry 37118 }


	iqhco30MemoriesMemoryNamesMemory14Name OBJECT-TYPE
		SYNTAX		RollCallString
		MAX-ACCESS		read-only
		STATUS			current
		DESCRIPTION
				"TYPE: - Display
				 PAGE: - Common
					Memory 14 Name  cmdID= 37119  format=   "
		::= { iqhco30CmdEntry 37119 }


	iqhco30MemoriesMemoryNamesMemory15Name OBJECT-TYPE
		SYNTAX		RollCallString
		MAX-ACCESS		read-only
		STATUS			current
		DESCRIPTION
				"TYPE: - Display
				 PAGE: - Common
					Memory 15 Name  cmdID= 37120  format=   "
		::= { iqhco30CmdEntry 37120 }


	iqhco30MemoriesMemoryNamesMemory16Name OBJECT-TYPE
		SYNTAX		RollCallString
		MAX-ACCESS		read-only
		STATUS			current
		DESCRIPTION
				"TYPE: - Display
				 PAGE: - Common
					Memory 16 Name  cmdID= 37121  format=   "
		::= { iqhco30CmdEntry 37121 }


	iqhco30LoggingLogMiscSlotStarten OBJECT-TYPE
		SYNTAX		INTEGER { disable(0), enable(1) }
		MAX-ACCESS		read-write
		STATUS			current
		DESCRIPTION
				"TYPE: - Checkbox
				 PAGE: - Common- Setup- Logging- Log Misc
					Slot Start_en  cmdID= 4976 "
		::= { iqhco30CmdEntry 4976 }


	iqhco30LoggingLogMiscSlotStart OBJECT-TYPE
		SYNTAX		RollCallString
		MAX-ACCESS		read-only
		STATUS			current
		DESCRIPTION
				"TYPE: - Display
				 PAGE: - Common- Setup- Logging- Log Misc
					Slot Start  cmdID= 4977  format=   "
		::= { iqhco30CmdEntry 4977 }


	iqhco30LoggingLogMiscSlotWidthen OBJECT-TYPE
		SYNTAX		INTEGER { disable(0), enable(1) }
		MAX-ACCESS		read-write
		STATUS			current
		DESCRIPTION
				"TYPE: - Checkbox
				 PAGE: - Common- Setup- Logging- Log Misc
					Slot Width_en  cmdID= 4978 "
		::= { iqhco30CmdEntry 4978 }


	iqhco30LoggingLogMiscSlotWidth OBJECT-TYPE
		SYNTAX		RollCallString
		MAX-ACCESS		read-only
		STATUS			current
		DESCRIPTION
				"TYPE: - Display
				 PAGE: - Common- Setup- Logging- Log Misc
					Slot Width  cmdID= 4979  format=   "
		::= { iqhco30CmdEntry 4979 }


	iqhco30LoggingLogMiscRearStatusen OBJECT-TYPE
		SYNTAX		INTEGER { disable(0), enable(1) }
		MAX-ACCESS		read-write
		STATUS			current
		DESCRIPTION
				"TYPE: - Checkbox
				 PAGE: - Common- Setup- Logging- Log Misc
					Rear Status_en  cmdID= 4980 "
		::= { iqhco30CmdEntry 4980 }


	iqhco30LoggingLogMiscRearStatus OBJECT-TYPE
		SYNTAX		RollCallString
		MAX-ACCESS		read-only
		STATUS			current
		DESCRIPTION
				"TYPE: - Display
				 PAGE: - Common- Setup- Logging- Log Misc
					Rear Status  cmdID= 4981  format=   "
		::= { iqhco30CmdEntry 4981 }


	iqhco30LoggingLogMiscRearIDen OBJECT-TYPE
		SYNTAX		INTEGER { disable(0), enable(1) }
		MAX-ACCESS		read-write
		STATUS			current
		DESCRIPTION
				"TYPE: - Checkbox
				 PAGE: - Common- Setup- Logging- Log Misc
					Rear ID_en  cmdID= 4982 "
		::= { iqhco30CmdEntry 4982 }


	iqhco30LoggingLogMiscRearID OBJECT-TYPE
		SYNTAX		RollCallString
		MAX-ACCESS		read-only
		STATUS			current
		DESCRIPTION
				"TYPE: - Display
				 PAGE: - Common- Setup- Logging- Log Misc
					Rear ID  cmdID= 4983  format=   "
		::= { iqhco30CmdEntry 4983 }


	iqhco30LoggingLogMiscFirmwareVersionen OBJECT-TYPE
		SYNTAX		INTEGER { disable(0), enable(1) }
		MAX-ACCESS		read-write
		STATUS			current
		DESCRIPTION
				"TYPE: - Checkbox
				 PAGE: - Common- Setup- Logging- Log Misc
					Firmware Version_en  cmdID= 4986 "
		::= { iqhco30CmdEntry 4986 }


	iqhco30LoggingLogMiscFirmwareVersion OBJECT-TYPE
		SYNTAX		RollCallString
		MAX-ACCESS		read-only
		STATUS			current
		DESCRIPTION
				"TYPE: - Display
				 PAGE: - Common- Setup- Logging- Log Misc
					Firmware Version  cmdID= 4987  format=   "
		::= { iqhco30CmdEntry 4987 }


	iqhco30LoggingLogMiscLicensedOptionsen OBJECT-TYPE
		SYNTAX		INTEGER { disable(0), enable(1) }
		MAX-ACCESS		read-write
		STATUS			current
		DESCRIPTION
				"TYPE: - Checkbox
				 PAGE: - Common- Setup- Logging- Log Misc
					Licensed Options_en  cmdID= 4988 "
		::= { iqhco30CmdEntry 4988 }


	iqhco30LoggingLogMiscLicensedOptions OBJECT-TYPE
		SYNTAX		RollCallString
		MAX-ACCESS		read-only
		STATUS			current
		DESCRIPTION
				"TYPE: - Display
				 PAGE: - Common- Setup- Logging- Log Misc
					Licensed Options  cmdID= 4989  format=   "
		::= { iqhco30CmdEntry 4989 }


	iqhco30LoggingLogMiscBuildNumberen OBJECT-TYPE
		SYNTAX		INTEGER { disable(0), enable(1) }
		MAX-ACCESS		read-write
		STATUS			current
		DESCRIPTION
				"TYPE: - Checkbox
				 PAGE: - Common- Setup- Logging- Log Misc
					Build Number_en  cmdID= 4992 "
		::= { iqhco30CmdEntry 4992 }


	iqhco30LoggingLogMiscBuildNumber OBJECT-TYPE
		SYNTAX		RollCallString
		MAX-ACCESS		read-only
		STATUS			current
		DESCRIPTION
				"TYPE: - Display
				 PAGE: - Common- Setup- Logging- Log Misc
					Build Number  cmdID= 4993  format=   "
		::= { iqhco30CmdEntry 4993 }


	iqhco30LoggingLogMiscOSVersionen OBJECT-TYPE
		SYNTAX		INTEGER { disable(0), enable(1) }
		MAX-ACCESS		read-write
		STATUS			current
		DESCRIPTION
				"TYPE: - Checkbox
				 PAGE: - Common- Setup- Logging- Log Misc
					OS Version_en  cmdID= 4994 "
		::= { iqhco30CmdEntry 4994 }


	iqhco30LoggingLogMiscOSVersion OBJECT-TYPE
		SYNTAX		RollCallString
		MAX-ACCESS		read-only
		STATUS			current
		DESCRIPTION
				"TYPE: - Display
				 PAGE: - Common- Setup- Logging- Log Misc
					OS Version  cmdID= 4995  format=   "
		::= { iqhco30CmdEntry 4995 }


	iqhco30LoggingLogMiscHardwareVersionen OBJECT-TYPE
		SYNTAX		INTEGER { disable(0), enable(1) }
		MAX-ACCESS		read-write
		STATUS			current
		DESCRIPTION
				"TYPE: - Checkbox
				 PAGE: - Common- Setup- Logging- Log Misc
					Hardware Version_en  cmdID= 4996 "
		::= { iqhco30CmdEntry 4996 }


	iqhco30LoggingLogMiscHardwareVersion OBJECT-TYPE
		SYNTAX		RollCallString
		MAX-ACCESS		read-only
		STATUS			current
		DESCRIPTION
				"TYPE: - Display
				 PAGE: - Common- Setup- Logging- Log Misc
					Hardware Version  cmdID= 4997  format=   "
		::= { iqhco30CmdEntry 4997 }


	iqhco30LoggingLogMiscUptimeen OBJECT-TYPE
		SYNTAX		INTEGER { disable(0), enable(1) }
		MAX-ACCESS		read-write
		STATUS			current
		DESCRIPTION
				"TYPE: - Checkbox
				 PAGE: - Common- Setup- Logging- Log Misc
					Uptime_en  cmdID= 4998 "
		::= { iqhco30CmdEntry 4998 }


	iqhco30LoggingLogMiscUptime OBJECT-TYPE
		SYNTAX		RollCallString
		MAX-ACCESS		read-only
		STATUS			current
		DESCRIPTION
				"TYPE: - Display
				 PAGE: - Common- Setup- Logging- Log Misc
					Uptime  cmdID= 4999  format=   "
		::= { iqhco30CmdEntry 4999 }


	iqhco30LoggingLogMiscSerialNumberen OBJECT-TYPE
		SYNTAX		INTEGER { disable(0), enable(1) }
		MAX-ACCESS		read-write
		STATUS			current
		DESCRIPTION
				"TYPE: - Checkbox
				 PAGE: - Common- Setup- Logging- Log Misc
					Serial Number_en  cmdID= 4990 "
		::= { iqhco30CmdEntry 4990 }


	iqhco30LoggingLogMiscSerialNumber OBJECT-TYPE
		SYNTAX		RollCallString
		MAX-ACCESS		read-only
		STATUS			current
		DESCRIPTION
				"TYPE: - Display
				 PAGE: - Common- Setup- Logging- Log Misc
					Serial Number  cmdID= 4991  format=   "
		::= { iqhco30CmdEntry 4991 }


	iqhco30LoggingLogVideoInput1Input1en OBJECT-TYPE
		SYNTAX		INTEGER { disable(0), enable(1) }
		MAX-ACCESS		read-write
		STATUS			current
		DESCRIPTION
				"TYPE: - Checkbox
				 PAGE: - Common- Setup- Logging- Log Video_Input_1
					Input1_en  cmdID= 4000 "
		::= { iqhco30CmdEntry 4000 }


	iqhco30LoggingLogVideoInput1Input1 OBJECT-TYPE
		SYNTAX		RollCallString
		MAX-ACCESS		read-only
		STATUS			current
		DESCRIPTION
				"TYPE: - Display
				 PAGE: - Common- Setup- Logging- Log Video_Input_1
					Input1  cmdID= 4001  format=   "
		::= { iqhco30CmdEntry 4001 }


	iqhco30LoggingLogVideoInput1Input1Standarden OBJECT-TYPE
		SYNTAX		INTEGER { disable(0), enable(1) }
		MAX-ACCESS		read-write
		STATUS			current
		DESCRIPTION
				"TYPE: - Checkbox
				 PAGE: - Common- Setup- Logging- Log Video_Input_1
					Input1 Standard_en  cmdID= 4004 "
		::= { iqhco30CmdEntry 4004 }


	iqhco30LoggingLogVideoInput1Input1Standard OBJECT-TYPE
		SYNTAX		RollCallString
		MAX-ACCESS		read-only
		STATUS			current
		DESCRIPTION
				"TYPE: - Display
				 PAGE: - Common- Setup- Logging- Log Video_Input_1
					Input1 Standard  cmdID= 4005  format=   "
		::= { iqhco30CmdEntry 4005 }


	iqhco30LoggingLogVideoInput1In1SDIERRSen OBJECT-TYPE
		SYNTAX		INTEGER { disable(0), enable(1) }
		MAX-ACCESS		read-write
		STATUS			current
		DESCRIPTION
				"TYPE: - Checkbox
				 PAGE: - Common- Setup- Logging- Log Video_Input_1
					In1 SDI ERRS_en  cmdID= 4012 "
		::= { iqhco30CmdEntry 4012 }


	iqhco30LoggingLogVideoInput1In1SDIERRS OBJECT-TYPE
		SYNTAX		RollCallString
		MAX-ACCESS		read-only
		STATUS			current
		DESCRIPTION
				"TYPE: - Display
				 PAGE: - Common- Setup- Logging- Log Video_Input_1
					In1 SDI ERRS  cmdID= 4013  format=   "
		::= { iqhco30CmdEntry 4013 }


	iqhco30LoggingLogVideoInput1In1SDIANCERRSen OBJECT-TYPE
		SYNTAX		INTEGER { disable(0), enable(1) }
		MAX-ACCESS		read-write
		STATUS			current
		DESCRIPTION
				"TYPE: - Checkbox
				 PAGE: - Common- Setup- Logging- Log Video_Input_1
					In1 SDI ANC ERRS_en  cmdID= 4020 "
		::= { iqhco30CmdEntry 4020 }


	iqhco30LoggingLogVideoInput1In1SDIANCERRS OBJECT-TYPE
		SYNTAX		RollCallString
		MAX-ACCESS		read-only
		STATUS			current
		DESCRIPTION
				"TYPE: - Display
				 PAGE: - Common- Setup- Logging- Log Video_Input_1
					In1 SDI ANC ERRS  cmdID= 4021  format=   "
		::= { iqhco30CmdEntry 4021 }


	iqhco30LoggingLogVideoInput1Input1Typeen OBJECT-TYPE
		SYNTAX		INTEGER { disable(0), enable(1) }
		MAX-ACCESS		read-write
		STATUS			current
		DESCRIPTION
				"TYPE: - Checkbox
				 PAGE: - Common- Setup- Logging- Log Video_Input_1
					Input1 Type_en  cmdID= 4024 "
		::= { iqhco30CmdEntry 4024 }


	iqhco30LoggingLogVideoInput1Input1Type OBJECT-TYPE
		SYNTAX		RollCallString
		MAX-ACCESS		read-only
		STATUS			current
		DESCRIPTION
				"TYPE: - Display
				 PAGE: - Common- Setup- Logging- Log Video_Input_1
					Input1 Type  cmdID= 4025  format=   "
		::= { iqhco30CmdEntry 4025 }


	iqhco30LoggingLogVideoInput1Input1Identen OBJECT-TYPE
		SYNTAX		INTEGER { disable(0), enable(1) }
		MAX-ACCESS		read-write
		STATUS			current
		DESCRIPTION
				"TYPE: - Checkbox
				 PAGE: - Common- Setup- Logging- Log Video_Input_1
					Input1 Ident_en  cmdID= 4028 "
		::= { iqhco30CmdEntry 4028 }


	iqhco30LoggingLogVideoInput1Input1Ident OBJECT-TYPE
		SYNTAX		RollCallString
		MAX-ACCESS		read-only
		STATUS			current
		DESCRIPTION
				"TYPE: - Display
				 PAGE: - Common- Setup- Logging- Log Video_Input_1
					Input1 Ident  cmdID= 4029  format=   "
		::= { iqhco30CmdEntry 4029 }


	iqhco30LoggingLogVideoInput1In1BlackERRSen OBJECT-TYPE
		SYNTAX		INTEGER { disable(0), enable(1) }
		MAX-ACCESS		read-write
		STATUS			current
		DESCRIPTION
				"TYPE: - Checkbox
				 PAGE: - Common- Setup- Logging- Log Video_Input_1
					In1 Black ERRS_en  cmdID= 4452 "
		::= { iqhco30CmdEntry 4452 }


	iqhco30LoggingLogVideoInput1In1BlackERRS OBJECT-TYPE
		SYNTAX		RollCallString
		MAX-ACCESS		read-only
		STATUS			current
		DESCRIPTION
				"TYPE: - Display
				 PAGE: - Common- Setup- Logging- Log Video_Input_1
					In1 Black ERRS  cmdID= 4453  format=   "
		::= { iqhco30CmdEntry 4453 }


	iqhco30LoggingLogVideoInput1In1FreezeERRSen OBJECT-TYPE
		SYNTAX		INTEGER { disable(0), enable(1) }
		MAX-ACCESS		read-write
		STATUS			current
		DESCRIPTION
				"TYPE: - Checkbox
				 PAGE: - Common- Setup- Logging- Log Video_Input_1
					In1 Freeze ERRS_en  cmdID= 4456 "
		::= { iqhco30CmdEntry 4456 }


	iqhco30LoggingLogVideoInput1In1FreezeERRS OBJECT-TYPE
		SYNTAX		RollCallString
		MAX-ACCESS		read-only
		STATUS			current
		DESCRIPTION
				"TYPE: - Display
				 PAGE: - Common- Setup- Logging- Log Video_Input_1
					In1 Freeze ERRS  cmdID= 4457  format=   "
		::= { iqhco30CmdEntry 4457 }


	iqhco30LoggingLogVideoInput2Input2en OBJECT-TYPE
		SYNTAX		INTEGER { disable(0), enable(1) }
		MAX-ACCESS		read-write
		STATUS			current
		DESCRIPTION
				"TYPE: - Checkbox
				 PAGE: - Common- Setup- Logging- Log Video_Input_2
					Input2_en  cmdID= 4002 "
		::= { iqhco30CmdEntry 4002 }


	iqhco30LoggingLogVideoInput2Input2 OBJECT-TYPE
		SYNTAX		RollCallString
		MAX-ACCESS		read-only
		STATUS			current
		DESCRIPTION
				"TYPE: - Display
				 PAGE: - Common- Setup- Logging- Log Video_Input_2
					Input2  cmdID= 4003  format=   "
		::= { iqhco30CmdEntry 4003 }


	iqhco30LoggingLogVideoInput2Input2Standarden OBJECT-TYPE
		SYNTAX		INTEGER { disable(0), enable(1) }
		MAX-ACCESS		read-write
		STATUS			current
		DESCRIPTION
				"TYPE: - Checkbox
				 PAGE: - Common- Setup- Logging- Log Video_Input_2
					Input2 Standard_en  cmdID= 4006 "
		::= { iqhco30CmdEntry 4006 }


	iqhco30LoggingLogVideoInput2Input2Standard OBJECT-TYPE
		SYNTAX		RollCallString
		MAX-ACCESS		read-only
		STATUS			current
		DESCRIPTION
				"TYPE: - Display
				 PAGE: - Common- Setup- Logging- Log Video_Input_2
					Input2 Standard  cmdID= 4007  format=   "
		::= { iqhco30CmdEntry 4007 }


	iqhco30LoggingLogVideoInput2In2SDIERRSen OBJECT-TYPE
		SYNTAX		INTEGER { disable(0), enable(1) }
		MAX-ACCESS		read-write
		STATUS			current
		DESCRIPTION
				"TYPE: - Checkbox
				 PAGE: - Common- Setup- Logging- Log Video_Input_2
					In2 SDI ERRS_en  cmdID= 4014 "
		::= { iqhco30CmdEntry 4014 }


	iqhco30LoggingLogVideoInput2In2SDIERRS OBJECT-TYPE
		SYNTAX		RollCallString
		MAX-ACCESS		read-only
		STATUS			current
		DESCRIPTION
				"TYPE: - Display
				 PAGE: - Common- Setup- Logging- Log Video_Input_2
					In2 SDI ERRS  cmdID= 4015  format=   "
		::= { iqhco30CmdEntry 4015 }


	iqhco30LoggingLogVideoInput2In2SDIANCERRSen OBJECT-TYPE
		SYNTAX		INTEGER { disable(0), enable(1) }
		MAX-ACCESS		read-write
		STATUS			current
		DESCRIPTION
				"TYPE: - Checkbox
				 PAGE: - Common- Setup- Logging- Log Video_Input_2
					In2 SDI ANC ERRS_en  cmdID= 4022 "
		::= { iqhco30CmdEntry 4022 }


	iqhco30LoggingLogVideoInput2In2SDIANCERRS OBJECT-TYPE
		SYNTAX		RollCallString
		MAX-ACCESS		read-only
		STATUS			current
		DESCRIPTION
				"TYPE: - Display
				 PAGE: - Common- Setup- Logging- Log Video_Input_2
					In2 SDI ANC ERRS  cmdID= 4023  format=   "
		::= { iqhco30CmdEntry 4023 }


	iqhco30LoggingLogVideoInput2Input2Typeen OBJECT-TYPE
		SYNTAX		INTEGER { disable(0), enable(1) }
		MAX-ACCESS		read-write
		STATUS			current
		DESCRIPTION
				"TYPE: - Checkbox
				 PAGE: - Common- Setup- Logging- Log Video_Input_2
					Input2 Type_en  cmdID= 4026 "
		::= { iqhco30CmdEntry 4026 }


	iqhco30LoggingLogVideoInput2Input2Type OBJECT-TYPE
		SYNTAX		RollCallString
		MAX-ACCESS		read-only
		STATUS			current
		DESCRIPTION
				"TYPE: - Display
				 PAGE: - Common- Setup- Logging- Log Video_Input_2
					Input2 Type  cmdID= 4027  format=   "
		::= { iqhco30CmdEntry 4027 }


	iqhco30LoggingLogVideoInput2Input2Identen OBJECT-TYPE
		SYNTAX		INTEGER { disable(0), enable(1) }
		MAX-ACCESS		read-write
		STATUS			current
		DESCRIPTION
				"TYPE: - Checkbox
				 PAGE: - Common- Setup- Logging- Log Video_Input_2
					Input2 Ident_en  cmdID= 4030 "
		::= { iqhco30CmdEntry 4030 }


	iqhco30LoggingLogVideoInput2Input2Ident OBJECT-TYPE
		SYNTAX		RollCallString
		MAX-ACCESS		read-only
		STATUS			current
		DESCRIPTION
				"TYPE: - Display
				 PAGE: - Common- Setup- Logging- Log Video_Input_2
					Input2 Ident  cmdID= 4031  format=   "
		::= { iqhco30CmdEntry 4031 }


	iqhco30LoggingLogVideoInput2In2BlackERRSen OBJECT-TYPE
		SYNTAX		INTEGER { disable(0), enable(1) }
		MAX-ACCESS		read-write
		STATUS			current
		DESCRIPTION
				"TYPE: - Checkbox
				 PAGE: - Common- Setup- Logging- Log Video_Input_2
					In2 Black ERRS_en  cmdID= 4454 "
		::= { iqhco30CmdEntry 4454 }


	iqhco30LoggingLogVideoInput2In2BlackERRS OBJECT-TYPE
		SYNTAX		RollCallString
		MAX-ACCESS		read-only
		STATUS			current
		DESCRIPTION
				"TYPE: - Display
				 PAGE: - Common- Setup- Logging- Log Video_Input_2
					In2 Black ERRS  cmdID= 4455  format=   "
		::= { iqhco30CmdEntry 4455 }


	iqhco30LoggingLogVideoInput2In2FreezeERRSen OBJECT-TYPE
		SYNTAX		INTEGER { disable(0), enable(1) }
		MAX-ACCESS		read-write
		STATUS			current
		DESCRIPTION
				"TYPE: - Checkbox
				 PAGE: - Common- Setup- Logging- Log Video_Input_2
					In2 Freeze ERRS_en  cmdID= 4458 "
		::= { iqhco30CmdEntry 4458 }


	iqhco30LoggingLogVideoInput2In2FreezeERRS OBJECT-TYPE
		SYNTAX		RollCallString
		MAX-ACCESS		read-only
		STATUS			current
		DESCRIPTION
				"TYPE: - Display
				 PAGE: - Common- Setup- Logging- Log Video_Input_2
					In2 Freeze ERRS  cmdID= 4459  format=   "
		::= { iqhco30CmdEntry 4459 }


	iqhco30LoggingLogAudioInput1Input1Audio11en OBJECT-TYPE
		SYNTAX		INTEGER { disable(0), enable(1) }
		MAX-ACCESS		read-write
		STATUS			current
		DESCRIPTION
				"TYPE: - Checkbox
				 PAGE: - Common- Setup- Logging- Log Audio_Input_1
					Input1 Audio 1 1_en  cmdID= 4064 "
		::= { iqhco30CmdEntry 4064 }


	iqhco30LoggingLogAudioInput1Input1Audio11 OBJECT-TYPE
		SYNTAX		RollCallString
		MAX-ACCESS		read-only
		STATUS			current
		DESCRIPTION
				"TYPE: - Display
				 PAGE: - Common- Setup- Logging- Log Audio_Input_1
					Input1 Audio 1 1  cmdID= 4065  format=   "
		::= { iqhco30CmdEntry 4065 }


	iqhco30LoggingLogAudioInput1Input1Audio12en OBJECT-TYPE
		SYNTAX		INTEGER { disable(0), enable(1) }
		MAX-ACCESS		read-write
		STATUS			current
		DESCRIPTION
				"TYPE: - Checkbox
				 PAGE: - Common- Setup- Logging- Log Audio_Input_1
					Input1 Audio 1 2_en  cmdID= 4068 "
		::= { iqhco30CmdEntry 4068 }


	iqhco30LoggingLogAudioInput1Input1Audio12 OBJECT-TYPE
		SYNTAX		RollCallString
		MAX-ACCESS		read-only
		STATUS			current
		DESCRIPTION
				"TYPE: - Display
				 PAGE: - Common- Setup- Logging- Log Audio_Input_1
					Input1 Audio 1 2  cmdID= 4069  format=   "
		::= { iqhco30CmdEntry 4069 }


	iqhco30LoggingLogAudioInput1Input1Audio21en OBJECT-TYPE
		SYNTAX		INTEGER { disable(0), enable(1) }
		MAX-ACCESS		read-write
		STATUS			current
		DESCRIPTION
				"TYPE: - Checkbox
				 PAGE: - Common- Setup- Logging- Log Audio_Input_1
					Input1 Audio 2 1_en  cmdID= 4072 "
		::= { iqhco30CmdEntry 4072 }


	iqhco30LoggingLogAudioInput1Input1Audio21 OBJECT-TYPE
		SYNTAX		RollCallString
		MAX-ACCESS		read-only
		STATUS			current
		DESCRIPTION
				"TYPE: - Display
				 PAGE: - Common- Setup- Logging- Log Audio_Input_1
					Input1 Audio 2 1  cmdID= 4073  format=   "
		::= { iqhco30CmdEntry 4073 }


	iqhco30LoggingLogAudioInput1Input1Audio22en OBJECT-TYPE
		SYNTAX		INTEGER { disable(0), enable(1) }
		MAX-ACCESS		read-write
		STATUS			current
		DESCRIPTION
				"TYPE: - Checkbox
				 PAGE: - Common- Setup- Logging- Log Audio_Input_1
					Input1 Audio 2 2_en  cmdID= 4076 "
		::= { iqhco30CmdEntry 4076 }


	iqhco30LoggingLogAudioInput1Input1Audio22 OBJECT-TYPE
		SYNTAX		RollCallString
		MAX-ACCESS		read-only
		STATUS			current
		DESCRIPTION
				"TYPE: - Display
				 PAGE: - Common- Setup- Logging- Log Audio_Input_1
					Input1 Audio 2 2  cmdID= 4077  format=   "
		::= { iqhco30CmdEntry 4077 }


	iqhco30LoggingLogAudioInput1Input1Audio31en OBJECT-TYPE
		SYNTAX		INTEGER { disable(0), enable(1) }
		MAX-ACCESS		read-write
		STATUS			current
		DESCRIPTION
				"TYPE: - Checkbox
				 PAGE: - Common- Setup- Logging- Log Audio_Input_1
					Input1 Audio 3 1_en  cmdID= 4080 "
		::= { iqhco30CmdEntry 4080 }


	iqhco30LoggingLogAudioInput1Input1Audio31 OBJECT-TYPE
		SYNTAX		RollCallString
		MAX-ACCESS		read-only
		STATUS			current
		DESCRIPTION
				"TYPE: - Display
				 PAGE: - Common- Setup- Logging- Log Audio_Input_1
					Input1 Audio 3 1  cmdID= 4081  format=   "
		::= { iqhco30CmdEntry 4081 }


	iqhco30LoggingLogAudioInput1Input1Audio32en OBJECT-TYPE
		SYNTAX		INTEGER { disable(0), enable(1) }
		MAX-ACCESS		read-write
		STATUS			current
		DESCRIPTION
				"TYPE: - Checkbox
				 PAGE: - Common- Setup- Logging- Log Audio_Input_1
					Input1 Audio 3 2_en  cmdID= 4084 "
		::= { iqhco30CmdEntry 4084 }


	iqhco30LoggingLogAudioInput1Input1Audio32 OBJECT-TYPE
		SYNTAX		RollCallString
		MAX-ACCESS		read-only
		STATUS			current
		DESCRIPTION
				"TYPE: - Display
				 PAGE: - Common- Setup- Logging- Log Audio_Input_1
					Input1 Audio 3 2  cmdID= 4085  format=   "
		::= { iqhco30CmdEntry 4085 }


	iqhco30LoggingLogAudioInput1Input1Audio41en OBJECT-TYPE
		SYNTAX		INTEGER { disable(0), enable(1) }
		MAX-ACCESS		read-write
		STATUS			current
		DESCRIPTION
				"TYPE: - Checkbox
				 PAGE: - Common- Setup- Logging- Log Audio_Input_1
					Input1 Audio 4 1_en  cmdID= 4088 "
		::= { iqhco30CmdEntry 4088 }


	iqhco30LoggingLogAudioInput1Input1Audio41 OBJECT-TYPE
		SYNTAX		RollCallString
		MAX-ACCESS		read-only
		STATUS			current
		DESCRIPTION
				"TYPE: - Display
				 PAGE: - Common- Setup- Logging- Log Audio_Input_1
					Input1 Audio 4 1  cmdID= 4089  format=   "
		::= { iqhco30CmdEntry 4089 }


	iqhco30LoggingLogAudioInput1Input1Audio42en OBJECT-TYPE
		SYNTAX		INTEGER { disable(0), enable(1) }
		MAX-ACCESS		read-write
		STATUS			current
		DESCRIPTION
				"TYPE: - Checkbox
				 PAGE: - Common- Setup- Logging- Log Audio_Input_1
					Input1 Audio 4 2_en  cmdID= 4092 "
		::= { iqhco30CmdEntry 4092 }


	iqhco30LoggingLogAudioInput1Input1Audio42 OBJECT-TYPE
		SYNTAX		RollCallString
		MAX-ACCESS		read-only
		STATUS			current
		DESCRIPTION
				"TYPE: - Display
				 PAGE: - Common- Setup- Logging- Log Audio_Input_1
					Input1 Audio 4 2  cmdID= 4093  format=   "
		::= { iqhco30CmdEntry 4093 }


	iqhco30LoggingLogAudioInput1Input1Audio51en OBJECT-TYPE
		SYNTAX		INTEGER { disable(0), enable(1) }
		MAX-ACCESS		read-write
		STATUS			current
		DESCRIPTION
				"TYPE: - Checkbox
				 PAGE: - Common- Setup- Logging- Log Audio_Input_1
					Input1 Audio 5 1_en  cmdID= 4096 "
		::= { iqhco30CmdEntry 4096 }


	iqhco30LoggingLogAudioInput1Input1Audio51 OBJECT-TYPE
		SYNTAX		RollCallString
		MAX-ACCESS		read-only
		STATUS			current
		DESCRIPTION
				"TYPE: - Display
				 PAGE: - Common- Setup- Logging- Log Audio_Input_1
					Input1 Audio 5 1  cmdID= 4097  format=   "
		::= { iqhco30CmdEntry 4097 }


	iqhco30LoggingLogAudioInput1Input1Audio52en OBJECT-TYPE
		SYNTAX		INTEGER { disable(0), enable(1) }
		MAX-ACCESS		read-write
		STATUS			current
		DESCRIPTION
				"TYPE: - Checkbox
				 PAGE: - Common- Setup- Logging- Log Audio_Input_1
					Input1 Audio 5 2_en  cmdID= 4100 "
		::= { iqhco30CmdEntry 4100 }


	iqhco30LoggingLogAudioInput1Input1Audio52 OBJECT-TYPE
		SYNTAX		RollCallString
		MAX-ACCESS		read-only
		STATUS			current
		DESCRIPTION
				"TYPE: - Display
				 PAGE: - Common- Setup- Logging- Log Audio_Input_1
					Input1 Audio 5 2  cmdID= 4101  format=   "
		::= { iqhco30CmdEntry 4101 }


	iqhco30LoggingLogAudioInput1Input1Audio61en OBJECT-TYPE
		SYNTAX		INTEGER { disable(0), enable(1) }
		MAX-ACCESS		read-write
		STATUS			current
		DESCRIPTION
				"TYPE: - Checkbox
				 PAGE: - Common- Setup- Logging- Log Audio_Input_1
					Input1 Audio 6 1_en  cmdID= 4104 "
		::= { iqhco30CmdEntry 4104 }


	iqhco30LoggingLogAudioInput1Input1Audio61 OBJECT-TYPE
		SYNTAX		RollCallString
		MAX-ACCESS		read-only
		STATUS			current
		DESCRIPTION
				"TYPE: - Display
				 PAGE: - Common- Setup- Logging- Log Audio_Input_1
					Input1 Audio 6 1  cmdID= 4105  format=   "
		::= { iqhco30CmdEntry 4105 }


	iqhco30LoggingLogAudioInput1Input1Audio62en OBJECT-TYPE
		SYNTAX		INTEGER { disable(0), enable(1) }
		MAX-ACCESS		read-write
		STATUS			current
		DESCRIPTION
				"TYPE: - Checkbox
				 PAGE: - Common- Setup- Logging- Log Audio_Input_1
					Input1 Audio 6 2_en  cmdID= 4108 "
		::= { iqhco30CmdEntry 4108 }


	iqhco30LoggingLogAudioInput1Input1Audio62 OBJECT-TYPE
		SYNTAX		RollCallString
		MAX-ACCESS		read-only
		STATUS			current
		DESCRIPTION
				"TYPE: - Display
				 PAGE: - Common- Setup- Logging- Log Audio_Input_1
					Input1 Audio 6 2  cmdID= 4109  format=   "
		::= { iqhco30CmdEntry 4109 }


	iqhco30LoggingLogAudioInput1Input1Audio71en OBJECT-TYPE
		SYNTAX		INTEGER { disable(0), enable(1) }
		MAX-ACCESS		read-write
		STATUS			current
		DESCRIPTION
				"TYPE: - Checkbox
				 PAGE: - Common- Setup- Logging- Log Audio_Input_1
					Input1 Audio 7 1_en  cmdID= 4112 "
		::= { iqhco30CmdEntry 4112 }


	iqhco30LoggingLogAudioInput1Input1Audio71 OBJECT-TYPE
		SYNTAX		RollCallString
		MAX-ACCESS		read-only
		STATUS			current
		DESCRIPTION
				"TYPE: - Display
				 PAGE: - Common- Setup- Logging- Log Audio_Input_1
					Input1 Audio 7 1  cmdID= 4113  format=   "
		::= { iqhco30CmdEntry 4113 }


	iqhco30LoggingLogAudioInput1Input1Audio72en OBJECT-TYPE
		SYNTAX		INTEGER { disable(0), enable(1) }
		MAX-ACCESS		read-write
		STATUS			current
		DESCRIPTION
				"TYPE: - Checkbox
				 PAGE: - Common- Setup- Logging- Log Audio_Input_1
					Input1 Audio 7 2_en  cmdID= 4116 "
		::= { iqhco30CmdEntry 4116 }


	iqhco30LoggingLogAudioInput1Input1Audio72 OBJECT-TYPE
		SYNTAX		RollCallString
		MAX-ACCESS		read-only
		STATUS			current
		DESCRIPTION
				"TYPE: - Display
				 PAGE: - Common- Setup- Logging- Log Audio_Input_1
					Input1 Audio 7 2  cmdID= 4117  format=   "
		::= { iqhco30CmdEntry 4117 }


	iqhco30LoggingLogAudioInput1Input1Audio81en OBJECT-TYPE
		SYNTAX		INTEGER { disable(0), enable(1) }
		MAX-ACCESS		read-write
		STATUS			current
		DESCRIPTION
				"TYPE: - Checkbox
				 PAGE: - Common- Setup- Logging- Log Audio_Input_1
					Input1 Audio 8 1_en  cmdID= 4120 "
		::= { iqhco30CmdEntry 4120 }


	iqhco30LoggingLogAudioInput1Input1Audio81 OBJECT-TYPE
		SYNTAX		RollCallString
		MAX-ACCESS		read-only
		STATUS			current
		DESCRIPTION
				"TYPE: - Display
				 PAGE: - Common- Setup- Logging- Log Audio_Input_1
					Input1 Audio 8 1  cmdID= 4121  format=   "
		::= { iqhco30CmdEntry 4121 }


	iqhco30LoggingLogAudioInput1Input1Audio82en OBJECT-TYPE
		SYNTAX		INTEGER { disable(0), enable(1) }
		MAX-ACCESS		read-write
		STATUS			current
		DESCRIPTION
				"TYPE: - Checkbox
				 PAGE: - Common- Setup- Logging- Log Audio_Input_1
					Input1 Audio 8 2_en  cmdID= 4124 "
		::= { iqhco30CmdEntry 4124 }


	iqhco30LoggingLogAudioInput1Input1Audio82 OBJECT-TYPE
		SYNTAX		RollCallString
		MAX-ACCESS		read-only
		STATUS			current
		DESCRIPTION
				"TYPE: - Display
				 PAGE: - Common- Setup- Logging- Log Audio_Input_1
					Input1 Audio 8 2  cmdID= 4125  format=   "
		::= { iqhco30CmdEntry 4125 }


	iqhco30LoggingLogAudioInput2Input2Audio11en OBJECT-TYPE
		SYNTAX		INTEGER { disable(0), enable(1) }
		MAX-ACCESS		read-write
		STATUS			current
		DESCRIPTION
				"TYPE: - Checkbox
				 PAGE: - Common- Setup- Logging- Log Audio_Input_2
					Input2 Audio 1 1_en  cmdID= 4128 "
		::= { iqhco30CmdEntry 4128 }


	iqhco30LoggingLogAudioInput2Input2Audio11 OBJECT-TYPE
		SYNTAX		RollCallString
		MAX-ACCESS		read-only
		STATUS			current
		DESCRIPTION
				"TYPE: - Display
				 PAGE: - Common- Setup- Logging- Log Audio_Input_2
					Input2 Audio 1 1  cmdID= 4129  format=   "
		::= { iqhco30CmdEntry 4129 }


	iqhco30LoggingLogAudioInput2Input2Audio12en OBJECT-TYPE
		SYNTAX		INTEGER { disable(0), enable(1) }
		MAX-ACCESS		read-write
		STATUS			current
		DESCRIPTION
				"TYPE: - Checkbox
				 PAGE: - Common- Setup- Logging- Log Audio_Input_2
					Input2 Audio 1 2_en  cmdID= 4132 "
		::= { iqhco30CmdEntry 4132 }


	iqhco30LoggingLogAudioInput2Input2Audio12 OBJECT-TYPE
		SYNTAX		RollCallString
		MAX-ACCESS		read-only
		STATUS			current
		DESCRIPTION
				"TYPE: - Display
				 PAGE: - Common- Setup- Logging- Log Audio_Input_2
					Input2 Audio 1 2  cmdID= 4133  format=   "
		::= { iqhco30CmdEntry 4133 }


	iqhco30LoggingLogAudioInput2Input2Audio21en OBJECT-TYPE
		SYNTAX		INTEGER { disable(0), enable(1) }
		MAX-ACCESS		read-write
		STATUS			current
		DESCRIPTION
				"TYPE: - Checkbox
				 PAGE: - Common- Setup- Logging- Log Audio_Input_2
					Input2 Audio 2 1_en  cmdID= 4136 "
		::= { iqhco30CmdEntry 4136 }


	iqhco30LoggingLogAudioInput2Input2Audio21 OBJECT-TYPE
		SYNTAX		RollCallString
		MAX-ACCESS		read-only
		STATUS			current
		DESCRIPTION
				"TYPE: - Display
				 PAGE: - Common- Setup- Logging- Log Audio_Input_2
					Input2 Audio 2 1  cmdID= 4137  format=   "
		::= { iqhco30CmdEntry 4137 }


	iqhco30LoggingLogAudioInput2Input2Audio22en OBJECT-TYPE
		SYNTAX		INTEGER { disable(0), enable(1) }
		MAX-ACCESS		read-write
		STATUS			current
		DESCRIPTION
				"TYPE: - Checkbox
				 PAGE: - Common- Setup- Logging- Log Audio_Input_2
					Input2 Audio 2 2_en  cmdID= 4140 "
		::= { iqhco30CmdEntry 4140 }


	iqhco30LoggingLogAudioInput2Input2Audio22 OBJECT-TYPE
		SYNTAX		RollCallString
		MAX-ACCESS		read-only
		STATUS			current
		DESCRIPTION
				"TYPE: - Display
				 PAGE: - Common- Setup- Logging- Log Audio_Input_2
					Input2 Audio 2 2  cmdID= 4141  format=   "
		::= { iqhco30CmdEntry 4141 }


	iqhco30LoggingLogAudioInput2Input2Audio31en OBJECT-TYPE
		SYNTAX		INTEGER { disable(0), enable(1) }
		MAX-ACCESS		read-write
		STATUS			current
		DESCRIPTION
				"TYPE: - Checkbox
				 PAGE: - Common- Setup- Logging- Log Audio_Input_2
					Input2 Audio 3 1_en  cmdID= 4144 "
		::= { iqhco30CmdEntry 4144 }


	iqhco30LoggingLogAudioInput2Input2Audio31 OBJECT-TYPE
		SYNTAX		RollCallString
		MAX-ACCESS		read-only
		STATUS			current
		DESCRIPTION
				"TYPE: - Display
				 PAGE: - Common- Setup- Logging- Log Audio_Input_2
					Input2 Audio 3 1  cmdID= 4145  format=   "
		::= { iqhco30CmdEntry 4145 }


	iqhco30LoggingLogAudioInput2Input2Audio32en OBJECT-TYPE
		SYNTAX		INTEGER { disable(0), enable(1) }
		MAX-ACCESS		read-write
		STATUS			current
		DESCRIPTION
				"TYPE: - Checkbox
				 PAGE: - Common- Setup- Logging- Log Audio_Input_2
					Input2 Audio 3 2_en  cmdID= 4148 "
		::= { iqhco30CmdEntry 4148 }


	iqhco30LoggingLogAudioInput2Input2Audio32 OBJECT-TYPE
		SYNTAX		RollCallString
		MAX-ACCESS		read-only
		STATUS			current
		DESCRIPTION
				"TYPE: - Display
				 PAGE: - Common- Setup- Logging- Log Audio_Input_2
					Input2 Audio 3 2  cmdID= 4149  format=   "
		::= { iqhco30CmdEntry 4149 }


	iqhco30LoggingLogAudioInput2Input2Audio41en OBJECT-TYPE
		SYNTAX		INTEGER { disable(0), enable(1) }
		MAX-ACCESS		read-write
		STATUS			current
		DESCRIPTION
				"TYPE: - Checkbox
				 PAGE: - Common- Setup- Logging- Log Audio_Input_2
					Input2 Audio 4 1_en  cmdID= 4152 "
		::= { iqhco30CmdEntry 4152 }


	iqhco30LoggingLogAudioInput2Input2Audio41 OBJECT-TYPE
		SYNTAX		RollCallString
		MAX-ACCESS		read-only
		STATUS			current
		DESCRIPTION
				"TYPE: - Display
				 PAGE: - Common- Setup- Logging- Log Audio_Input_2
					Input2 Audio 4 1  cmdID= 4153  format=   "
		::= { iqhco30CmdEntry 4153 }


	iqhco30LoggingLogAudioInput2Input2Audio42en OBJECT-TYPE
		SYNTAX		INTEGER { disable(0), enable(1) }
		MAX-ACCESS		read-write
		STATUS			current
		DESCRIPTION
				"TYPE: - Checkbox
				 PAGE: - Common- Setup- Logging- Log Audio_Input_2
					Input2 Audio 4 2_en  cmdID= 4156 "
		::= { iqhco30CmdEntry 4156 }


	iqhco30LoggingLogAudioInput2Input2Audio42 OBJECT-TYPE
		SYNTAX		RollCallString
		MAX-ACCESS		read-only
		STATUS			current
		DESCRIPTION
				"TYPE: - Display
				 PAGE: - Common- Setup- Logging- Log Audio_Input_2
					Input2 Audio 4 2  cmdID= 4157  format=   "
		::= { iqhco30CmdEntry 4157 }


	iqhco30LoggingLogAudioInput2Input2Audio51en OBJECT-TYPE
		SYNTAX		INTEGER { disable(0), enable(1) }
		MAX-ACCESS		read-write
		STATUS			current
		DESCRIPTION
				"TYPE: - Checkbox
				 PAGE: - Common- Setup- Logging- Log Audio_Input_2
					Input2 Audio 5 1_en  cmdID= 4160 "
		::= { iqhco30CmdEntry 4160 }


	iqhco30LoggingLogAudioInput2Input2Audio51 OBJECT-TYPE
		SYNTAX		RollCallString
		MAX-ACCESS		read-only
		STATUS			current
		DESCRIPTION
				"TYPE: - Display
				 PAGE: - Common- Setup- Logging- Log Audio_Input_2
					Input2 Audio 5 1  cmdID= 4161  format=   "
		::= { iqhco30CmdEntry 4161 }


	iqhco30LoggingLogAudioInput2Input2Audio52en OBJECT-TYPE
		SYNTAX		INTEGER { disable(0), enable(1) }
		MAX-ACCESS		read-write
		STATUS			current
		DESCRIPTION
				"TYPE: - Checkbox
				 PAGE: - Common- Setup- Logging- Log Audio_Input_2
					Input2 Audio 5 2_en  cmdID= 4164 "
		::= { iqhco30CmdEntry 4164 }


	iqhco30LoggingLogAudioInput2Input2Audio52 OBJECT-TYPE
		SYNTAX		RollCallString
		MAX-ACCESS		read-only
		STATUS			current
		DESCRIPTION
				"TYPE: - Display
				 PAGE: - Common- Setup- Logging- Log Audio_Input_2
					Input2 Audio 5 2  cmdID= 4165  format=   "
		::= { iqhco30CmdEntry 4165 }


	iqhco30LoggingLogAudioInput2Input2Audio61en OBJECT-TYPE
		SYNTAX		INTEGER { disable(0), enable(1) }
		MAX-ACCESS		read-write
		STATUS			current
		DESCRIPTION
				"TYPE: - Checkbox
				 PAGE: - Common- Setup- Logging- Log Audio_Input_2
					Input2 Audio 6 1_en  cmdID= 4168 "
		::= { iqhco30CmdEntry 4168 }


	iqhco30LoggingLogAudioInput2Input2Audio61 OBJECT-TYPE
		SYNTAX		RollCallString
		MAX-ACCESS		read-only
		STATUS			current
		DESCRIPTION
				"TYPE: - Display
				 PAGE: - Common- Setup- Logging- Log Audio_Input_2
					Input2 Audio 6 1  cmdID= 4169  format=   "
		::= { iqhco30CmdEntry 4169 }


	iqhco30LoggingLogAudioInput2Input2Audio62en OBJECT-TYPE
		SYNTAX		INTEGER { disable(0), enable(1) }
		MAX-ACCESS		read-write
		STATUS			current
		DESCRIPTION
				"TYPE: - Checkbox
				 PAGE: - Common- Setup- Logging- Log Audio_Input_2
					Input2 Audio 6 2_en  cmdID= 4172 "
		::= { iqhco30CmdEntry 4172 }


	iqhco30LoggingLogAudioInput2Input2Audio62 OBJECT-TYPE
		SYNTAX		RollCallString
		MAX-ACCESS		read-only
		STATUS			current
		DESCRIPTION
				"TYPE: - Display
				 PAGE: - Common- Setup- Logging- Log Audio_Input_2
					Input2 Audio 6 2  cmdID= 4173  format=   "
		::= { iqhco30CmdEntry 4173 }


	iqhco30LoggingLogAudioInput2Input2Audio71en OBJECT-TYPE
		SYNTAX		INTEGER { disable(0), enable(1) }
		MAX-ACCESS		read-write
		STATUS			current
		DESCRIPTION
				"TYPE: - Checkbox
				 PAGE: - Common- Setup- Logging- Log Audio_Input_2
					Input2 Audio 7 1_en  cmdID= 4176 "
		::= { iqhco30CmdEntry 4176 }


	iqhco30LoggingLogAudioInput2Input2Audio71 OBJECT-TYPE
		SYNTAX		RollCallString
		MAX-ACCESS		read-only
		STATUS			current
		DESCRIPTION
				"TYPE: - Display
				 PAGE: - Common- Setup- Logging- Log Audio_Input_2
					Input2 Audio 7 1  cmdID= 4177  format=   "
		::= { iqhco30CmdEntry 4177 }


	iqhco30LoggingLogAudioInput2Input2Audio72en OBJECT-TYPE
		SYNTAX		INTEGER { disable(0), enable(1) }
		MAX-ACCESS		read-write
		STATUS			current
		DESCRIPTION
				"TYPE: - Checkbox
				 PAGE: - Common- Setup- Logging- Log Audio_Input_2
					Input2 Audio 7 2_en  cmdID= 4180 "
		::= { iqhco30CmdEntry 4180 }


	iqhco30LoggingLogAudioInput2Input2Audio72 OBJECT-TYPE
		SYNTAX		RollCallString
		MAX-ACCESS		read-only
		STATUS			current
		DESCRIPTION
				"TYPE: - Display
				 PAGE: - Common- Setup- Logging- Log Audio_Input_2
					Input2 Audio 7 2  cmdID= 4181  format=   "
		::= { iqhco30CmdEntry 4181 }


	iqhco30LoggingLogAudioInput2Input2Audio81en OBJECT-TYPE
		SYNTAX		INTEGER { disable(0), enable(1) }
		MAX-ACCESS		read-write
		STATUS			current
		DESCRIPTION
				"TYPE: - Checkbox
				 PAGE: - Common- Setup- Logging- Log Audio_Input_2
					Input2 Audio 8 1_en  cmdID= 4184 "
		::= { iqhco30CmdEntry 4184 }


	iqhco30LoggingLogAudioInput2Input2Audio81 OBJECT-TYPE
		SYNTAX		RollCallString
		MAX-ACCESS		read-only
		STATUS			current
		DESCRIPTION
				"TYPE: - Display
				 PAGE: - Common- Setup- Logging- Log Audio_Input_2
					Input2 Audio 8 1  cmdID= 4185  format=   "
		::= { iqhco30CmdEntry 4185 }


	iqhco30LoggingLogAudioInput2Input2Audio82en OBJECT-TYPE
		SYNTAX		INTEGER { disable(0), enable(1) }
		MAX-ACCESS		read-write
		STATUS			current
		DESCRIPTION
				"TYPE: - Checkbox
				 PAGE: - Common- Setup- Logging- Log Audio_Input_2
					Input2 Audio 8 2_en  cmdID= 4188 "
		::= { iqhco30CmdEntry 4188 }


	iqhco30LoggingLogAudioInput2Input2Audio82 OBJECT-TYPE
		SYNTAX		RollCallString
		MAX-ACCESS		read-only
		STATUS			current
		DESCRIPTION
				"TYPE: - Display
				 PAGE: - Common- Setup- Logging- Log Audio_Input_2
					Input2 Audio 8 2  cmdID= 4189  format=   "
		::= { iqhco30CmdEntry 4189 }


	iqhco30LoggingLogVideoOutputOutput1Typeen OBJECT-TYPE
		SYNTAX		INTEGER { disable(0), enable(1) }
		MAX-ACCESS		read-write
		STATUS			current
		DESCRIPTION
				"TYPE: - Checkbox
				 PAGE: - Common- Setup- Logging- Log Video_Output
					Output1 Type_en  cmdID= 4192 "
		::= { iqhco30CmdEntry 4192 }


	iqhco30LoggingLogVideoOutputOutput1Type OBJECT-TYPE
		SYNTAX		RollCallString
		MAX-ACCESS		read-only
		STATUS			current
		DESCRIPTION
				"TYPE: - Display
				 PAGE: - Common- Setup- Logging- Log Video_Output
					Output1 Type  cmdID= 4193  format=   "
		::= { iqhco30CmdEntry 4193 }


	iqhco30LoggingLogVideoOutputOutput1Stateen OBJECT-TYPE
		SYNTAX		INTEGER { disable(0), enable(1) }
		MAX-ACCESS		read-write
		STATUS			current
		DESCRIPTION
				"TYPE: - Checkbox
				 PAGE: - Common- Setup- Logging- Log Video_Output
					Output1 State_en  cmdID= 4196 "
		::= { iqhco30CmdEntry 4196 }


	iqhco30LoggingLogVideoOutputOutput1State OBJECT-TYPE
		SYNTAX		RollCallString
		MAX-ACCESS		read-only
		STATUS			current
		DESCRIPTION
				"TYPE: - Display
				 PAGE: - Common- Setup- Logging- Log Video_Output
					Output1 State  cmdID= 4197  format=   "
		::= { iqhco30CmdEntry 4197 }


	iqhco30LoggingLogVideoOutputOutput1Stden OBJECT-TYPE
		SYNTAX		INTEGER { disable(0), enable(1) }
		MAX-ACCESS		read-write
		STATUS			current
		DESCRIPTION
				"TYPE: - Checkbox
				 PAGE: - Common- Setup- Logging- Log Video_Output
					Output1 Std_en  cmdID= 4200 "
		::= { iqhco30CmdEntry 4200 }


	iqhco30LoggingLogVideoOutputOutput1Std OBJECT-TYPE
		SYNTAX		RollCallString
		MAX-ACCESS		read-only
		STATUS			current
		DESCRIPTION
				"TYPE: - Display
				 PAGE: - Common- Setup- Logging- Log Video_Output
					Output1 Std  cmdID= 4201  format=   "
		::= { iqhco30CmdEntry 4201 }


	iqhco30LoggingLogVideoOutputOutput1en OBJECT-TYPE
		SYNTAX		INTEGER { disable(0), enable(1) }
		MAX-ACCESS		read-write
		STATUS			current
		DESCRIPTION
				"TYPE: - Checkbox
				 PAGE: - Common- Setup- Logging- Log Video_Output
					Output1_en  cmdID= 4208 "
		::= { iqhco30CmdEntry 4208 }


	iqhco30LoggingLogVideoOutputOutput1 OBJECT-TYPE
		SYNTAX		RollCallString
		MAX-ACCESS		read-only
		STATUS			current
		DESCRIPTION
				"TYPE: - Display
				 PAGE: - Common- Setup- Logging- Log Video_Output
					Output1  cmdID= 4209  format=   "
		::= { iqhco30CmdEntry 4209 }


	iqhco30LoggingLogChangeoverMasterStateen OBJECT-TYPE
		SYNTAX		INTEGER { disable(0), enable(1) }
		MAX-ACCESS		read-write
		STATUS			current
		DESCRIPTION
				"TYPE: - Checkbox
				 PAGE: - Common- Setup- Logging- Log Changeover
					Master State_en  cmdID= 4032 "
		::= { iqhco30CmdEntry 4032 }


	iqhco30LoggingLogChangeoverMasterState OBJECT-TYPE
		SYNTAX		RollCallString
		MAX-ACCESS		read-only
		STATUS			current
		DESCRIPTION
				"TYPE: - Display
				 PAGE: - Common- Setup- Logging- Log Changeover
					Master State  cmdID= 4033  format=   "
		::= { iqhco30CmdEntry 4033 }


	iqhco30LoggingLogChangeoverBackupStateen OBJECT-TYPE
		SYNTAX		INTEGER { disable(0), enable(1) }
		MAX-ACCESS		read-write
		STATUS			current
		DESCRIPTION
				"TYPE: - Checkbox
				 PAGE: - Common- Setup- Logging- Log Changeover
					Backup State_en  cmdID= 4034 "
		::= { iqhco30CmdEntry 4034 }


	iqhco30LoggingLogChangeoverBackupState OBJECT-TYPE
		SYNTAX		RollCallString
		MAX-ACCESS		read-only
		STATUS			current
		DESCRIPTION
				"TYPE: - Display
				 PAGE: - Common- Setup- Logging- Log Changeover
					Backup State  cmdID= 4035  format=   "
		::= { iqhco30CmdEntry 4035 }


	iqhco30LoggingLogChangeoverRulesStateen OBJECT-TYPE
		SYNTAX		INTEGER { disable(0), enable(1) }
		MAX-ACCESS		read-write
		STATUS			current
		DESCRIPTION
				"TYPE: - Checkbox
				 PAGE: - Common- Setup- Logging- Log Changeover
					Rules State_en  cmdID= 4212 "
		::= { iqhco30CmdEntry 4212 }


	iqhco30LoggingLogChangeoverRulesState OBJECT-TYPE
		SYNTAX		RollCallString
		MAX-ACCESS		read-only
		STATUS			current
		DESCRIPTION
				"TYPE: - Display
				 PAGE: - Common- Setup- Logging- Log Changeover
					Rules State  cmdID= 4213  format=   "
		::= { iqhco30CmdEntry 4213 }


	iqhco30LoggingLogChangeoverGpi1Stateen OBJECT-TYPE
		SYNTAX		INTEGER { disable(0), enable(1) }
		MAX-ACCESS		read-write
		STATUS			current
		DESCRIPTION
				"TYPE: - Checkbox
				 PAGE: - Common- Setup- Logging- Log Changeover
					Gpi1 State_en  cmdID= 4404 "
		::= { iqhco30CmdEntry 4404 }


	iqhco30LoggingLogChangeoverGpi1State OBJECT-TYPE
		SYNTAX		RollCallString
		MAX-ACCESS		read-only
		STATUS			current
		DESCRIPTION
				"TYPE: - Display
				 PAGE: - Common- Setup- Logging- Log Changeover
					Gpi1 State  cmdID= 4405  format=   "
		::= { iqhco30CmdEntry 4405 }


	iqhco30LoggingLogChangeoverGpi2Stateen OBJECT-TYPE
		SYNTAX		INTEGER { disable(0), enable(1) }
		MAX-ACCESS		read-write
		STATUS			current
		DESCRIPTION
				"TYPE: - Checkbox
				 PAGE: - Common- Setup- Logging- Log Changeover
					Gpi2 State_en  cmdID= 4408 "
		::= { iqhco30CmdEntry 4408 }


	iqhco30LoggingLogChangeoverGpi2State OBJECT-TYPE
		SYNTAX		RollCallString
		MAX-ACCESS		read-only
		STATUS			current
		DESCRIPTION
				"TYPE: - Display
				 PAGE: - Common- Setup- Logging- Log Changeover
					Gpi2 State  cmdID= 4409  format=   "
		::= { iqhco30CmdEntry 4409 }


	iqhco30LoggingLogChangeoverGpi3Stateen OBJECT-TYPE
		SYNTAX		INTEGER { disable(0), enable(1) }
		MAX-ACCESS		read-write
		STATUS			current
		DESCRIPTION
				"TYPE: - Checkbox
				 PAGE: - Common- Setup- Logging- Log Changeover
					Gpi3 State_en  cmdID= 4412 "
		::= { iqhco30CmdEntry 4412 }


	iqhco30LoggingLogChangeoverGpi3State OBJECT-TYPE
		SYNTAX		RollCallString
		MAX-ACCESS		read-only
		STATUS			current
		DESCRIPTION
				"TYPE: - Display
				 PAGE: - Common- Setup- Logging- Log Changeover
					Gpi3 State  cmdID= 4413  format=   "
		::= { iqhco30CmdEntry 4413 }


	iqhco30LoggingLogChangeoverGpi4Stateen OBJECT-TYPE
		SYNTAX		INTEGER { disable(0), enable(1) }
		MAX-ACCESS		read-write
		STATUS			current
		DESCRIPTION
				"TYPE: - Checkbox
				 PAGE: - Common- Setup- Logging- Log Changeover
					Gpi4 State_en  cmdID= 4416 "
		::= { iqhco30CmdEntry 4416 }


	iqhco30LoggingLogChangeoverGpi4State OBJECT-TYPE
		SYNTAX		RollCallString
		MAX-ACCESS		read-only
		STATUS			current
		DESCRIPTION
				"TYPE: - Display
				 PAGE: - Common- Setup- Logging- Log Changeover
					Gpi4 State  cmdID= 4417  format=   "
		::= { iqhco30CmdEntry 4417 }


	iqhco30LoggingLogChangeoverRollCall101State4420 OBJECT-TYPE
		SYNTAX		INTEGER { disable(0), enable(1) }
		MAX-ACCESS		read-write
		STATUS			current
		DESCRIPTION
				"TYPE: - Checkbox
				 PAGE: - Common- Setup- Logging- Log Changeover
					RollCall 101 State_  cmdID= 4420 "
		::= { iqhco30CmdEntry 4420 }


	iqhco30LoggingLogChangeoverRollCall101State4421 OBJECT-TYPE
		SYNTAX		RollCallString
		MAX-ACCESS		read-only
		STATUS			current
		DESCRIPTION
				"TYPE: - Display
				 PAGE: - Common- Setup- Logging- Log Changeover
					RollCall 101 State  cmdID= 4421  format=   "
		::= { iqhco30CmdEntry 4421 }


	iqhco30LoggingLogChangeoverRollCall102State4424 OBJECT-TYPE
		SYNTAX		INTEGER { disable(0), enable(1) }
		MAX-ACCESS		read-write
		STATUS			current
		DESCRIPTION
				"TYPE: - Checkbox
				 PAGE: - Common- Setup- Logging- Log Changeover
					RollCall 102 State_  cmdID= 4424 "
		::= { iqhco30CmdEntry 4424 }


	iqhco30LoggingLogChangeoverRollCall102State4425 OBJECT-TYPE
		SYNTAX		RollCallString
		MAX-ACCESS		read-only
		STATUS			current
		DESCRIPTION
				"TYPE: - Display
				 PAGE: - Common- Setup- Logging- Log Changeover
					RollCall 102 State  cmdID= 4425  format=   "
		::= { iqhco30CmdEntry 4425 }


	iqhco30LoggingLogChangeoverRollCall103State4428 OBJECT-TYPE
		SYNTAX		INTEGER { disable(0), enable(1) }
		MAX-ACCESS		read-write
		STATUS			current
		DESCRIPTION
				"TYPE: - Checkbox
				 PAGE: - Common- Setup- Logging- Log Changeover
					RollCall 103 State_  cmdID= 4428 "
		::= { iqhco30CmdEntry 4428 }


	iqhco30LoggingLogChangeoverRollCall103State4429 OBJECT-TYPE
		SYNTAX		RollCallString
		MAX-ACCESS		read-only
		STATUS			current
		DESCRIPTION
				"TYPE: - Display
				 PAGE: - Common- Setup- Logging- Log Changeover
					RollCall 103 State  cmdID= 4429  format=   "
		::= { iqhco30CmdEntry 4429 }


	iqhco30LoggingLogChangeoverRollCall104State4432 OBJECT-TYPE
		SYNTAX		INTEGER { disable(0), enable(1) }
		MAX-ACCESS		read-write
		STATUS			current
		DESCRIPTION
				"TYPE: - Checkbox
				 PAGE: - Common- Setup- Logging- Log Changeover
					RollCall 104 State_  cmdID= 4432 "
		::= { iqhco30CmdEntry 4432 }


	iqhco30LoggingLogChangeoverRollCall104State4433 OBJECT-TYPE
		SYNTAX		RollCallString
		MAX-ACCESS		read-only
		STATUS			current
		DESCRIPTION
				"TYPE: - Display
				 PAGE: - Common- Setup- Logging- Log Changeover
					RollCall 104 State  cmdID= 4433  format=   "
		::= { iqhco30CmdEntry 4433 }


	iqhco30LoggingLogChangeoverRollTrkOut1State4436 OBJECT-TYPE
		SYNTAX		INTEGER { disable(0), enable(1) }
		MAX-ACCESS		read-write
		STATUS			current
		DESCRIPTION
				"TYPE: - Checkbox
				 PAGE: - Common- Setup- Logging- Log Changeover
					RollTrk Out1 State_  cmdID= 4436 "
		::= { iqhco30CmdEntry 4436 }


	iqhco30LoggingLogChangeoverRollTrkOut1State4437 OBJECT-TYPE
		SYNTAX		RollCallString
		MAX-ACCESS		read-only
		STATUS			current
		DESCRIPTION
				"TYPE: - Display
				 PAGE: - Common- Setup- Logging- Log Changeover
					RollTrk Out1 State  cmdID= 4437  format=   "
		::= { iqhco30CmdEntry 4437 }


	iqhco30LoggingLogChangeoverRollTrkOut2State4440 OBJECT-TYPE
		SYNTAX		INTEGER { disable(0), enable(1) }
		MAX-ACCESS		read-write
		STATUS			current
		DESCRIPTION
				"TYPE: - Checkbox
				 PAGE: - Common- Setup- Logging- Log Changeover
					RollTrk Out2 State_  cmdID= 4440 "
		::= { iqhco30CmdEntry 4440 }


	iqhco30LoggingLogChangeoverRollTrkOut2State4441 OBJECT-TYPE
		SYNTAX		RollCallString
		MAX-ACCESS		read-only
		STATUS			current
		DESCRIPTION
				"TYPE: - Display
				 PAGE: - Common- Setup- Logging- Log Changeover
					RollTrk Out2 State  cmdID= 4441  format=   "
		::= { iqhco30CmdEntry 4441 }


	iqhco30LoggingLogChangeoverRollTrkOut3State4444 OBJECT-TYPE
		SYNTAX		INTEGER { disable(0), enable(1) }
		MAX-ACCESS		read-write
		STATUS			current
		DESCRIPTION
				"TYPE: - Checkbox
				 PAGE: - Common- Setup- Logging- Log Changeover
					RollTrk Out3 State_  cmdID= 4444 "
		::= { iqhco30CmdEntry 4444 }


	iqhco30LoggingLogChangeoverRollTrkOut3State4445 OBJECT-TYPE
		SYNTAX		RollCallString
		MAX-ACCESS		read-only
		STATUS			current
		DESCRIPTION
				"TYPE: - Display
				 PAGE: - Common- Setup- Logging- Log Changeover
					RollTrk Out3 State  cmdID= 4445  format=   "
		::= { iqhco30CmdEntry 4445 }


	iqhco30LoggingLogChangeoverRollTrkOut4State4448 OBJECT-TYPE
		SYNTAX		INTEGER { disable(0), enable(1) }
		MAX-ACCESS		read-write
		STATUS			current
		DESCRIPTION
				"TYPE: - Checkbox
				 PAGE: - Common- Setup- Logging- Log Changeover
					RollTrk Out4 State_  cmdID= 4448 "
		::= { iqhco30CmdEntry 4448 }


	iqhco30LoggingLogChangeoverRollTrkOut4State4449 OBJECT-TYPE
		SYNTAX		RollCallString
		MAX-ACCESS		read-only
		STATUS			current
		DESCRIPTION
				"TYPE: - Display
				 PAGE: - Common- Setup- Logging- Log Changeover
					RollTrk Out4 State  cmdID= 4449  format=   "
		::= { iqhco30CmdEntry 4449 }


	iqhco30SetupRollTracksRollTrackIndex1495 OBJECT-TYPE
		SYNTAX		INTEGER
		MAX-ACCESS		read-write
		STATUS			current
		DESCRIPTION
				"TYPE: - Number
				 PAGE: - Common- Setup- RollTracks
					RollTrack Index  cmdID= 1495  min= 1  max= 70  step= 1  format= %.0f  div_scale= 1 
					Min = 1  Max = 70  Step = 1 "
		::= { iqhco30CmdEntry 1495 }


	iqhco30SetupRollTracksRollTrackSource1496 OBJECT-TYPE
		SYNTAX		INTEGER
		MAX-ACCESS		read-write
		STATUS			current
		DESCRIPTION
				"TYPE: - Number
				 PAGE: - Common- Setup- RollTracks
					RollTrack Source  cmdID= 1496  min= -1  max= 28  step= 1  format= %.0f  div_scale= 1 
					Min = -1  Max = 28  Step = 1 "
		::= { iqhco30CmdEntry 1496 }


	iqhco30SetupRollTracksRollTrackDisable OBJECT-TYPE
		SYNTAX		INTEGER { disable(0), enable(1) }
		MAX-ACCESS		read-write
		STATUS			current
		DESCRIPTION
				"TYPE: - Checkbox
				 PAGE: - Common- Setup- RollTracks
					RollTrack Disable  cmdID= 1513 "
		::= { iqhco30CmdEntry 1513 }


	iqhco30SetupRollTracksRollTrackAddress1497 OBJECT-TYPE
		SYNTAX		RollCallString
		MAX-ACCESS		read-write
		STATUS			current
		DESCRIPTION
				"TYPE: - Editstring
				 PAGE: - Common- Setup- RollTracks
					RollTrack Address  cmdID= 1497  "
		::= { iqhco30CmdEntry 1497 }


	iqhco30SetupRollTracksRollTrackCommand1498 OBJECT-TYPE
		SYNTAX		RollCallString
		MAX-ACCESS		read-write
		STATUS			current
		DESCRIPTION
				"TYPE: - Editstring
				 PAGE: - Common- Setup- RollTracks
					RollTrack Command  cmdID= 1498  "
		::= { iqhco30CmdEntry 1498 }


	iqhco30SetupRollTracksRollTrackSending OBJECT-TYPE
		SYNTAX		RollCallString
		MAX-ACCESS		read-only
		STATUS			current
		DESCRIPTION
				"TYPE: - Display
				 PAGE: - Common- Setup- RollTracks
					RollTrack Sending  cmdID= 1514  format=   "
		::= { iqhco30CmdEntry 1514 }


	iqhco30SetupRollTracksRollTrackStatus OBJECT-TYPE
		SYNTAX		RollCallString
		MAX-ACCESS		read-only
		STATUS			current
		DESCRIPTION
				"TYPE: - Display
				 PAGE: - Common- Setup- RollTracks
					RollTrack Status  cmdID= 1511  format=   "
		::= { iqhco30CmdEntry 1511 }


	iqhco30SetupRollTracksRollTrackIndex2870 OBJECT-TYPE
		SYNTAX		INTEGER
		MAX-ACCESS		read-write
		STATUS			current
		DESCRIPTION
				"TYPE: - Number
				 PAGE: - Common- Setup- RollTracks
					RollTrack Index  cmdID= 2870  min= 1  max= 70  step= 1  format= %.0f  div_scale= 1 
					Min = 1  Max = 70  Step = 1 "
		::= { iqhco30CmdEntry 2870 }


	iqhco30SetupRollTracksRollTrackSource2871 OBJECT-TYPE
		SYNTAX		INTEGER
		MAX-ACCESS		read-write
		STATUS			current
		DESCRIPTION
				"TYPE: - Number
				 PAGE: - Common- Setup- RollTracks
					RollTrack Source  cmdID= 2871  min= -1  max= 28  step= 1  format= %.0f  div_scale= 1 
					Min = -1  Max = 28  Step = 1 "
		::= { iqhco30CmdEntry 2871 }


	iqhco30SetupRollTracksRollTrackAddress2872 OBJECT-TYPE
		SYNTAX		RollCallString
		MAX-ACCESS		read-write
		STATUS			current
		DESCRIPTION
				"TYPE: - Editstring
				 PAGE: - Common- Setup- RollTracks
					RollTrack Address  cmdID= 2872  "
		::= { iqhco30CmdEntry 2872 }


	iqhco30SetupRollTracksRollTrackCommand2873 OBJECT-TYPE
		SYNTAX		RollCallString
		MAX-ACCESS		read-write
		STATUS			current
		DESCRIPTION
				"TYPE: - Editstring
				 PAGE: - Common- Setup- RollTracks
					RollTrack Command  cmdID= 2873  "
		::= { iqhco30CmdEntry 2873 }


	iqhco30CommonStatusStatusDisplay OBJECT-TYPE
		SYNTAX		INTEGER {
							val-Video-Status(0),
							val-Audio-Input-Status(1),
							val-Rules-Status(2)
							}
		MAX-ACCESS		read-write
		STATUS			current
		DESCRIPTION
				"TYPE: - RadiobuttonList
				 PAGE: - Common
					Status Display  cmdID= 1915 
					Video Status  value= 0  
					Audio Input Status  value= 1  
					Rules Status  value= 2  "
		::= { iqhco30CmdEntry 1915 }


	iqhco30CommonStatusProduct OBJECT-TYPE
		SYNTAX		RollCallString
		MAX-ACCESS		read-only
		STATUS			current
		DESCRIPTION
				"TYPE: - Display
				 PAGE: - Common
					Product  cmdID= 5000  format=   "
		::= { iqhco30CmdEntry 5000 }


	iqhco30CommonStatusSoftwareVersion OBJECT-TYPE
		SYNTAX		RollCallString
		MAX-ACCESS		read-only
		STATUS			current
		DESCRIPTION
				"TYPE: - Display
				 PAGE: - Common
					Software Version  cmdID= 2  format=   "
		::= { iqhco30CmdEntry 2 }


	iqhco30CommonStatusSerialNo OBJECT-TYPE
		SYNTAX		RollCallString
		MAX-ACCESS		read-only
		STATUS			current
		DESCRIPTION
				"TYPE: - Display
				 PAGE: - Common
					Serial No  cmdID= 1  format=   "
		::= { iqhco30CmdEntry 1 }


	iqhco30CommonStatusFactoryDefaults OBJECT-TYPE
		SYNTAX		INTEGER { noAction(0),val-Factory-Defaults(1) }
		MAX-ACCESS		read-write
		STATUS			current
		DESCRIPTION
				"TYPE: - Button
				 PAGE: - Common
					Factory Defaults  cmdID= 5020  value= 1  "
		::= { iqhco30CmdEntry 5020 }


	iqhco30CommonStatusDefaultSetting OBJECT-TYPE
		SYNTAX		INTEGER { noAction(0),val-Default-Setting(1) }
		MAX-ACCESS		read-write
		STATUS			current
		DESCRIPTION
				"TYPE: - Button
				 PAGE: - Common
					Default Setting  cmdID= 5021  value= 1  "
		::= { iqhco30CmdEntry 5021 }


	iqhco30CommonStatusRestart OBJECT-TYPE
		SYNTAX		INTEGER { noAction(0),val-Restart(1) }
		MAX-ACCESS		read-write
		STATUS			current
		DESCRIPTION
				"TYPE: - Button
				 PAGE: - Common
					Restart  cmdID= 4  value= 1  "
		::= { iqhco30CmdEntry 4 }


	iqhco30CommonStatusBuild OBJECT-TYPE
		SYNTAX		RollCallString
		MAX-ACCESS		read-only
		STATUS			current
		DESCRIPTION
				"TYPE: - Display
				 PAGE: - Common
					Build  cmdID= 5  format=   "
		::= { iqhco30CmdEntry 5 }


	iqhco30CommonStatusPCB OBJECT-TYPE
		SYNTAX		RollCallString
		MAX-ACCESS		read-only
		STATUS			current
		DESCRIPTION
				"TYPE: - Display
				 PAGE: - Common
					PCB  cmdID= 6  format=   "
		::= { iqhco30CmdEntry 6 }


	iqhco30CommonStatusKOSVersion OBJECT-TYPE
		SYNTAX		RollCallString
		MAX-ACCESS		read-only
		STATUS			current
		DESCRIPTION
				"TYPE: - Display
				 PAGE: - Common
					KOS Version  cmdID= 7  format=   "
		::= { iqhco30CmdEntry 7 }


	iqhco30CommonStatusFirmwareVersion OBJECT-TYPE
		SYNTAX		RollCallString
		MAX-ACCESS		read-only
		STATUS			current
		DESCRIPTION
				"TYPE: - Display
				 PAGE: - Common
					Firmware Version  cmdID= 5001  format=   "
		::= { iqhco30CmdEntry 5001 }


	iqhco30CommonStatusUpTime OBJECT-TYPE
		SYNTAX		RollCallString
		MAX-ACCESS		read-only
		STATUS			current
		DESCRIPTION
				"TYPE: - Display
				 PAGE: - Common
					Up Time  cmdID= 8  format=   "
		::= { iqhco30CmdEntry 8 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S51083157
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:04:00
--				: 
-- Comments		: 
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
-- Vary			: YES
--
-- Value(s)		: 18
--				: 
-- Comments		: 
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: BACKUP
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 1
--				: 
-- Comments		: 
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				: 
-- Comments		: 
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
-- Vary			: YES
--
-- Value(s)		: 5
--				: 
-- Comments		: 
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
-- Vary			: YES
--
-- Value(s)		: 2
--				: 
-- Comments		: 
--
---------------------------------------------------------------------------------------------------
-- Header		: GPI_1_STATE
--
-- MIB ref		: swCardEventLogSlotXX       .11.71.80.73.95.49.95.83.84.65.84.69
-- absolute OID	: 1.3.6.1.4.1.7995.2.6.1.1.XX.11.71.80.73.95.49.95.83.84.65.84.69
-- Vary			: YES
--
-- Value(s)		: OK:Unused
--				: 
-- Comments		: 
--
---------------------------------------------------------------------------------------------------
-- Header		: GPI_2_STATE
--
-- MIB ref		: swCardEventLogSlotXX       .11.71.80.73.95.50.95.83.84.65.84.69
-- absolute OID	: 1.3.6.1.4.1.7995.2.6.1.1.XX.11.71.80.73.95.50.95.83.84.65.84.69
-- Vary			: YES
--
-- Value(s)		: OK:Unused
--				: 
-- Comments		: 
--
---------------------------------------------------------------------------------------------------
-- Header		: GPI_3_STATE
--
-- MIB ref		: swCardEventLogSlotXX       .11.71.80.73.95.51.95.83.84.65.84.69
-- absolute OID	: 1.3.6.1.4.1.7995.2.6.1.1.XX.11.71.80.73.95.51.95.83.84.65.84.69
-- Vary			: YES
--
-- Value(s)		: OK:Unused
--				: 
-- Comments		: 
--
---------------------------------------------------------------------------------------------------
-- Header		: GPI_4_STATE
--
-- MIB ref		: swCardEventLogSlotXX       .11.71.80.73.95.52.95.83.84.65.84.69
-- absolute OID	: 1.3.6.1.4.1.7995.2.6.1.1.XX.11.71.80.73.95.52.95.83.84.65.84.69
-- Vary			: YES
--
-- Value(s)		: OK:Unused
--				: 
-- Comments		: 
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
-- Vary			: YES
--
-- Value(s)		: OK
--				: 
-- Comments		: 
--
---------------------------------------------------------------------------------------------------
-- Header		: RULES_STATE
--
-- MIB ref		: swCardEventLogSlotXX       .11.82.85.76.69.83.95.83.84.65.84.69
-- absolute OID	: 1.3.6.1.4.1.7995.2.6.1.1.XX.11.82.85.76.69.83.95.83.84.65.84.69
-- Vary			: YES
--
-- Value(s)		: ACTIVE:BACKUP
--				: 
-- Comments		: 
--
---------------------------------------------------------------------------------------------------
-- Header		: BACKUP_STATE
--
-- MIB ref		: swCardEventLogSlotXX       .12.66.65.67.75.85.80.95.83.84.65.84.69
-- absolute OID	: 1.3.6.1.4.1.7995.2.6.1.1.XX.12.66.65.67.75.85.80.95.83.84.65.84.69
-- Vary			: YES
--
-- Value(s)		: FAIL
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 4713.4713.4713
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD/SD/3G SDI
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: HD/SD/3G SDI
--				: 
-- Comments		: 
--
---------------------------------------------------------------------------------------------------
-- Header		: MASTER_STATE
--
-- MIB ref		: swCardEventLogSlotXX       .12.77.65.83.84.69.82.95.83.84.65.84.69
-- absolute OID	: 1.3.6.1.4.1.7995.2.6.1.1.XX.12.77.65.83.84.69.82.95.83.84.65.84.69
-- Vary			: YES
--
-- Value(s)		: FAIL
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2014-11-13T14:51:38Z
--				: 
-- Comments		: 
--
---------------------------------------------------------------------------------------------------
-- Header		: CMD_101_STATE
--
-- MIB ref		: swCardEventLogSlotXX       .13.67.77.68.95.49.48.49.95.83.84.65.84.69
-- absolute OID	: 1.3.6.1.4.1.7995.2.6.1.1.XX.13.67.77.68.95.49.48.49.95.83.84.65.84.69
-- Vary			: YES
--
-- Value(s)		: OK:Unused
--				: 
-- Comments		: 
--
---------------------------------------------------------------------------------------------------
-- Header		: CMD_102_STATE
--
-- MIB ref		: swCardEventLogSlotXX       .13.67.77.68.95.49.48.50.95.83.84.65.84.69
-- absolute OID	: 1.3.6.1.4.1.7995.2.6.1.1.XX.13.67.77.68.95.49.48.50.95.83.84.65.84.69
-- Vary			: YES
--
-- Value(s)		: OK:Unused
--				: 
-- Comments		: 
--
---------------------------------------------------------------------------------------------------
-- Header		: CMD_103_STATE
--
-- MIB ref		: swCardEventLogSlotXX       .13.67.77.68.95.49.48.51.95.83.84.65.84.69
-- absolute OID	: 1.3.6.1.4.1.7995.2.6.1.1.XX.13.67.77.68.95.49.48.51.95.83.84.65.84.69
-- Vary			: YES
--
-- Value(s)		: OK:Unused
--				: 
-- Comments		: 
--
---------------------------------------------------------------------------------------------------
-- Header		: CMD_104_STATE
--
-- MIB ref		: swCardEventLogSlotXX       .13.67.77.68.95.49.48.52.95.83.84.65.84.69
-- absolute OID	: 1.3.6.1.4.1.7995.2.6.1.1.XX.13.67.77.68.95.49.48.52.95.83.84.65.84.69
-- Vary			: YES
--
-- Value(s)		: OK:Unused
--				: 
-- Comments		: 
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: SERIAL IN 1
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: 
-- Comments		: 
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: SERIAL IN 2
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 3G / HD / SD SDI
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: FAIL:Pattern
--				: 
-- Comments		: 
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 4700
--				: 
-- Comments		: 
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: HDBASP2B
--				: 
-- Comments		: 
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: INFO:OK
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--				: 
-- Comments		: 
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
-- Vary			: YES
--
-- Value(s)		: INFO:OK
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: Unknown
--				: 
-- Comments		: 
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
-- Vary			: YES
--
-- Value(s)		: SDHD;3G
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 1080/29i
--				: 
-- Comments		: 
--
---------------------------------------------------------------------------------------------------
-- Header		: INPUT_1_BLACK_ERRS
--
-- MIB ref		: swCardEventLogSlotXX       .18.73.78.80.85.84.95.49.95.66.76.65.67.75.95.69.82.82.83
-- absolute OID	: 1.3.6.1.4.1.7995.2.6.1.1.XX.18.73.78.80.85.84.95.49.95.66.76.65.67.75.95.69.82.82.83
-- Vary			: YES
--
-- Value(s)		: OK
--				: 
-- Comments		: 
--
---------------------------------------------------------------------------------------------------
-- Header		: INPUT_2_BLACK_ERRS
--
-- MIB ref		: swCardEventLogSlotXX       .18.73.78.80.85.84.95.50.95.66.76.65.67.75.95.69.82.82.83
-- absolute OID	: 1.3.6.1.4.1.7995.2.6.1.1.XX.18.73.78.80.85.84.95.50.95.66.76.65.67.75.95.69.82.82.83
-- Vary			: YES
--
-- Value(s)		: OK
--				: 
-- Comments		: 
--
---------------------------------------------------------------------------------------------------
-- Header		: RTRACK_1_OUT_STATE
--
-- MIB ref		: swCardEventLogSlotXX       .18.82.84.82.65.67.75.95.49.95.79.85.84.95.83.84.65.84.69
-- absolute OID	: 1.3.6.1.4.1.7995.2.6.1.1.XX.18.82.84.82.65.67.75.95.49.95.79.85.84.95.83.84.65.84.69
-- Vary			: YES
--
-- Value(s)		: FALSE
--				: 
-- Comments		: 
--
---------------------------------------------------------------------------------------------------
-- Header		: RTRACK_2_OUT_STATE
--
-- MIB ref		: swCardEventLogSlotXX       .18.82.84.82.65.67.75.95.50.95.79.85.84.95.83.84.65.84.69
-- absolute OID	: 1.3.6.1.4.1.7995.2.6.1.1.XX.18.82.84.82.65.67.75.95.50.95.79.85.84.95.83.84.65.84.69
-- Vary			: YES
--
-- Value(s)		: FALSE
--				: 
-- Comments		: 
--
---------------------------------------------------------------------------------------------------
-- Header		: RTRACK_3_OUT_STATE
--
-- MIB ref		: swCardEventLogSlotXX       .18.82.84.82.65.67.75.95.51.95.79.85.84.95.83.84.65.84.69
-- absolute OID	: 1.3.6.1.4.1.7995.2.6.1.1.XX.18.82.84.82.65.67.75.95.51.95.79.85.84.95.83.84.65.84.69
-- Vary			: YES
--
-- Value(s)		: FALSE
--				: 
-- Comments		: 
--
---------------------------------------------------------------------------------------------------
-- Header		: RTRACK_4_OUT_STATE
--
-- MIB ref		: swCardEventLogSlotXX       .18.82.84.82.65.67.75.95.52.95.79.85.84.95.83.84.65.84.69
-- absolute OID	: 1.3.6.1.4.1.7995.2.6.1.1.XX.18.82.84.82.65.67.75.95.52.95.79.85.84.95.83.84.65.84.69
-- Vary			: YES
--
-- Value(s)		: FALSE
--				: 
-- Comments		: 
--
---------------------------------------------------------------------------------------------------
-- Header		: INPUT_1_FREEZE_ERRS
--
-- MIB ref		: swCardEventLogSlotXX       .19.73.78.80.85.84.95.49.95.70.82.69.69.90.69.95.69.82.82.83
-- absolute OID	: 1.3.6.1.4.1.7995.2.6.1.1.XX.19.73.78.80.85.84.95.49.95.70.82.69.69.90.69.95.69.82.82.83
-- Vary			: YES
--
-- Value(s)		: OK
--				: 
-- Comments		: 
--
---------------------------------------------------------------------------------------------------
-- Header		: INPUT_2_FREEZE_ERRS
--
-- MIB ref		: swCardEventLogSlotXX       .19.73.78.80.85.84.95.50.95.70.82.69.69.90.69.95.69.82.82.83
-- absolute OID	: 1.3.6.1.4.1.7995.2.6.1.1.XX.19.73.78.80.85.84.95.50.95.70.82.69.69.90.69.95.69.82.82.83
-- Vary			: YES
--
-- Value(s)		: OK
--				: 
-- Comments		: 
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: INFO:OK
--				: 
-- Comments		: 
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
-- Vary			: YES
--
-- Value(s)		: INFO:OK
--				: 
-- Comments		: 
--
---------------------------------------------------------------------------------------------------
-- Header		: INPUT_1_EMBEDDED_AUDIO_1_1_STATE
--
-- MIB ref		: swCardEventLogSlotXX       .32.73.78.80.85.84.95.49.95.69.77.66.69.68.68.69.68.95.65.85.68.73.79.95.49.95.49.95.83.84.65.84.69
-- absolute OID	: 1.3.6.1.4.1.7995.2.6.1.1.XX.32.73.78.80.85.84.95.49.95.69.77.66.69.68.68.69.68.95.65.85.68.73.79.95.49.95.49.95.83.84.65.84.69
-- Vary			: YES
--
-- Value(s)		: FAIL:Input Lost
--				: 
-- Comments		: 
--
---------------------------------------------------------------------------------------------------
-- Header		: INPUT_1_EMBEDDED_AUDIO_1_2_STATE
--
-- MIB ref		: swCardEventLogSlotXX       .32.73.78.80.85.84.95.49.95.69.77.66.69.68.68.69.68.95.65.85.68.73.79.95.49.95.50.95.83.84.65.84.69
-- absolute OID	: 1.3.6.1.4.1.7995.2.6.1.1.XX.32.73.78.80.85.84.95.49.95.69.77.66.69.68.68.69.68.95.65.85.68.73.79.95.49.95.50.95.83.84.65.84.69
-- Vary			: YES
--
-- Value(s)		: FAIL:Input Lost
--				: 
-- Comments		: 
--
---------------------------------------------------------------------------------------------------
-- Header		: INPUT_1_EMBEDDED_AUDIO_2_1_STATE
--
-- MIB ref		: swCardEventLogSlotXX       .32.73.78.80.85.84.95.49.95.69.77.66.69.68.68.69.68.95.65.85.68.73.79.95.50.95.49.95.83.84.65.84.69
-- absolute OID	: 1.3.6.1.4.1.7995.2.6.1.1.XX.32.73.78.80.85.84.95.49.95.69.77.66.69.68.68.69.68.95.65.85.68.73.79.95.50.95.49.95.83.84.65.84.69
-- Vary			: YES
--
-- Value(s)		: FAIL:Input Lost
--				: 
-- Comments		: 
--
---------------------------------------------------------------------------------------------------
-- Header		: INPUT_1_EMBEDDED_AUDIO_2_2_STATE
--
-- MIB ref		: swCardEventLogSlotXX       .32.73.78.80.85.84.95.49.95.69.77.66.69.68.68.69.68.95.65.85.68.73.79.95.50.95.50.95.83.84.65.84.69
-- absolute OID	: 1.3.6.1.4.1.7995.2.6.1.1.XX.32.73.78.80.85.84.95.49.95.69.77.66.69.68.68.69.68.95.65.85.68.73.79.95.50.95.50.95.83.84.65.84.69
-- Vary			: YES
--
-- Value(s)		: FAIL:Input Lost
--				: 
-- Comments		: 
--
---------------------------------------------------------------------------------------------------
-- Header		: INPUT_1_EMBEDDED_AUDIO_3_1_STATE
--
-- MIB ref		: swCardEventLogSlotXX       .32.73.78.80.85.84.95.49.95.69.77.66.69.68.68.69.68.95.65.85.68.73.79.95.51.95.49.95.83.84.65.84.69
-- absolute OID	: 1.3.6.1.4.1.7995.2.6.1.1.XX.32.73.78.80.85.84.95.49.95.69.77.66.69.68.68.69.68.95.65.85.68.73.79.95.51.95.49.95.83.84.65.84.69
-- Vary			: YES
--
-- Value(s)		: FAIL:Input Lost
--				: 
-- Comments		: 
--
---------------------------------------------------------------------------------------------------
-- Header		: INPUT_1_EMBEDDED_AUDIO_3_2_STATE
--
-- MIB ref		: swCardEventLogSlotXX       .32.73.78.80.85.84.95.49.95.69.77.66.69.68.68.69.68.95.65.85.68.73.79.95.51.95.50.95.83.84.65.84.69
-- absolute OID	: 1.3.6.1.4.1.7995.2.6.1.1.XX.32.73.78.80.85.84.95.49.95.69.77.66.69.68.68.69.68.95.65.85.68.73.79.95.51.95.50.95.83.84.65.84.69
-- Vary			: YES
--
-- Value(s)		: FAIL:Input Lost
--				: 
-- Comments		: 
--
---------------------------------------------------------------------------------------------------
-- Header		: INPUT_1_EMBEDDED_AUDIO_4_1_STATE
--
-- MIB ref		: swCardEventLogSlotXX       .32.73.78.80.85.84.95.49.95.69.77.66.69.68.68.69.68.95.65.85.68.73.79.95.52.95.49.95.83.84.65.84.69
-- absolute OID	: 1.3.6.1.4.1.7995.2.6.1.1.XX.32.73.78.80.85.84.95.49.95.69.77.66.69.68.68.69.68.95.65.85.68.73.79.95.52.95.49.95.83.84.65.84.69
-- Vary			: YES
--
-- Value(s)		: FAIL:Input Lost
--				: 
-- Comments		: 
--
---------------------------------------------------------------------------------------------------
-- Header		: INPUT_1_EMBEDDED_AUDIO_4_2_STATE
--
-- MIB ref		: swCardEventLogSlotXX       .32.73.78.80.85.84.95.49.95.69.77.66.69.68.68.69.68.95.65.85.68.73.79.95.52.95.50.95.83.84.65.84.69
-- absolute OID	: 1.3.6.1.4.1.7995.2.6.1.1.XX.32.73.78.80.85.84.95.49.95.69.77.66.69.68.68.69.68.95.65.85.68.73.79.95.52.95.50.95.83.84.65.84.69
-- Vary			: YES
--
-- Value(s)		: FAIL:Input Lost
--				: 
-- Comments		: 
--
---------------------------------------------------------------------------------------------------
-- Header		: INPUT_1_EMBEDDED_AUDIO_5_1_STATE
--
-- MIB ref		: swCardEventLogSlotXX       .32.73.78.80.85.84.95.49.95.69.77.66.69.68.68.69.68.95.65.85.68.73.79.95.53.95.49.95.83.84.65.84.69
-- absolute OID	: 1.3.6.1.4.1.7995.2.6.1.1.XX.32.73.78.80.85.84.95.49.95.69.77.66.69.68.68.69.68.95.65.85.68.73.79.95.53.95.49.95.83.84.65.84.69
-- Vary			: YES
--
-- Value(s)		: FAIL:Input Lost
--				: 
-- Comments		: 
--
---------------------------------------------------------------------------------------------------
-- Header		: INPUT_1_EMBEDDED_AUDIO_5_2_STATE
--
-- MIB ref		: swCardEventLogSlotXX       .32.73.78.80.85.84.95.49.95.69.77.66.69.68.68.69.68.95.65.85.68.73.79.95.53.95.50.95.83.84.65.84.69
-- absolute OID	: 1.3.6.1.4.1.7995.2.6.1.1.XX.32.73.78.80.85.84.95.49.95.69.77.66.69.68.68.69.68.95.65.85.68.73.79.95.53.95.50.95.83.84.65.84.69
-- Vary			: YES
--
-- Value(s)		: FAIL:Input Lost
--				: 
-- Comments		: 
--
---------------------------------------------------------------------------------------------------
-- Header		: INPUT_1_EMBEDDED_AUDIO_6_1_STATE
--
-- MIB ref		: swCardEventLogSlotXX       .32.73.78.80.85.84.95.49.95.69.77.66.69.68.68.69.68.95.65.85.68.73.79.95.54.95.49.95.83.84.65.84.69
-- absolute OID	: 1.3.6.1.4.1.7995.2.6.1.1.XX.32.73.78.80.85.84.95.49.95.69.77.66.69.68.68.69.68.95.65.85.68.73.79.95.54.95.49.95.83.84.65.84.69
-- Vary			: YES
--
-- Value(s)		: FAIL:Input Lost
--				: 
-- Comments		: 
--
---------------------------------------------------------------------------------------------------
-- Header		: INPUT_1_EMBEDDED_AUDIO_6_2_STATE
--
-- MIB ref		: swCardEventLogSlotXX       .32.73.78.80.85.84.95.49.95.69.77.66.69.68.68.69.68.95.65.85.68.73.79.95.54.95.50.95.83.84.65.84.69
-- absolute OID	: 1.3.6.1.4.1.7995.2.6.1.1.XX.32.73.78.80.85.84.95.49.95.69.77.66.69.68.68.69.68.95.65.85.68.73.79.95.54.95.50.95.83.84.65.84.69
-- Vary			: YES
--
-- Value(s)		: FAIL:Input Lost
--				: 
-- Comments		: 
--
---------------------------------------------------------------------------------------------------
-- Header		: INPUT_1_EMBEDDED_AUDIO_7_1_STATE
--
-- MIB ref		: swCardEventLogSlotXX       .32.73.78.80.85.84.95.49.95.69.77.66.69.68.68.69.68.95.65.85.68.73.79.95.55.95.49.95.83.84.65.84.69
-- absolute OID	: 1.3.6.1.4.1.7995.2.6.1.1.XX.32.73.78.80.85.84.95.49.95.69.77.66.69.68.68.69.68.95.65.85.68.73.79.95.55.95.49.95.83.84.65.84.69
-- Vary			: YES
--
-- Value(s)		: FAIL:Input Lost
--				: 
-- Comments		: 
--
---------------------------------------------------------------------------------------------------
-- Header		: INPUT_1_EMBEDDED_AUDIO_7_2_STATE
--
-- MIB ref		: swCardEventLogSlotXX       .32.73.78.80.85.84.95.49.95.69.77.66.69.68.68.69.68.95.65.85.68.73.79.95.55.95.50.95.83.84.65.84.69
-- absolute OID	: 1.3.6.1.4.1.7995.2.6.1.1.XX.32.73.78.80.85.84.95.49.95.69.77.66.69.68.68.69.68.95.65.85.68.73.79.95.55.95.50.95.83.84.65.84.69
-- Vary			: YES
--
-- Value(s)		: FAIL:Input Lost
--				: 
-- Comments		: 
--
---------------------------------------------------------------------------------------------------
-- Header		: INPUT_1_EMBEDDED_AUDIO_8_1_STATE
--
-- MIB ref		: swCardEventLogSlotXX       .32.73.78.80.85.84.95.49.95.69.77.66.69.68.68.69.68.95.65.85.68.73.79.95.56.95.49.95.83.84.65.84.69
-- absolute OID	: 1.3.6.1.4.1.7995.2.6.1.1.XX.32.73.78.80.85.84.95.49.95.69.77.66.69.68.68.69.68.95.65.85.68.73.79.95.56.95.49.95.83.84.65.84.69
-- Vary			: YES
--
-- Value(s)		: FAIL:Input Lost
--				: 
-- Comments		: 
--
---------------------------------------------------------------------------------------------------
-- Header		: INPUT_1_EMBEDDED_AUDIO_8_2_STATE
--
-- MIB ref		: swCardEventLogSlotXX       .32.73.78.80.85.84.95.49.95.69.77.66.69.68.68.69.68.95.65.85.68.73.79.95.56.95.50.95.83.84.65.84.69
-- absolute OID	: 1.3.6.1.4.1.7995.2.6.1.1.XX.32.73.78.80.85.84.95.49.95.69.77.66.69.68.68.69.68.95.65.85.68.73.79.95.56.95.50.95.83.84.65.84.69
-- Vary			: YES
--
-- Value(s)		: FAIL:Input Lost
--				: 
-- Comments		: 
--
---------------------------------------------------------------------------------------------------
-- Header		: INPUT_2_EMBEDDED_AUDIO_1_1_STATE
--
-- MIB ref		: swCardEventLogSlotXX       .32.73.78.80.85.84.95.50.95.69.77.66.69.68.68.69.68.95.65.85.68.73.79.95.49.95.49.95.83.84.65.84.69
-- absolute OID	: 1.3.6.1.4.1.7995.2.6.1.1.XX.32.73.78.80.85.84.95.50.95.69.77.66.69.68.68.69.68.95.65.85.68.73.79.95.49.95.49.95.83.84.65.84.69
-- Vary			: YES
--
-- Value(s)		: FAIL:Input Lost
--				: 
-- Comments		: 
--
---------------------------------------------------------------------------------------------------
-- Header		: INPUT_2_EMBEDDED_AUDIO_1_2_STATE
--
-- MIB ref		: swCardEventLogSlotXX       .32.73.78.80.85.84.95.50.95.69.77.66.69.68.68.69.68.95.65.85.68.73.79.95.49.95.50.95.83.84.65.84.69
-- absolute OID	: 1.3.6.1.4.1.7995.2.6.1.1.XX.32.73.78.80.85.84.95.50.95.69.77.66.69.68.68.69.68.95.65.85.68.73.79.95.49.95.50.95.83.84.65.84.69
-- Vary			: YES
--
-- Value(s)		: FAIL:Input Lost
--				: 
-- Comments		: 
--
---------------------------------------------------------------------------------------------------
-- Header		: INPUT_2_EMBEDDED_AUDIO_2_1_STATE
--
-- MIB ref		: swCardEventLogSlotXX       .32.73.78.80.85.84.95.50.95.69.77.66.69.68.68.69.68.95.65.85.68.73.79.95.50.95.49.95.83.84.65.84.69
-- absolute OID	: 1.3.6.1.4.1.7995.2.6.1.1.XX.32.73.78.80.85.84.95.50.95.69.77.66.69.68.68.69.68.95.65.85.68.73.79.95.50.95.49.95.83.84.65.84.69
-- Vary			: YES
--
-- Value(s)		: FAIL:Input Lost
--				: 
-- Comments		: 
--
---------------------------------------------------------------------------------------------------
-- Header		: INPUT_2_EMBEDDED_AUDIO_2_2_STATE
--
-- MIB ref		: swCardEventLogSlotXX       .32.73.78.80.85.84.95.50.95.69.77.66.69.68.68.69.68.95.65.85.68.73.79.95.50.95.50.95.83.84.65.84.69
-- absolute OID	: 1.3.6.1.4.1.7995.2.6.1.1.XX.32.73.78.80.85.84.95.50.95.69.77.66.69.68.68.69.68.95.65.85.68.73.79.95.50.95.50.95.83.84.65.84.69
-- Vary			: YES
--
-- Value(s)		: FAIL:Input Lost
--				: 
-- Comments		: 
--
---------------------------------------------------------------------------------------------------
-- Header		: INPUT_2_EMBEDDED_AUDIO_3_1_STATE
--
-- MIB ref		: swCardEventLogSlotXX       .32.73.78.80.85.84.95.50.95.69.77.66.69.68.68.69.68.95.65.85.68.73.79.95.51.95.49.95.83.84.65.84.69
-- absolute OID	: 1.3.6.1.4.1.7995.2.6.1.1.XX.32.73.78.80.85.84.95.50.95.69.77.66.69.68.68.69.68.95.65.85.68.73.79.95.51.95.49.95.83.84.65.84.69
-- Vary			: YES
--
-- Value(s)		: FAIL:Input Lost
--				: 
-- Comments		: 
--
---------------------------------------------------------------------------------------------------
-- Header		: INPUT_2_EMBEDDED_AUDIO_3_2_STATE
--
-- MIB ref		: swCardEventLogSlotXX       .32.73.78.80.85.84.95.50.95.69.77.66.69.68.68.69.68.95.65.85.68.73.79.95.51.95.50.95.83.84.65.84.69
-- absolute OID	: 1.3.6.1.4.1.7995.2.6.1.1.XX.32.73.78.80.85.84.95.50.95.69.77.66.69.68.68.69.68.95.65.85.68.73.79.95.51.95.50.95.83.84.65.84.69
-- Vary			: YES
--
-- Value(s)		: FAIL:Input Lost
--				: 
-- Comments		: 
--
---------------------------------------------------------------------------------------------------
-- Header		: INPUT_2_EMBEDDED_AUDIO_4_1_STATE
--
-- MIB ref		: swCardEventLogSlotXX       .32.73.78.80.85.84.95.50.95.69.77.66.69.68.68.69.68.95.65.85.68.73.79.95.52.95.49.95.83.84.65.84.69
-- absolute OID	: 1.3.6.1.4.1.7995.2.6.1.1.XX.32.73.78.80.85.84.95.50.95.69.77.66.69.68.68.69.68.95.65.85.68.73.79.95.52.95.49.95.83.84.65.84.69
-- Vary			: YES
--
-- Value(s)		: FAIL:Input Lost
--				: 
-- Comments		: 
--
---------------------------------------------------------------------------------------------------
-- Header		: INPUT_2_EMBEDDED_AUDIO_4_2_STATE
--
-- MIB ref		: swCardEventLogSlotXX       .32.73.78.80.85.84.95.50.95.69.77.66.69.68.68.69.68.95.65.85.68.73.79.95.52.95.50.95.83.84.65.84.69
-- absolute OID	: 1.3.6.1.4.1.7995.2.6.1.1.XX.32.73.78.80.85.84.95.50.95.69.77.66.69.68.68.69.68.95.65.85.68.73.79.95.52.95.50.95.83.84.65.84.69
-- Vary			: YES
--
-- Value(s)		: FAIL:Input Lost
--				: 
-- Comments		: 
--
---------------------------------------------------------------------------------------------------
-- Header		: INPUT_2_EMBEDDED_AUDIO_5_1_STATE
--
-- MIB ref		: swCardEventLogSlotXX       .32.73.78.80.85.84.95.50.95.69.77.66.69.68.68.69.68.95.65.85.68.73.79.95.53.95.49.95.83.84.65.84.69
-- absolute OID	: 1.3.6.1.4.1.7995.2.6.1.1.XX.32.73.78.80.85.84.95.50.95.69.77.66.69.68.68.69.68.95.65.85.68.73.79.95.53.95.49.95.83.84.65.84.69
-- Vary			: YES
--
-- Value(s)		: FAIL:Input Lost
--				: 
-- Comments		: 
--
---------------------------------------------------------------------------------------------------
-- Header		: INPUT_2_EMBEDDED_AUDIO_5_2_STATE
--
-- MIB ref		: swCardEventLogSlotXX       .32.73.78.80.85.84.95.50.95.69.77.66.69.68.68.69.68.95.65.85.68.73.79.95.53.95.50.95.83.84.65.84.69
-- absolute OID	: 1.3.6.1.4.1.7995.2.6.1.1.XX.32.73.78.80.85.84.95.50.95.69.77.66.69.68.68.69.68.95.65.85.68.73.79.95.53.95.50.95.83.84.65.84.69
-- Vary			: YES
--
-- Value(s)		: FAIL:Input Lost
--				: 
-- Comments		: 
--
---------------------------------------------------------------------------------------------------
-- Header		: INPUT_2_EMBEDDED_AUDIO_6_1_STATE
--
-- MIB ref		: swCardEventLogSlotXX       .32.73.78.80.85.84.95.50.95.69.77.66.69.68.68.69.68.95.65.85.68.73.79.95.54.95.49.95.83.84.65.84.69
-- absolute OID	: 1.3.6.1.4.1.7995.2.6.1.1.XX.32.73.78.80.85.84.95.50.95.69.77.66.69.68.68.69.68.95.65.85.68.73.79.95.54.95.49.95.83.84.65.84.69
-- Vary			: YES
--
-- Value(s)		: FAIL:Input Lost
--				: 
-- Comments		: 
--
---------------------------------------------------------------------------------------------------
-- Header		: INPUT_2_EMBEDDED_AUDIO_6_2_STATE
--
-- MIB ref		: swCardEventLogSlotXX       .32.73.78.80.85.84.95.50.95.69.77.66.69.68.68.69.68.95.65.85.68.73.79.95.54.95.50.95.83.84.65.84.69
-- absolute OID	: 1.3.6.1.4.1.7995.2.6.1.1.XX.32.73.78.80.85.84.95.50.95.69.77.66.69.68.68.69.68.95.65.85.68.73.79.95.54.95.50.95.83.84.65.84.69
-- Vary			: YES
--
-- Value(s)		: FAIL:Input Lost
--				: 
-- Comments		: 
--
---------------------------------------------------------------------------------------------------
-- Header		: INPUT_2_EMBEDDED_AUDIO_7_1_STATE
--
-- MIB ref		: swCardEventLogSlotXX       .32.73.78.80.85.84.95.50.95.69.77.66.69.68.68.69.68.95.65.85.68.73.79.95.55.95.49.95.83.84.65.84.69
-- absolute OID	: 1.3.6.1.4.1.7995.2.6.1.1.XX.32.73.78.80.85.84.95.50.95.69.77.66.69.68.68.69.68.95.65.85.68.73.79.95.55.95.49.95.83.84.65.84.69
-- Vary			: YES
--
-- Value(s)		: FAIL:Input Lost
--				: 
-- Comments		: 
--
---------------------------------------------------------------------------------------------------
-- Header		: INPUT_2_EMBEDDED_AUDIO_7_2_STATE
--
-- MIB ref		: swCardEventLogSlotXX       .32.73.78.80.85.84.95.50.95.69.77.66.69.68.68.69.68.95.65.85.68.73.79.95.55.95.50.95.83.84.65.84.69
-- absolute OID	: 1.3.6.1.4.1.7995.2.6.1.1.XX.32.73.78.80.85.84.95.50.95.69.77.66.69.68.68.69.68.95.65.85.68.73.79.95.55.95.50.95.83.84.65.84.69
-- Vary			: YES
--
-- Value(s)		: FAIL:Input Lost
--				: 
-- Comments		: 
--
---------------------------------------------------------------------------------------------------
-- Header		: INPUT_2_EMBEDDED_AUDIO_8_1_STATE
--
-- MIB ref		: swCardEventLogSlotXX       .32.73.78.80.85.84.95.50.95.69.77.66.69.68.68.69.68.95.65.85.68.73.79.95.56.95.49.95.83.84.65.84.69
-- absolute OID	: 1.3.6.1.4.1.7995.2.6.1.1.XX.32.73.78.80.85.84.95.50.95.69.77.66.69.68.68.69.68.95.65.85.68.73.79.95.56.95.49.95.83.84.65.84.69
-- Vary			: YES
--
-- Value(s)		: FAIL:Input Lost
--				: 
-- Comments		: 
--
---------------------------------------------------------------------------------------------------
-- Header		: INPUT_2_EMBEDDED_AUDIO_8_2_STATE
--
-- MIB ref		: swCardEventLogSlotXX       .32.73.78.80.85.84.95.50.95.69.77.66.69.68.68.69.68.95.65.85.68.73.79.95.56.95.50.95.83.84.65.84.69
-- absolute OID	: 1.3.6.1.4.1.7995.2.6.1.1.XX.32.73.78.80.85.84.95.50.95.69.77.66.69.68.68.69.68.95.65.85.68.73.79.95.56.95.50.95.83.84.65.84.69
-- Vary			: YES
--
-- Value(s)		: FAIL:Input Lost
--				: 
-- Comments		: 
--
---------------------------------------------------------------------------------------------------
