-- ************************************************************************************
-- Snell&Wilcox Card:IQDSDES
--        Module Id#:285
--       Command Set:6
--          Filename:SNELL-IQDSDES-CMD-MIB.mib
--            Author:Jonathan Riches
--              Date:10/06/2005
--              Time:13:34
--
-- Copyright (c) 2005 Snell & Wilcox Ltd
-- All rights reserved.
--
-- ************************************************************************************

SNELL-IQDSDES-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDSDES,
    moduleIQDSDESMIB
        FROM SNELL-WILCOX-PRODUCT-REG;

 moduleIQDSDESCmdMi MODULE-IDENTITY
    LAST-UPDATED "0506101334Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDSDESMIB 1 }




--********************************************************************************
--*
--*  Snell Wilcox Card:
--*  command set:
--*  list commands/menus:
--*
--******************************************************************************
	iqdsdesCmdTable OBJECT-TYPE
		SYNTAX			SEQUENCE OF IqdsdesCmdEntry
		MAX-ACCESS		not-accessible
		STATUS			current
		DESCRIPTION
				"Note the instance of this table is relected in the command set Version"
		::= { moduleIQDSDES 1 }

	iqdsdesCmdEntry OBJECT-TYPE
		SYNTAX		IqdsdesCmdEntry
		MAX-ACCESS		not-accessible
		STATUS			current
		DESCRIPTION
				"Entry in command table."
		INDEX	{ iqdsdesSlotIndex }
		::= { iqdsdesCmdTable 1 }

	IqdsdesCmdEntry ::=
		SEQUENCE {
			iqdsdesSlotIndex
				Unsigned32,
			iqdsdesVideoInputStandard525
				INTEGER,
			iqdsdesVideoInputStandard625
				INTEGER,
			iqdsdesVideoEncoder525OutputStd
				INTEGER,
			iqdsdesVideoEncoder625OutputStd
				INTEGER,
			iqdsdesVideoEncoderVBIPass
				INTEGER,
			iqdsdesVideoEncoderCBandwidth2MHz
				INTEGER,
			iqdsdesVideoEncoderDefaultOP
				INTEGER,
			iqdsdesVideoEncoderPatternOn
				INTEGER,
			iqdsdesVideoResetEDH
				INTEGER,
			iqdsdesUnitSoftwareVersion
				RollCallString,
			iqdsdesUnitSerialNo
				RollCallString,
			iqdsdesUnitPresetUnit
				INTEGER,
			iqdsdesUnitRestart
				INTEGER,
			iqdsdesUnitBuildNo
				RollCallString,
			iqdsdesLoggingInput
				INTEGER,
			iqdsdesLoggingStandard
				INTEGER,
			iqdsdesLoggingEDHErrors
				INTEGER,
			iqdsdesLoggingEDHErrorSeconds
				INTEGER,
			iqdsdesRollTrackRollTrackIndex
				INTEGER,
			iqdsdesRollTrackRollTrackSource
				INTEGER,
			iqdsdesRollTrackRollTrackDisable
				INTEGER,
			iqdsdesRollTrackRollTrackAddress
				RollCallString,
			iqdsdesRollTrackRollTrackCommand
				RollCallString,
			iqdsdesRollTrackRollTrackStatus
				RollCallString
		}

	iqdsdesSlotIndex OBJECT-TYPE
		SYNTAX		Unsigned32
		MAX-ACCESS		not-accessible
		STATUS			current
		DESCRIPTION
				"The unique Index value for each slot.  Its value
					ranges between 1 and the value of slotNumber."
		::= { iqdsdesCmdEntry 0 }


	iqdsdesVideoInputStandard525 OBJECT-TYPE
		SYNTAX		INTEGER { disable(0), enable(1) }
		MAX-ACCESS		read-write
		STATUS			current
		DESCRIPTION
				"TYPE: - Checkbox
					525  cmdID= 1405 "
		::= { iqdsdesCmdEntry 1405 }


	iqdsdesVideoInputStandard625 OBJECT-TYPE
		SYNTAX		INTEGER { disable(0), enable(1) }
		MAX-ACCESS		read-write
		STATUS			current
		DESCRIPTION
				"TYPE: - Checkbox
					625  cmdID= 1406 "
		::= { iqdsdesCmdEntry 1406 }


	iqdsdesVideoEncoder525OutputStd OBJECT-TYPE
		SYNTAX		INTEGER {
							val_NTSC(0),
							val_NTSCJ(1),
							val_PALM(2),
							val_N4_4(3)
							}
		MAX-ACCESS		read-write
		STATUS			current
		DESCRIPTION
				"TYPE: - RadiobuttonList
					525 Output Std  cmdID= 2620 
					NTSC  value= 0  
					NTSCJ  value= 1  
					PALM  value= 2  
					N4.4  value= 3  "
		::= { iqdsdesCmdEntry 2620 }


	iqdsdesVideoEncoder625OutputStd OBJECT-TYPE
		SYNTAX		INTEGER {
							val_PAL(0),
							val_PALN(1)
							}
		MAX-ACCESS		read-write
		STATUS			current
		DESCRIPTION
				"TYPE: - RadiobuttonList
					625 Output Std  cmdID= 2621 
					PAL  value= 0  
					PALN  value= 1  "
		::= { iqdsdesCmdEntry 2621 }


	iqdsdesVideoEncoderVBIPass OBJECT-TYPE
		SYNTAX		INTEGER { disable(0), enable(1) }
		MAX-ACCESS		read-write
		STATUS			current
		DESCRIPTION
				"TYPE: - Checkbox
					VBI Pass  cmdID= 2690 "
		::= { iqdsdesCmdEntry 2690 }


	iqdsdesVideoEncoderCBandwidth2MHz OBJECT-TYPE
		SYNTAX		INTEGER { disable(0), enable(1) }
		MAX-ACCESS		read-write
		STATUS			current
		DESCRIPTION
				"TYPE: - Checkbox
					C Bandwidth 2MHz  cmdID= 2622 "
		::= { iqdsdesCmdEntry 2622 }


	iqdsdesVideoEncoderDefaultOP OBJECT-TYPE
		SYNTAX		INTEGER {
							val_Mute(0),
							val_Black(1),
							val_Bars(2)
							}
		MAX-ACCESS		read-write
		STATUS			current
		DESCRIPTION
				"TYPE: - RadiobuttonList
					Default O/P  cmdID= 2623 
					Mute  value= 0  
					Black  value= 1  
					Bars  value= 2  "
		::= { iqdsdesCmdEntry 2623 }


	iqdsdesVideoEncoderPatternOn OBJECT-TYPE
		SYNTAX		INTEGER { disable(0), enable(1) }
		MAX-ACCESS		read-write
		STATUS			current
		DESCRIPTION
				"TYPE: - Checkbox
					Pattern On  cmdID= 2624 "
		::= { iqdsdesCmdEntry 2624 }


	iqdsdesVideoResetEDH OBJECT-TYPE
		SYNTAX		INTEGER { noAction(0),val_Reset_EDH(1) }
		MAX-ACCESS		read-write
		STATUS			current
		DESCRIPTION
				"TYPE: - Button
					Reset EDH  cmdID= 1409  value= 1  "
		::= { iqdsdesCmdEntry 1409 }


	iqdsdesUnitSoftwareVersion OBJECT-TYPE
		SYNTAX		RollCallString
		MAX-ACCESS		read-only
		STATUS			current
		DESCRIPTION
				"TYPE: - Display
					Software Version  cmdID= 2  format=   "
		::= { iqdsdesCmdEntry 2 }


	iqdsdesUnitSerialNo OBJECT-TYPE
		SYNTAX		RollCallString
		MAX-ACCESS		read-only
		STATUS			current
		DESCRIPTION
				"TYPE: - Display
					Serial No  cmdID= 1  format=   "
		::= { iqdsdesCmdEntry 1 }


	iqdsdesUnitPresetUnit OBJECT-TYPE
		SYNTAX		INTEGER { noAction(0),val_Preset_Unit(1) }
		MAX-ACCESS		read-write
		STATUS			current
		DESCRIPTION
				"TYPE: - Button
					Preset Unit  cmdID= 3  value= 1  "
		::= { iqdsdesCmdEntry 3 }


	iqdsdesUnitRestart OBJECT-TYPE
		SYNTAX		INTEGER { noAction(0),val_Restart(1) }
		MAX-ACCESS		read-write
		STATUS			current
		DESCRIPTION
				"TYPE: - Button
					Restart  cmdID= 4  value= 1  "
		::= { iqdsdesCmdEntry 4 }


	iqdsdesUnitBuildNo OBJECT-TYPE
		SYNTAX		RollCallString
		MAX-ACCESS		read-only
		STATUS			current
		DESCRIPTION
				"TYPE: - Display
					Build No  cmdID= 5  format=   "
		::= { iqdsdesCmdEntry 5 }


	iqdsdesLoggingInput OBJECT-TYPE
		SYNTAX		INTEGER { disable(0), enable(1) }
		MAX-ACCESS		read-write
		STATUS			current
		DESCRIPTION
				"TYPE: - Checkbox
					Input  cmdID= 1060 "
		::= { iqdsdesCmdEntry 1060 }


	iqdsdesLoggingStandard OBJECT-TYPE
		SYNTAX		INTEGER { disable(0), enable(1) }
		MAX-ACCESS		read-write
		STATUS			current
		DESCRIPTION
				"TYPE: - Checkbox
					Standard  cmdID= 1061 "
		::= { iqdsdesCmdEntry 1061 }


	iqdsdesLoggingEDHErrors OBJECT-TYPE
		SYNTAX		INTEGER { disable(0), enable(1) }
		MAX-ACCESS		read-write
		STATUS			current
		DESCRIPTION
				"TYPE: - Checkbox
					EDH Errors  cmdID= 1064 "
		::= { iqdsdesCmdEntry 1064 }


	iqdsdesLoggingEDHErrorSeconds OBJECT-TYPE
		SYNTAX		INTEGER { disable(0), enable(1) }
		MAX-ACCESS		read-write
		STATUS			current
		DESCRIPTION
				"TYPE: - Checkbox
					EDH Error Seconds  cmdID= 1070 "
		::= { iqdsdesCmdEntry 1070 }


	iqdsdesRollTrackRollTrackIndex OBJECT-TYPE
		SYNTAX		INTEGER
		MAX-ACCESS		read-write
		STATUS			current
		DESCRIPTION
				"TYPE: - Number
					RollTrack Index  cmdID= 1495  min= 0  max= 5  step= 1  format= %.0f  div_scale= 1 
					Min = 0  Max = 5  Step = 1 "
		::= { iqdsdesCmdEntry 1495 }


	iqdsdesRollTrackRollTrackSource OBJECT-TYPE
		SYNTAX		INTEGER
		MAX-ACCESS		read-write
		STATUS			current
		DESCRIPTION
				"TYPE: - Number
					RollTrack Source  cmdID= 1496  min= -1  max= 2  step= 1  format= %.0f  div_scale= 1 
					Min = -1  Max = 2  Step = 1 "
		::= { iqdsdesCmdEntry 1496 }


	iqdsdesRollTrackRollTrackDisable OBJECT-TYPE
		SYNTAX		INTEGER { disable(0), enable(1) }
		MAX-ACCESS		read-write
		STATUS			current
		DESCRIPTION
				"TYPE: - Checkbox
					RollTrack Disable  cmdID= 1513 "
		::= { iqdsdesCmdEntry 1513 }


	iqdsdesRollTrackRollTrackAddress OBJECT-TYPE
		SYNTAX		RollCallString
		MAX-ACCESS		read-write
		STATUS			current
		DESCRIPTION
				"TYPE: - Editstring
					RollTrack Address  cmdID= 1497  "
		::= { iqdsdesCmdEntry 1497 }


	iqdsdesRollTrackRollTrackCommand OBJECT-TYPE
		SYNTAX		RollCallString
		MAX-ACCESS		read-write
		STATUS			current
		DESCRIPTION
				"TYPE: - Editstring
					RollTrack Command  cmdID= 1498  "
		::= { iqdsdesCmdEntry 1498 }


	iqdsdesRollTrackRollTrackStatus OBJECT-TYPE
		SYNTAX		RollCallString
		MAX-ACCESS		read-only
		STATUS			current
		DESCRIPTION
				"TYPE: - Display
					RollTrack Status  cmdID= 1511  format=   "
		::= { iqdsdesCmdEntry 1511 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: ERR
--				: RESET
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: 525
--				: 625
--				: ERR
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
--				: ERR
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary number  : YES
-- Value(s)		: 
--				: 
-- Comments		: 
--
---------------------------------------------------------------------------------------------------
