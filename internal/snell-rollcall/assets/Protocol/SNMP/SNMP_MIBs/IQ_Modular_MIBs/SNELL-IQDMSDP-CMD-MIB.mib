-- ************************************************************************************
-- Snell&Wilcox Card:IQDMSDP
--        Module Id#:101
--       Command Set:6
--          Filename:SNELL-IQDMSDP-CMD-MIB.mib
--            Author:Jonathan Riches
--              Date:30/06/2005
--              Time:08:27
--
-- Copyright (c) 2005 Snell & Wilcox Ltd
-- All rights reserved.
--
-- ************************************************************************************

SNELL-IQDMSDP-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMSDP,
    moduleIQDMSDPMIB
        FROM SNELL-WILCOX-PRODUCT-REG;

 moduleIQDMSDPCmdMi MODULE-IDENTITY
    LAST-UPDATED "0506300827Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMSDPMIB 1 }




--********************************************************************************
--*
--*  Snell Wilcox Card:
--*  command set:
--*  list commands/menus:
--*
--******************************************************************************
	iqdmsdpCmdTable OBJECT-TYPE
		SYNTAX			SEQUENCE OF IqdmsdpCmdEntry
		MAX-ACCESS		not-accessible
		STATUS			current
		DESCRIPTION
				"Note the instance of this table is relected in the command set Version"
		::= { moduleIQDMSDP 1 }

	iqdmsdpCmdEntry OBJECT-TYPE
		SYNTAX		IqdmsdpCmdEntry
		MAX-ACCESS		not-accessible
		STATUS			current
		DESCRIPTION
				"Entry in command table."
		INDEX	{ iqdmsdpSlotIndex }
		::= { iqdmsdpCmdTable 1 }

	IqdmsdpCmdEntry ::=
		SEQUENCE {
			iqdmsdpSlotIndex
				Unsigned32,
			iqdmsdpStandard
				INTEGER,
			iqdmsdpModeDecodeMode
				INTEGER,
			iqdmsdpModeLockMode
				INTEGER,
			iqdmsdpPattern
				INTEGER,
			iqdmsdpGenlockMode
				INTEGER,
			iqdmsdpGenlockHPhase
				INTEGER,
			iqdmsdpGenlockVPhase
				INTEGER,
			iqdmsdpFreeze
				INTEGER,
			iqdmsdpProcAmpVideoGain
				INTEGER,
			iqdmsdpProcAmpBlackLevel
				INTEGER,
			iqdmsdpProcAmpChromaGain
				INTEGER,
			iqdmsdpProcAmpNTSCHue
				INTEGER,
			iqdmsdpProcAmpYCDelay
				INTEGER,
			iqdmsdpEDHEDHEnable
				INTEGER,
			iqdmsdpEDHFlagsANEDA
				INTEGER,
			iqdmsdpEDHFlagsANIDA
				INTEGER,
			iqdmsdpEDHFlagsANEDH
				INTEGER,
			iqdmsdpEDHFlagsANIDH
				INTEGER,
			iqdmsdpEDHFlagsANUES
				INTEGER,
			iqdmsdpEDHFlagsAPEDH
				INTEGER,
			iqdmsdpEDHFlagsAPEDA
				INTEGER,
			iqdmsdpEDHFlagsAPIDH
				INTEGER,
			iqdmsdpEDHFlagsAPIDA
				INTEGER,
			iqdmsdpEDHFlagsAPUES
				INTEGER,
			iqdmsdpEDHFlagsFFEDH
				INTEGER,
			iqdmsdpEDHFlagsFFEDA
				INTEGER,
			iqdmsdpEDHFlagsFFIDH
				INTEGER,
			iqdmsdpEDHFlagsFFIDA
				INTEGER,
			iqdmsdpEDHFlagsFFUES
				INTEGER,
			iqdmsdpNoiseReducerC
				INTEGER,
			iqdmsdpNoiseReducerY
				INTEGER,
			iqdmsdpSetupLineStandard
				INTEGER,
			iqdmsdpSetupAutoFreeze
				INTEGER,
			iqdmsdpSetupVITSPass
				INTEGER,
			iqdmsdpSetupPedestalStrip
				INTEGER,
			iqdmsdpSetupAudioDelayUnit1
				RollCallString,
			iqdmsdpSetupAudioDelayUnit2
				RollCallString,
			iqdmsdpSetupAudioDelayUnit3
				RollCallString,
			iqdmsdpSetupAudioDelayUnit4
				RollCallString,
			iqdmsdpSetupAudioDelayUnit5
				RollCallString,
			iqdmsdpSetupAudioDelayUnit6
				RollCallString,
			iqdmsdpSetupAudioDelayUnit7
				RollCallString,
			iqdmsdpSetupAudioDelayUnit8
				RollCallString,
			iqdmsdpSetupLoggingInpStdChange
				INTEGER,
			iqdmsdpSetupLoggingReferenceLoss
				INTEGER,
			iqdmsdpSetupPresetUnit
				INTEGER,
			iqdmsdpSetupSoftwareVersion
				RollCallString,
			iqdmsdpSetupSerialNo
				RollCallString
		}

	iqdmsdpSlotIndex OBJECT-TYPE
		SYNTAX		Unsigned32
		MAX-ACCESS		not-accessible
		STATUS			current
		DESCRIPTION
				"The unique Index value for each slot.  Its value
					ranges between 1 and the value of slotNumber."
		::= { iqdmsdpCmdEntry 0 }


	iqdmsdpStandard OBJECT-TYPE
		SYNTAX		INTEGER {
							val_PAL_NTSC(0),
							val_PAL_N_PAL_M(1),
							val_SECAM_NTSC_4_43(2)
							}
		MAX-ACCESS		read-write
		STATUS			current
		DESCRIPTION
				"TYPE: - RadiobuttonList
					Standard  cmdID= 37 
					PAL/NTSC  value= 0  
					PAL-N/PAL-M  value= 1  
					SECAM/NTSC-4.43  value= 2  "
		::= { iqdmsdpCmdEntry 37 }


	iqdmsdpModeDecodeMode OBJECT-TYPE
		SYNTAX		INTEGER {
							val_Studio(0),
							val_Display(1),
							val_Simple(2)
							}
		MAX-ACCESS		read-write
		STATUS			current
		DESCRIPTION
				"TYPE: - RadiobuttonList
					Decode_Mode  cmdID= 21 
					Studio  value= 0  
					Display  value= 1  
					Simple  value= 2  "
		::= { iqdmsdpCmdEntry 21 }


	iqdmsdpModeLockMode OBJECT-TYPE
		SYNTAX		INTEGER {
							val_Broadcast(0),
							val_TV(1),
							val_VHS(2)
							}
		MAX-ACCESS		read-write
		STATUS			current
		DESCRIPTION
				"TYPE: - RadiobuttonList
					Lock_Mode  cmdID= 32 
					Broadcast  value= 0  
					TV  value= 1  
					VHS  value= 2  "
		::= { iqdmsdpCmdEntry 32 }


	iqdmsdpPattern OBJECT-TYPE
		SYNTAX		INTEGER {
							val_Video(0),
							val_Black(1),
							val_100_Colour_Bars(32),
							val_75_Colour_Bars(96),
							val_Multi_Burst(64)
							}
		MAX-ACCESS		read-write
		STATUS			current
		DESCRIPTION
				"TYPE: - RadiobuttonList
					Pattern  cmdID= 22 
					Video  value= 0  
					Black  value= 1  
					100%_Colour_Bars  value= 32  
					75%_Colour_Bars  value= 96  
					Multi_Burst  value= 64  "
		::= { iqdmsdpCmdEntry 22 }


	iqdmsdpGenlockMode OBJECT-TYPE
		SYNTAX		INTEGER {
							val_Genlock(0),
							val_Free_Run(2)
							}
		MAX-ACCESS		read-write
		STATUS			current
		DESCRIPTION
				"TYPE: - RadiobuttonList
					Mode  cmdID= 46 
					Genlock  value= 0  
					Free_Run  value= 2  "
		::= { iqdmsdpCmdEntry 46 }


	iqdmsdpGenlockHPhase OBJECT-TYPE
		SYNTAX		INTEGER
		MAX-ACCESS		read-write
		STATUS			current
		DESCRIPTION
				"TYPE: - Number
					H_Phase  cmdID= 24  min= -31968  max= 31968  step= 37  format= %4.0fns  div_scale= 1 
					Min = -31968ns  Max = 31968ns  Step =   37ns "
		::= { iqdmsdpCmdEntry 24 }


	iqdmsdpGenlockVPhase OBJECT-TYPE
		SYNTAX		INTEGER
		MAX-ACCESS		read-write
		STATUS			current
		DESCRIPTION
				"TYPE: - Number
					V_Phase  cmdID= 23  min= -7  max= 7  step= 1  format= %4.0f Lines  div_scale= 1 
					Min =   -7 Lines  Max =    7 Lines  Step =    1 Lines "
		::= { iqdmsdpCmdEntry 23 }


	iqdmsdpFreeze OBJECT-TYPE
		SYNTAX		INTEGER { disable(0), enable(1) }
		MAX-ACCESS		read-write
		STATUS			current
		DESCRIPTION
				"TYPE: - Checkbox
					Freeze  cmdID= 33 "
		::= { iqdmsdpCmdEntry 33 }


	iqdmsdpProcAmpVideoGain OBJECT-TYPE
		SYNTAX		INTEGER
		MAX-ACCESS		read-write
		STATUS			current
		DESCRIPTION
				"TYPE: - Number
					Video_Gain  cmdID= 25  min= -20  max= 20  step= 1  format= %1.1f dB  div_scale= 10 
					Min = -2.0 dB  Max = 2.0 dB  Step = 0.1 dB "
		::= { iqdmsdpCmdEntry 25 }


	iqdmsdpProcAmpBlackLevel OBJECT-TYPE
		SYNTAX		INTEGER
		MAX-ACCESS		read-write
		STATUS			current
		DESCRIPTION
				"TYPE: - Number
					Black_Level  cmdID= 26  min= -75  max= 75  step= 1  format= %1.0f  div_scale= 1 
					Min = -75  Max = 75  Step = 1 "
		::= { iqdmsdpCmdEntry 26 }


	iqdmsdpProcAmpChromaGain OBJECT-TYPE
		SYNTAX		INTEGER
		MAX-ACCESS		read-write
		STATUS			current
		DESCRIPTION
				"TYPE: - Number
					Chroma_Gain  cmdID= 27  min= -30  max= 30  step= 1  format= %1.1f dB  div_scale= 10 
					Min = -3.0 dB  Max = 3.0 dB  Step = 0.1 dB "
		::= { iqdmsdpCmdEntry 27 }


	iqdmsdpProcAmpNTSCHue OBJECT-TYPE
		SYNTAX		INTEGER
		MAX-ACCESS		read-write
		STATUS			current
		DESCRIPTION
				"TYPE: - Number
					NTSC_Hue  cmdID= 28  min= -30  max= 30  step= 1  format= %1.0f Deg  div_scale= 1 
					Min = -30 Deg  Max = 30 Deg  Step = 1 Deg "
		::= { iqdmsdpCmdEntry 28 }


	iqdmsdpProcAmpYCDelay OBJECT-TYPE
		SYNTAX		INTEGER
		MAX-ACCESS		read-write
		STATUS			current
		DESCRIPTION
				"TYPE: - Number
					YC_Delay  cmdID= 29  min= -222  max= 148  step= 74  format= %4.0fns  div_scale= 1 
					Min = -222ns  Max =  148ns  Step =   74ns "
		::= { iqdmsdpCmdEntry 29 }


	iqdmsdpEDHEDHEnable OBJECT-TYPE
		SYNTAX		INTEGER { disable(0), enable(1) }
		MAX-ACCESS		read-write
		STATUS			current
		DESCRIPTION
				"TYPE: - Checkbox
					EDH_Enable  cmdID= 5 "
		::= { iqdmsdpCmdEntry 5 }


	iqdmsdpEDHFlagsANEDA OBJECT-TYPE
		SYNTAX		INTEGER { disable(0), enable(1) }
		MAX-ACCESS		read-write
		STATUS			current
		DESCRIPTION
				"TYPE: - Checkbox
					ANEDA  cmdID= 7 "
		::= { iqdmsdpCmdEntry 7 }


	iqdmsdpEDHFlagsANIDA OBJECT-TYPE
		SYNTAX		INTEGER { disable(0), enable(1) }
		MAX-ACCESS		read-write
		STATUS			current
		DESCRIPTION
				"TYPE: - Checkbox
					ANIDA  cmdID= 9 "
		::= { iqdmsdpCmdEntry 9 }


	iqdmsdpEDHFlagsANEDH OBJECT-TYPE
		SYNTAX		INTEGER { disable(0), enable(1) }
		MAX-ACCESS		read-write
		STATUS			current
		DESCRIPTION
				"TYPE: - Checkbox
					ANEDH  cmdID= 6 "
		::= { iqdmsdpCmdEntry 6 }


	iqdmsdpEDHFlagsANIDH OBJECT-TYPE
		SYNTAX		INTEGER { disable(0), enable(1) }
		MAX-ACCESS		read-write
		STATUS			current
		DESCRIPTION
				"TYPE: - Checkbox
					ANIDH  cmdID= 8 "
		::= { iqdmsdpCmdEntry 8 }


	iqdmsdpEDHFlagsANUES OBJECT-TYPE
		SYNTAX		INTEGER { disable(0), enable(1) }
		MAX-ACCESS		read-write
		STATUS			current
		DESCRIPTION
				"TYPE: - Checkbox
					ANUES  cmdID= 10 "
		::= { iqdmsdpCmdEntry 10 }


	iqdmsdpEDHFlagsAPEDH OBJECT-TYPE
		SYNTAX		INTEGER { disable(0), enable(1) }
		MAX-ACCESS		read-write
		STATUS			current
		DESCRIPTION
				"TYPE: - Checkbox
					APEDH  cmdID= 11 "
		::= { iqdmsdpCmdEntry 11 }


	iqdmsdpEDHFlagsAPEDA OBJECT-TYPE
		SYNTAX		INTEGER { disable(0), enable(1) }
		MAX-ACCESS		read-write
		STATUS			current
		DESCRIPTION
				"TYPE: - Checkbox
					APEDA  cmdID= 12 "
		::= { iqdmsdpCmdEntry 12 }


	iqdmsdpEDHFlagsAPIDH OBJECT-TYPE
		SYNTAX		INTEGER { disable(0), enable(1) }
		MAX-ACCESS		read-write
		STATUS			current
		DESCRIPTION
				"TYPE: - Checkbox
					APIDH  cmdID= 13 "
		::= { iqdmsdpCmdEntry 13 }


	iqdmsdpEDHFlagsAPIDA OBJECT-TYPE
		SYNTAX		INTEGER { disable(0), enable(1) }
		MAX-ACCESS		read-write
		STATUS			current
		DESCRIPTION
				"TYPE: - Checkbox
					APIDA  cmdID= 14 "
		::= { iqdmsdpCmdEntry 14 }


	iqdmsdpEDHFlagsAPUES OBJECT-TYPE
		SYNTAX		INTEGER { disable(0), enable(1) }
		MAX-ACCESS		read-write
		STATUS			current
		DESCRIPTION
				"TYPE: - Checkbox
					APUES  cmdID= 15 "
		::= { iqdmsdpCmdEntry 15 }


	iqdmsdpEDHFlagsFFEDH OBJECT-TYPE
		SYNTAX		INTEGER { disable(0), enable(1) }
		MAX-ACCESS		read-write
		STATUS			current
		DESCRIPTION
				"TYPE: - Checkbox
					FFEDH  cmdID= 16 "
		::= { iqdmsdpCmdEntry 16 }


	iqdmsdpEDHFlagsFFEDA OBJECT-TYPE
		SYNTAX		INTEGER { disable(0), enable(1) }
		MAX-ACCESS		read-write
		STATUS			current
		DESCRIPTION
				"TYPE: - Checkbox
					FFEDA  cmdID= 17 "
		::= { iqdmsdpCmdEntry 17 }


	iqdmsdpEDHFlagsFFIDH OBJECT-TYPE
		SYNTAX		INTEGER { disable(0), enable(1) }
		MAX-ACCESS		read-write
		STATUS			current
		DESCRIPTION
				"TYPE: - Checkbox
					FFIDH  cmdID= 18 "
		::= { iqdmsdpCmdEntry 18 }


	iqdmsdpEDHFlagsFFIDA OBJECT-TYPE
		SYNTAX		INTEGER { disable(0), enable(1) }
		MAX-ACCESS		read-write
		STATUS			current
		DESCRIPTION
				"TYPE: - Checkbox
					FFIDA  cmdID= 19 "
		::= { iqdmsdpCmdEntry 19 }


	iqdmsdpEDHFlagsFFUES OBJECT-TYPE
		SYNTAX		INTEGER { disable(0), enable(1) }
		MAX-ACCESS		read-write
		STATUS			current
		DESCRIPTION
				"TYPE: - Checkbox
					FFUES  cmdID= 20 "
		::= { iqdmsdpCmdEntry 20 }


	iqdmsdpNoiseReducerC OBJECT-TYPE
		SYNTAX		INTEGER {
							val_C_Off(0),
							val_C_Low(1),
							val_C_Medium(2),
							val_C_High(3)
							}
		MAX-ACCESS		read-write
		STATUS			current
		DESCRIPTION
				"TYPE: - Button
					C_Off  cmdID= 48  value= 0  
					C_Low  cmdID= 48  value= 1  
					C_Medium  cmdID= 48  value= 2  
					C_High  cmdID= 48  value= 3  "
		::= { iqdmsdpCmdEntry 48 }


	iqdmsdpNoiseReducerY OBJECT-TYPE
		SYNTAX		INTEGER {
							val_Y_Off(0),
							val_Y_Low(1),
							val_Y_Medium(2),
							val_Y_High(3)
							}
		MAX-ACCESS		read-write
		STATUS			current
		DESCRIPTION
				"TYPE: - Button
					Y_Off  cmdID= 49  value= 0  
					Y_Low  cmdID= 49  value= 1  
					Y_Medium  cmdID= 49  value= 2  
					Y_High  cmdID= 49  value= 3  "
		::= { iqdmsdpCmdEntry 49 }


	iqdmsdpSetupLineStandard OBJECT-TYPE
		SYNTAX		INTEGER {
							val_525(0),
							val_625(1),
							val_Auto(2)
							}
		MAX-ACCESS		read-write
		STATUS			current
		DESCRIPTION
				"TYPE: - RadiobuttonList
					Line_Standard  cmdID= 34 
					525  value= 0  
					625  value= 1  
					Auto  value= 2  "
		::= { iqdmsdpCmdEntry 34 }


	iqdmsdpSetupAutoFreeze OBJECT-TYPE
		SYNTAX		INTEGER { disable(0), enable(1) }
		MAX-ACCESS		read-write
		STATUS			current
		DESCRIPTION
				"TYPE: - Checkbox
					Auto_Freeze  cmdID= 47 "
		::= { iqdmsdpCmdEntry 47 }


	iqdmsdpSetupVITSPass OBJECT-TYPE
		SYNTAX		INTEGER { disable(0), enable(1) }
		MAX-ACCESS		read-write
		STATUS			current
		DESCRIPTION
				"TYPE: - Checkbox
					VITS_Pass  cmdID= 30 "
		::= { iqdmsdpCmdEntry 30 }


	iqdmsdpSetupPedestalStrip OBJECT-TYPE
		SYNTAX		INTEGER { disable(0), enable(1) }
		MAX-ACCESS		read-write
		STATUS			current
		DESCRIPTION
				"TYPE: - Checkbox
					Pedestal_Strip  cmdID= 35 "
		::= { iqdmsdpCmdEntry 35 }


	iqdmsdpSetupAudioDelayUnit1 OBJECT-TYPE
		SYNTAX		RollCallString
		MAX-ACCESS		read-write
		STATUS			current
		DESCRIPTION
				"TYPE: - Editstring
					Unit_1  cmdID= 38  "
		::= { iqdmsdpCmdEntry 38 }


	iqdmsdpSetupAudioDelayUnit2 OBJECT-TYPE
		SYNTAX		RollCallString
		MAX-ACCESS		read-write
		STATUS			current
		DESCRIPTION
				"TYPE: - Editstring
					Unit_2  cmdID= 39  "
		::= { iqdmsdpCmdEntry 39 }


	iqdmsdpSetupAudioDelayUnit3 OBJECT-TYPE
		SYNTAX		RollCallString
		MAX-ACCESS		read-write
		STATUS			current
		DESCRIPTION
				"TYPE: - Editstring
					Unit_3  cmdID= 40  "
		::= { iqdmsdpCmdEntry 40 }


	iqdmsdpSetupAudioDelayUnit4 OBJECT-TYPE
		SYNTAX		RollCallString
		MAX-ACCESS		read-write
		STATUS			current
		DESCRIPTION
				"TYPE: - Editstring
					Unit_4  cmdID= 41  "
		::= { iqdmsdpCmdEntry 41 }


	iqdmsdpSetupAudioDelayUnit5 OBJECT-TYPE
		SYNTAX		RollCallString
		MAX-ACCESS		read-write
		STATUS			current
		DESCRIPTION
				"TYPE: - Editstring
					Unit_5  cmdID= 42  "
		::= { iqdmsdpCmdEntry 42 }


	iqdmsdpSetupAudioDelayUnit6 OBJECT-TYPE
		SYNTAX		RollCallString
		MAX-ACCESS		read-write
		STATUS			current
		DESCRIPTION
				"TYPE: - Editstring
					Unit_6  cmdID= 43  "
		::= { iqdmsdpCmdEntry 43 }


	iqdmsdpSetupAudioDelayUnit7 OBJECT-TYPE
		SYNTAX		RollCallString
		MAX-ACCESS		read-write
		STATUS			current
		DESCRIPTION
				"TYPE: - Editstring
					Unit_7  cmdID= 44  "
		::= { iqdmsdpCmdEntry 44 }


	iqdmsdpSetupAudioDelayUnit8 OBJECT-TYPE
		SYNTAX		RollCallString
		MAX-ACCESS		read-write
		STATUS			current
		DESCRIPTION
				"TYPE: - Editstring
					Unit_8  cmdID= 45  "
		::= { iqdmsdpCmdEntry 45 }


	iqdmsdpSetupLoggingInpStdChange OBJECT-TYPE
		SYNTAX		INTEGER { disable(0), enable(1) }
		MAX-ACCESS		read-write
		STATUS			current
		DESCRIPTION
				"TYPE: - Checkbox
					Inp/Std_Change  cmdID= 31 "
		::= { iqdmsdpCmdEntry 31 }


	iqdmsdpSetupLoggingReferenceLoss OBJECT-TYPE
		SYNTAX		INTEGER { disable(0), enable(1) }
		MAX-ACCESS		read-write
		STATUS			current
		DESCRIPTION
				"TYPE: - Checkbox
					Reference_Loss  cmdID= 36 "
		::= { iqdmsdpCmdEntry 36 }


	iqdmsdpSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdmsdpCmdEntry 3 }


	iqdmsdpSetupSoftwareVersion OBJECT-TYPE
		SYNTAX		RollCallString
		MAX-ACCESS		read-only
		STATUS			current
		DESCRIPTION
				"TYPE: - Display
					Software_Version  cmdID= 2  format=   "
		::= { iqdmsdpCmdEntry 2 }


	iqdmsdpSetupSerialNo OBJECT-TYPE
		SYNTAX		RollCallString
		MAX-ACCESS		read-only
		STATUS			current
		DESCRIPTION
				"TYPE: - Display
					Serial_No  cmdID= 1  format=   "
		::= { iqdmsdpCmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: AUTO
--				: NTSC
--				: PAL
--				: PAL-M
--				: PAL-N
--				: NTSC-443
--				: SECAM
--				: MONO
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: ERROR
--				: OK
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: N/A
--				: LOST
--				: OK
-- Comments		: 
--
---------------------------------------------------------------------------------------------------
