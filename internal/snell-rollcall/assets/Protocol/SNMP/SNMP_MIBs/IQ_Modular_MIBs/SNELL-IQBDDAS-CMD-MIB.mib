-- ************************************************************************************
-- Snell&Wilcox Card:IQBDDAS
--        Module Id#:86
--       Command Set:6
--          Filename:SNELL-IQBDDAS-CMD-MIB.mib
--            Author:Jonathan Riches
--              Date:28/06/2005
--              Time:12:49
--
-- Copyright (c) 2005 Snell & Wilcox Ltd
-- All rights reserved.
--
-- ************************************************************************************

SNELL-IQBDDAS-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQBDDAS,
    moduleIQBDDASMIB
        FROM SNELL-WILCOX-PRODUCT-REG;

 moduleIQBDDASCmdMi MODULE-IDENTITY
    LAST-UPDATED "0506281249Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQBDDASMIB 1 }




--********************************************************************************
--*
--*  Snell Wilcox Card:
--*  command set:
--*  list commands/menus:
--*
--******************************************************************************
	iqbddasCmdTable OBJECT-TYPE
		SYNTAX			SEQUENCE OF IqbddasCmdEntry
		MAX-ACCESS		not-accessible
		STATUS			current
		DESCRIPTION
				"Note the instance of this table is relected in the command set Version"
		::= { moduleIQBDDAS 1 }

	iqbddasCmdEntry OBJECT-TYPE
		SYNTAX		IqbddasCmdEntry
		MAX-ACCESS		not-accessible
		STATUS			current
		DESCRIPTION
				"Entry in command table."
		INDEX	{ iqbddasSlotIndex }
		::= { iqbddasCmdTable 1 }

	IqbddasCmdEntry ::=
		SEQUENCE {
			iqbddasSlotIndex
				Unsigned32,
			iqbddasDisplayChannelStatusInf
				INTEGER,
			iqbddasDisplayChannelStatusSetupUp
				INTEGER,
			iqbddasDisplayChannelStatusSetupSubframe
				INTEGER,
			iqbddasDisplayChannelStatusSetupDown
				INTEGER,
			iqbddasDisplayChannelStatusSetup
				INTEGER,
			iqbddasSetupLoggingAESInputChange
				INTEGER,
			iqbddasSetupPresetUnit
				INTEGER,
			iqbddasSetupSoftwareVersion
				RollCallString,
			iqbddasSetupSerialNo
				RollCallString
		}

	iqbddasSlotIndex OBJECT-TYPE
		SYNTAX		Unsigned32
		MAX-ACCESS		not-accessible
		STATUS			current
		DESCRIPTION
				"The unique Index value for each slot.  Its value
					ranges between 1 and the value of slotNumber."
		::= { iqbddasCmdEntry 0 }


	iqbddasDisplayChannelStatusInf OBJECT-TYPE
		SYNTAX		INTEGER { disable(0), enable(1) }
		MAX-ACCESS		read-write
		STATUS			current
		DESCRIPTION
				"TYPE: - Checkbox
					Channel_Status_Inf  cmdID= 35 "
		::= { iqbddasCmdEntry 35 }


	iqbddasDisplayChannelStatusSetupUp OBJECT-TYPE
		SYNTAX		INTEGER { noAction(0),val_Up(1) }
		MAX-ACCESS		read-write
		STATUS			current
		DESCRIPTION
				"TYPE: - Button
					Up  cmdID= 30  value= 1  "
		::= { iqbddasCmdEntry 30 }


	iqbddasDisplayChannelStatusSetupSubframe OBJECT-TYPE
		SYNTAX		INTEGER {
							val_Subframe_1(0),
							val_Subframe_2(1)
							}
		MAX-ACCESS		read-write
		STATUS			current
		DESCRIPTION
				"TYPE: - Button
					Subframe_1  cmdID= 32  value= 0  
					Subframe_2  cmdID= 32  value= 1  "
		::= { iqbddasCmdEntry 32 }


	iqbddasDisplayChannelStatusSetupDown OBJECT-TYPE
		SYNTAX		INTEGER { noAction(0),val_Down(1) }
		MAX-ACCESS		read-write
		STATUS			current
		DESCRIPTION
				"TYPE: - Button
					Down  cmdID= 31  value= 1  "
		::= { iqbddasCmdEntry 31 }


	iqbddasDisplayChannelStatusSetup OBJECT-TYPE
		SYNTAX		INTEGER {
							val_Input_A(0),
							val_unspecified(3)
							}
		MAX-ACCESS		read-write
		STATUS			current
		DESCRIPTION
				"TYPE: - Button
					Input_A  cmdID= 33  value= 0  
					  cmdID= 33  value= 3  "
		::= { iqbddasCmdEntry 33 }


	iqbddasSetupLoggingAESInputChange OBJECT-TYPE
		SYNTAX		INTEGER { disable(0), enable(1) }
		MAX-ACCESS		read-write
		STATUS			current
		DESCRIPTION
				"TYPE: - Checkbox
					AES_Input_Change  cmdID= 19 "
		::= { iqbddasCmdEntry 19 }


	iqbddasSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqbddasCmdEntry 3 }


	iqbddasSetupSoftwareVersion OBJECT-TYPE
		SYNTAX		RollCallString
		MAX-ACCESS		read-only
		STATUS			current
		DESCRIPTION
				"TYPE: - Display
					Software_Version  cmdID= 2  format=   "
		::= { iqbddasCmdEntry 2 }


	iqbddasSetupSerialNo OBJECT-TYPE
		SYNTAX		RollCallString
		MAX-ACCESS		read-only
		STATUS			current
		DESCRIPTION
				"TYPE: - Display
					Serial_No  cmdID= 1  format=   "
		::= { iqbddasCmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: INT
--				: AES
--				: 625
--				: 525
-- Comments		: 
--
---------------------------------------------------------------------------------------------------
-- Header		: AESREF
--
-- MIB ref		: swCardEventLogSlotXX       .6.65.69.83.82.69.70
-- absolute OID	: 1.3.6.1.4.1.7995.2.6.1.1.XX.6.65.69.83.82.69.70
-- Vary			: YES
--
-- Value(s)		: 1
--				: 0
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: OFF
--				: ERROR
--				: OK
-- Comments		: 
--
---------------------------------------------------------------------------------------------------
-- Header		: VIDREF
--
-- MIB ref		: swCardEventLogSlotXX       .6.86.73.68.82.69.70
-- absolute OID	: 1.3.6.1.4.1.7995.2.6.1.1.XX.6.86.73.68.82.69.70
-- Vary			: YES
--
-- Value(s)		: 1
--				: 0
-- Comments		: 
--
---------------------------------------------------------------------------------------------------
