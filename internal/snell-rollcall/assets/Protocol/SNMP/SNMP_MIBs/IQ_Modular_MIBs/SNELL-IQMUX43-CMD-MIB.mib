-- ************************************************************************************
-- Snell    Card:IQMUX43
--        Module Id#:390
--       Command Set:17
--          Filename:SNELL-IQMUX43-CMD-MIB.mib
--            Author:Jonathan Riches
--              Date:27/01/2010
--              Time:10:46
--
-- Copyright (c) 2010 Snell Ltd
-- All rights reserved.
--
-- ************************************************************************************

SNELL-IQMUX43-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQMUX43,
    moduleIQMUX43MIB
        FROM SNELL-WILCOX-PRODUCT-REG;

 moduleIQMUX43CmdMi MODULE-IDENTITY
    LAST-UPDATED "1001271046Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQMUX43MIB 1 }




--********************************************************************************
--*
--*  Snell Wilcox Card:
--*  command set:
--*  list commands/menus:
--*
--******************************************************************************
	iqmux43CmdTable OBJECT-TYPE
		SYNTAX			SEQUENCE OF Iqmux43CmdEntry
		MAX-ACCESS		not-accessible
		STATUS			current
		DESCRIPTION
				"Note the instance of this table is relected in the command set Version"
		::= { moduleIQMUX43 1 }

	iqmux43CmdEntry OBJECT-TYPE
		SYNTAX		Iqmux43CmdEntry
		MAX-ACCESS		not-accessible
		STATUS			current
		DESCRIPTION
				"Entry in command table."
		INDEX	{ iqmux43SlotIndex }
		::= { iqmux43CmdTable 1 }

	Iqmux43CmdEntry ::=
		SEQUENCE {
			iqmux43SlotIndex
				Unsigned32,
			iqmux43InputIPLoss
				INTEGER,
			iqmux43InputValidStdsAllValid
				INTEGER,
			iqmux43InputValidStdsAllInvalid
				INTEGER,
			iqmux43InputValidStds108023sF
				INTEGER,
			iqmux43InputValidStds108023p
				INTEGER,
			iqmux43InputValidStds108024sF
				INTEGER,
			iqmux43InputValidStds108024p
				INTEGER,
			iqmux43InputValidStds108025i
				INTEGER,
			iqmux43InputValidStds108025p
				INTEGER,
			iqmux43InputValidStds103529i
				INTEGER,
			iqmux43InputValidStds108029i
				INTEGER,
			iqmux43InputValidStds108029p
				INTEGER,
			iqmux43InputValidStds103530i
				INTEGER,
			iqmux43InputValidStds108030i
				INTEGER,
			iqmux43InputValidStds108030p
				INTEGER,
			iqmux43InputValidStds72050p
				INTEGER,
			iqmux43InputValidStds72059p
				INTEGER,
			iqmux43InputValidStds72060p
				INTEGER,
			iqmux43InputValidStds62525i
				INTEGER,
			iqmux43InputValidStds52529i
				INTEGER,
			iqmux43InputErrorsCRCErrs
				RollCallString,
			iqmux43InputErrorsCRCErrSec
				RollCallString,
			iqmux43InputErrorsANCErrs
				RollCallString,
			iqmux43InputErrorsANCErrSec
				RollCallString,
			iqmux43InputErrorsResetSec
				RollCallString,
			iqmux43InputErrorsErrorReset
				INTEGER,
			iqmux43OutputStandard
				INTEGER,
			iqmux43OutputSelectStandard
				INTEGER,
			iqmux43OutputVideoProcAmpsMasterGain
				INTEGER,
			iqmux43OutputVideoProcAmpsYGain
				INTEGER,
			iqmux43OutputVideoProcAmpsCGain
				INTEGER,
			iqmux43OutputVideoProcAmpsBlackLevel
				INTEGER,
			iqmux43OutputDefaultOutput
				INTEGER,
			iqmux43OutputDefaultOPStd
				INTEGER,
			iqmux43AudioADelaySourcesManual
				INTEGER,
			iqmux43AudioADelaySourcesGPIPWM
				INTEGER,
			iqmux43AudioADelaySourcesRollTrack14
				INTEGER,
			iqmux43AudioADelaySourcesRollTrack15
				INTEGER,
			iqmux43AudioADelaySourcesRollTrack16
				INTEGER,
			iqmux43AudioADelaySourcesRollTrack17
				INTEGER,
			iqmux43AudioAAdjustCoarseDelay
				INTEGER,
			iqmux43AudioACurrentAudioDelay
				RollCallString,
			iqmux43AudioBDelaySourcesManual
				INTEGER,
			iqmux43AudioBDelaySourcesGPIPWM
				INTEGER,
			iqmux43AudioBDelaySourcesRollTrack14
				INTEGER,
			iqmux43AudioBDelaySourcesRollTrack15
				INTEGER,
			iqmux43AudioBDelaySourcesRollTrack16
				INTEGER,
			iqmux43AudioBDelaySourcesRollTrack17
				INTEGER,
			iqmux43AudioBAdjustCoarseDelay
				INTEGER,
			iqmux43AudioBCurrentAudioDelay
				RollCallString,
			iqmux43AudioAESDelaySelectDelay1
				INTEGER,
			iqmux43AudioAESDelaySelectInternal1
				INTEGER,
			iqmux43AudioAESDelaySelectAutoDolbyEPhase1
				INTEGER,
			iqmux43AudioAESDelaySelectDelayLimit1
				RollCallString,
			iqmux43AudioAESDelaySelectAES1FineDelay
				INTEGER,
			iqmux43AudioAESDelaySelectDelay2
				INTEGER,
			iqmux43AudioAESDelaySelectInternal2
				INTEGER,
			iqmux43AudioAESDelaySelectAutoDolbyEPhase2
				INTEGER,
			iqmux43AudioAESDelaySelectDelayLimit2
				RollCallString,
			iqmux43AudioAESDelaySelectAES2FineDelay
				INTEGER,
			iqmux43AudioAESDelaySelectDelay3
				INTEGER,
			iqmux43AudioAESDelaySelectInternal3
				INTEGER,
			iqmux43AudioAESDelaySelectAutoDolbyEPhase3
				INTEGER,
			iqmux43AudioAESDelaySelectDelayLimit3
				RollCallString,
			iqmux43AudioAESDelaySelectAES3FineDelay
				INTEGER,
			iqmux43AudioAESDelaySelectDelay4
				INTEGER,
			iqmux43AudioAESDelaySelectInternal4
				INTEGER,
			iqmux43AudioAESDelaySelectAutoDolbyEPhase4
				INTEGER,
			iqmux43AudioAESDelaySelectDelayLimit4
				RollCallString,
			iqmux43AudioAESDelaySelectAES4FineDelay
				INTEGER,
			iqmux43AudioAESDelaySelectDelay5
				INTEGER,
			iqmux43AudioAESDelaySelectInternal5
				INTEGER,
			iqmux43AudioAESDelaySelectAutoDolbyEPhase5
				INTEGER,
			iqmux43AudioAESDelaySelectDelayLimit5
				RollCallString,
			iqmux43AudioAESDelaySelectAES5FineDelay
				INTEGER,
			iqmux43AudioAESDelaySelectDelay6
				INTEGER,
			iqmux43AudioAESDelaySelectInternal6
				INTEGER,
			iqmux43AudioAESDelaySelectAutoDolbyEPhase6
				INTEGER,
			iqmux43AudioAESDelaySelectDelayLimit6
				RollCallString,
			iqmux43AudioAESDelaySelectAES6FineDelay
				INTEGER,
			iqmux43AudioAESDelaySelectDelay7
				INTEGER,
			iqmux43AudioAESDelaySelectInternal7
				INTEGER,
			iqmux43AudioAESDelaySelectAutoDolbyEPhase7
				INTEGER,
			iqmux43AudioAESDelaySelectDelayLimit7
				RollCallString,
			iqmux43AudioAESDelaySelectAES7FineDelay
				INTEGER,
			iqmux43AudioAESDelaySelectDelay8
				INTEGER,
			iqmux43AudioAESDelaySelectInternal8
				INTEGER,
			iqmux43AudioAESDelaySelectAutoDolbyEPhase8
				INTEGER,
			iqmux43AudioAESDelaySelectDelayLimit8
				RollCallString,
			iqmux43AudioAESDelaySelectAES8FineDelay
				INTEGER,
			iqmux43AudEMBDelaySelectDelay1
				INTEGER,
			iqmux43AudEMBDelaySelectInternal1
				INTEGER,
			iqmux43AudEMBDelaySelectAutoDolbyEPhase1
				INTEGER,
			iqmux43AudEMBDelaySelectDelayLimit1
				RollCallString,
			iqmux43AudEMBDelaySelectEMB1FineDelay
				INTEGER,
			iqmux43AudEMBDelaySelectDelay2
				INTEGER,
			iqmux43AudEMBDelaySelectInternal2
				INTEGER,
			iqmux43AudEMBDelaySelectAutoDolbyEPhase2
				INTEGER,
			iqmux43AudEMBDelaySelectDelayLimit2
				RollCallString,
			iqmux43AudEMBDelaySelectEMB2FineDelay
				INTEGER,
			iqmux43AudEMBDelaySelectDelay3
				INTEGER,
			iqmux43AudEMBDelaySelectInternal3
				INTEGER,
			iqmux43AudEMBDelaySelectAutoDolbyEPhase3
				INTEGER,
			iqmux43AudEMBDelaySelectDelayLimit3
				RollCallString,
			iqmux43AudEMBDelaySelectEMB3FineDelay
				INTEGER,
			iqmux43AudEMBDelaySelectDelay4
				INTEGER,
			iqmux43AudEMBDelaySelectInternal4
				INTEGER,
			iqmux43AudEMBDelaySelectAutoDolbyEPhase4
				INTEGER,
			iqmux43AudEMBDelaySelectDelayLimit4
				RollCallString,
			iqmux43AudEMBDelaySelectEMB4FineDelay
				INTEGER,
			iqmux43AudEMBDelaySelectDelay5
				INTEGER,
			iqmux43AudEMBDelaySelectInternal5
				INTEGER,
			iqmux43AudEMBDelaySelectAutoDolbyEPhase5
				INTEGER,
			iqmux43AudEMBDelaySelectDelayLimit5
				RollCallString,
			iqmux43AudEMBDelaySelectEMB5FineDelay
				INTEGER,
			iqmux43AudEMBDelaySelectDelay6
				INTEGER,
			iqmux43AudEMBDelaySelectInternal6
				INTEGER,
			iqmux43AudEMBDelaySelectAutoDolbyEPhase6
				INTEGER,
			iqmux43AudEMBDelaySelectDelayLimit6
				RollCallString,
			iqmux43AudEMBDelaySelectEMB6FineDelay
				INTEGER,
			iqmux43AudEMBDelaySelectDelay7
				INTEGER,
			iqmux43AudEMBDelaySelectInternal7
				INTEGER,
			iqmux43AudEMBDelaySelectAutoDolbyEPhase7
				INTEGER,
			iqmux43AudEMBDelaySelectDelayLimit7
				RollCallString,
			iqmux43AudEMBDelaySelectEMB7FineDelay
				INTEGER,
			iqmux43AudEMBDelaySelectDelay8
				INTEGER,
			iqmux43AudEMBDelaySelectInternal8
				INTEGER,
			iqmux43AudEMBDelaySelectDelayLimit8
				RollCallString,
			iqmux43AudEMBDelaySelectAutoDolbyEPhase8
				INTEGER,
			iqmux43AudEMBDelaySelectEMB8FineDelay
				INTEGER,
			iqmux43AudioDelaysRollTrack14
				RollCallString,
			iqmux43AudioDelaysRollTrack15
				RollCallString,
			iqmux43AudioDelaysRollTrack16
				RollCallString,
			iqmux43AudioDelaysRollTrack17
				RollCallString,
			iqmux43AudioDelaysCrashSRCLimit
				INTEGER,
			iqmux43EmbCtrlGroupGroup1Audio
				INTEGER,
			iqmux43EmbCtrlGroupGroup2Audio
				INTEGER,
			iqmux43EmbCtrlGroupGroup3Audio
				INTEGER,
			iqmux43EmbCtrlGroupGroup4Audio
				INTEGER,
			iqmux43EmbCtrlChannelPair1LActive
				INTEGER,
			iqmux43EmbCtrlChannelPair1RActive
				INTEGER,
			iqmux43EmbCtrlChannelPair2LActive
				INTEGER,
			iqmux43EmbCtrlChannelPair2RActive
				INTEGER,
			iqmux43EmbCtrlChannelPair3LActive
				INTEGER,
			iqmux43EmbCtrlChannelPair3RActive
				INTEGER,
			iqmux43EmbCtrlChannelPair4LActive
				INTEGER,
			iqmux43EmbCtrlChannelPair4RActive
				INTEGER,
			iqmux43EmbCtrlChannelPair5LActive
				INTEGER,
			iqmux43EmbCtrlChannelPair5RActive
				INTEGER,
			iqmux43EmbCtrlChannelPair6LActive
				INTEGER,
			iqmux43EmbCtrlChannelPair6RActive
				INTEGER,
			iqmux43EmbCtrlChannelPair7LActive
				INTEGER,
			iqmux43EmbCtrlChannelPair7RActive
				INTEGER,
			iqmux43EmbCtrlChannelPair8LActive
				INTEGER,
			iqmux43EmbCtrlChannelPair8RActive
				INTEGER,
			iqmux43AudioEmbCtrlEmbedderPriority
				INTEGER,
			iqmux43EmbGainEmbedPair1Embed1MuteL
				INTEGER,
			iqmux43EmbGainEmbedPair1Embed1MuteR
				INTEGER,
			iqmux43EmbGainEmbedPair1Embed1LGain
				INTEGER,
			iqmux43EmbGainEmbedPair1Embed1RGain
				INTEGER,
			iqmux43EmbGainEmbedPair1Stereo
				INTEGER,
			iqmux43EmbGainEmbedPair1Embed1InvertL
				INTEGER,
			iqmux43EmbGainEmbedPair1Embed1InvertR
				INTEGER,
			iqmux43EmbGainEmbedPair1Embed1LClip
				RollCallString,
			iqmux43EmbGainEmbedPair1Embed1RClip
				RollCallString,
			iqmux43EmbGainEmbedPair2Embed2MuteL
				INTEGER,
			iqmux43EmbGainEmbedPair2Embed2MuteR
				INTEGER,
			iqmux43EmbGainEmbedPair2Embed2LGain
				INTEGER,
			iqmux43EmbGainEmbedPair2Embed2RGain
				INTEGER,
			iqmux43EmbGainEmbedPair2Stereo
				INTEGER,
			iqmux43EmbGainEmbedPair2Embed2InvertL
				INTEGER,
			iqmux43EmbGainEmbedPair2Embed2InvertR
				INTEGER,
			iqmux43EmbGainEmbedPair2Embed2LClip
				RollCallString,
			iqmux43EmbGainEmbedPair2Embed2RClip
				RollCallString,
			iqmux43EmbGainEmbedPair3Embed3MuteL
				INTEGER,
			iqmux43EmbGainEmbedPair3Embed3MuteR
				INTEGER,
			iqmux43EmbGainEmbedPair3Embed3LGain
				INTEGER,
			iqmux43EmbGainEmbedPair3Embed3RGain
				INTEGER,
			iqmux43EmbGainEmbedPair3Stereo
				INTEGER,
			iqmux43EmbGainEmbedPair3Embed3InvertL
				INTEGER,
			iqmux43EmbGainEmbedPair3Embed3InvertR
				INTEGER,
			iqmux43EmbGainEmbedPair3Embed3LClip
				RollCallString,
			iqmux43EmbGainEmbedPair3Embed3RClip
				RollCallString,
			iqmux43EmbGainEmbedPair4Embed4MuteL
				INTEGER,
			iqmux43EmbGainEmbedPair4Embed4MuteR
				INTEGER,
			iqmux43EmbGainEmbedPair4Embed4LGain
				INTEGER,
			iqmux43EmbGainEmbedPair4Embed4RGain
				INTEGER,
			iqmux43EmbGainEmbedPair4Stereo
				INTEGER,
			iqmux43EmbGainEmbedPair4Embed4InvertL
				INTEGER,
			iqmux43EmbGainEmbedPair4Embed4InvertR
				INTEGER,
			iqmux43EmbGainEmbedPair4Embed4LClip
				RollCallString,
			iqmux43EmbGainEmbedPair4Embed4RClip
				RollCallString,
			iqmux43EmbGainEmbedPair5Embed5MuteL
				INTEGER,
			iqmux43EmbGainEmbedPair5Embed5MuteR
				INTEGER,
			iqmux43EmbGainEmbedPair5Embed5LGain
				INTEGER,
			iqmux43EmbGainEmbedPair5Embed5RGain
				INTEGER,
			iqmux43EmbGainEmbedPair5Stereo
				INTEGER,
			iqmux43EmbGainEmbedPair5Embed5InvertL
				INTEGER,
			iqmux43EmbGainEmbedPair5Embed5InvertR
				INTEGER,
			iqmux43EmbGainEmbedPair5Embed5LClip
				RollCallString,
			iqmux43EmbGainEmbedPair5Embed5RClip
				RollCallString,
			iqmux43EmbGainEmbedPair6Embed6MuteL
				INTEGER,
			iqmux43EmbGainEmbedPair6Embed6MuteR
				INTEGER,
			iqmux43EmbGainEmbedPair6Embed6LGain
				INTEGER,
			iqmux43EmbGainEmbedPair6Embed6RGain
				INTEGER,
			iqmux43EmbGainEmbedPair6Stereo
				INTEGER,
			iqmux43EmbGainEmbedPair6Embed6InvertL
				INTEGER,
			iqmux43EmbGainEmbedPair6Embed6InvertR
				INTEGER,
			iqmux43EmbGainEmbedPair6Embed6LClip
				RollCallString,
			iqmux43EmbGainEmbedPair6Embed6RClip
				RollCallString,
			iqmux43EmbGainEmbedPair7Embed7MuteL
				INTEGER,
			iqmux43EmbGainEmbedPair7Embed7MuteR
				INTEGER,
			iqmux43EmbGainEmbedPair7Embed7LGain
				INTEGER,
			iqmux43EmbGainEmbedPair7Embed7RGain
				INTEGER,
			iqmux43EmbGainEmbedPair7Stereo
				INTEGER,
			iqmux43EmbGainEmbedPair7Embed7InvertL
				INTEGER,
			iqmux43EmbGainEmbedPair7Embed7InvertR
				INTEGER,
			iqmux43EmbGainEmbedPair7Embed7LClip
				RollCallString,
			iqmux43EmbGainEmbedPair7Embed7RClip
				RollCallString,
			iqmux43EmbGainEmbedPair8Embed8MuteL
				INTEGER,
			iqmux43EmbGainEmbedPair8Embed8MuteR
				INTEGER,
			iqmux43EmbGainEmbedPair8Embed8LGain
				INTEGER,
			iqmux43EmbGainEmbedPair8Embed8RGain
				INTEGER,
			iqmux43EmbGainEmbedPair8Stereo
				INTEGER,
			iqmux43EmbGainEmbedPair8Embed8InvertL
				INTEGER,
			iqmux43EmbGainEmbedPair8Embed8InvertR
				INTEGER,
			iqmux43EmbGainEmbedPair8Embed8LClip
				RollCallString,
			iqmux43EmbGainEmbedPair8Embed8RClip
				RollCallString,
			iqmux43EmbOutEmbedPair1Left
				INTEGER,
			iqmux43EmbOutEmbedPair1Right
				INTEGER,
			iqmux43EmbOutEmbedPair1LinkLRSelection
				INTEGER,
			iqmux43EmbOutEmbedPair2Left
				INTEGER,
			iqmux43EmbOutEmbedPair2Right
				INTEGER,
			iqmux43EmbOutEmbedPair2LinkLRSelection
				INTEGER,
			iqmux43EmbOutEmbedPair3Left
				INTEGER,
			iqmux43EmbOutEmbedPair3Right
				INTEGER,
			iqmux43EmbOutEmbedPair3LinkLRSelection
				INTEGER,
			iqmux43EmbOutEmbedPair4Left
				INTEGER,
			iqmux43EmbOutEmbedPair4Right
				INTEGER,
			iqmux43EmbOutEmbedPair4LinkLRSelection
				INTEGER,
			iqmux43EmbOutEmbedPair5Left
				INTEGER,
			iqmux43EmbOutEmbedPair5Right
				INTEGER,
			iqmux43EmbOutEmbedPair5LinkLRSelection
				INTEGER,
			iqmux43EmbOutEmbedPair6Left
				INTEGER,
			iqmux43EmbOutEmbedPair6Right
				INTEGER,
			iqmux43EmbOutEmbedPair6LinkLRSelection
				INTEGER,
			iqmux43EmbOutEmbedPair7Left
				INTEGER,
			iqmux43EmbOutEmbedPair7Right
				INTEGER,
			iqmux43EmbOutEmbedPair7LinkLRSelection
				INTEGER,
			iqmux43EmbOutEmbedPair8Left
				INTEGER,
			iqmux43EmbOutEmbedPair8Right
				INTEGER,
			iqmux43EmbOutEmbedPair8LinkLRSelection
				INTEGER,
			iqmux43AudioEmbModeInput1
				INTEGER,
			iqmux43AudioEmbModeInput2
				INTEGER,
			iqmux43AudioEmbModeInput3
				INTEGER,
			iqmux43AudioEmbModeInput4
				INTEGER,
			iqmux43AudioEmbModeInput5
				INTEGER,
			iqmux43AudioEmbModeInput6
				INTEGER,
			iqmux43AudioEmbModeInput7
				INTEGER,
			iqmux43AudioEmbModeInput8
				INTEGER,
			iqmux43EmbedNamesDisembeder1
				RollCallString,
			iqmux43EmbedNamesDisembeder1R
				RollCallString,
			iqmux43EmbedNamesDisembeder2
				RollCallString,
			iqmux43EmbedNamesDisembeder2R
				RollCallString,
			iqmux43EmbedNamesDisembeder3
				RollCallString,
			iqmux43EmbedNamesDisembeder3R
				RollCallString,
			iqmux43EmbedNamesDisembeder4
				RollCallString,
			iqmux43EmbedNamesDisembeder4R
				RollCallString,
			iqmux43EmbedNamesDisembeder5
				RollCallString,
			iqmux43EmbedNamesDisembeder5R
				RollCallString,
			iqmux43EmbedNamesDisembeder6
				RollCallString,
			iqmux43EmbedNamesDisembeder6R
				RollCallString,
			iqmux43EmbedNamesDisembeder7
				RollCallString,
			iqmux43EmbedNamesDisembeder7R
				RollCallString,
			iqmux43EmbedNamesDisembeder8
				RollCallString,
			iqmux43EmbedNamesDisembeder8R
				RollCallString,
			iqmux43EmbedNamesEmbeddedOP1
				RollCallString,
			iqmux43EmbedNamesEmbeddedOP1R
				RollCallString,
			iqmux43EmbedNamesEmbeddedOP2
				RollCallString,
			iqmux43EmbedNamesEmbeddedOP2R
				RollCallString,
			iqmux43EmbedNamesEmbeddedOP3
				RollCallString,
			iqmux43EmbedNamesEmbeddedOP3R
				RollCallString,
			iqmux43EmbedNamesEmbeddedOP4
				RollCallString,
			iqmux43EmbedNamesEmbeddedOP4R
				RollCallString,
			iqmux43EmbedNamesEmbeddedOP5
				RollCallString,
			iqmux43EmbedNamesEmbeddedOP5R
				RollCallString,
			iqmux43EmbedNamesEmbeddedOP6
				RollCallString,
			iqmux43EmbedNamesEmbeddedOP6R
				RollCallString,
			iqmux43EmbedNamesEmbeddedOP7
				RollCallString,
			iqmux43EmbedNamesEmbeddedOP7R
				RollCallString,
			iqmux43EmbedNamesEmbeddedOP8
				RollCallString,
			iqmux43EmbedNamesEmbeddedOP8R
				RollCallString,
			iqmux43EmbedNamesIPStereoDisemb1
				INTEGER,
			iqmux43EmbedNamesIPStereoDisemb2
				INTEGER,
			iqmux43EmbedNamesIPStereoDisemb3
				INTEGER,
			iqmux43EmbedNamesIPStereoDisemb4
				INTEGER,
			iqmux43EmbedNamesIPStereoDisemb5
				INTEGER,
			iqmux43EmbedNamesIPStereoDisemb6
				INTEGER,
			iqmux43EmbedNamesIPStereoDisemb7
				INTEGER,
			iqmux43EmbedNamesIPStereoDisemb8
				INTEGER,
			iqmux43EmbedNamesOPStereoEmbed1
				INTEGER,
			iqmux43EmbedNamesOPStereoEmbed2
				INTEGER,
			iqmux43EmbedNamesOPStereoEmbed3
				INTEGER,
			iqmux43EmbedNamesOPStereoEmbed4
				INTEGER,
			iqmux43EmbedNamesOPStereoEmbed5
				INTEGER,
			iqmux43EmbedNamesOPStereoEmbed6
				INTEGER,
			iqmux43EmbedNamesOPStereoEmbed7
				INTEGER,
			iqmux43EmbedNamesOPStereoEmbed8
				INTEGER,
			iqmux43AudioMixNamesMix1
				RollCallString,
			iqmux43AudioMixNamesMix2
				RollCallString,
			iqmux43AudioMixNamesMix3
				RollCallString,
			iqmux43AudioMixNamesMix4
				RollCallString,
			iqmux43Mix1RoutingSource1
				INTEGER,
			iqmux43Mix1RoutingInvert1
				INTEGER,
			iqmux43Mix1RoutingSource2
				INTEGER,
			iqmux43Mix1RoutingInvert2
				INTEGER,
			iqmux43Mix1RoutingSource3
				INTEGER,
			iqmux43Mix1RoutingInvert3
				INTEGER,
			iqmux43Mix1RoutingSource4
				INTEGER,
			iqmux43Mix1RoutingInvert4
				INTEGER,
			iqmux43Mix1GainGain1
				INTEGER,
			iqmux43Mix1GainMute1
				INTEGER,
			iqmux43Mix1GainGain2
				INTEGER,
			iqmux43Mix1GainMute2
				INTEGER,
			iqmux43Mix1GainGain3
				INTEGER,
			iqmux43Mix1GainMute3
				INTEGER,
			iqmux43Mix1GainGain4
				INTEGER,
			iqmux43Mix1GainMute4
				INTEGER,
			iqmux43Mix1GainInp1Clip
				RollCallString,
			iqmux43Mix1GainInp2Clip
				RollCallString,
			iqmux43Mix1GainInp3Clip
				RollCallString,
			iqmux43Mix1GainInp4Clip
				RollCallString,
			iqmux43Mix1GainOPClip
				RollCallString,
			iqmux43Mix2RoutingSource1
				INTEGER,
			iqmux43Mix2RoutingInvert1
				INTEGER,
			iqmux43Mix2RoutingSource2
				INTEGER,
			iqmux43Mix2RoutingInvert2
				INTEGER,
			iqmux43Mix2RoutingSource3
				INTEGER,
			iqmux43Mix2RoutingInvert3
				INTEGER,
			iqmux43Mix2RoutingSource4
				INTEGER,
			iqmux43Mix2RoutingInvert4
				INTEGER,
			iqmux43Mix2GainGain1
				INTEGER,
			iqmux43Mix2GainMute1
				INTEGER,
			iqmux43Mix2GainGain2
				INTEGER,
			iqmux43Mix2GainMute2
				INTEGER,
			iqmux43Mix2GainGain3
				INTEGER,
			iqmux43Mix2GainMute3
				INTEGER,
			iqmux43Mix2GainGain4
				INTEGER,
			iqmux43Mix2GainMute4
				INTEGER,
			iqmux43Mix2GainInp1Clip
				RollCallString,
			iqmux43Mix2GainInp2Clip
				RollCallString,
			iqmux43Mix2GainInp3Clip
				RollCallString,
			iqmux43Mix2GainInp4Clip
				RollCallString,
			iqmux43Mix2GainOPClip
				RollCallString,
			iqmux43Mix3RoutingSource1
				INTEGER,
			iqmux43Mix3RoutingInvert1
				INTEGER,
			iqmux43Mix3RoutingSource2
				INTEGER,
			iqmux43Mix3RoutingInvert2
				INTEGER,
			iqmux43Mix3RoutingSource3
				INTEGER,
			iqmux43Mix3RoutingInvert3
				INTEGER,
			iqmux43Mix3RoutingSource4
				INTEGER,
			iqmux43Mix3RoutingInvert4
				INTEGER,
			iqmux43Mix3GainGain1
				INTEGER,
			iqmux43Mix3GainMute1
				INTEGER,
			iqmux43Mix3GainGain2
				INTEGER,
			iqmux43Mix3GainMute2
				INTEGER,
			iqmux43Mix3GainGain3
				INTEGER,
			iqmux43Mix3GainMute3
				INTEGER,
			iqmux43Mix3GainGain4
				INTEGER,
			iqmux43Mix3GainMute4
				INTEGER,
			iqmux43Mix3GainInp1Clip
				RollCallString,
			iqmux43Mix3GainInp2Clip
				RollCallString,
			iqmux43Mix3GainInp3Clip
				RollCallString,
			iqmux43Mix3GainInp4Clip
				RollCallString,
			iqmux43Mix3GainOPClip
				RollCallString,
			iqmux43Mix4RoutingSource1
				INTEGER,
			iqmux43Mix4RoutingInvert1
				INTEGER,
			iqmux43Mix4RoutingSource2
				INTEGER,
			iqmux43Mix4RoutingInvert2
				INTEGER,
			iqmux43Mix4RoutingSource3
				INTEGER,
			iqmux43Mix4RoutingInvert3
				INTEGER,
			iqmux43Mix4RoutingSource4
				INTEGER,
			iqmux43Mix4RoutingInvert4
				INTEGER,
			iqmux43Mix4GainGain1
				INTEGER,
			iqmux43Mix4GainMute1
				INTEGER,
			iqmux43Mix4GainGain2
				INTEGER,
			iqmux43Mix4GainMute2
				INTEGER,
			iqmux43Mix4GainGain3
				INTEGER,
			iqmux43Mix4GainMute3
				INTEGER,
			iqmux43Mix4GainGain4
				INTEGER,
			iqmux43Mix4GainMute4
				INTEGER,
			iqmux43Mix4GainInp1Clip
				RollCallString,
			iqmux43Mix4GainInp2Clip
				RollCallString,
			iqmux43Mix4GainInp3Clip
				RollCallString,
			iqmux43Mix4GainInp4Clip
				RollCallString,
			iqmux43Mix4GainOPClip
				RollCallString,
			iqmux43AESGainOut1AESOut1MuteL
				INTEGER,
			iqmux43AESGainOut1AESOut1MuteR
				INTEGER,
			iqmux43AESGainOut1AESOut1LGain
				INTEGER,
			iqmux43AESGainOut1AESOut1RGain
				INTEGER,
			iqmux43AESGainOut1Stereo
				INTEGER,
			iqmux43AESGainOut1AESOut1InvertL
				INTEGER,
			iqmux43AESGainOut1AESOut1InvertR
				INTEGER,
			iqmux43AESGainOut1AESOut1LClip
				RollCallString,
			iqmux43AESGainOut1AESOut1RClip
				RollCallString,
			iqmux43AESGainOut2AESOut2MuteL
				INTEGER,
			iqmux43AESGainOut2AESOut2MuteR
				INTEGER,
			iqmux43AESGainOut2AESOut2LGain
				INTEGER,
			iqmux43AESGainOut2AESOut2RGain
				INTEGER,
			iqmux43AESGainOut2Stereo
				INTEGER,
			iqmux43AESGainOut2AESOut2InvertL
				INTEGER,
			iqmux43AESGainOut2AESOut2InvertR
				INTEGER,
			iqmux43AESGainOut2AESOut2LClip
				RollCallString,
			iqmux43AESGainOut2AESOut2RClip
				RollCallString,
			iqmux43AESGainOut3AESOut3MuteL
				INTEGER,
			iqmux43AESGainOut3AESOut3MuteR
				INTEGER,
			iqmux43AESGainOut3AESOut3LGain
				INTEGER,
			iqmux43AESGainOut3AESOut3RGain
				INTEGER,
			iqmux43AESGainOut3Stereo
				INTEGER,
			iqmux43AESGainOut3AESOut3InvertL
				INTEGER,
			iqmux43AESGainOut3AESOut3InvertR
				INTEGER,
			iqmux43AESGainOut3AESOut3LClip
				RollCallString,
			iqmux43AESGainOut3AESOut3RClip
				RollCallString,
			iqmux43AESGainOut4AESOut4MuteL
				INTEGER,
			iqmux43AESGainOut4AESOut4MuteR
				INTEGER,
			iqmux43AESGainOut4AESOut4LGain
				INTEGER,
			iqmux43AESGainOut4AESOut4RGain
				INTEGER,
			iqmux43AESGainOut4Stereo
				INTEGER,
			iqmux43AESGainOut4AESOut4InvertL
				INTEGER,
			iqmux43AESGainOut4AESOut4InvertR
				INTEGER,
			iqmux43AESGainOut4AESOut4LClip
				RollCallString,
			iqmux43AESGainOut4AESOut4RClip
				RollCallString,
			iqmux43AESGainOut5AESOut5MuteL
				INTEGER,
			iqmux43AESGainOut5AESOut5MuteR
				INTEGER,
			iqmux43AESGainOut5AESOut5LGain
				INTEGER,
			iqmux43AESGainOut5AESOut5RGain
				INTEGER,
			iqmux43AESGainOut5Stereo
				INTEGER,
			iqmux43AESGainOut5AESOut5InvertL
				INTEGER,
			iqmux43AESGainOut5AESOut5InvertR
				INTEGER,
			iqmux43AESGainOut5AESOut5LClip
				RollCallString,
			iqmux43AESGainOut5AESOut5RClip
				RollCallString,
			iqmux43AESGainOut6AESOut6MuteL
				INTEGER,
			iqmux43AESGainOut6AESOut6MuteR
				INTEGER,
			iqmux43AESGainOut6AESOut6LGain
				INTEGER,
			iqmux43AESGainOut6AESOut6RGain
				INTEGER,
			iqmux43AESGainOut6Stereo
				INTEGER,
			iqmux43AESGainOut6AESOut6InvertL
				INTEGER,
			iqmux43AESGainOut6AESOut6InvertR
				INTEGER,
			iqmux43AESGainOut6AESOut6LClip
				RollCallString,
			iqmux43AESGainOut6AESOut6RClip
				RollCallString,
			iqmux43AESGainOut7AESOut7MuteL
				INTEGER,
			iqmux43AESGainOut7AESOut7MuteR
				INTEGER,
			iqmux43AESGainOut7AESOut7LGain
				INTEGER,
			iqmux43AESGainOut7AESOut7RGain
				INTEGER,
			iqmux43AESGainOut7Stereo
				INTEGER,
			iqmux43AESGainOut7AESOut7InvertL
				INTEGER,
			iqmux43AESGainOut7AESOut7InvertR
				INTEGER,
			iqmux43AESGainOut7AESOut7LClip
				RollCallString,
			iqmux43AESGainOut7AESOut7RClip
				RollCallString,
			iqmux43AESGainOut8AESOut8MuteL
				INTEGER,
			iqmux43AESGainOut8AESOut8MuteR
				INTEGER,
			iqmux43AESGainOut8AESOut8LGain
				INTEGER,
			iqmux43AESGainOut8AESOut8RGain
				INTEGER,
			iqmux43AESGainOut8Stereo
				INTEGER,
			iqmux43AESGainOut8AESOut8InvertL
				INTEGER,
			iqmux43AESGainOut8AESOut8InvertR
				INTEGER,
			iqmux43AESGainOut8AESOut8LClip
				RollCallString,
			iqmux43AESGainOut8AESOut8RClip
				RollCallString,
			iqmux43AESOut1Left
				INTEGER,
			iqmux43AESOut1Right
				INTEGER,
			iqmux43AESOut1LinkLRSelection
				INTEGER,
			iqmux43AESOut2Left
				INTEGER,
			iqmux43AESOut2Right
				INTEGER,
			iqmux43AESOut2LinkLRSelection
				INTEGER,
			iqmux43AESOut3Left
				INTEGER,
			iqmux43AESOut3Right
				INTEGER,
			iqmux43AESOut3LinkLRSelection
				INTEGER,
			iqmux43AESOut4Left
				INTEGER,
			iqmux43AESOut4Right
				INTEGER,
			iqmux43AESOut4LinkLRSelection
				INTEGER,
			iqmux43AESOut5Left
				INTEGER,
			iqmux43AESOut5Right
				INTEGER,
			iqmux43AESOut5LinkLRSelection
				INTEGER,
			iqmux43AESOut6Left
				INTEGER,
			iqmux43AESOut6Right
				INTEGER,
			iqmux43AESOut6LinkLRSelection
				INTEGER,
			iqmux43AESOut7Left
				INTEGER,
			iqmux43AESOut7Right
				INTEGER,
			iqmux43AESOut7LinkLRSelection
				INTEGER,
			iqmux43AESOut8Left
				INTEGER,
			iqmux43AESOut8Right
				INTEGER,
			iqmux43AESOut8LinkLRSelection
				INTEGER,
			iqmux43AESOutMonitoropLeft
				INTEGER,
			iqmux43AESOutMonitoropRight
				INTEGER,
			iqmux43AESOutMonitoropLinkLRSelection
				INTEGER,
			iqmux43AESOutPortNamesAESPort1Stereo
				INTEGER,
			iqmux43AESOutPortNamesAESPort1L
				RollCallString,
			iqmux43AESOutPortNamesAESPort1R
				RollCallString,
			iqmux43AESOutPortNamesAESPort2Stereo
				INTEGER,
			iqmux43AESOutPortNamesAESPort2L
				RollCallString,
			iqmux43AESOutPortNamesAESPort2R
				RollCallString,
			iqmux43AESOutPortNamesAESPort3Stereo
				INTEGER,
			iqmux43AESOutPortNamesAESPort3L
				RollCallString,
			iqmux43AESOutPortNamesAESPort3R
				RollCallString,
			iqmux43AESOutPortNamesAESPort4Stereo
				INTEGER,
			iqmux43AESOutPortNamesAESPort4L
				RollCallString,
			iqmux43AESOutPortNamesAESPort4R
				RollCallString,
			iqmux43AESOutPortNamesAESPort5Stereo
				INTEGER,
			iqmux43AESOutPortNamesAESPort5L
				RollCallString,
			iqmux43AESOutPortNamesAESPort5R
				RollCallString,
			iqmux43AESOutPortNamesAESPort6Stereo
				INTEGER,
			iqmux43AESOutPortNamesAESPort6L
				RollCallString,
			iqmux43AESOutPortNamesAESPort6R
				RollCallString,
			iqmux43AESOutPortNamesAESPort7Stereo
				INTEGER,
			iqmux43AESOutPortNamesAESPort7L
				RollCallString,
			iqmux43AESOutPortNamesAESPort7R
				RollCallString,
			iqmux43AESOutPortNamesAESPort8Stereo
				INTEGER,
			iqmux43AESOutPortNamesAESPort8L
				RollCallString,
			iqmux43AESOutPortNamesAESPort8R
				RollCallString,
			iqmux43AESBusDataModeInput1
				INTEGER,
			iqmux43AESBusDataModeInput2
				INTEGER,
			iqmux43AESBusDataModeInput3
				INTEGER,
			iqmux43AESBusDataModeInput4
				INTEGER,
			iqmux43AESBusDataModeInput5
				INTEGER,
			iqmux43AESBusDataModeInput6
				INTEGER,
			iqmux43AESBusDataModeInput7
				INTEGER,
			iqmux43AESBusDataModeInput8
				INTEGER,
			iqmux43AESBusNamesAESBus1Stereo
				INTEGER,
			iqmux43AESBusNamesAESBus1
				RollCallString,
			iqmux43AESBusNamesAESBus1R
				RollCallString,
			iqmux43AESBusNamesAESBus2Stereo
				INTEGER,
			iqmux43AESBusNamesAESBus2
				RollCallString,
			iqmux43AESBusNamesAESBus2R
				RollCallString,
			iqmux43AESBusNamesAESBus3Stereo
				INTEGER,
			iqmux43AESBusNamesAESBus3
				RollCallString,
			iqmux43AESBusNamesAESBus3R
				RollCallString,
			iqmux43AESBusNamesAESBus4Stereo
				INTEGER,
			iqmux43AESBusNamesAESBus4
				RollCallString,
			iqmux43AESBusNamesAESBus4R
				RollCallString,
			iqmux43AESBusNamesAESBus5Stereo
				INTEGER,
			iqmux43AESBusNamesAESBus5
				RollCallString,
			iqmux43AESBusNamesAESBus5R
				RollCallString,
			iqmux43AESBusNamesAESBus6Stereo
				INTEGER,
			iqmux43AESBusNamesAESBus6
				RollCallString,
			iqmux43AESBusNamesAESBus6R
				RollCallString,
			iqmux43AESBusNamesAESBus7Stereo
				INTEGER,
			iqmux43AESBusNamesAESBus7
				RollCallString,
			iqmux43AESBusNamesAESBus7R
				RollCallString,
			iqmux43AESBusNamesAESBus8Stereo
				INTEGER,
			iqmux43AESBusNamesAESBus8
				RollCallString,
			iqmux43AESBusNamesAESBus8R
				RollCallString,
			iqmux43AESBusRoutingSource1
				INTEGER,
			iqmux43AESBusRoutingSource2
				INTEGER,
			iqmux43AESBusRoutingSource3
				INTEGER,
			iqmux43AESBusRoutingSource4
				INTEGER,
			iqmux43AESBusRoutingSource5
				INTEGER,
			iqmux43AESBusRoutingSource6
				INTEGER,
			iqmux43AESBusRoutingSource7
				INTEGER,
			iqmux43AESBusRoutingSource8
				INTEGER,
			iqmux43AESPortsDirectionAES1Out
				INTEGER,
			iqmux43AESPortsDirectionAES2Out
				INTEGER,
			iqmux43AESPortsDirectionAES3Out
				INTEGER,
			iqmux43AESPortsDirectionAES4Out
				INTEGER,
			iqmux43AESPortsDirectionAES5Out
				INTEGER,
			iqmux43AESPortsDirectionAES6Out
				INTEGER,
			iqmux43AESPortsDirectionAES7Out
				INTEGER,
			iqmux43AESPortsDirectionAES8Out
				INTEGER,
			iqmux43AudioDolbyETimingSelAudioPair
				INTEGER,
			iqmux43AudioDolbyETimingRelativeTiming
				RollCallString,
			iqmux43AudioDolbyETimingStatus
				RollCallString,
			iqmux43AudioDolbyETimingError
				RollCallString,
			iqmux43DolbyETimingLineStandard
				INTEGER,
			iqmux43DolbyETimingLineAutoLineNo
				INTEGER,
			iqmux43DolbyELineUserDolbyELinePair1
				INTEGER,
			iqmux43DolbyELineUserDolbyELinePair2
				INTEGER,
			iqmux43DolbyELineUserDolbyELinePair3
				INTEGER,
			iqmux43DolbyELineUserDolbyELinePair4
				INTEGER,
			iqmux43DolbyELineUserDolbyELinePair5
				INTEGER,
			iqmux43DolbyELineUserDolbyELinePair6
				INTEGER,
			iqmux43DolbyELineUserDolbyELinePair7
				INTEGER,
			iqmux43DolbyELineUserDolbyELinePair8
				INTEGER,
			iqmux43VidDelayInternalDelay
				RollCallString,
			iqmux43VidDelayDelayMode
				INTEGER,
			iqmux43VidSetDelayDelayFrames
				INTEGER,
			iqmux43VidSetDelayVerticalTiming
				INTEGER,
			iqmux43VidSetDelayHorizontalTiming
				INTEGER,
			iqmux43VidSetDelayDelayms
				INTEGER,
			iqmux43UtilsPatternsPatternEnable
				INTEGER,
			iqmux43UtilsPatternsScrollPattern
				INTEGER,
			iqmux43UtilsPatternsPatternType
				INTEGER,
			iqmux43UtilsANCblankonMismat
				INTEGER,
			iqmux43UtilsFreezeForceFreeze
				INTEGER,
			iqmux43UtilsFreezeFreezeType
				INTEGER,
			iqmux43UtilsMonochrome
				INTEGER,
			iqmux43UtilsMonochromeMonochromeType
				INTEGER,
			iqmux43UtilsVBIBlankingANCMode
				INTEGER,
			iqmux43UtilsVBIBlankingStandard
				INTEGER,
			iqmux43UtilsVBIBlankingBlankAll
				INTEGER,
			iqmux43UtilsVBIBlankingPassAll
				INTEGER,
			iqmux43UtilsVBIBlankingBlank1
				INTEGER,
			iqmux43UtilsVBIBlankingBlank2
				INTEGER,
			iqmux43UtilsVBIBlankingBlank3
				INTEGER,
			iqmux43UtilsVBIBlankingBlank4
				INTEGER,
			iqmux43UtilsVBIBlankingBlank5
				INTEGER,
			iqmux43UtilsVBIBlankingBlank6
				INTEGER,
			iqmux43UtilsVBIBlankingBlank7
				INTEGER,
			iqmux43UtilsVBIBlankingBlank8
				INTEGER,
			iqmux43UtilsVBIBlankingBlank9
				INTEGER,
			iqmux43UtilsVBIBlankingBlank10
				INTEGER,
			iqmux43UtilsVBIBlankingBlank11
				INTEGER,
			iqmux43UtilsVBIBlankingBlank12
				INTEGER,
			iqmux43UtilsVBIBlankingBlank13
				INTEGER,
			iqmux43UtilsVBIBlankingBlank14
				INTEGER,
			iqmux43UtilsVBIBlankingBlank15
				INTEGER,
			iqmux43UtilsVBIBlankingBlank16
				INTEGER,
			iqmux43UtilsVBIBlankingBlank17
				INTEGER,
			iqmux43UtilsVBIBlankingBlank18
				INTEGER,
			iqmux43UtilsVBIBlankingBlank19
				INTEGER,
			iqmux43UtilsVBIBlankingBlank20
				INTEGER,
			iqmux43UtilsVBIBlankingBlank21
				INTEGER,
			iqmux43UtilsVBIBlankingBlank22
				INTEGER,
			iqmux43UtilsVBIBlankingBlank23
				INTEGER,
			iqmux43UtilsVBIBlankingBlank24
				INTEGER,
			iqmux43UtilsVBIBlankingBlank25
				INTEGER,
			iqmux43UtilsVBIBlankingBlank26
				INTEGER,
			iqmux43UtilsVBIBlankingBlank27
				INTEGER,
			iqmux43UtilsVBIBlankingBlank28
				INTEGER,
			iqmux43UtilsVBIBlankingBlank29
				INTEGER,
			iqmux43UtilsVBIBlankingBlank30
				INTEGER,
			iqmux43UtilsVBIBlankingBlank31
				INTEGER,
			iqmux43UtilsVBIBlankingBlank32
				INTEGER,
			iqmux43UtilsVBIBlankingBlank33
				INTEGER,
			iqmux43UtilsVBIBlankingBlank34
				INTEGER,
			iqmux43MemoriesRecallMemory
				INTEGER,
			iqmux43MemoriesSelMemory
				INTEGER,
			iqmux43SaveMemories
				INTEGER,
			iqmux43ClearMemories
				INTEGER,
			iqmux43MemoriesMemoryNameChangeName
				RollCallString,
			iqmux43MemoriesLastUserMemory
				RollCallString,
			iqmux43MemoriesMemoryName1
				RollCallString,
			iqmux43MemoriesMemoryName2
				RollCallString,
			iqmux43MemoriesMemoryName3
				RollCallString,
			iqmux43MemoriesMemoryName4
				RollCallString,
			iqmux43MemoriesMemoryName5
				RollCallString,
			iqmux43MemoriesMemoryName6
				RollCallString,
			iqmux43MemoriesMemoryName7
				RollCallString,
			iqmux43MemoriesMemoryName8
				RollCallString,
			iqmux43MemoriesMemoryName9
				RollCallString,
			iqmux43MemoriesMemoryName10
				RollCallString,
			iqmux43MemoriesMemoryName11
				RollCallString,
			iqmux43MemoriesMemoryName12
				RollCallString,
			iqmux43MemoriesMemoryName13
				RollCallString,
			iqmux43MemoriesMemoryName14
				RollCallString,
			iqmux43MemoriesMemoryName15
				RollCallString,
			iqmux43MemoriesMemoryName16
				RollCallString,
			iqmux43LoggingVideoLogInput1Type
				INTEGER,
			iqmux43LoggingVideoInput1Type
				RollCallString,
			iqmux43LoggingVideoLogInput1Status
				INTEGER,
			iqmux43LoggingVideoInput1Status
				RollCallString,
			iqmux43LoggingVideoLogInput1Std
				INTEGER,
			iqmux43LoggingVideoInput1Std
				RollCallString,
			iqmux43LoggingVideoLogInput1Errors
				INTEGER,
			iqmux43LoggingVideoInput1Errors
				RollCallString,
			iqmux43LoggingVideoLogInput1ErrSecs
				INTEGER,
			iqmux43LoggingVideoInput1ErrSecs
				RollCallString,
			iqmux43LoggingVideoLogInput1ANCErr35000
				INTEGER,
			iqmux43LoggingVideoInput1ANCErrors
				RollCallString,
			iqmux43LoggingVideoLogInput1ANCErr35001
				INTEGER,
			iqmux43LoggingVideoInput1ANCErrSecs
				RollCallString,
			iqmux43LoggingVideoLogOutputState
				INTEGER,
			iqmux43LoggingVideoOutputState
				RollCallString,
			iqmux43LoggingVideoLogOutputType
				INTEGER,
			iqmux43LoggingVideoOutputType
				RollCallString,
			iqmux43LoggingVideoLogOutputStandard
				INTEGER,
			iqmux43LoggingVideoOutputStandard
				RollCallString,
			iqmux43LoggingVideoLogoutputANCstat
				INTEGER,
			iqmux43LoggingVideoOutputANCstate
				RollCallString,
			iqmux43LoggingEmbedAudioLogInp1Emb1stat
				INTEGER,
			iqmux43LoggingEmbedAudioInp1Emb1state
				RollCallString,
			iqmux43LoggingEmbedAudioLogInp1Emb2stat
				INTEGER,
			iqmux43LoggingEmbedAudioInp1Emb2state
				RollCallString,
			iqmux43LoggingEmbedAudioLogInp1Emb3stat
				INTEGER,
			iqmux43LoggingEmbedAudioInp1Emb3state
				RollCallString,
			iqmux43LoggingEmbedAudioLogInp1Emb4stat
				INTEGER,
			iqmux43LoggingEmbedAudioInp1Emb4state
				RollCallString,
			iqmux43LoggingEmbedAudioLogInp1Emb5stat
				INTEGER,
			iqmux43LoggingEmbedAudioInp1Emb5state
				RollCallString,
			iqmux43LoggingEmbedAudioLogInp1Emb6stat
				INTEGER,
			iqmux43LoggingEmbedAudioInp1Emb6state
				RollCallString,
			iqmux43LoggingEmbedAudioLogInp1Emb7stat
				INTEGER,
			iqmux43LoggingEmbedAudioInp1Emb7state
				RollCallString,
			iqmux43LoggingEmbedAudioLogInp1Emb8stat
				INTEGER,
			iqmux43LoggingEmbedAudioInp1Emb8state
				RollCallString,
			iqmux43LoggingEmbedAudioLogInp1Emb1type
				INTEGER,
			iqmux43LoggingEmbedAudioInp1Emb1type
				RollCallString,
			iqmux43LoggingEmbedAudioLogInp1Emb2type
				INTEGER,
			iqmux43LoggingEmbedAudioInp1Emb2type
				RollCallString,
			iqmux43LoggingEmbedAudioLogInp1Emb3type
				INTEGER,
			iqmux43LoggingEmbedAudioInp1Emb3type
				RollCallString,
			iqmux43LoggingEmbedAudioLogInp1Emb4type
				INTEGER,
			iqmux43LoggingEmbedAudioInp1Emb4type
				RollCallString,
			iqmux43LoggingEmbedAudioLogInp1Emb5type
				INTEGER,
			iqmux43LoggingEmbedAudioInp1Emb5type
				RollCallString,
			iqmux43LoggingEmbedAudioLogInp1Emb6type
				INTEGER,
			iqmux43LoggingEmbedAudioInp1Emb6type
				RollCallString,
			iqmux43LoggingEmbedAudioLogInp1Emb7type
				INTEGER,
			iqmux43LoggingEmbedAudioInp1Emb7type
				RollCallString,
			iqmux43LoggingEmbedAudioLogInp1Emb8type
				INTEGER,
			iqmux43LoggingEmbedAudioInp1Emb8type
				RollCallString,
			iqmux43LoggingOPAudioLogOutEmb1state
				INTEGER,
			iqmux43LoggingOPAudioOutEmb1state
				RollCallString,
			iqmux43LoggingOPAudioLogOutEmb2state
				INTEGER,
			iqmux43LoggingOPAudioOutEmb2state
				RollCallString,
			iqmux43LoggingOPAudioLogOutEmb3state
				INTEGER,
			iqmux43LoggingOPAudioOutEmb3state
				RollCallString,
			iqmux43LoggingOPAudioLogOutEmb4state
				INTEGER,
			iqmux43LoggingOPAudioOutEmb4state
				RollCallString,
			iqmux43LoggingOPAudioLogOutEmb5state
				INTEGER,
			iqmux43LoggingOPAudioOutEmb5state
				RollCallString,
			iqmux43LoggingOPAudioLogOutEmb6state
				INTEGER,
			iqmux43LoggingOPAudioOutEmb6state
				RollCallString,
			iqmux43LoggingOPAudioLogOutEmb7state
				INTEGER,
			iqmux43LoggingOPAudioOutEmb7state
				RollCallString,
			iqmux43LoggingOPAudioLogOutEmb8state
				INTEGER,
			iqmux43LoggingOPAudioOutEmb8state
				RollCallString,
			iqmux43LoggingOPAudioLogOutEmb1type
				INTEGER,
			iqmux43LoggingOPAudioOutEmb1type
				RollCallString,
			iqmux43LoggingOPAudioLogOutEmb2type
				INTEGER,
			iqmux43LoggingOPAudioOutEmb2type
				RollCallString,
			iqmux43LoggingOPAudioLogOutEmb3type
				INTEGER,
			iqmux43LoggingOPAudioOutEmb3type
				RollCallString,
			iqmux43LoggingOPAudioLogOutEmb4type
				INTEGER,
			iqmux43LoggingOPAudioOutEmb4type
				RollCallString,
			iqmux43LoggingOPAudioLogOutEmb5type
				INTEGER,
			iqmux43LoggingOPAudioOutEmb5type
				RollCallString,
			iqmux43LoggingOPAudioLogOutEmb6type
				INTEGER,
			iqmux43LoggingOPAudioOutEmb6type
				RollCallString,
			iqmux43LoggingOPAudioLogOutEmb7type
				INTEGER,
			iqmux43LoggingOPAudioOutEmb7type
				RollCallString,
			iqmux43LoggingOPAudioLogOutEmb8type
				INTEGER,
			iqmux43LoggingOPAudioOutEmb8type
				RollCallString,
			iqmux43LoggingOPAudioLevelLogOutEmb1LLev
				INTEGER,
			iqmux43LoggingOPAudioLevelOutEmb1LLevel
				RollCallString,
			iqmux43LoggingOPAudioLevelLogOutEmb1RLev
				INTEGER,
			iqmux43LoggingOPAudioLevelOutEmb1RLevel
				RollCallString,
			iqmux43LoggingOPAudioLevelLogOutEmb2LLev
				INTEGER,
			iqmux43LoggingOPAudioLevelOutEmb2LLevel
				RollCallString,
			iqmux43LoggingOPAudioLevelLogOutEmb2RLev
				INTEGER,
			iqmux43LoggingOPAudioLevelOutEmb2RLevel
				RollCallString,
			iqmux43LoggingOPAudioLevelLogOutEmb3LLev
				INTEGER,
			iqmux43LoggingOPAudioLevelOutEmb3LLevel
				RollCallString,
			iqmux43LoggingOPAudioLevelLogOutEmb3RLev
				INTEGER,
			iqmux43LoggingOPAudioLevelOutEmb3RLevel
				RollCallString,
			iqmux43LoggingOPAudioLevelLogOutEmb4LLev
				INTEGER,
			iqmux43LoggingOPAudioLevelOutEmb4LLevel
				RollCallString,
			iqmux43LoggingOPAudioLevelLogOutEmb4RLev
				INTEGER,
			iqmux43LoggingOPAudioLevelOutEmb4RLevel
				RollCallString,
			iqmux43LoggingOPAudioLevelLogOutEmb5LLev
				INTEGER,
			iqmux43LoggingOPAudioLevelOutEmb5LLevel
				RollCallString,
			iqmux43LoggingOPAudioLevelLogOutEmb5RLev
				INTEGER,
			iqmux43LoggingOPAudioLevelOutEmb5RLevel
				RollCallString,
			iqmux43LoggingOPAudioLevelLogOutEmb6LLev
				INTEGER,
			iqmux43LoggingOPAudioLevelOutEmb6LLevel
				RollCallString,
			iqmux43LoggingOPAudioLevelLogOutEmb6RLev
				INTEGER,
			iqmux43LoggingOPAudioLevelOutEmb6RLevel
				RollCallString,
			iqmux43LoggingOPAudioLevelLogOutEmb7LLev
				INTEGER,
			iqmux43LoggingOPAudioLevelOutEmb7LLevel
				RollCallString,
			iqmux43LoggingOPAudioLevelLogOutEmb7RLev
				INTEGER,
			iqmux43LoggingOPAudioLevelOutEmb7RLevel
				RollCallString,
			iqmux43LoggingOPAudioLevelLogOutEmb8LLev
				INTEGER,
			iqmux43LoggingOPAudioLevelOutEmb8LLevel
				RollCallString,
			iqmux43LoggingOPAudioLevelLogOutEmb8RLev
				INTEGER,
			iqmux43LoggingOPAudioLevelOutEmb8RLevel
				RollCallString,
			iqmux43LoggingOPDolbyELogEmbDolbyE1
				INTEGER,
			iqmux43LoggingOPDolbyEEmbDolbyE1
				RollCallString,
			iqmux43LoggingOPDolbyELogEmbDolbyE2
				INTEGER,
			iqmux43LoggingOPDolbyEEmbDolbyE2
				RollCallString,
			iqmux43LoggingOPDolbyELogEmbDolbyE3
				INTEGER,
			iqmux43LoggingOPDolbyEEmbDolbyE3
				RollCallString,
			iqmux43LoggingOPDolbyELogEmbDolbyE4
				INTEGER,
			iqmux43LoggingOPDolbyEEmbDolbyE4
				RollCallString,
			iqmux43LoggingOPDolbyELogEmbDolbyE5
				INTEGER,
			iqmux43LoggingOPDolbyEEmbDolbyE5
				RollCallString,
			iqmux43LoggingOPDolbyELogEmbDolbyE6
				INTEGER,
			iqmux43LoggingOPDolbyEEmbDolbyE6
				RollCallString,
			iqmux43LoggingOPDolbyELogEmbDolbyE7
				INTEGER,
			iqmux43LoggingOPDolbyEEmbDolbyE7
				RollCallString,
			iqmux43LoggingOPDolbyELogEmbDolbyE8
				INTEGER,
			iqmux43LoggingOPDolbyEEmbDolbyE8
				RollCallString,
			iqmux43LoggingAESInputLogAESInput1sta
				INTEGER,
			iqmux43LoggingAESInputAESInput1state
				RollCallString,
			iqmux43LoggingAESInputLogAESInput2sta
				INTEGER,
			iqmux43LoggingAESInputAESInput2state
				RollCallString,
			iqmux43LoggingAESInputLogAESInput3sta
				INTEGER,
			iqmux43LoggingAESInputAESInput3state
				RollCallString,
			iqmux43LoggingAESInputLogAESInput4sta
				INTEGER,
			iqmux43LoggingAESInputAESInput4state
				RollCallString,
			iqmux43LoggingAESInputLogAESInput5sta
				INTEGER,
			iqmux43LoggingAESInputAESInput5state
				RollCallString,
			iqmux43LoggingAESInputLogAESInput6sta
				INTEGER,
			iqmux43LoggingAESInputAESInput6state
				RollCallString,
			iqmux43LoggingAESInputLogAESInput7sta
				INTEGER,
			iqmux43LoggingAESInputAESInput7state
				RollCallString,
			iqmux43LoggingAESInputLogAESInput8sta
				INTEGER,
			iqmux43LoggingAESInputAESInput8state
				RollCallString,
			iqmux43LoggingAESInputLogAESInput1typ
				INTEGER,
			iqmux43LoggingAESInputAESInput1type
				RollCallString,
			iqmux43LoggingAESInputLogAESInput2typ
				INTEGER,
			iqmux43LoggingAESInputAESInput2type
				RollCallString,
			iqmux43LoggingAESInputLogAESInput3typ
				INTEGER,
			iqmux43LoggingAESInputAESInput3type
				RollCallString,
			iqmux43LoggingAESInputLogAESInput4typ
				INTEGER,
			iqmux43LoggingAESInputAESInput4type
				RollCallString,
			iqmux43LoggingAESInputLogAESInput5typ
				INTEGER,
			iqmux43LoggingAESInputAESInput5type
				RollCallString,
			iqmux43LoggingAESInputLogAESInput6typ
				INTEGER,
			iqmux43LoggingAESInputAESInput6type
				RollCallString,
			iqmux43LoggingAESInputLogAESInput7typ
				INTEGER,
			iqmux43LoggingAESInputAESInput7type
				RollCallString,
			iqmux43LoggingAESInputLogAESInput8typ
				INTEGER,
			iqmux43LoggingAESInputAESInput8type
				RollCallString,
			iqmux43LoggingAESOutputLogAESOutput1st
				INTEGER,
			iqmux43LoggingAESOutputAESOutput1state
				RollCallString,
			iqmux43LoggingAESOutputLogAESOutput2st
				INTEGER,
			iqmux43LoggingAESOutputAESOutput2state
				RollCallString,
			iqmux43LoggingAESOutputLogAESOutput3st
				INTEGER,
			iqmux43LoggingAESOutputAESOutput3state
				RollCallString,
			iqmux43LoggingAESOutputLogAESOutput4st
				INTEGER,
			iqmux43LoggingAESOutputAESOutput4state
				RollCallString,
			iqmux43LoggingAESOutputLogAESOutput5st
				INTEGER,
			iqmux43LoggingAESOutputAESOutput5state
				RollCallString,
			iqmux43LoggingAESOutputLogAESOutput6st
				INTEGER,
			iqmux43LoggingAESOutputAESOutput6state
				RollCallString,
			iqmux43LoggingAESOutputLogAESOutput7st
				INTEGER,
			iqmux43LoggingAESOutputAESOutput7state
				RollCallString,
			iqmux43LoggingAESOutputLogAESOutput8st
				INTEGER,
			iqmux43LoggingAESOutputAESOutput8state
				RollCallString,
			iqmux43LoggingAESOutputLogAESOutput1ty
				INTEGER,
			iqmux43LoggingAESOutputAESOutput1type
				RollCallString,
			iqmux43LoggingAESOutputLogAESOutput2ty
				INTEGER,
			iqmux43LoggingAESOutputAESOutput2type
				RollCallString,
			iqmux43LoggingAESOutputLogAESOutput3ty
				INTEGER,
			iqmux43LoggingAESOutputAESOutput3type
				RollCallString,
			iqmux43LoggingAESOutputLogAESOutput4ty
				INTEGER,
			iqmux43LoggingAESOutputAESOutput4type
				RollCallString,
			iqmux43LoggingAESOutputLogAESOutput5ty
				INTEGER,
			iqmux43LoggingAESOutputAESOutput5type
				RollCallString,
			iqmux43LoggingAESOutputLogAESOutput6ty
				INTEGER,
			iqmux43LoggingAESOutputAESOutput6type
				RollCallString,
			iqmux43LoggingAESOutputLogAESOutput7ty
				INTEGER,
			iqmux43LoggingAESOutputAESOutput7type
				RollCallString,
			iqmux43LoggingAESOutputLogAESOutput8ty
				INTEGER,
			iqmux43LoggingAESOutputAESOutput8type
				RollCallString,
			iqmux43LoggingMiscLogSerialNo
				INTEGER,
			iqmux43LoggingMiscSerialNo
				RollCallString,
			iqmux43LoggingMiscLogOSVersion
				INTEGER,
			iqmux43LoggingMiscOSVersion
				RollCallString,
			iqmux43LoggingMiscLogBuildNo
				INTEGER,
			iqmux43LoggingMiscBuildNo
				RollCallString,
			iqmux43LoggingMiscLogHardwareVer
				INTEGER,
			iqmux43LoggingMiscHardwareVer
				RollCallString,
			iqmux43LoggingMiscLogFirmwareVer
				INTEGER,
			iqmux43LoggingMiscFirmwareVer
				RollCallString,
			iqmux43LoggingMiscLogUpTime
				INTEGER,
			iqmux43LoggingMiscUpTime
				RollCallString,
			iqmux43RollCallRollTrackDisableAll
				INTEGER,
			iqmux43RollCallRollTrackIndex
				INTEGER,
			iqmux43RollCallRollTrackSource
				INTEGER,
			iqmux43RollCallRollTrackAddress
				RollCallString,
			iqmux43RollCallRollTrackCommand
				RollCallString,
			iqmux43RollCallRollTrackStatus
				RollCallString,
			iqmux43RollCallRollTrackSending
				RollCallString,
			iqmux43SetupProduct
				RollCallString,
			iqmux43SetupRelease
				RollCallString,
			iqmux43SetupBuild
				RollCallString,
			iqmux43SetupKOS
				RollCallString,
			iqmux43SetupSerial
				RollCallString,
			iqmux43SetupFirmware
				RollCallString,
			iqmux43SetupPCB
				RollCallString,
			iqmux43SetupFactoryDefault
				INTEGER,
			iqmux43SetupRestart
				INTEGER,
			iqmux43SetupDefaultSettings
				INTEGER,
			iqmux43SetupDisplay
				INTEGER,
			iqmux43SetupSerialNumber
				RollCallString,
			iqmux43SetupBoardID
				INTEGER,
			iqmux43SetupSaveID
				INTEGER,
			iqmux43EngineerPassword
				RollCallString,
			iqmux43EngineerShowEngineer
				INTEGER,
			iqmux43EngineerPageOptionsS134014
				INTEGER,
			iqmux43EngineerPageOptionsS134015
				INTEGER,
			iqmux43EngineerPageOptionsS1
				INTEGER,
			iqmux43EngineerPageUndoChanges
				INTEGER,
			iqmux43EngineerPageLineNumber
				RollCallString,
			iqmux43EngineerPageSampleNumber
				RollCallString,
			iqmux43EngineerPaAutoalignEmbeddedInputs
				INTEGER,
			iqmux43EngineerPaAutoalignAESInputs
				INTEGER,
			iqmux43ShowEngineer2
				INTEGER,
			iqmux43EngineerUseEmbDelayFbac
				INTEGER
		}

	iqmux43SlotIndex OBJECT-TYPE
		SYNTAX		Unsigned32
		MAX-ACCESS		not-accessible
		STATUS			current
		DESCRIPTION
				"The unique Index value for each slot.  Its value
					ranges between 1 and the value of slotNumber."
		::= { iqmux43CmdEntry 0 }


	iqmux43InputIPLoss OBJECT-TYPE
		SYNTAX		INTEGER {
							val_No_Input(0),
							val_In_Out_Std_Mismatch(1)
							}
		MAX-ACCESS		read-write
		STATUS			current
		DESCRIPTION
				"TYPE: - RadiobuttonList
				 PAGE: - Input
					I/P Loss  cmdID= 33030
					No Input  value= 0
					In/Out Std.Mismatch  value= 1  "
		::= { iqmux43CmdEntry 33030 }


	iqmux43InputValidStdsAllValid OBJECT-TYPE
		SYNTAX		INTEGER { noAction(0),val_All_Valid(1) }
		MAX-ACCESS		read-write
		STATUS			current
		DESCRIPTION
				"TYPE: - Button
				 PAGE: - Input
					All Valid  cmdID= 32900  value= 1  "
		::= { iqmux43CmdEntry 32900 }


	iqmux43InputValidStdsAllInvalid OBJECT-TYPE
		SYNTAX		INTEGER { noAction(0),val_All_Invalid(1) }
		MAX-ACCESS		read-write
		STATUS			current
		DESCRIPTION
				"TYPE: - Button
				 PAGE: - Input
					All Invalid  cmdID= 32901  value= 1  "
		::= { iqmux43CmdEntry 32901 }


	iqmux43InputValidStds108023sF OBJECT-TYPE
		SYNTAX		INTEGER { disable(0), enable(1) }
		MAX-ACCESS		read-write
		STATUS			current
		DESCRIPTION
				"TYPE: - Checkbox
				 PAGE: - Input
					1080/23sF  cmdID= 32916 "
		::= { iqmux43CmdEntry 32916 }


	iqmux43InputValidStds108023p OBJECT-TYPE
		SYNTAX		INTEGER { disable(0), enable(1) }
		MAX-ACCESS		read-write
		STATUS			current
		DESCRIPTION
				"TYPE: - Checkbox
				 PAGE: - Input
					1080/23p  cmdID= 32915 "
		::= { iqmux43CmdEntry 32915 }


	iqmux43InputValidStds108024sF OBJECT-TYPE
		SYNTAX		INTEGER { disable(0), enable(1) }
		MAX-ACCESS		read-write
		STATUS			current
		DESCRIPTION
				"TYPE: - Checkbox
				 PAGE: - Input
					1080/24sF  cmdID= 32917 "
		::= { iqmux43CmdEntry 32917 }


	iqmux43InputValidStds108024p OBJECT-TYPE
		SYNTAX		INTEGER { disable(0), enable(1) }
		MAX-ACCESS		read-write
		STATUS			current
		DESCRIPTION
				"TYPE: - Checkbox
				 PAGE: - Input
					1080/24p  cmdID= 32914 "
		::= { iqmux43CmdEntry 32914 }


	iqmux43InputValidStds108025i OBJECT-TYPE
		SYNTAX		INTEGER { disable(0), enable(1) }
		MAX-ACCESS		read-write
		STATUS			current
		DESCRIPTION
				"TYPE: - Checkbox
				 PAGE: - Input
					1080/25i  cmdID= 32910 "
		::= { iqmux43CmdEntry 32910 }


	iqmux43InputValidStds108025p OBJECT-TYPE
		SYNTAX		INTEGER { disable(0), enable(1) }
		MAX-ACCESS		read-write
		STATUS			current
		DESCRIPTION
				"TYPE: - Checkbox
				 PAGE: - Input
					1080/25p  cmdID= 32911 "
		::= { iqmux43CmdEntry 32911 }


	iqmux43InputValidStds103529i OBJECT-TYPE
		SYNTAX		INTEGER { disable(0), enable(1) }
		MAX-ACCESS		read-write
		STATUS			current
		DESCRIPTION
				"TYPE: - Checkbox
				 PAGE: - Input
					1035/29i  cmdID= 32921 "
		::= { iqmux43CmdEntry 32921 }


	iqmux43InputValidStds108029i OBJECT-TYPE
		SYNTAX		INTEGER { disable(0), enable(1) }
		MAX-ACCESS		read-write
		STATUS			current
		DESCRIPTION
				"TYPE: - Checkbox
				 PAGE: - Input
					1080/29i  cmdID= 32919 "
		::= { iqmux43CmdEntry 32919 }


	iqmux43InputValidStds108029p OBJECT-TYPE
		SYNTAX		INTEGER { disable(0), enable(1) }
		MAX-ACCESS		read-write
		STATUS			current
		DESCRIPTION
				"TYPE: - Checkbox
				 PAGE: - Input
					1080/29p  cmdID= 32918 "
		::= { iqmux43CmdEntry 32918 }


	iqmux43InputValidStds103530i OBJECT-TYPE
		SYNTAX		INTEGER { disable(0), enable(1) }
		MAX-ACCESS		read-write
		STATUS			current
		DESCRIPTION
				"TYPE: - Checkbox
				 PAGE: - Input
					1035/30i  cmdID= 32920 "
		::= { iqmux43CmdEntry 32920 }


	iqmux43InputValidStds108030i OBJECT-TYPE
		SYNTAX		INTEGER { disable(0), enable(1) }
		MAX-ACCESS		read-write
		STATUS			current
		DESCRIPTION
				"TYPE: - Checkbox
				 PAGE: - Input
					1080/30i  cmdID= 32912 "
		::= { iqmux43CmdEntry 32912 }


	iqmux43InputValidStds108030p OBJECT-TYPE
		SYNTAX		INTEGER { disable(0), enable(1) }
		MAX-ACCESS		read-write
		STATUS			current
		DESCRIPTION
				"TYPE: - Checkbox
				 PAGE: - Input
					1080/30p  cmdID= 32913 "
		::= { iqmux43CmdEntry 32913 }


	iqmux43InputValidStds72050p OBJECT-TYPE
		SYNTAX		INTEGER { disable(0), enable(1) }
		MAX-ACCESS		read-write
		STATUS			current
		DESCRIPTION
				"TYPE: - Checkbox
				 PAGE: - Input
					720/50p  cmdID= 32922 "
		::= { iqmux43CmdEntry 32922 }


	iqmux43InputValidStds72059p OBJECT-TYPE
		SYNTAX		INTEGER { disable(0), enable(1) }
		MAX-ACCESS		read-write
		STATUS			current
		DESCRIPTION
				"TYPE: - Checkbox
				 PAGE: - Input
					720/59p  cmdID= 32924 "
		::= { iqmux43CmdEntry 32924 }


	iqmux43InputValidStds72060p OBJECT-TYPE
		SYNTAX		INTEGER { disable(0), enable(1) }
		MAX-ACCESS		read-write
		STATUS			current
		DESCRIPTION
				"TYPE: - Checkbox
				 PAGE: - Input
					720/60p  cmdID= 32923 "
		::= { iqmux43CmdEntry 32923 }


	iqmux43InputValidStds62525i OBJECT-TYPE
		SYNTAX		INTEGER { disable(0), enable(1) }
		MAX-ACCESS		read-write
		STATUS			current
		DESCRIPTION
				"TYPE: - Checkbox
				 PAGE: - Input
					625/25i  cmdID= 32925 "
		::= { iqmux43CmdEntry 32925 }


	iqmux43InputValidStds52529i OBJECT-TYPE
		SYNTAX		INTEGER { disable(0), enable(1) }
		MAX-ACCESS		read-write
		STATUS			current
		DESCRIPTION
				"TYPE: - Checkbox
				 PAGE: - Input
					525/29i  cmdID= 32926 "
		::= { iqmux43CmdEntry 32926 }


	iqmux43InputErrorsCRCErrs OBJECT-TYPE
		SYNTAX		RollCallString
		MAX-ACCESS		read-only
		STATUS			current
		DESCRIPTION
				"TYPE: - Display
				 PAGE: - Input
					CRC Errs  cmdID= 33050  format=   "
		::= { iqmux43CmdEntry 33050 }


	iqmux43InputErrorsCRCErrSec OBJECT-TYPE
		SYNTAX		RollCallString
		MAX-ACCESS		read-only
		STATUS			current
		DESCRIPTION
				"TYPE: - Display
				 PAGE: - Input
					CRC ErrSec  cmdID= 33051  format=   "
		::= { iqmux43CmdEntry 33051 }


	iqmux43InputErrorsANCErrs OBJECT-TYPE
		SYNTAX		RollCallString
		MAX-ACCESS		read-only
		STATUS			current
		DESCRIPTION
				"TYPE: - Display
				 PAGE: - Input
					ANC Errs  cmdID= 33053  format=   "
		::= { iqmux43CmdEntry 33053 }


	iqmux43InputErrorsANCErrSec OBJECT-TYPE
		SYNTAX		RollCallString
		MAX-ACCESS		read-only
		STATUS			current
		DESCRIPTION
				"TYPE: - Display
				 PAGE: - Input
					ANC ErrSec  cmdID= 33054  format=   "
		::= { iqmux43CmdEntry 33054 }


	iqmux43InputErrorsResetSec OBJECT-TYPE
		SYNTAX		RollCallString
		MAX-ACCESS		read-only
		STATUS			current
		DESCRIPTION
				"TYPE: - Display
				 PAGE: - Input
					ResetSec  cmdID= 33055  format=   "
		::= { iqmux43CmdEntry 33055 }


	iqmux43InputErrorsErrorReset OBJECT-TYPE
		SYNTAX		INTEGER { noAction(0),val_Error_Reset(1) }
		MAX-ACCESS		read-write
		STATUS			current
		DESCRIPTION
				"TYPE: - Button
				 PAGE: - Input
					Error Reset  cmdID= 33052  value= 1  "
		::= { iqmux43CmdEntry 33052 }


	iqmux43OutputStandard OBJECT-TYPE
		SYNTAX		INTEGER {
							val_Manual(0),
							val_Follows_Input(1)
							}
		MAX-ACCESS		read-write
		STATUS			current
		DESCRIPTION
				"TYPE: - RadiobuttonList
					Output Standard  cmdID= 33011
					Manual  value= 0
					Follows Input  value= 1  "
		::= { iqmux43CmdEntry 33011 }


	iqmux43OutputSelectStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Select Standard  cmdID= 33010
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux43CmdEntry 33010 }


	iqmux43OutputVideoProcAmpsMasterGain OBJECT-TYPE
		SYNTAX		INTEGER
		MAX-ACCESS		read-write
		STATUS			current
		DESCRIPTION
				"TYPE: - Number
					Master Gain  cmdID= 33000  min= -600  max= 600  step= 10  format= %0.1f dB  div_scale= 100
					Min = -6.0 dB  Max = 6.0 dB  Step = 0.1 dB "
		::= { iqmux43CmdEntry 33000 }


	iqmux43OutputVideoProcAmpsYGain OBJECT-TYPE
		SYNTAX		INTEGER
		MAX-ACCESS		read-write
		STATUS			current
		DESCRIPTION
				"TYPE: - Number
					Y Gain  cmdID= 33001  min= -600  max= 600  step= 10  format= %0.1f dB  div_scale= 100
					Min = -6.0 dB  Max = 6.0 dB  Step = 0.1 dB "
		::= { iqmux43CmdEntry 33001 }


	iqmux43OutputVideoProcAmpsCGain OBJECT-TYPE
		SYNTAX		INTEGER
		MAX-ACCESS		read-write
		STATUS			current
		DESCRIPTION
				"TYPE: - Number
					C Gain  cmdID= 33003  min= -600  max= 600  step= 10  format= %0.1f dB  div_scale= 100
					Min = -6.0 dB  Max = 6.0 dB  Step = 0.1 dB "
		::= { iqmux43CmdEntry 33003 }


	iqmux43OutputVideoProcAmpsBlackLevel OBJECT-TYPE
		SYNTAX		INTEGER
		MAX-ACCESS		read-write
		STATUS			current
		DESCRIPTION
				"TYPE: - Number
					Black Level  cmdID= 33002  min= -200  max= 200  step= 1  format= %0.0f mV  div_scale= 1
					Min = -200 mV  Max = 200 mV  Step = 1 mV "
		::= { iqmux43CmdEntry 33002 }


	iqmux43OutputDefaultOutput OBJECT-TYPE
		SYNTAX		INTEGER {
							val_Freeze_Frame(1),
							val_Freeze_Field(5),
							val_Black(2),
							val_Input(3),
							val_Out_Pattern(4)
							}
		MAX-ACCESS		read-write
		STATUS			current
		DESCRIPTION
				"TYPE: - RadiobuttonList
					Default Output  cmdID= 33031
					Freeze Frame  value= 1
					Freeze Field  value= 5
					Black  value= 2
					Input  value= 3
					Out Pattern  value= 4  "
		::= { iqmux43CmdEntry 33031 }


	iqmux43OutputDefaultOPStd OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Default O/P Std.  cmdID= 33012
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux43CmdEntry 33012 }


	iqmux43AudioADelaySourcesManual OBJECT-TYPE
		SYNTAX		INTEGER { disable(0), enable(1) }
		MAX-ACCESS		read-write
		STATUS			current
		DESCRIPTION
				"TYPE: - Checkbox
				 PAGE: - Audio- Aud.Delays
					Manual  cmdID= 38041 "
		::= { iqmux43CmdEntry 38041 }


	iqmux43AudioADelaySourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38042 "
		::= { iqmux43CmdEntry 38042 }


	iqmux43AudioADelaySourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38044 "
		::= { iqmux43CmdEntry 38044 }


	iqmux43AudioADelaySourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38045 "
		::= { iqmux43CmdEntry 38045 }


	iqmux43AudioADelaySourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38046 "
		::= { iqmux43CmdEntry 38046 }


	iqmux43AudioADelaySourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38047 "
		::= { iqmux43CmdEntry 38047 }


	iqmux43AudioAAdjustCoarseDelay OBJECT-TYPE
		SYNTAX		INTEGER
		MAX-ACCESS		read-write
		STATUS			current
		DESCRIPTION
				"TYPE: - Number
				 PAGE: - Audio- Aud.Delays
					Adjust Coarse Delay  cmdID= 38043  min= -4000  max= 200000  step= 25  format= %0.2f ms  div_scale= 100
					Min = -40.00 ms  Max = 2000.00 ms  Step = 0.25 ms "
		::= { iqmux43CmdEntry 38043 }


	iqmux43AudioACurrentAudioDelay OBJECT-TYPE
		SYNTAX		RollCallString
		MAX-ACCESS		read-only
		STATUS			current
		DESCRIPTION
				"TYPE: - Display
				 PAGE: - Audio- Aud.Delays
					Current Audio Delay  cmdID= 38048  format=   "
		::= { iqmux43CmdEntry 38048 }


	iqmux43AudioBDelaySourcesManual OBJECT-TYPE
		SYNTAX		INTEGER { disable(0), enable(1) }
		MAX-ACCESS		read-write
		STATUS			current
		DESCRIPTION
				"TYPE: - Checkbox
				 PAGE: - Audio- Aud.Delays
					Manual  cmdID= 38061 "
		::= { iqmux43CmdEntry 38061 }


	iqmux43AudioBDelaySourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38062 "
		::= { iqmux43CmdEntry 38062 }


	iqmux43AudioBDelaySourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38064 "
		::= { iqmux43CmdEntry 38064 }


	iqmux43AudioBDelaySourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38065 "
		::= { iqmux43CmdEntry 38065 }


	iqmux43AudioBDelaySourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38066 "
		::= { iqmux43CmdEntry 38066 }


	iqmux43AudioBDelaySourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38067 "
		::= { iqmux43CmdEntry 38067 }


	iqmux43AudioBAdjustCoarseDelay OBJECT-TYPE
		SYNTAX		INTEGER
		MAX-ACCESS		read-write
		STATUS			current
		DESCRIPTION
				"TYPE: - Number
				 PAGE: - Audio- Aud.Delays
					Adjust Coarse Delay  cmdID= 38063  min= -4000  max= 200000  step= 25  format= %0.2f ms  div_scale= 100
					Min = -40.00 ms  Max = 2000.00 ms  Step = 0.25 ms "
		::= { iqmux43CmdEntry 38063 }


	iqmux43AudioBCurrentAudioDelay OBJECT-TYPE
		SYNTAX		RollCallString
		MAX-ACCESS		read-only
		STATUS			current
		DESCRIPTION
				"TYPE: - Display
				 PAGE: - Audio- Aud.Delays
					Current Audio Delay  cmdID= 38068  format=   "
		::= { iqmux43CmdEntry 38068 }


	iqmux43AudioAESDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38600
					Min  value= 0
					Delay A  value= 1
					Delay B  value= 2  "
		::= { iqmux43CmdEntry 38600 }


	iqmux43AudioAESDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38620 "
		::= { iqmux43CmdEntry 38620 }


	iqmux43AudioAESDelaySelectAutoDolbyEPhase1 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38118 "
		::= { iqmux43CmdEntry 38118 }


	iqmux43AudioAESDelaySelectDelayLimit1 OBJECT-TYPE
		SYNTAX		RollCallString
		MAX-ACCESS		read-only
		STATUS			current
		DESCRIPTION
				"TYPE: - Display
				 PAGE: - Audio- Aud.Delays
					Delay Limit  cmdID= 38300  format=   "
		::= { iqmux43CmdEntry 38300 }


	iqmux43AudioAESDelaySelectAES1FineDelay OBJECT-TYPE
		SYNTAX		INTEGER
		MAX-ACCESS		read-write
		STATUS			current
		DESCRIPTION
				"TYPE: - Number
				 PAGE: - Audio- Aud.Delays
					AES 1 Fine Delay  cmdID= 38130  min= -2450  max= 2450  step= 52  format= %0.3f ms  div_scale= 10000
					Min = -0.245 ms  Max = 0.245 ms  Step = 0.005 ms "
		::= { iqmux43CmdEntry 38130 }


	iqmux43AudioAESDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38601
					Min  value= 0
					Delay A  value= 1
					Delay B  value= 2  "
		::= { iqmux43CmdEntry 38601 }


	iqmux43AudioAESDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38621 "
		::= { iqmux43CmdEntry 38621 }


	iqmux43AudioAESDelaySelectAutoDolbyEPhase2 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38119 "
		::= { iqmux43CmdEntry 38119 }


	iqmux43AudioAESDelaySelectDelayLimit2 OBJECT-TYPE
		SYNTAX		RollCallString
		MAX-ACCESS		read-only
		STATUS			current
		DESCRIPTION
				"TYPE: - Display
				 PAGE: - Audio- Aud.Delays
					Delay Limit  cmdID= 38301  format=   "
		::= { iqmux43CmdEntry 38301 }


	iqmux43AudioAESDelaySelectAES2FineDelay OBJECT-TYPE
		SYNTAX		INTEGER
		MAX-ACCESS		read-write
		STATUS			current
		DESCRIPTION
				"TYPE: - Number
				 PAGE: - Audio- Aud.Delays
					AES 2 Fine Delay  cmdID= 38131  min= -2450  max= 2450  step= 52  format= %0.3f ms  div_scale= 10000
					Min = -0.245 ms  Max = 0.245 ms  Step = 0.005 ms "
		::= { iqmux43CmdEntry 38131 }


	iqmux43AudioAESDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38602
					Min  value= 0
					Delay A  value= 1
					Delay B  value= 2  "
		::= { iqmux43CmdEntry 38602 }


	iqmux43AudioAESDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38622 "
		::= { iqmux43CmdEntry 38622 }


	iqmux43AudioAESDelaySelectAutoDolbyEPhase3 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38120 "
		::= { iqmux43CmdEntry 38120 }


	iqmux43AudioAESDelaySelectDelayLimit3 OBJECT-TYPE
		SYNTAX		RollCallString
		MAX-ACCESS		read-only
		STATUS			current
		DESCRIPTION
				"TYPE: - Display
				 PAGE: - Audio- Aud.Delays
					Delay Limit  cmdID= 38302  format=   "
		::= { iqmux43CmdEntry 38302 }


	iqmux43AudioAESDelaySelectAES3FineDelay OBJECT-TYPE
		SYNTAX		INTEGER
		MAX-ACCESS		read-write
		STATUS			current
		DESCRIPTION
				"TYPE: - Number
				 PAGE: - Audio- Aud.Delays
					AES 3 Fine Delay  cmdID= 38132  min= -2450  max= 2450  step= 52  format= %0.3f ms  div_scale= 10000
					Min = -0.245 ms  Max = 0.245 ms  Step = 0.005 ms "
		::= { iqmux43CmdEntry 38132 }


	iqmux43AudioAESDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38603
					Min  value= 0
					Delay A  value= 1
					Delay B  value= 2  "
		::= { iqmux43CmdEntry 38603 }


	iqmux43AudioAESDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38623 "
		::= { iqmux43CmdEntry 38623 }


	iqmux43AudioAESDelaySelectAutoDolbyEPhase4 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38121 "
		::= { iqmux43CmdEntry 38121 }


	iqmux43AudioAESDelaySelectDelayLimit4 OBJECT-TYPE
		SYNTAX		RollCallString
		MAX-ACCESS		read-only
		STATUS			current
		DESCRIPTION
				"TYPE: - Display
				 PAGE: - Audio- Aud.Delays
					Delay Limit  cmdID= 38303  format=   "
		::= { iqmux43CmdEntry 38303 }


	iqmux43AudioAESDelaySelectAES4FineDelay OBJECT-TYPE
		SYNTAX		INTEGER
		MAX-ACCESS		read-write
		STATUS			current
		DESCRIPTION
				"TYPE: - Number
				 PAGE: - Audio- Aud.Delays
					AES 4 Fine Delay  cmdID= 38133  min= -2450  max= 2450  step= 52  format= %0.3f ms  div_scale= 10000
					Min = -0.245 ms  Max = 0.245 ms  Step = 0.005 ms "
		::= { iqmux43CmdEntry 38133 }


	iqmux43AudioAESDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38604
					Min  value= 0
					Delay A  value= 1
					Delay B  value= 2  "
		::= { iqmux43CmdEntry 38604 }


	iqmux43AudioAESDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38624 "
		::= { iqmux43CmdEntry 38624 }


	iqmux43AudioAESDelaySelectAutoDolbyEPhase5 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38122 "
		::= { iqmux43CmdEntry 38122 }


	iqmux43AudioAESDelaySelectDelayLimit5 OBJECT-TYPE
		SYNTAX		RollCallString
		MAX-ACCESS		read-only
		STATUS			current
		DESCRIPTION
				"TYPE: - Display
				 PAGE: - Audio- Aud.Delays
					Delay Limit  cmdID= 38304  format=   "
		::= { iqmux43CmdEntry 38304 }


	iqmux43AudioAESDelaySelectAES5FineDelay OBJECT-TYPE
		SYNTAX		INTEGER
		MAX-ACCESS		read-write
		STATUS			current
		DESCRIPTION
				"TYPE: - Number
				 PAGE: - Audio- Aud.Delays
					AES 5 Fine Delay  cmdID= 38134  min= -2450  max= 2450  step= 52  format= %0.3f ms  div_scale= 10000
					Min = -0.245 ms  Max = 0.245 ms  Step = 0.005 ms "
		::= { iqmux43CmdEntry 38134 }


	iqmux43AudioAESDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38605
					Min  value= 0
					Delay A  value= 1
					Delay B  value= 2  "
		::= { iqmux43CmdEntry 38605 }


	iqmux43AudioAESDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38625 "
		::= { iqmux43CmdEntry 38625 }


	iqmux43AudioAESDelaySelectAutoDolbyEPhase6 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38123 "
		::= { iqmux43CmdEntry 38123 }


	iqmux43AudioAESDelaySelectDelayLimit6 OBJECT-TYPE
		SYNTAX		RollCallString
		MAX-ACCESS		read-only
		STATUS			current
		DESCRIPTION
				"TYPE: - Display
				 PAGE: - Audio- Aud.Delays
					Delay Limit  cmdID= 38305  format=   "
		::= { iqmux43CmdEntry 38305 }


	iqmux43AudioAESDelaySelectAES6FineDelay OBJECT-TYPE
		SYNTAX		INTEGER
		MAX-ACCESS		read-write
		STATUS			current
		DESCRIPTION
				"TYPE: - Number
				 PAGE: - Audio- Aud.Delays
					AES 6 Fine Delay  cmdID= 38135  min= -2450  max= 2450  step= 52  format= %0.3f ms  div_scale= 10000
					Min = -0.245 ms  Max = 0.245 ms  Step = 0.005 ms "
		::= { iqmux43CmdEntry 38135 }


	iqmux43AudioAESDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38606
					Min  value= 0
					Delay A  value= 1
					Delay B  value= 2  "
		::= { iqmux43CmdEntry 38606 }


	iqmux43AudioAESDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38626 "
		::= { iqmux43CmdEntry 38626 }


	iqmux43AudioAESDelaySelectAutoDolbyEPhase7 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38124 "
		::= { iqmux43CmdEntry 38124 }


	iqmux43AudioAESDelaySelectDelayLimit7 OBJECT-TYPE
		SYNTAX		RollCallString
		MAX-ACCESS		read-only
		STATUS			current
		DESCRIPTION
				"TYPE: - Display
				 PAGE: - Audio- Aud.Delays
					Delay Limit  cmdID= 38306  format=   "
		::= { iqmux43CmdEntry 38306 }


	iqmux43AudioAESDelaySelectAES7FineDelay OBJECT-TYPE
		SYNTAX		INTEGER
		MAX-ACCESS		read-write
		STATUS			current
		DESCRIPTION
				"TYPE: - Number
				 PAGE: - Audio- Aud.Delays
					AES 7 Fine Delay  cmdID= 38136  min= -2450  max= 2450  step= 52  format= %0.3f ms  div_scale= 10000
					Min = -0.245 ms  Max = 0.245 ms  Step = 0.005 ms "
		::= { iqmux43CmdEntry 38136 }


	iqmux43AudioAESDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38607
					Min  value= 0
					Delay A  value= 1
					Delay B  value= 2  "
		::= { iqmux43CmdEntry 38607 }


	iqmux43AudioAESDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38627 "
		::= { iqmux43CmdEntry 38627 }


	iqmux43AudioAESDelaySelectAutoDolbyEPhase8 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38125 "
		::= { iqmux43CmdEntry 38125 }


	iqmux43AudioAESDelaySelectDelayLimit8 OBJECT-TYPE
		SYNTAX		RollCallString
		MAX-ACCESS		read-only
		STATUS			current
		DESCRIPTION
				"TYPE: - Display
				 PAGE: - Audio- Aud.Delays
					Delay Limit  cmdID= 38307  format=   "
		::= { iqmux43CmdEntry 38307 }


	iqmux43AudioAESDelaySelectAES8FineDelay OBJECT-TYPE
		SYNTAX		INTEGER
		MAX-ACCESS		read-write
		STATUS			current
		DESCRIPTION
				"TYPE: - Number
				 PAGE: - Audio- Aud.Delays
					AES 8 Fine Delay  cmdID= 38137  min= -2450  max= 2450  step= 52  format= %0.3f ms  div_scale= 10000
					Min = -0.245 ms  Max = 0.245 ms  Step = 0.005 ms "
		::= { iqmux43CmdEntry 38137 }


	iqmux43AudEMBDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38080
					Min  value= 0
					Delay A  value= 1
					Delay B  value= 2  "
		::= { iqmux43CmdEntry 38080 }


	iqmux43AudEMBDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38100 "
		::= { iqmux43CmdEntry 38100 }


	iqmux43AudEMBDelaySelectAutoDolbyEPhase1 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38110 "
		::= { iqmux43CmdEntry 38110 }


	iqmux43AudEMBDelaySelectDelayLimit1 OBJECT-TYPE
		SYNTAX		RollCallString
		MAX-ACCESS		read-only
		STATUS			current
		DESCRIPTION
				"TYPE: - Display
				 PAGE: - Audio- Aud.Delays
					Delay Limit  cmdID= 38308  format=   "
		::= { iqmux43CmdEntry 38308 }


	iqmux43AudEMBDelaySelectEMB1FineDelay OBJECT-TYPE
		SYNTAX		INTEGER
		MAX-ACCESS		read-write
		STATUS			current
		DESCRIPTION
				"TYPE: - Number
				 PAGE: - Audio- Aud.Delays
					EMB 1 Fine Delay  cmdID= 38138  min= -2450  max= 2450  step= 52  format= %0.3f ms  div_scale= 10000
					Min = -0.245 ms  Max = 0.245 ms  Step = 0.005 ms "
		::= { iqmux43CmdEntry 38138 }


	iqmux43AudEMBDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38081
					Min  value= 0
					Delay A  value= 1
					Delay B  value= 2  "
		::= { iqmux43CmdEntry 38081 }


	iqmux43AudEMBDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38101 "
		::= { iqmux43CmdEntry 38101 }


	iqmux43AudEMBDelaySelectAutoDolbyEPhase2 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38111 "
		::= { iqmux43CmdEntry 38111 }


	iqmux43AudEMBDelaySelectDelayLimit2 OBJECT-TYPE
		SYNTAX		RollCallString
		MAX-ACCESS		read-only
		STATUS			current
		DESCRIPTION
				"TYPE: - Display
				 PAGE: - Audio- Aud.Delays
					Delay Limit  cmdID= 38309  format=   "
		::= { iqmux43CmdEntry 38309 }


	iqmux43AudEMBDelaySelectEMB2FineDelay OBJECT-TYPE
		SYNTAX		INTEGER
		MAX-ACCESS		read-write
		STATUS			current
		DESCRIPTION
				"TYPE: - Number
				 PAGE: - Audio- Aud.Delays
					EMB 2 Fine Delay  cmdID= 38139  min= -2450  max= 2450  step= 52  format= %0.3f ms  div_scale= 10000
					Min = -0.245 ms  Max = 0.245 ms  Step = 0.005 ms "
		::= { iqmux43CmdEntry 38139 }


	iqmux43AudEMBDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38082
					Min  value= 0
					Delay A  value= 1
					Delay B  value= 2  "
		::= { iqmux43CmdEntry 38082 }


	iqmux43AudEMBDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38102 "
		::= { iqmux43CmdEntry 38102 }


	iqmux43AudEMBDelaySelectAutoDolbyEPhase3 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38112 "
		::= { iqmux43CmdEntry 38112 }


	iqmux43AudEMBDelaySelectDelayLimit3 OBJECT-TYPE
		SYNTAX		RollCallString
		MAX-ACCESS		read-only
		STATUS			current
		DESCRIPTION
				"TYPE: - Display
				 PAGE: - Audio- Aud.Delays
					Delay Limit  cmdID= 38310  format=   "
		::= { iqmux43CmdEntry 38310 }


	iqmux43AudEMBDelaySelectEMB3FineDelay OBJECT-TYPE
		SYNTAX		INTEGER
		MAX-ACCESS		read-write
		STATUS			current
		DESCRIPTION
				"TYPE: - Number
				 PAGE: - Audio- Aud.Delays
					EMB 3 Fine Delay  cmdID= 38140  min= -2450  max= 2450  step= 52  format= %0.3f ms  div_scale= 10000
					Min = -0.245 ms  Max = 0.245 ms  Step = 0.005 ms "
		::= { iqmux43CmdEntry 38140 }


	iqmux43AudEMBDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38083
					Min  value= 0
					Delay A  value= 1
					Delay B  value= 2  "
		::= { iqmux43CmdEntry 38083 }


	iqmux43AudEMBDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38103 "
		::= { iqmux43CmdEntry 38103 }


	iqmux43AudEMBDelaySelectAutoDolbyEPhase4 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38113 "
		::= { iqmux43CmdEntry 38113 }


	iqmux43AudEMBDelaySelectDelayLimit4 OBJECT-TYPE
		SYNTAX		RollCallString
		MAX-ACCESS		read-only
		STATUS			current
		DESCRIPTION
				"TYPE: - Display
				 PAGE: - Audio- Aud.Delays
					Delay Limit  cmdID= 38311  format=   "
		::= { iqmux43CmdEntry 38311 }


	iqmux43AudEMBDelaySelectEMB4FineDelay OBJECT-TYPE
		SYNTAX		INTEGER
		MAX-ACCESS		read-write
		STATUS			current
		DESCRIPTION
				"TYPE: - Number
				 PAGE: - Audio- Aud.Delays
					EMB 4 Fine Delay  cmdID= 38141  min= -2450  max= 2450  step= 52  format= %0.3f ms  div_scale= 10000
					Min = -0.245 ms  Max = 0.245 ms  Step = 0.005 ms "
		::= { iqmux43CmdEntry 38141 }


	iqmux43AudEMBDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38084
					Min  value= 0
					Delay A  value= 1
					Delay B  value= 2  "
		::= { iqmux43CmdEntry 38084 }


	iqmux43AudEMBDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38104 "
		::= { iqmux43CmdEntry 38104 }


	iqmux43AudEMBDelaySelectAutoDolbyEPhase5 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38114 "
		::= { iqmux43CmdEntry 38114 }


	iqmux43AudEMBDelaySelectDelayLimit5 OBJECT-TYPE
		SYNTAX		RollCallString
		MAX-ACCESS		read-only
		STATUS			current
		DESCRIPTION
				"TYPE: - Display
				 PAGE: - Audio- Aud.Delays
					Delay Limit  cmdID= 38312  format=   "
		::= { iqmux43CmdEntry 38312 }


	iqmux43AudEMBDelaySelectEMB5FineDelay OBJECT-TYPE
		SYNTAX		INTEGER
		MAX-ACCESS		read-write
		STATUS			current
		DESCRIPTION
				"TYPE: - Number
				 PAGE: - Audio- Aud.Delays
					EMB 5 Fine Delay  cmdID= 38142  min= -2450  max= 2450  step= 52  format= %0.3f ms  div_scale= 10000
					Min = -0.245 ms  Max = 0.245 ms  Step = 0.005 ms "
		::= { iqmux43CmdEntry 38142 }


	iqmux43AudEMBDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38085
					Min  value= 0
					Delay A  value= 1
					Delay B  value= 2  "
		::= { iqmux43CmdEntry 38085 }


	iqmux43AudEMBDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38105 "
		::= { iqmux43CmdEntry 38105 }


	iqmux43AudEMBDelaySelectAutoDolbyEPhase6 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38115 "
		::= { iqmux43CmdEntry 38115 }


	iqmux43AudEMBDelaySelectDelayLimit6 OBJECT-TYPE
		SYNTAX		RollCallString
		MAX-ACCESS		read-only
		STATUS			current
		DESCRIPTION
				"TYPE: - Display
				 PAGE: - Audio- Aud.Delays
					Delay Limit  cmdID= 38313  format=   "
		::= { iqmux43CmdEntry 38313 }


	iqmux43AudEMBDelaySelectEMB6FineDelay OBJECT-TYPE
		SYNTAX		INTEGER
		MAX-ACCESS		read-write
		STATUS			current
		DESCRIPTION
				"TYPE: - Number
				 PAGE: - Audio- Aud.Delays
					EMB 6 Fine Delay  cmdID= 38143  min= -2450  max= 2450  step= 52  format= %0.3f ms  div_scale= 10000
					Min = -0.245 ms  Max = 0.245 ms  Step = 0.005 ms "
		::= { iqmux43CmdEntry 38143 }


	iqmux43AudEMBDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38086
					Min  value= 0
					Delay A  value= 1
					Delay B  value= 2  "
		::= { iqmux43CmdEntry 38086 }


	iqmux43AudEMBDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38106 "
		::= { iqmux43CmdEntry 38106 }


	iqmux43AudEMBDelaySelectAutoDolbyEPhase7 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38116 "
		::= { iqmux43CmdEntry 38116 }


	iqmux43AudEMBDelaySelectDelayLimit7 OBJECT-TYPE
		SYNTAX		RollCallString
		MAX-ACCESS		read-only
		STATUS			current
		DESCRIPTION
				"TYPE: - Display
				 PAGE: - Audio- Aud.Delays
					Delay Limit  cmdID= 38314  format=   "
		::= { iqmux43CmdEntry 38314 }


	iqmux43AudEMBDelaySelectEMB7FineDelay OBJECT-TYPE
		SYNTAX		INTEGER
		MAX-ACCESS		read-write
		STATUS			current
		DESCRIPTION
				"TYPE: - Number
				 PAGE: - Audio- Aud.Delays
					EMB 7 Fine Delay  cmdID= 38144  min= -2450  max= 2450  step= 52  format= %0.3f ms  div_scale= 10000
					Min = -0.245 ms  Max = 0.245 ms  Step = 0.005 ms "
		::= { iqmux43CmdEntry 38144 }


	iqmux43AudEMBDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38087
					Min  value= 0
					Delay A  value= 1
					Delay B  value= 2  "
		::= { iqmux43CmdEntry 38087 }


	iqmux43AudEMBDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38107 "
		::= { iqmux43CmdEntry 38107 }


	iqmux43AudEMBDelaySelectDelayLimit8 OBJECT-TYPE
		SYNTAX		RollCallString
		MAX-ACCESS		read-only
		STATUS			current
		DESCRIPTION
				"TYPE: - Display
				 PAGE: - Audio- Aud.Delays
					Delay Limit  cmdID= 38315  format=   "
		::= { iqmux43CmdEntry 38315 }


	iqmux43AudEMBDelaySelectAutoDolbyEPhase8 OBJECT-TYPE
		SYNTAX		INTEGER { disable(0), enable(1) }
		MAX-ACCESS		read-write
		STATUS			current
		DESCRIPTION
				"TYPE: - Checkbox
				 PAGE: - Audio- Aud.Delays
					Auto Dolby-E Phase  cmdID= 38117 "
		::= { iqmux43CmdEntry 38117 }


	iqmux43AudEMBDelaySelectEMB8FineDelay OBJECT-TYPE
		SYNTAX		INTEGER
		MAX-ACCESS		read-write
		STATUS			current
		DESCRIPTION
				"TYPE: - Number
				 PAGE: - Audio- Aud.Delays
					EMB 8 Fine Delay  cmdID= 38145  min= -2450  max= 2450  step= 52  format= %0.3f ms  div_scale= 10000
					Min = -0.245 ms  Max = 0.245 ms  Step = 0.005 ms "
		::= { iqmux43CmdEntry 38145 }


	iqmux43AudioDelaysRollTrack14 OBJECT-TYPE
		SYNTAX		RollCallString
		MAX-ACCESS		read-only
		STATUS			current
		DESCRIPTION
				"TYPE: - Display
				 PAGE: - Audio- Aud.Delays
					RollTrack14  cmdID= 14  format=   "
		::= { iqmux43CmdEntry 14 }


	iqmux43AudioDelaysRollTrack15 OBJECT-TYPE
		SYNTAX		RollCallString
		MAX-ACCESS		read-only
		STATUS			current
		DESCRIPTION
				"TYPE: - Display
				 PAGE: - Audio- Aud.Delays
					RollTrack15  cmdID= 15  format=   "
		::= { iqmux43CmdEntry 15 }


	iqmux43AudioDelaysRollTrack16 OBJECT-TYPE
		SYNTAX		RollCallString
		MAX-ACCESS		read-only
		STATUS			current
		DESCRIPTION
				"TYPE: - Display
				 PAGE: - Audio- Aud.Delays
					RollTrack16  cmdID= 16  format=   "
		::= { iqmux43CmdEntry 16 }


	iqmux43AudioDelaysRollTrack17 OBJECT-TYPE
		SYNTAX		RollCallString
		MAX-ACCESS		read-only
		STATUS			current
		DESCRIPTION
				"TYPE: - Display
				 PAGE: - Audio- Aud.Delays
					RollTrack17  cmdID= 17  format=   "
		::= { iqmux43CmdEntry 17 }


	iqmux43AudioDelaysCrashSRCLimit OBJECT-TYPE
		SYNTAX		INTEGER
		MAX-ACCESS		read-write
		STATUS			current
		DESCRIPTION
				"TYPE: - Number
				 PAGE: - Audio- Aud.Delays
					Crash SRC Limit  cmdID= 38678  min= 0  max= 80  step= 1  format= %0.0f ms  div_scale= 1
					Min = 0 ms  Max = 80 ms  Step = 1 ms "
		::= { iqmux43CmdEntry 38678 }


	iqmux43EmbCtrlGroupGroup1Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 1 Audio  cmdID= 37450
					Pass  value= 0
					Blank  value= 2
					Embed  value= 1  "
		::= { iqmux43CmdEntry 37450 }


	iqmux43EmbCtrlGroupGroup2Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 2 Audio  cmdID= 37451
					Pass  value= 0
					Blank  value= 2
					Embed  value= 1  "
		::= { iqmux43CmdEntry 37451 }


	iqmux43EmbCtrlGroupGroup3Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 3 Audio  cmdID= 37452
					Pass  value= 0
					Blank  value= 2
					Embed  value= 1  "
		::= { iqmux43CmdEntry 37452 }


	iqmux43EmbCtrlGroupGroup4Audio OBJECT-TYPE
		SYNTAX		INTEGER {
							val_Pass(0),
							val_Blank(2),
							val_Embed(1)
							}
		MAX-ACCESS		read-write
		STATUS			current
		DESCRIPTION
				"TYPE: - RadiobuttonList
				 PAGE: - Audio- Emb.Ctrl
					Group 4 Audio  cmdID= 37453
					Pass  value= 0
					Blank  value= 2
					Embed  value= 1  "
		::= { iqmux43CmdEntry 37453 }


	iqmux43EmbCtrlChannelPair1LActive OBJECT-TYPE
		SYNTAX		INTEGER { disable(0), enable(1) }
		MAX-ACCESS		read-write
		STATUS			current
		DESCRIPTION
				"TYPE: - Checkbox
				 PAGE: - Audio- Emb.Ctrl
					Pair 1-L Active  cmdID= 37431 "
		::= { iqmux43CmdEntry 37431 }


	iqmux43EmbCtrlChannelPair1RActive OBJECT-TYPE
		SYNTAX		INTEGER { disable(0), enable(1) }
		MAX-ACCESS		read-write
		STATUS			current
		DESCRIPTION
				"TYPE: - Checkbox
				 PAGE: - Audio- Emb.Ctrl
					Pair 1-R Active  cmdID= 37432 "
		::= { iqmux43CmdEntry 37432 }


	iqmux43EmbCtrlChannelPair2LActive OBJECT-TYPE
		SYNTAX		INTEGER { disable(0), enable(1) }
		MAX-ACCESS		read-write
		STATUS			current
		DESCRIPTION
				"TYPE: - Checkbox
				 PAGE: - Audio- Emb.Ctrl
					Pair 2-L Active  cmdID= 37433 "
		::= { iqmux43CmdEntry 37433 }


	iqmux43EmbCtrlChannelPair2RActive OBJECT-TYPE
		SYNTAX		INTEGER { disable(0), enable(1) }
		MAX-ACCESS		read-write
		STATUS			current
		DESCRIPTION
				"TYPE: - Checkbox
				 PAGE: - Audio- Emb.Ctrl
					Pair 2-R Active  cmdID= 37434 "
		::= { iqmux43CmdEntry 37434 }


	iqmux43EmbCtrlChannelPair3LActive OBJECT-TYPE
		SYNTAX		INTEGER { disable(0), enable(1) }
		MAX-ACCESS		read-write
		STATUS			current
		DESCRIPTION
				"TYPE: - Checkbox
				 PAGE: - Audio- Emb.Ctrl
					Pair 3-L Active  cmdID= 37435 "
		::= { iqmux43CmdEntry 37435 }


	iqmux43EmbCtrlChannelPair3RActive OBJECT-TYPE
		SYNTAX		INTEGER { disable(0), enable(1) }
		MAX-ACCESS		read-write
		STATUS			current
		DESCRIPTION
				"TYPE: - Checkbox
				 PAGE: - Audio- Emb.Ctrl
					Pair 3-R Active  cmdID= 37436 "
		::= { iqmux43CmdEntry 37436 }


	iqmux43EmbCtrlChannelPair4LActive OBJECT-TYPE
		SYNTAX		INTEGER { disable(0), enable(1) }
		MAX-ACCESS		read-write
		STATUS			current
		DESCRIPTION
				"TYPE: - Checkbox
				 PAGE: - Audio- Emb.Ctrl
					Pair 4-L Active  cmdID= 37437 "
		::= { iqmux43CmdEntry 37437 }


	iqmux43EmbCtrlChannelPair4RActive OBJECT-TYPE
		SYNTAX		INTEGER { disable(0), enable(1) }
		MAX-ACCESS		read-write
		STATUS			current
		DESCRIPTION
				"TYPE: - Checkbox
				 PAGE: - Audio- Emb.Ctrl
					Pair 4-R Active  cmdID= 37438 "
		::= { iqmux43CmdEntry 37438 }


	iqmux43EmbCtrlChannelPair5LActive OBJECT-TYPE
		SYNTAX		INTEGER { disable(0), enable(1) }
		MAX-ACCESS		read-write
		STATUS			current
		DESCRIPTION
				"TYPE: - Checkbox
				 PAGE: - Audio- Emb.Ctrl
					Pair 5-L Active  cmdID= 37439 "
		::= { iqmux43CmdEntry 37439 }


	iqmux43EmbCtrlChannelPair5RActive OBJECT-TYPE
		SYNTAX		INTEGER { disable(0), enable(1) }
		MAX-ACCESS		read-write
		STATUS			current
		DESCRIPTION
				"TYPE: - Checkbox
				 PAGE: - Audio- Emb.Ctrl
					Pair 5-R Active  cmdID= 37440 "
		::= { iqmux43CmdEntry 37440 }


	iqmux43EmbCtrlChannelPair6LActive OBJECT-TYPE
		SYNTAX		INTEGER { disable(0), enable(1) }
		MAX-ACCESS		read-write
		STATUS			current
		DESCRIPTION
				"TYPE: - Checkbox
				 PAGE: - Audio- Emb.Ctrl
					Pair 6-L Active  cmdID= 37441 "
		::= { iqmux43CmdEntry 37441 }


	iqmux43EmbCtrlChannelPair6RActive OBJECT-TYPE
		SYNTAX		INTEGER { disable(0), enable(1) }
		MAX-ACCESS		read-write
		STATUS			current
		DESCRIPTION
				"TYPE: - Checkbox
				 PAGE: - Audio- Emb.Ctrl
					Pair 6-R Active  cmdID= 37442 "
		::= { iqmux43CmdEntry 37442 }


	iqmux43EmbCtrlChannelPair7LActive OBJECT-TYPE
		SYNTAX		INTEGER { disable(0), enable(1) }
		MAX-ACCESS		read-write
		STATUS			current
		DESCRIPTION
				"TYPE: - Checkbox
				 PAGE: - Audio- Emb.Ctrl
					Pair 7-L Active  cmdID= 37443 "
		::= { iqmux43CmdEntry 37443 }


	iqmux43EmbCtrlChannelPair7RActive OBJECT-TYPE
		SYNTAX		INTEGER { disable(0), enable(1) }
		MAX-ACCESS		read-write
		STATUS			current
		DESCRIPTION
				"TYPE: - Checkbox
				 PAGE: - Audio- Emb.Ctrl
					Pair 7-R Active  cmdID= 37444 "
		::= { iqmux43CmdEntry 37444 }


	iqmux43EmbCtrlChannelPair8LActive OBJECT-TYPE
		SYNTAX		INTEGER { disable(0), enable(1) }
		MAX-ACCESS		read-write
		STATUS			current
		DESCRIPTION
				"TYPE: - Checkbox
				 PAGE: - Audio- Emb.Ctrl
					Pair 8-L Active  cmdID= 37445 "
		::= { iqmux43CmdEntry 37445 }


	iqmux43EmbCtrlChannelPair8RActive OBJECT-TYPE
		SYNTAX		INTEGER { disable(0), enable(1) }
		MAX-ACCESS		read-write
		STATUS			current
		DESCRIPTION
				"TYPE: - Checkbox
				 PAGE: - Audio- Emb.Ctrl
					Pair 8-R Active  cmdID= 37446 "
		::= { iqmux43CmdEntry 37446 }


	iqmux43AudioEmbCtrlEmbedderPriority OBJECT-TYPE
		SYNTAX		INTEGER {
							val_Normal(0),
							val_Audio_Dolby_E(1)
							}
		MAX-ACCESS		read-write
		STATUS			current
		DESCRIPTION
				"TYPE: - RadiobuttonList
				 PAGE: - Audio- Emb.Ctrl
					Embedder Priority  cmdID= 37460
					Normal  value= 0
					Audio (Dolby-E)  value= 1  "
		::= { iqmux43CmdEntry 37460 }


	iqmux43EmbGainEmbedPair1Embed1MuteL OBJECT-TYPE
		SYNTAX		INTEGER { disable(0), enable(1) }
		MAX-ACCESS		read-write
		STATUS			current
		DESCRIPTION
				"TYPE: - Checkbox
				 PAGE: - Audio
					Embed 1 Mute L  cmdID= 37340 "
		::= { iqmux43CmdEntry 37340 }


	iqmux43EmbGainEmbedPair1Embed1MuteR OBJECT-TYPE
		SYNTAX		INTEGER { disable(0), enable(1) }
		MAX-ACCESS		read-write
		STATUS			current
		DESCRIPTION
				"TYPE: - Checkbox
				 PAGE: - Audio
					Embed 1 Mute R  cmdID= 37341 "
		::= { iqmux43CmdEntry 37341 }


	iqmux43EmbGainEmbedPair1Embed1LGain OBJECT-TYPE
		SYNTAX		INTEGER
		MAX-ACCESS		read-write
		STATUS			current
		DESCRIPTION
				"TYPE: - Number
				 PAGE: - Audio
					Embed 1 L Gain  cmdID= 37320  min= -661  max= 120  step= 1  format= %0.1f dB  div_scale= 10
					Min = -66.1 dB  Max = 12.0 dB  Step = 0.1 dB "
		::= { iqmux43CmdEntry 37320 }


	iqmux43EmbGainEmbedPair1Embed1RGain OBJECT-TYPE
		SYNTAX		INTEGER
		MAX-ACCESS		read-write
		STATUS			current
		DESCRIPTION
				"TYPE: - Number
				 PAGE: - Audio
					Embed 1 R Gain  cmdID= 37321  min= -661  max= 120  step= 1  format= %0.1f dB  div_scale= 10
					Min = -66.1 dB  Max = 12.0 dB  Step = 0.1 dB "
		::= { iqmux43CmdEntry 37321 }


	iqmux43EmbGainEmbedPair1Stereo OBJECT-TYPE
		SYNTAX		INTEGER { disable(0), enable(1) }
		MAX-ACCESS		read-write
		STATUS			current
		DESCRIPTION
				"TYPE: - Checkbox
				 PAGE: - Audio
					Stereo  cmdID= 37380 "
		::= { iqmux43CmdEntry 37380 }


	iqmux43EmbGainEmbedPair1Embed1InvertL OBJECT-TYPE
		SYNTAX		INTEGER { disable(0), enable(1) }
		MAX-ACCESS		read-write
		STATUS			current
		DESCRIPTION
				"TYPE: - Checkbox
				 PAGE: - Audio
					Embed 1 Invert L  cmdID= 37360 "
		::= { iqmux43CmdEntry 37360 }


	iqmux43EmbGainEmbedPair1Embed1InvertR OBJECT-TYPE
		SYNTAX		INTEGER { disable(0), enable(1) }
		MAX-ACCESS		read-write
		STATUS			current
		DESCRIPTION
				"TYPE: - Checkbox
				 PAGE: - Audio
					Embed 1 Invert R  cmdID= 37361 "
		::= { iqmux43CmdEntry 37361 }


	iqmux43EmbGainEmbedPair1Embed1LClip OBJECT-TYPE
		SYNTAX		RollCallString
		MAX-ACCESS		read-only
		STATUS			current
		DESCRIPTION
				"TYPE: - Display
				 PAGE: - Audio
					Embed 1-L Clip  cmdID= 37540  format=   "
		::= { iqmux43CmdEntry 37540 }


	iqmux43EmbGainEmbedPair1Embed1RClip OBJECT-TYPE
		SYNTAX		RollCallString
		MAX-ACCESS		read-only
		STATUS			current
		DESCRIPTION
				"TYPE: - Display
				 PAGE: - Audio
					Embed 1-R Clip  cmdID= 37541  format=   "
		::= { iqmux43CmdEntry 37541 }


	iqmux43EmbGainEmbedPair2Embed2MuteL OBJECT-TYPE
		SYNTAX		INTEGER { disable(0), enable(1) }
		MAX-ACCESS		read-write
		STATUS			current
		DESCRIPTION
				"TYPE: - Checkbox
				 PAGE: - Audio
					Embed 2 Mute L  cmdID= 37342 "
		::= { iqmux43CmdEntry 37342 }


	iqmux43EmbGainEmbedPair2Embed2MuteR OBJECT-TYPE
		SYNTAX		INTEGER { disable(0), enable(1) }
		MAX-ACCESS		read-write
		STATUS			current
		DESCRIPTION
				"TYPE: - Checkbox
				 PAGE: - Audio
					Embed 2 Mute R  cmdID= 37343 "
		::= { iqmux43CmdEntry 37343 }


	iqmux43EmbGainEmbedPair2Embed2LGain OBJECT-TYPE
		SYNTAX		INTEGER
		MAX-ACCESS		read-write
		STATUS			current
		DESCRIPTION
				"TYPE: - Number
				 PAGE: - Audio
					Embed 2 L Gain  cmdID= 37322  min= -661  max= 120  step= 1  format= %0.1f dB  div_scale= 10
					Min = -66.1 dB  Max = 12.0 dB  Step = 0.1 dB "
		::= { iqmux43CmdEntry 37322 }


	iqmux43EmbGainEmbedPair2Embed2RGain OBJECT-TYPE
		SYNTAX		INTEGER
		MAX-ACCESS		read-write
		STATUS			current
		DESCRIPTION
				"TYPE: - Number
				 PAGE: - Audio
					Embed 2 R Gain  cmdID= 37323  min= -661  max= 120  step= 1  format= %0.1f dB  div_scale= 10
					Min = -66.1 dB  Max = 12.0 dB  Step = 0.1 dB "
		::= { iqmux43CmdEntry 37323 }


	iqmux43EmbGainEmbedPair2Stereo OBJECT-TYPE
		SYNTAX		INTEGER { disable(0), enable(1) }
		MAX-ACCESS		read-write
		STATUS			current
		DESCRIPTION
				"TYPE: - Checkbox
				 PAGE: - Audio
					Stereo  cmdID= 37381 "
		::= { iqmux43CmdEntry 37381 }


	iqmux43EmbGainEmbedPair2Embed2InvertL OBJECT-TYPE
		SYNTAX		INTEGER { disable(0), enable(1) }
		MAX-ACCESS		read-write
		STATUS			current
		DESCRIPTION
				"TYPE: - Checkbox
				 PAGE: - Audio
					Embed 2 Invert L  cmdID= 37362 "
		::= { iqmux43CmdEntry 37362 }


	iqmux43EmbGainEmbedPair2Embed2InvertR OBJECT-TYPE
		SYNTAX		INTEGER { disable(0), enable(1) }
		MAX-ACCESS		read-write
		STATUS			current
		DESCRIPTION
				"TYPE: - Checkbox
				 PAGE: - Audio
					Embed 2 Invert R  cmdID= 37363 "
		::= { iqmux43CmdEntry 37363 }


	iqmux43EmbGainEmbedPair2Embed2LClip OBJECT-TYPE
		SYNTAX		RollCallString
		MAX-ACCESS		read-only
		STATUS			current
		DESCRIPTION
				"TYPE: - Display
				 PAGE: - Audio
					Embed 2-L Clip  cmdID= 37542  format=   "
		::= { iqmux43CmdEntry 37542 }


	iqmux43EmbGainEmbedPair2Embed2RClip OBJECT-TYPE
		SYNTAX		RollCallString
		MAX-ACCESS		read-only
		STATUS			current
		DESCRIPTION
				"TYPE: - Display
				 PAGE: - Audio
					Embed 2-R Clip  cmdID= 37543  format=   "
		::= { iqmux43CmdEntry 37543 }


	iqmux43EmbGainEmbedPair3Embed3MuteL OBJECT-TYPE
		SYNTAX		INTEGER { disable(0), enable(1) }
		MAX-ACCESS		read-write
		STATUS			current
		DESCRIPTION
				"TYPE: - Checkbox
				 PAGE: - Audio
					Embed 3 Mute L  cmdID= 37344 "
		::= { iqmux43CmdEntry 37344 }


	iqmux43EmbGainEmbedPair3Embed3MuteR OBJECT-TYPE
		SYNTAX		INTEGER { disable(0), enable(1) }
		MAX-ACCESS		read-write
		STATUS			current
		DESCRIPTION
				"TYPE: - Checkbox
				 PAGE: - Audio
					Embed 3 Mute R  cmdID= 37345 "
		::= { iqmux43CmdEntry 37345 }


	iqmux43EmbGainEmbedPair3Embed3LGain OBJECT-TYPE
		SYNTAX		INTEGER
		MAX-ACCESS		read-write
		STATUS			current
		DESCRIPTION
				"TYPE: - Number
				 PAGE: - Audio
					Embed 3 L Gain  cmdID= 37324  min= -661  max= 120  step= 1  format= %0.1f dB  div_scale= 10
					Min = -66.1 dB  Max = 12.0 dB  Step = 0.1 dB "
		::= { iqmux43CmdEntry 37324 }


	iqmux43EmbGainEmbedPair3Embed3RGain OBJECT-TYPE
		SYNTAX		INTEGER
		MAX-ACCESS		read-write
		STATUS			current
		DESCRIPTION
				"TYPE: - Number
				 PAGE: - Audio
					Embed 3 R Gain  cmdID= 37325  min= -661  max= 120  step= 1  format= %0.1f dB  div_scale= 10
					Min = -66.1 dB  Max = 12.0 dB  Step = 0.1 dB "
		::= { iqmux43CmdEntry 37325 }


	iqmux43EmbGainEmbedPair3Stereo OBJECT-TYPE
		SYNTAX		INTEGER { disable(0), enable(1) }
		MAX-ACCESS		read-write
		STATUS			current
		DESCRIPTION
				"TYPE: - Checkbox
				 PAGE: - Audio
					Stereo  cmdID= 37382 "
		::= { iqmux43CmdEntry 37382 }


	iqmux43EmbGainEmbedPair3Embed3InvertL OBJECT-TYPE
		SYNTAX		INTEGER { disable(0), enable(1) }
		MAX-ACCESS		read-write
		STATUS			current
		DESCRIPTION
				"TYPE: - Checkbox
				 PAGE: - Audio
					Embed 3 Invert L  cmdID= 37364 "
		::= { iqmux43CmdEntry 37364 }


	iqmux43EmbGainEmbedPair3Embed3InvertR OBJECT-TYPE
		SYNTAX		INTEGER { disable(0), enable(1) }
		MAX-ACCESS		read-write
		STATUS			current
		DESCRIPTION
				"TYPE: - Checkbox
				 PAGE: - Audio
					Embed 3 Invert R  cmdID= 37365 "
		::= { iqmux43CmdEntry 37365 }


	iqmux43EmbGainEmbedPair3Embed3LClip OBJECT-TYPE
		SYNTAX		RollCallString
		MAX-ACCESS		read-only
		STATUS			current
		DESCRIPTION
				"TYPE: - Display
				 PAGE: - Audio
					Embed 3-L Clip  cmdID= 37544  format=   "
		::= { iqmux43CmdEntry 37544 }


	iqmux43EmbGainEmbedPair3Embed3RClip OBJECT-TYPE
		SYNTAX		RollCallString
		MAX-ACCESS		read-only
		STATUS			current
		DESCRIPTION
				"TYPE: - Display
				 PAGE: - Audio
					Embed 3-R Clip  cmdID= 37545  format=   "
		::= { iqmux43CmdEntry 37545 }


	iqmux43EmbGainEmbedPair4Embed4MuteL OBJECT-TYPE
		SYNTAX		INTEGER { disable(0), enable(1) }
		MAX-ACCESS		read-write
		STATUS			current
		DESCRIPTION
				"TYPE: - Checkbox
				 PAGE: - Audio
					Embed 4 Mute L  cmdID= 37346 "
		::= { iqmux43CmdEntry 37346 }


	iqmux43EmbGainEmbedPair4Embed4MuteR OBJECT-TYPE
		SYNTAX		INTEGER { disable(0), enable(1) }
		MAX-ACCESS		read-write
		STATUS			current
		DESCRIPTION
				"TYPE: - Checkbox
				 PAGE: - Audio
					Embed 4 Mute R  cmdID= 37347 "
		::= { iqmux43CmdEntry 37347 }


	iqmux43EmbGainEmbedPair4Embed4LGain OBJECT-TYPE
		SYNTAX		INTEGER
		MAX-ACCESS		read-write
		STATUS			current
		DESCRIPTION
				"TYPE: - Number
				 PAGE: - Audio
					Embed 4 L Gain  cmdID= 37326  min= -661  max= 120  step= 1  format= %0.1f dB  div_scale= 10
					Min = -66.1 dB  Max = 12.0 dB  Step = 0.1 dB "
		::= { iqmux43CmdEntry 37326 }


	iqmux43EmbGainEmbedPair4Embed4RGain OBJECT-TYPE
		SYNTAX		INTEGER
		MAX-ACCESS		read-write
		STATUS			current
		DESCRIPTION
				"TYPE: - Number
				 PAGE: - Audio
					Embed 4 R Gain  cmdID= 37327  min= -661  max= 120  step= 1  format= %0.1f dB  div_scale= 10
					Min = -66.1 dB  Max = 12.0 dB  Step = 0.1 dB "
		::= { iqmux43CmdEntry 37327 }


	iqmux43EmbGainEmbedPair4Stereo OBJECT-TYPE
		SYNTAX		INTEGER { disable(0), enable(1) }
		MAX-ACCESS		read-write
		STATUS			current
		DESCRIPTION
				"TYPE: - Checkbox
				 PAGE: - Audio
					Stereo  cmdID= 37383 "
		::= { iqmux43CmdEntry 37383 }


	iqmux43EmbGainEmbedPair4Embed4InvertL OBJECT-TYPE
		SYNTAX		INTEGER { disable(0), enable(1) }
		MAX-ACCESS		read-write
		STATUS			current
		DESCRIPTION
				"TYPE: - Checkbox
				 PAGE: - Audio
					Embed 4 Invert L  cmdID= 37366 "
		::= { iqmux43CmdEntry 37366 }


	iqmux43EmbGainEmbedPair4Embed4InvertR OBJECT-TYPE
		SYNTAX		INTEGER { disable(0), enable(1) }
		MAX-ACCESS		read-write
		STATUS			current
		DESCRIPTION
				"TYPE: - Checkbox
				 PAGE: - Audio
					Embed 4 Invert R  cmdID= 37367 "
		::= { iqmux43CmdEntry 37367 }


	iqmux43EmbGainEmbedPair4Embed4LClip OBJECT-TYPE
		SYNTAX		RollCallString
		MAX-ACCESS		read-only
		STATUS			current
		DESCRIPTION
				"TYPE: - Display
				 PAGE: - Audio
					Embed 4-L Clip  cmdID= 37546  format=   "
		::= { iqmux43CmdEntry 37546 }


	iqmux43EmbGainEmbedPair4Embed4RClip OBJECT-TYPE
		SYNTAX		RollCallString
		MAX-ACCESS		read-only
		STATUS			current
		DESCRIPTION
				"TYPE: - Display
				 PAGE: - Audio
					Embed 4-R Clip  cmdID= 37547  format=   "
		::= { iqmux43CmdEntry 37547 }


	iqmux43EmbGainEmbedPair5Embed5MuteL OBJECT-TYPE
		SYNTAX		INTEGER { disable(0), enable(1) }
		MAX-ACCESS		read-write
		STATUS			current
		DESCRIPTION
				"TYPE: - Checkbox
				 PAGE: - Audio
					Embed 5 Mute L  cmdID= 37348 "
		::= { iqmux43CmdEntry 37348 }


	iqmux43EmbGainEmbedPair5Embed5MuteR OBJECT-TYPE
		SYNTAX		INTEGER { disable(0), enable(1) }
		MAX-ACCESS		read-write
		STATUS			current
		DESCRIPTION
				"TYPE: - Checkbox
				 PAGE: - Audio
					Embed 5 Mute R  cmdID= 37349 "
		::= { iqmux43CmdEntry 37349 }


	iqmux43EmbGainEmbedPair5Embed5LGain OBJECT-TYPE
		SYNTAX		INTEGER
		MAX-ACCESS		read-write
		STATUS			current
		DESCRIPTION
				"TYPE: - Number
				 PAGE: - Audio
					Embed 5 L Gain  cmdID= 37328  min= -661  max= 120  step= 1  format= %0.1f dB  div_scale= 10
					Min = -66.1 dB  Max = 12.0 dB  Step = 0.1 dB "
		::= { iqmux43CmdEntry 37328 }


	iqmux43EmbGainEmbedPair5Embed5RGain OBJECT-TYPE
		SYNTAX		INTEGER
		MAX-ACCESS		read-write
		STATUS			current
		DESCRIPTION
				"TYPE: - Number
				 PAGE: - Audio
					Embed 5 R Gain  cmdID= 37329  min= -661  max= 120  step= 1  format= %0.1f dB  div_scale= 10
					Min = -66.1 dB  Max = 12.0 dB  Step = 0.1 dB "
		::= { iqmux43CmdEntry 37329 }


	iqmux43EmbGainEmbedPair5Stereo OBJECT-TYPE
		SYNTAX		INTEGER { disable(0), enable(1) }
		MAX-ACCESS		read-write
		STATUS			current
		DESCRIPTION
				"TYPE: - Checkbox
				 PAGE: - Audio
					Stereo  cmdID= 37384 "
		::= { iqmux43CmdEntry 37384 }


	iqmux43EmbGainEmbedPair5Embed5InvertL OBJECT-TYPE
		SYNTAX		INTEGER { disable(0), enable(1) }
		MAX-ACCESS		read-write
		STATUS			current
		DESCRIPTION
				"TYPE: - Checkbox
				 PAGE: - Audio
					Embed 5 Invert L  cmdID= 37368 "
		::= { iqmux43CmdEntry 37368 }


	iqmux43EmbGainEmbedPair5Embed5InvertR OBJECT-TYPE
		SYNTAX		INTEGER { disable(0), enable(1) }
		MAX-ACCESS		read-write
		STATUS			current
		DESCRIPTION
				"TYPE: - Checkbox
				 PAGE: - Audio
					Embed 5 Invert R  cmdID= 37369 "
		::= { iqmux43CmdEntry 37369 }


	iqmux43EmbGainEmbedPair5Embed5LClip OBJECT-TYPE
		SYNTAX		RollCallString
		MAX-ACCESS		read-only
		STATUS			current
		DESCRIPTION
				"TYPE: - Display
				 PAGE: - Audio
					Embed 5-L Clip  cmdID= 37548  format=   "
		::= { iqmux43CmdEntry 37548 }


	iqmux43EmbGainEmbedPair5Embed5RClip OBJECT-TYPE
		SYNTAX		RollCallString
		MAX-ACCESS		read-only
		STATUS			current
		DESCRIPTION
				"TYPE: - Display
				 PAGE: - Audio
					Embed 5-R Clip  cmdID= 37549  format=   "
		::= { iqmux43CmdEntry 37549 }


	iqmux43EmbGainEmbedPair6Embed6MuteL OBJECT-TYPE
		SYNTAX		INTEGER { disable(0), enable(1) }
		MAX-ACCESS		read-write
		STATUS			current
		DESCRIPTION
				"TYPE: - Checkbox
				 PAGE: - Audio
					Embed 6 Mute L  cmdID= 37350 "
		::= { iqmux43CmdEntry 37350 }


	iqmux43EmbGainEmbedPair6Embed6MuteR OBJECT-TYPE
		SYNTAX		INTEGER { disable(0), enable(1) }
		MAX-ACCESS		read-write
		STATUS			current
		DESCRIPTION
				"TYPE: - Checkbox
				 PAGE: - Audio
					Embed 6 Mute R  cmdID= 37351 "
		::= { iqmux43CmdEntry 37351 }


	iqmux43EmbGainEmbedPair6Embed6LGain OBJECT-TYPE
		SYNTAX		INTEGER
		MAX-ACCESS		read-write
		STATUS			current
		DESCRIPTION
				"TYPE: - Number
				 PAGE: - Audio
					Embed 6 L Gain  cmdID= 37330  min= -661  max= 120  step= 1  format= %0.1f dB  div_scale= 10
					Min = -66.1 dB  Max = 12.0 dB  Step = 0.1 dB "
		::= { iqmux43CmdEntry 37330 }


	iqmux43EmbGainEmbedPair6Embed6RGain OBJECT-TYPE
		SYNTAX		INTEGER
		MAX-ACCESS		read-write
		STATUS			current
		DESCRIPTION
				"TYPE: - Number
				 PAGE: - Audio
					Embed 6 R Gain  cmdID= 37331  min= -661  max= 120  step= 1  format= %0.1f dB  div_scale= 10
					Min = -66.1 dB  Max = 12.0 dB  Step = 0.1 dB "
		::= { iqmux43CmdEntry 37331 }


	iqmux43EmbGainEmbedPair6Stereo OBJECT-TYPE
		SYNTAX		INTEGER { disable(0), enable(1) }
		MAX-ACCESS		read-write
		STATUS			current
		DESCRIPTION
				"TYPE: - Checkbox
				 PAGE: - Audio
					Stereo  cmdID= 37385 "
		::= { iqmux43CmdEntry 37385 }


	iqmux43EmbGainEmbedPair6Embed6InvertL OBJECT-TYPE
		SYNTAX		INTEGER { disable(0), enable(1) }
		MAX-ACCESS		read-write
		STATUS			current
		DESCRIPTION
				"TYPE: - Checkbox
				 PAGE: - Audio
					Embed 6 Invert L  cmdID= 37370 "
		::= { iqmux43CmdEntry 37370 }


	iqmux43EmbGainEmbedPair6Embed6InvertR OBJECT-TYPE
		SYNTAX		INTEGER { disable(0), enable(1) }
		MAX-ACCESS		read-write
		STATUS			current
		DESCRIPTION
				"TYPE: - Checkbox
				 PAGE: - Audio
					Embed 6 Invert R  cmdID= 37371 "
		::= { iqmux43CmdEntry 37371 }


	iqmux43EmbGainEmbedPair6Embed6LClip OBJECT-TYPE
		SYNTAX		RollCallString
		MAX-ACCESS		read-only
		STATUS			current
		DESCRIPTION
				"TYPE: - Display
				 PAGE: - Audio
					Embed 6-L Clip  cmdID= 37550  format=   "
		::= { iqmux43CmdEntry 37550 }


	iqmux43EmbGainEmbedPair6Embed6RClip OBJECT-TYPE
		SYNTAX		RollCallString
		MAX-ACCESS		read-only
		STATUS			current
		DESCRIPTION
				"TYPE: - Display
				 PAGE: - Audio
					Embed 6-R Clip  cmdID= 37551  format=   "
		::= { iqmux43CmdEntry 37551 }


	iqmux43EmbGainEmbedPair7Embed7MuteL OBJECT-TYPE
		SYNTAX		INTEGER { disable(0), enable(1) }
		MAX-ACCESS		read-write
		STATUS			current
		DESCRIPTION
				"TYPE: - Checkbox
				 PAGE: - Audio
					Embed 7 Mute L  cmdID= 37352 "
		::= { iqmux43CmdEntry 37352 }


	iqmux43EmbGainEmbedPair7Embed7MuteR OBJECT-TYPE
		SYNTAX		INTEGER { disable(0), enable(1) }
		MAX-ACCESS		read-write
		STATUS			current
		DESCRIPTION
				"TYPE: - Checkbox
				 PAGE: - Audio
					Embed 7 Mute R  cmdID= 37353 "
		::= { iqmux43CmdEntry 37353 }


	iqmux43EmbGainEmbedPair7Embed7LGain OBJECT-TYPE
		SYNTAX		INTEGER
		MAX-ACCESS		read-write
		STATUS			current
		DESCRIPTION
				"TYPE: - Number
				 PAGE: - Audio
					Embed 7 L Gain  cmdID= 37332  min= -661  max= 120  step= 1  format= %0.1f dB  div_scale= 10
					Min = -66.1 dB  Max = 12.0 dB  Step = 0.1 dB "
		::= { iqmux43CmdEntry 37332 }


	iqmux43EmbGainEmbedPair7Embed7RGain OBJECT-TYPE
		SYNTAX		INTEGER
		MAX-ACCESS		read-write
		STATUS			current
		DESCRIPTION
				"TYPE: - Number
				 PAGE: - Audio
					Embed 7 R Gain  cmdID= 37333  min= -661  max= 120  step= 1  format= %0.1f dB  div_scale= 10
					Min = -66.1 dB  Max = 12.0 dB  Step = 0.1 dB "
		::= { iqmux43CmdEntry 37333 }


	iqmux43EmbGainEmbedPair7Stereo OBJECT-TYPE
		SYNTAX		INTEGER { disable(0), enable(1) }
		MAX-ACCESS		read-write
		STATUS			current
		DESCRIPTION
				"TYPE: - Checkbox
				 PAGE: - Audio
					Stereo  cmdID= 37386 "
		::= { iqmux43CmdEntry 37386 }


	iqmux43EmbGainEmbedPair7Embed7InvertL OBJECT-TYPE
		SYNTAX		INTEGER { disable(0), enable(1) }
		MAX-ACCESS		read-write
		STATUS			current
		DESCRIPTION
				"TYPE: - Checkbox
				 PAGE: - Audio
					Embed 7 Invert L  cmdID= 37372 "
		::= { iqmux43CmdEntry 37372 }


	iqmux43EmbGainEmbedPair7Embed7InvertR OBJECT-TYPE
		SYNTAX		INTEGER { disable(0), enable(1) }
		MAX-ACCESS		read-write
		STATUS			current
		DESCRIPTION
				"TYPE: - Checkbox
				 PAGE: - Audio
					Embed 7 Invert R  cmdID= 37373 "
		::= { iqmux43CmdEntry 37373 }


	iqmux43EmbGainEmbedPair7Embed7LClip OBJECT-TYPE
		SYNTAX		RollCallString
		MAX-ACCESS		read-only
		STATUS			current
		DESCRIPTION
				"TYPE: - Display
				 PAGE: - Audio
					Embed 7-L Clip  cmdID= 37552  format=   "
		::= { iqmux43CmdEntry 37552 }


	iqmux43EmbGainEmbedPair7Embed7RClip OBJECT-TYPE
		SYNTAX		RollCallString
		MAX-ACCESS		read-only
		STATUS			current
		DESCRIPTION
				"TYPE: - Display
				 PAGE: - Audio
					Embed 7-R Clip  cmdID= 37553  format=   "
		::= { iqmux43CmdEntry 37553 }


	iqmux43EmbGainEmbedPair8Embed8MuteL OBJECT-TYPE
		SYNTAX		INTEGER { disable(0), enable(1) }
		MAX-ACCESS		read-write
		STATUS			current
		DESCRIPTION
				"TYPE: - Checkbox
				 PAGE: - Audio
					Embed 8 Mute L  cmdID= 37354 "
		::= { iqmux43CmdEntry 37354 }


	iqmux43EmbGainEmbedPair8Embed8MuteR OBJECT-TYPE
		SYNTAX		INTEGER { disable(0), enable(1) }
		MAX-ACCESS		read-write
		STATUS			current
		DESCRIPTION
				"TYPE: - Checkbox
				 PAGE: - Audio
					Embed 8 Mute R  cmdID= 37355 "
		::= { iqmux43CmdEntry 37355 }


	iqmux43EmbGainEmbedPair8Embed8LGain OBJECT-TYPE
		SYNTAX		INTEGER
		MAX-ACCESS		read-write
		STATUS			current
		DESCRIPTION
				"TYPE: - Number
				 PAGE: - Audio
					Embed 8 L Gain  cmdID= 37334  min= -661  max= 120  step= 1  format= %0.1f dB  div_scale= 10
					Min = -66.1 dB  Max = 12.0 dB  Step = 0.1 dB "
		::= { iqmux43CmdEntry 37334 }


	iqmux43EmbGainEmbedPair8Embed8RGain OBJECT-TYPE
		SYNTAX		INTEGER
		MAX-ACCESS		read-write
		STATUS			current
		DESCRIPTION
				"TYPE: - Number
				 PAGE: - Audio
					Embed 8 R Gain  cmdID= 37335  min= -661  max= 120  step= 1  format= %0.1f dB  div_scale= 10
					Min = -66.1 dB  Max = 12.0 dB  Step = 0.1 dB "
		::= { iqmux43CmdEntry 37335 }


	iqmux43EmbGainEmbedPair8Stereo OBJECT-TYPE
		SYNTAX		INTEGER { disable(0), enable(1) }
		MAX-ACCESS		read-write
		STATUS			current
		DESCRIPTION
				"TYPE: - Checkbox
				 PAGE: - Audio
					Stereo  cmdID= 37387 "
		::= { iqmux43CmdEntry 37387 }


	iqmux43EmbGainEmbedPair8Embed8InvertL OBJECT-TYPE
		SYNTAX		INTEGER { disable(0), enable(1) }
		MAX-ACCESS		read-write
		STATUS			current
		DESCRIPTION
				"TYPE: - Checkbox
				 PAGE: - Audio
					Embed 8 Invert L  cmdID= 37374 "
		::= { iqmux43CmdEntry 37374 }


	iqmux43EmbGainEmbedPair8Embed8InvertR OBJECT-TYPE
		SYNTAX		INTEGER { disable(0), enable(1) }
		MAX-ACCESS		read-write
		STATUS			current
		DESCRIPTION
				"TYPE: - Checkbox
				 PAGE: - Audio
					Embed 8 Invert R  cmdID= 37375 "
		::= { iqmux43CmdEntry 37375 }


	iqmux43EmbGainEmbedPair8Embed8LClip OBJECT-TYPE
		SYNTAX		RollCallString
		MAX-ACCESS		read-only
		STATUS			current
		DESCRIPTION
				"TYPE: - Display
				 PAGE: - Audio
					Embed 8-L Clip  cmdID= 37554  format=   "
		::= { iqmux43CmdEntry 37554 }


	iqmux43EmbGainEmbedPair8Embed8RClip OBJECT-TYPE
		SYNTAX		RollCallString
		MAX-ACCESS		read-only
		STATUS			current
		DESCRIPTION
				"TYPE: - Display
				 PAGE: - Audio
					Embed 8-R Clip  cmdID= 37555  format=   "
		::= { iqmux43CmdEntry 37555 }


	iqmux43EmbOutEmbedPair1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Left  cmdID= 37300
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37300 }


	iqmux43EmbOutEmbedPair1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Right  cmdID= 37301
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37301 }


	iqmux43EmbOutEmbedPair1LinkLRSelection OBJECT-TYPE
		SYNTAX		INTEGER { disable(0), enable(1) }
		MAX-ACCESS		read-write
		STATUS			current
		DESCRIPTION
				"TYPE: - Checkbox
				 PAGE: - Audio- Embed Pair 1
					Link L+R Selection  cmdID= 37390 "
		::= { iqmux43CmdEntry 37390 }


	iqmux43EmbOutEmbedPair2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Left  cmdID= 37302
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37302 }


	iqmux43EmbOutEmbedPair2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Right  cmdID= 37303
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37303 }


	iqmux43EmbOutEmbedPair2LinkLRSelection OBJECT-TYPE
		SYNTAX		INTEGER { disable(0), enable(1) }
		MAX-ACCESS		read-write
		STATUS			current
		DESCRIPTION
				"TYPE: - Checkbox
				 PAGE: - Audio- Embed Pair 2
					Link L+R Selection  cmdID= 37391 "
		::= { iqmux43CmdEntry 37391 }


	iqmux43EmbOutEmbedPair3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Left  cmdID= 37304
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37304 }


	iqmux43EmbOutEmbedPair3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Right  cmdID= 37305
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37305 }


	iqmux43EmbOutEmbedPair3LinkLRSelection OBJECT-TYPE
		SYNTAX		INTEGER { disable(0), enable(1) }
		MAX-ACCESS		read-write
		STATUS			current
		DESCRIPTION
				"TYPE: - Checkbox
				 PAGE: - Audio- Embed Pair 3
					Link L+R Selection  cmdID= 37392 "
		::= { iqmux43CmdEntry 37392 }


	iqmux43EmbOutEmbedPair4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Left  cmdID= 37306
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37306 }


	iqmux43EmbOutEmbedPair4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Right  cmdID= 37307
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37307 }


	iqmux43EmbOutEmbedPair4LinkLRSelection OBJECT-TYPE
		SYNTAX		INTEGER { disable(0), enable(1) }
		MAX-ACCESS		read-write
		STATUS			current
		DESCRIPTION
				"TYPE: - Checkbox
				 PAGE: - Audio- Embed Pair 4
					Link L+R Selection  cmdID= 37393 "
		::= { iqmux43CmdEntry 37393 }


	iqmux43EmbOutEmbedPair5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Left  cmdID= 37308
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37308 }


	iqmux43EmbOutEmbedPair5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Right  cmdID= 37309
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37309 }


	iqmux43EmbOutEmbedPair5LinkLRSelection OBJECT-TYPE
		SYNTAX		INTEGER { disable(0), enable(1) }
		MAX-ACCESS		read-write
		STATUS			current
		DESCRIPTION
				"TYPE: - Checkbox
				 PAGE: - Audio- Embed Pair 5
					Link L+R Selection  cmdID= 37394 "
		::= { iqmux43CmdEntry 37394 }


	iqmux43EmbOutEmbedPair6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Left  cmdID= 37310
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37310 }


	iqmux43EmbOutEmbedPair6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Right  cmdID= 37311
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37311 }


	iqmux43EmbOutEmbedPair6LinkLRSelection OBJECT-TYPE
		SYNTAX		INTEGER { disable(0), enable(1) }
		MAX-ACCESS		read-write
		STATUS			current
		DESCRIPTION
				"TYPE: - Checkbox
				 PAGE: - Audio- Embed Pair 6
					Link L+R Selection  cmdID= 37395 "
		::= { iqmux43CmdEntry 37395 }


	iqmux43EmbOutEmbedPair7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Left  cmdID= 37312
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37312 }


	iqmux43EmbOutEmbedPair7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Right  cmdID= 37313
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37313 }


	iqmux43EmbOutEmbedPair7LinkLRSelection OBJECT-TYPE
		SYNTAX		INTEGER { disable(0), enable(1) }
		MAX-ACCESS		read-write
		STATUS			current
		DESCRIPTION
				"TYPE: - Checkbox
				 PAGE: - Audio- Embed Pair 7
					Link L+R Selection  cmdID= 37396 "
		::= { iqmux43CmdEntry 37396 }


	iqmux43EmbOutEmbedPair8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Left  cmdID= 37314
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37314 }


	iqmux43EmbOutEmbedPair8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Right  cmdID= 37315
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37315 }


	iqmux43EmbOutEmbedPair8LinkLRSelection OBJECT-TYPE
		SYNTAX		INTEGER { disable(0), enable(1) }
		MAX-ACCESS		read-write
		STATUS			current
		DESCRIPTION
				"TYPE: - Checkbox
				 PAGE: - Audio- Embed Pair 8
					Link L+R Selection  cmdID= 37397 "
		::= { iqmux43CmdEntry 37397 }


	iqmux43AudioEmbModeInput1 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 1  cmdID= 37420
					PCM  value= 0
					Data  value= 1
					Mixed  value= 2  "
		::= { iqmux43CmdEntry 37420 }


	iqmux43AudioEmbModeInput2 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 2  cmdID= 37421
					PCM  value= 0
					Data  value= 1
					Mixed  value= 2  "
		::= { iqmux43CmdEntry 37421 }


	iqmux43AudioEmbModeInput3 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 3  cmdID= 37422
					PCM  value= 0
					Data  value= 1
					Mixed  value= 2  "
		::= { iqmux43CmdEntry 37422 }


	iqmux43AudioEmbModeInput4 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 4  cmdID= 37423
					PCM  value= 0
					Data  value= 1
					Mixed  value= 2  "
		::= { iqmux43CmdEntry 37423 }


	iqmux43AudioEmbModeInput5 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 5  cmdID= 37424
					PCM  value= 0
					Data  value= 1
					Mixed  value= 2  "
		::= { iqmux43CmdEntry 37424 }


	iqmux43AudioEmbModeInput6 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 6  cmdID= 37425
					PCM  value= 0
					Data  value= 1
					Mixed  value= 2  "
		::= { iqmux43CmdEntry 37425 }


	iqmux43AudioEmbModeInput7 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 7  cmdID= 37426
					PCM  value= 0
					Data  value= 1
					Mixed  value= 2  "
		::= { iqmux43CmdEntry 37426 }


	iqmux43AudioEmbModeInput8 OBJECT-TYPE
		SYNTAX		INTEGER {
							val_PCM(0),
							val_Data(1),
							val_Mixed(2)
							}
		MAX-ACCESS		read-write
		STATUS			current
		DESCRIPTION
				"TYPE: - RadiobuttonList
				 PAGE: - Audio- Emb.Mode
					Input 8  cmdID= 37427
					PCM  value= 0
					Data  value= 1
					Mixed  value= 2  "
		::= { iqmux43CmdEntry 37427 }


	iqmux43EmbedNamesDisembeder1 OBJECT-TYPE
		SYNTAX		RollCallString
		MAX-ACCESS		read-write
		STATUS			current
		DESCRIPTION
				"TYPE: - Editstring
				 PAGE: - Audio- Emb.Names
					Disembed 1  cmdID= 37500  "
		::= { iqmux43CmdEntry 37500 }


	iqmux43EmbedNamesDisembeder1R OBJECT-TYPE
		SYNTAX		RollCallString
		MAX-ACCESS		read-write
		STATUS			current
		DESCRIPTION
				"TYPE: - Editstring
				 PAGE: - Audio- Emb.Names
					Disembed 1-R  cmdID= 37501  "
		::= { iqmux43CmdEntry 37501 }


	iqmux43EmbedNamesDisembeder2 OBJECT-TYPE
		SYNTAX		RollCallString
		MAX-ACCESS		read-write
		STATUS			current
		DESCRIPTION
				"TYPE: - Editstring
				 PAGE: - Audio- Emb.Names
					Disembed 2  cmdID= 37502  "
		::= { iqmux43CmdEntry 37502 }


	iqmux43EmbedNamesDisembeder2R OBJECT-TYPE
		SYNTAX		RollCallString
		MAX-ACCESS		read-write
		STATUS			current
		DESCRIPTION
				"TYPE: - Editstring
				 PAGE: - Audio- Emb.Names
					Disembed 2-R  cmdID= 37503  "
		::= { iqmux43CmdEntry 37503 }


	iqmux43EmbedNamesDisembeder3 OBJECT-TYPE
		SYNTAX		RollCallString
		MAX-ACCESS		read-write
		STATUS			current
		DESCRIPTION
				"TYPE: - Editstring
				 PAGE: - Audio- Emb.Names
					Disembed 3  cmdID= 37504  "
		::= { iqmux43CmdEntry 37504 }


	iqmux43EmbedNamesDisembeder3R OBJECT-TYPE
		SYNTAX		RollCallString
		MAX-ACCESS		read-write
		STATUS			current
		DESCRIPTION
				"TYPE: - Editstring
				 PAGE: - Audio- Emb.Names
					Disembed 3-R  cmdID= 37505  "
		::= { iqmux43CmdEntry 37505 }


	iqmux43EmbedNamesDisembeder4 OBJECT-TYPE
		SYNTAX		RollCallString
		MAX-ACCESS		read-write
		STATUS			current
		DESCRIPTION
				"TYPE: - Editstring
				 PAGE: - Audio- Emb.Names
					Disembed 4  cmdID= 37506  "
		::= { iqmux43CmdEntry 37506 }


	iqmux43EmbedNamesDisembeder4R OBJECT-TYPE
		SYNTAX		RollCallString
		MAX-ACCESS		read-write
		STATUS			current
		DESCRIPTION
				"TYPE: - Editstring
				 PAGE: - Audio- Emb.Names
					Disembed 4-R  cmdID= 37507  "
		::= { iqmux43CmdEntry 37507 }


	iqmux43EmbedNamesDisembeder5 OBJECT-TYPE
		SYNTAX		RollCallString
		MAX-ACCESS		read-write
		STATUS			current
		DESCRIPTION
				"TYPE: - Editstring
				 PAGE: - Audio- Emb.Names
					Disembed 5  cmdID= 37508  "
		::= { iqmux43CmdEntry 37508 }


	iqmux43EmbedNamesDisembeder5R OBJECT-TYPE
		SYNTAX		RollCallString
		MAX-ACCESS		read-write
		STATUS			current
		DESCRIPTION
				"TYPE: - Editstring
				 PAGE: - Audio- Emb.Names
					Disembed 5-R  cmdID= 37509  "
		::= { iqmux43CmdEntry 37509 }


	iqmux43EmbedNamesDisembeder6 OBJECT-TYPE
		SYNTAX		RollCallString
		MAX-ACCESS		read-write
		STATUS			current
		DESCRIPTION
				"TYPE: - Editstring
				 PAGE: - Audio- Emb.Names
					Disembed 6  cmdID= 37510  "
		::= { iqmux43CmdEntry 37510 }


	iqmux43EmbedNamesDisembeder6R OBJECT-TYPE
		SYNTAX		RollCallString
		MAX-ACCESS		read-write
		STATUS			current
		DESCRIPTION
				"TYPE: - Editstring
				 PAGE: - Audio- Emb.Names
					Disembed 6-R  cmdID= 37511  "
		::= { iqmux43CmdEntry 37511 }


	iqmux43EmbedNamesDisembeder7 OBJECT-TYPE
		SYNTAX		RollCallString
		MAX-ACCESS		read-write
		STATUS			current
		DESCRIPTION
				"TYPE: - Editstring
				 PAGE: - Audio- Emb.Names
					Disembed 7  cmdID= 37512  "
		::= { iqmux43CmdEntry 37512 }


	iqmux43EmbedNamesDisembeder7R OBJECT-TYPE
		SYNTAX		RollCallString
		MAX-ACCESS		read-write
		STATUS			current
		DESCRIPTION
				"TYPE: - Editstring
				 PAGE: - Audio- Emb.Names
					Disembed 7-R  cmdID= 37513  "
		::= { iqmux43CmdEntry 37513 }


	iqmux43EmbedNamesDisembeder8 OBJECT-TYPE
		SYNTAX		RollCallString
		MAX-ACCESS		read-write
		STATUS			current
		DESCRIPTION
				"TYPE: - Editstring
				 PAGE: - Audio- Emb.Names
					Disembed 8  cmdID= 37514  "
		::= { iqmux43CmdEntry 37514 }


	iqmux43EmbedNamesDisembeder8R OBJECT-TYPE
		SYNTAX		RollCallString
		MAX-ACCESS		read-write
		STATUS			current
		DESCRIPTION
				"TYPE: - Editstring
				 PAGE: - Audio- Emb.Names
					Disembed 8-R  cmdID= 37515  "
		::= { iqmux43CmdEntry 37515 }


	iqmux43EmbedNamesEmbeddedOP1 OBJECT-TYPE
		SYNTAX		RollCallString
		MAX-ACCESS		read-write
		STATUS			current
		DESCRIPTION
				"TYPE: - Editstring
				 PAGE: - Audio- Emb.Names
					Embed 1  cmdID= 37520  "
		::= { iqmux43CmdEntry 37520 }


	iqmux43EmbedNamesEmbeddedOP1R OBJECT-TYPE
		SYNTAX		RollCallString
		MAX-ACCESS		read-write
		STATUS			current
		DESCRIPTION
				"TYPE: - Editstring
				 PAGE: - Audio- Emb.Names
					Embed 1-R  cmdID= 37521  "
		::= { iqmux43CmdEntry 37521 }


	iqmux43EmbedNamesEmbeddedOP2 OBJECT-TYPE
		SYNTAX		RollCallString
		MAX-ACCESS		read-write
		STATUS			current
		DESCRIPTION
				"TYPE: - Editstring
				 PAGE: - Audio- Emb.Names
					Embed 2  cmdID= 37522  "
		::= { iqmux43CmdEntry 37522 }


	iqmux43EmbedNamesEmbeddedOP2R OBJECT-TYPE
		SYNTAX		RollCallString
		MAX-ACCESS		read-write
		STATUS			current
		DESCRIPTION
				"TYPE: - Editstring
				 PAGE: - Audio- Emb.Names
					Embed 2-R  cmdID= 37523  "
		::= { iqmux43CmdEntry 37523 }


	iqmux43EmbedNamesEmbeddedOP3 OBJECT-TYPE
		SYNTAX		RollCallString
		MAX-ACCESS		read-write
		STATUS			current
		DESCRIPTION
				"TYPE: - Editstring
				 PAGE: - Audio- Emb.Names
					Embed 3  cmdID= 37524  "
		::= { iqmux43CmdEntry 37524 }


	iqmux43EmbedNamesEmbeddedOP3R OBJECT-TYPE
		SYNTAX		RollCallString
		MAX-ACCESS		read-write
		STATUS			current
		DESCRIPTION
				"TYPE: - Editstring
				 PAGE: - Audio- Emb.Names
					Embed 3-R  cmdID= 37525  "
		::= { iqmux43CmdEntry 37525 }


	iqmux43EmbedNamesEmbeddedOP4 OBJECT-TYPE
		SYNTAX		RollCallString
		MAX-ACCESS		read-write
		STATUS			current
		DESCRIPTION
				"TYPE: - Editstring
				 PAGE: - Audio- Emb.Names
					Embed 4  cmdID= 37526  "
		::= { iqmux43CmdEntry 37526 }


	iqmux43EmbedNamesEmbeddedOP4R OBJECT-TYPE
		SYNTAX		RollCallString
		MAX-ACCESS		read-write
		STATUS			current
		DESCRIPTION
				"TYPE: - Editstring
				 PAGE: - Audio- Emb.Names
					Embed 4-R  cmdID= 37527  "
		::= { iqmux43CmdEntry 37527 }


	iqmux43EmbedNamesEmbeddedOP5 OBJECT-TYPE
		SYNTAX		RollCallString
		MAX-ACCESS		read-write
		STATUS			current
		DESCRIPTION
				"TYPE: - Editstring
				 PAGE: - Audio- Emb.Names
					Embed 5  cmdID= 37528  "
		::= { iqmux43CmdEntry 37528 }


	iqmux43EmbedNamesEmbeddedOP5R OBJECT-TYPE
		SYNTAX		RollCallString
		MAX-ACCESS		read-write
		STATUS			current
		DESCRIPTION
				"TYPE: - Editstring
				 PAGE: - Audio- Emb.Names
					Embed 5-R  cmdID= 37529  "
		::= { iqmux43CmdEntry 37529 }


	iqmux43EmbedNamesEmbeddedOP6 OBJECT-TYPE
		SYNTAX		RollCallString
		MAX-ACCESS		read-write
		STATUS			current
		DESCRIPTION
				"TYPE: - Editstring
				 PAGE: - Audio- Emb.Names
					Embed 6  cmdID= 37530  "
		::= { iqmux43CmdEntry 37530 }


	iqmux43EmbedNamesEmbeddedOP6R OBJECT-TYPE
		SYNTAX		RollCallString
		MAX-ACCESS		read-write
		STATUS			current
		DESCRIPTION
				"TYPE: - Editstring
				 PAGE: - Audio- Emb.Names
					Embed 6-R  cmdID= 37531  "
		::= { iqmux43CmdEntry 37531 }


	iqmux43EmbedNamesEmbeddedOP7 OBJECT-TYPE
		SYNTAX		RollCallString
		MAX-ACCESS		read-write
		STATUS			current
		DESCRIPTION
				"TYPE: - Editstring
				 PAGE: - Audio- Emb.Names
					Embed 7  cmdID= 37532  "
		::= { iqmux43CmdEntry 37532 }


	iqmux43EmbedNamesEmbeddedOP7R OBJECT-TYPE
		SYNTAX		RollCallString
		MAX-ACCESS		read-write
		STATUS			current
		DESCRIPTION
				"TYPE: - Editstring
				 PAGE: - Audio- Emb.Names
					Embed 7-R  cmdID= 37533  "
		::= { iqmux43CmdEntry 37533 }


	iqmux43EmbedNamesEmbeddedOP8 OBJECT-TYPE
		SYNTAX		RollCallString
		MAX-ACCESS		read-write
		STATUS			current
		DESCRIPTION
				"TYPE: - Editstring
				 PAGE: - Audio- Emb.Names
					Embed 8  cmdID= 37534  "
		::= { iqmux43CmdEntry 37534 }


	iqmux43EmbedNamesEmbeddedOP8R OBJECT-TYPE
		SYNTAX		RollCallString
		MAX-ACCESS		read-write
		STATUS			current
		DESCRIPTION
				"TYPE: - Editstring
				 PAGE: - Audio- Emb.Names
					Embed 8-R  cmdID= 37535  "
		::= { iqmux43CmdEntry 37535 }


	iqmux43EmbedNamesIPStereoDisemb1 OBJECT-TYPE
		SYNTAX		INTEGER { disable(0), enable(1) }
		MAX-ACCESS		read-write
		STATUS			current
		DESCRIPTION
				"TYPE: - Checkbox
				 PAGE: - Audio- Emb.Names
					Disemb 1  cmdID= 37400 "
		::= { iqmux43CmdEntry 37400 }


	iqmux43EmbedNamesIPStereoDisemb2 OBJECT-TYPE
		SYNTAX		INTEGER { disable(0), enable(1) }
		MAX-ACCESS		read-write
		STATUS			current
		DESCRIPTION
				"TYPE: - Checkbox
				 PAGE: - Audio- Emb.Names
					Disemb 2  cmdID= 37401 "
		::= { iqmux43CmdEntry 37401 }


	iqmux43EmbedNamesIPStereoDisemb3 OBJECT-TYPE
		SYNTAX		INTEGER { disable(0), enable(1) }
		MAX-ACCESS		read-write
		STATUS			current
		DESCRIPTION
				"TYPE: - Checkbox
				 PAGE: - Audio- Emb.Names
					Disemb 3  cmdID= 37402 "
		::= { iqmux43CmdEntry 37402 }


	iqmux43EmbedNamesIPStereoDisemb4 OBJECT-TYPE
		SYNTAX		INTEGER { disable(0), enable(1) }
		MAX-ACCESS		read-write
		STATUS			current
		DESCRIPTION
				"TYPE: - Checkbox
				 PAGE: - Audio- Emb.Names
					Disemb 4  cmdID= 37403 "
		::= { iqmux43CmdEntry 37403 }


	iqmux43EmbedNamesIPStereoDisemb5 OBJECT-TYPE
		SYNTAX		INTEGER { disable(0), enable(1) }
		MAX-ACCESS		read-write
		STATUS			current
		DESCRIPTION
				"TYPE: - Checkbox
				 PAGE: - Audio- Emb.Names
					Disemb 5  cmdID= 37404 "
		::= { iqmux43CmdEntry 37404 }


	iqmux43EmbedNamesIPStereoDisemb6 OBJECT-TYPE
		SYNTAX		INTEGER { disable(0), enable(1) }
		MAX-ACCESS		read-write
		STATUS			current
		DESCRIPTION
				"TYPE: - Checkbox
				 PAGE: - Audio- Emb.Names
					Disemb 6  cmdID= 37405 "
		::= { iqmux43CmdEntry 37405 }


	iqmux43EmbedNamesIPStereoDisemb7 OBJECT-TYPE
		SYNTAX		INTEGER { disable(0), enable(1) }
		MAX-ACCESS		read-write
		STATUS			current
		DESCRIPTION
				"TYPE: - Checkbox
				 PAGE: - Audio- Emb.Names
					Disemb 7  cmdID= 37406 "
		::= { iqmux43CmdEntry 37406 }


	iqmux43EmbedNamesIPStereoDisemb8 OBJECT-TYPE
		SYNTAX		INTEGER { disable(0), enable(1) }
		MAX-ACCESS		read-write
		STATUS			current
		DESCRIPTION
				"TYPE: - Checkbox
				 PAGE: - Audio- Emb.Names
					Disemb 8  cmdID= 37407 "
		::= { iqmux43CmdEntry 37407 }


	iqmux43EmbedNamesOPStereoEmbed1 OBJECT-TYPE
		SYNTAX		INTEGER { disable(0), enable(1) }
		MAX-ACCESS		read-write
		STATUS			current
		DESCRIPTION
				"TYPE: - Checkbox
				 PAGE: - Audio- Emb.Names
					Embed 1  cmdID= 37410 "
		::= { iqmux43CmdEntry 37410 }


	iqmux43EmbedNamesOPStereoEmbed2 OBJECT-TYPE
		SYNTAX		INTEGER { disable(0), enable(1) }
		MAX-ACCESS		read-write
		STATUS			current
		DESCRIPTION
				"TYPE: - Checkbox
				 PAGE: - Audio- Emb.Names
					Embed 2  cmdID= 37411 "
		::= { iqmux43CmdEntry 37411 }


	iqmux43EmbedNamesOPStereoEmbed3 OBJECT-TYPE
		SYNTAX		INTEGER { disable(0), enable(1) }
		MAX-ACCESS		read-write
		STATUS			current
		DESCRIPTION
				"TYPE: - Checkbox
				 PAGE: - Audio- Emb.Names
					Embed 3  cmdID= 37412 "
		::= { iqmux43CmdEntry 37412 }


	iqmux43EmbedNamesOPStereoEmbed4 OBJECT-TYPE
		SYNTAX		INTEGER { disable(0), enable(1) }
		MAX-ACCESS		read-write
		STATUS			current
		DESCRIPTION
				"TYPE: - Checkbox
				 PAGE: - Audio- Emb.Names
					Embed 4  cmdID= 37413 "
		::= { iqmux43CmdEntry 37413 }


	iqmux43EmbedNamesOPStereoEmbed5 OBJECT-TYPE
		SYNTAX		INTEGER { disable(0), enable(1) }
		MAX-ACCESS		read-write
		STATUS			current
		DESCRIPTION
				"TYPE: - Checkbox
				 PAGE: - Audio- Emb.Names
					Embed 5  cmdID= 37414 "
		::= { iqmux43CmdEntry 37414 }


	iqmux43EmbedNamesOPStereoEmbed6 OBJECT-TYPE
		SYNTAX		INTEGER { disable(0), enable(1) }
		MAX-ACCESS		read-write
		STATUS			current
		DESCRIPTION
				"TYPE: - Checkbox
				 PAGE: - Audio- Emb.Names
					Embed 6  cmdID= 37415 "
		::= { iqmux43CmdEntry 37415 }


	iqmux43EmbedNamesOPStereoEmbed7 OBJECT-TYPE
		SYNTAX		INTEGER { disable(0), enable(1) }
		MAX-ACCESS		read-write
		STATUS			current
		DESCRIPTION
				"TYPE: - Checkbox
				 PAGE: - Audio- Emb.Names
					Embed 7  cmdID= 37416 "
		::= { iqmux43CmdEntry 37416 }


	iqmux43EmbedNamesOPStereoEmbed8 OBJECT-TYPE
		SYNTAX		INTEGER { disable(0), enable(1) }
		MAX-ACCESS		read-write
		STATUS			current
		DESCRIPTION
				"TYPE: - Checkbox
				 PAGE: - Audio- Emb.Names
					Embed 8  cmdID= 37417 "
		::= { iqmux43CmdEntry 37417 }


	iqmux43AudioMixNamesMix1 OBJECT-TYPE
		SYNTAX		RollCallString
		MAX-ACCESS		read-write
		STATUS			current
		DESCRIPTION
				"TYPE: - Editstring
				 PAGE: - Audio
					Mix 1  cmdID= 37810  "
		::= { iqmux43CmdEntry 37810 }


	iqmux43AudioMixNamesMix2 OBJECT-TYPE
		SYNTAX		RollCallString
		MAX-ACCESS		read-write
		STATUS			current
		DESCRIPTION
				"TYPE: - Editstring
				 PAGE: - Audio
					Mix 2  cmdID= 37811  "
		::= { iqmux43CmdEntry 37811 }


	iqmux43AudioMixNamesMix3 OBJECT-TYPE
		SYNTAX		RollCallString
		MAX-ACCESS		read-write
		STATUS			current
		DESCRIPTION
				"TYPE: - Editstring
				 PAGE: - Audio
					Mix 3  cmdID= 37812  "
		::= { iqmux43CmdEntry 37812 }


	iqmux43AudioMixNamesMix4 OBJECT-TYPE
		SYNTAX		RollCallString
		MAX-ACCESS		read-write
		STATUS			current
		DESCRIPTION
				"TYPE: - Editstring
				 PAGE: - Audio
					Mix 4  cmdID= 37813  "
		::= { iqmux43CmdEntry 37813 }


	iqmux43Mix1RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 1  cmdID= 37600
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37600 }


	iqmux43Mix1RoutingInvert1 OBJECT-TYPE
		SYNTAX		INTEGER { disable(0), enable(1) }
		MAX-ACCESS		read-write
		STATUS			current
		DESCRIPTION
				"TYPE: - Checkbox
				 PAGE: - Audio- Mix 1
					Invert 1  cmdID= 37720 "
		::= { iqmux43CmdEntry 37720 }


	iqmux43Mix1RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 2  cmdID= 37601
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37601 }


	iqmux43Mix1RoutingInvert2 OBJECT-TYPE
		SYNTAX		INTEGER { disable(0), enable(1) }
		MAX-ACCESS		read-write
		STATUS			current
		DESCRIPTION
				"TYPE: - Checkbox
				 PAGE: - Audio- Mix 1
					Invert 2  cmdID= 37721 "
		::= { iqmux43CmdEntry 37721 }


	iqmux43Mix1RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 3  cmdID= 37602
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37602 }


	iqmux43Mix1RoutingInvert3 OBJECT-TYPE
		SYNTAX		INTEGER { disable(0), enable(1) }
		MAX-ACCESS		read-write
		STATUS			current
		DESCRIPTION
				"TYPE: - Checkbox
				 PAGE: - Audio- Mix 1
					Invert 3  cmdID= 37722 "
		::= { iqmux43CmdEntry 37722 }


	iqmux43Mix1RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 4  cmdID= 37603
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37603 }


	iqmux43Mix1RoutingInvert4 OBJECT-TYPE
		SYNTAX		INTEGER { disable(0), enable(1) }
		MAX-ACCESS		read-write
		STATUS			current
		DESCRIPTION
				"TYPE: - Checkbox
				 PAGE: - Audio- Mix 1
					Invert 4  cmdID= 37723 "
		::= { iqmux43CmdEntry 37723 }


	iqmux43Mix1GainGain1 OBJECT-TYPE
		SYNTAX		INTEGER
		MAX-ACCESS		read-write
		STATUS			current
		DESCRIPTION
				"TYPE: - Number
				 PAGE: - Audio- Mix 1
					Gain 1  cmdID= 37640  min= -360  max= 120  step= 1  format= %0.1f dB  div_scale= 10
					Min = -36.0 dB  Max = 12.0 dB  Step = 0.1 dB "
		::= { iqmux43CmdEntry 37640 }


	iqmux43Mix1GainMute1 OBJECT-TYPE
		SYNTAX		INTEGER { disable(0), enable(1) }
		MAX-ACCESS		read-write
		STATUS			current
		DESCRIPTION
				"TYPE: - Checkbox
				 PAGE: - Audio- Mix 1
					Mute 1  cmdID= 37680 "
		::= { iqmux43CmdEntry 37680 }


	iqmux43Mix1GainGain2 OBJECT-TYPE
		SYNTAX		INTEGER
		MAX-ACCESS		read-write
		STATUS			current
		DESCRIPTION
				"TYPE: - Number
				 PAGE: - Audio- Mix 1
					Gain 2  cmdID= 37641  min= -360  max= 120  step= 1  format= %0.1f dB  div_scale= 10
					Min = -36.0 dB  Max = 12.0 dB  Step = 0.1 dB "
		::= { iqmux43CmdEntry 37641 }


	iqmux43Mix1GainMute2 OBJECT-TYPE
		SYNTAX		INTEGER { disable(0), enable(1) }
		MAX-ACCESS		read-write
		STATUS			current
		DESCRIPTION
				"TYPE: - Checkbox
				 PAGE: - Audio- Mix 1
					Mute 2  cmdID= 37681 "
		::= { iqmux43CmdEntry 37681 }


	iqmux43Mix1GainGain3 OBJECT-TYPE
		SYNTAX		INTEGER
		MAX-ACCESS		read-write
		STATUS			current
		DESCRIPTION
				"TYPE: - Number
				 PAGE: - Audio- Mix 1
					Gain 3  cmdID= 37642  min= -360  max= 120  step= 1  format= %0.1f dB  div_scale= 10
					Min = -36.0 dB  Max = 12.0 dB  Step = 0.1 dB "
		::= { iqmux43CmdEntry 37642 }


	iqmux43Mix1GainMute3 OBJECT-TYPE
		SYNTAX		INTEGER { disable(0), enable(1) }
		MAX-ACCESS		read-write
		STATUS			current
		DESCRIPTION
				"TYPE: - Checkbox
				 PAGE: - Audio- Mix 1
					Mute 3  cmdID= 37682 "
		::= { iqmux43CmdEntry 37682 }


	iqmux43Mix1GainGain4 OBJECT-TYPE
		SYNTAX		INTEGER
		MAX-ACCESS		read-write
		STATUS			current
		DESCRIPTION
				"TYPE: - Number
				 PAGE: - Audio- Mix 1
					Gain 4  cmdID= 37643  min= -360  max= 120  step= 1  format= %0.1f dB  div_scale= 10
					Min = -36.0 dB  Max = 12.0 dB  Step = 0.1 dB "
		::= { iqmux43CmdEntry 37643 }


	iqmux43Mix1GainMute4 OBJECT-TYPE
		SYNTAX		INTEGER { disable(0), enable(1) }
		MAX-ACCESS		read-write
		STATUS			current
		DESCRIPTION
				"TYPE: - Checkbox
				 PAGE: - Audio- Mix 1
					Mute 4  cmdID= 37683 "
		::= { iqmux43CmdEntry 37683 }


	iqmux43Mix1GainInp1Clip OBJECT-TYPE
		SYNTAX		RollCallString
		MAX-ACCESS		read-only
		STATUS			current
		DESCRIPTION
				"TYPE: - Display
				 PAGE: - Audio- Mix 1
					Inp1 Clip  cmdID= 37760  format=   "
		::= { iqmux43CmdEntry 37760 }


	iqmux43Mix1GainInp2Clip OBJECT-TYPE
		SYNTAX		RollCallString
		MAX-ACCESS		read-only
		STATUS			current
		DESCRIPTION
				"TYPE: - Display
				 PAGE: - Audio- Mix 1
					Inp2 Clip  cmdID= 37761  format=   "
		::= { iqmux43CmdEntry 37761 }


	iqmux43Mix1GainInp3Clip OBJECT-TYPE
		SYNTAX		RollCallString
		MAX-ACCESS		read-only
		STATUS			current
		DESCRIPTION
				"TYPE: - Display
				 PAGE: - Audio- Mix 1
					Inp3 Clip  cmdID= 37762  format=   "
		::= { iqmux43CmdEntry 37762 }


	iqmux43Mix1GainInp4Clip OBJECT-TYPE
		SYNTAX		RollCallString
		MAX-ACCESS		read-only
		STATUS			current
		DESCRIPTION
				"TYPE: - Display
				 PAGE: - Audio- Mix 1
					Inp4 Clip  cmdID= 37763  format=   "
		::= { iqmux43CmdEntry 37763 }


	iqmux43Mix1GainOPClip OBJECT-TYPE
		SYNTAX		RollCallString
		MAX-ACCESS		read-only
		STATUS			current
		DESCRIPTION
				"TYPE: - Display
				 PAGE: - Audio- Mix 1
					O/P Clip  cmdID= 37800  format=   "
		::= { iqmux43CmdEntry 37800 }


	iqmux43Mix2RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 1  cmdID= 37604
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37604 }


	iqmux43Mix2RoutingInvert1 OBJECT-TYPE
		SYNTAX		INTEGER { disable(0), enable(1) }
		MAX-ACCESS		read-write
		STATUS			current
		DESCRIPTION
				"TYPE: - Checkbox
				 PAGE: - Audio- Mix 2
					Invert 1  cmdID= 37724 "
		::= { iqmux43CmdEntry 37724 }


	iqmux43Mix2RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 2  cmdID= 37605
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37605 }


	iqmux43Mix2RoutingInvert2 OBJECT-TYPE
		SYNTAX		INTEGER { disable(0), enable(1) }
		MAX-ACCESS		read-write
		STATUS			current
		DESCRIPTION
				"TYPE: - Checkbox
				 PAGE: - Audio- Mix 2
					Invert 2  cmdID= 37725 "
		::= { iqmux43CmdEntry 37725 }


	iqmux43Mix2RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 3  cmdID= 37606
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37606 }


	iqmux43Mix2RoutingInvert3 OBJECT-TYPE
		SYNTAX		INTEGER { disable(0), enable(1) }
		MAX-ACCESS		read-write
		STATUS			current
		DESCRIPTION
				"TYPE: - Checkbox
				 PAGE: - Audio- Mix 2
					Invert 3  cmdID= 37726 "
		::= { iqmux43CmdEntry 37726 }


	iqmux43Mix2RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 4  cmdID= 37607
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37607 }


	iqmux43Mix2RoutingInvert4 OBJECT-TYPE
		SYNTAX		INTEGER { disable(0), enable(1) }
		MAX-ACCESS		read-write
		STATUS			current
		DESCRIPTION
				"TYPE: - Checkbox
				 PAGE: - Audio- Mix 2
					Invert 4  cmdID= 37727 "
		::= { iqmux43CmdEntry 37727 }


	iqmux43Mix2GainGain1 OBJECT-TYPE
		SYNTAX		INTEGER
		MAX-ACCESS		read-write
		STATUS			current
		DESCRIPTION
				"TYPE: - Number
				 PAGE: - Audio- Mix 2
					Gain 1  cmdID= 37644  min= -360  max= 120  step= 1  format= %0.1f dB  div_scale= 10
					Min = -36.0 dB  Max = 12.0 dB  Step = 0.1 dB "
		::= { iqmux43CmdEntry 37644 }


	iqmux43Mix2GainMute1 OBJECT-TYPE
		SYNTAX		INTEGER { disable(0), enable(1) }
		MAX-ACCESS		read-write
		STATUS			current
		DESCRIPTION
				"TYPE: - Checkbox
				 PAGE: - Audio- Mix 2
					Mute 1  cmdID= 37684 "
		::= { iqmux43CmdEntry 37684 }


	iqmux43Mix2GainGain2 OBJECT-TYPE
		SYNTAX		INTEGER
		MAX-ACCESS		read-write
		STATUS			current
		DESCRIPTION
				"TYPE: - Number
				 PAGE: - Audio- Mix 2
					Gain 2  cmdID= 37645  min= -360  max= 120  step= 1  format= %0.1f dB  div_scale= 10
					Min = -36.0 dB  Max = 12.0 dB  Step = 0.1 dB "
		::= { iqmux43CmdEntry 37645 }


	iqmux43Mix2GainMute2 OBJECT-TYPE
		SYNTAX		INTEGER { disable(0), enable(1) }
		MAX-ACCESS		read-write
		STATUS			current
		DESCRIPTION
				"TYPE: - Checkbox
				 PAGE: - Audio- Mix 2
					Mute 2  cmdID= 37685 "
		::= { iqmux43CmdEntry 37685 }


	iqmux43Mix2GainGain3 OBJECT-TYPE
		SYNTAX		INTEGER
		MAX-ACCESS		read-write
		STATUS			current
		DESCRIPTION
				"TYPE: - Number
				 PAGE: - Audio- Mix 2
					Gain 3  cmdID= 37646  min= -360  max= 120  step= 1  format= %0.1f dB  div_scale= 10
					Min = -36.0 dB  Max = 12.0 dB  Step = 0.1 dB "
		::= { iqmux43CmdEntry 37646 }


	iqmux43Mix2GainMute3 OBJECT-TYPE
		SYNTAX		INTEGER { disable(0), enable(1) }
		MAX-ACCESS		read-write
		STATUS			current
		DESCRIPTION
				"TYPE: - Checkbox
				 PAGE: - Audio- Mix 2
					Mute 3  cmdID= 37686 "
		::= { iqmux43CmdEntry 37686 }


	iqmux43Mix2GainGain4 OBJECT-TYPE
		SYNTAX		INTEGER
		MAX-ACCESS		read-write
		STATUS			current
		DESCRIPTION
				"TYPE: - Number
				 PAGE: - Audio- Mix 2
					Gain 4  cmdID= 37647  min= -360  max= 120  step= 1  format= %0.1f dB  div_scale= 10
					Min = -36.0 dB  Max = 12.0 dB  Step = 0.1 dB "
		::= { iqmux43CmdEntry 37647 }


	iqmux43Mix2GainMute4 OBJECT-TYPE
		SYNTAX		INTEGER { disable(0), enable(1) }
		MAX-ACCESS		read-write
		STATUS			current
		DESCRIPTION
				"TYPE: - Checkbox
				 PAGE: - Audio- Mix 2
					Mute 4  cmdID= 37687 "
		::= { iqmux43CmdEntry 37687 }


	iqmux43Mix2GainInp1Clip OBJECT-TYPE
		SYNTAX		RollCallString
		MAX-ACCESS		read-only
		STATUS			current
		DESCRIPTION
				"TYPE: - Display
				 PAGE: - Audio- Mix 2
					Inp1 Clip  cmdID= 37764  format=   "
		::= { iqmux43CmdEntry 37764 }


	iqmux43Mix2GainInp2Clip OBJECT-TYPE
		SYNTAX		RollCallString
		MAX-ACCESS		read-only
		STATUS			current
		DESCRIPTION
				"TYPE: - Display
				 PAGE: - Audio- Mix 2
					Inp2 Clip  cmdID= 37765  format=   "
		::= { iqmux43CmdEntry 37765 }


	iqmux43Mix2GainInp3Clip OBJECT-TYPE
		SYNTAX		RollCallString
		MAX-ACCESS		read-only
		STATUS			current
		DESCRIPTION
				"TYPE: - Display
				 PAGE: - Audio- Mix 2
					Inp3 Clip  cmdID= 37766  format=   "
		::= { iqmux43CmdEntry 37766 }


	iqmux43Mix2GainInp4Clip OBJECT-TYPE
		SYNTAX		RollCallString
		MAX-ACCESS		read-only
		STATUS			current
		DESCRIPTION
				"TYPE: - Display
				 PAGE: - Audio- Mix 2
					Inp4 Clip  cmdID= 37767  format=   "
		::= { iqmux43CmdEntry 37767 }


	iqmux43Mix2GainOPClip OBJECT-TYPE
		SYNTAX		RollCallString
		MAX-ACCESS		read-only
		STATUS			current
		DESCRIPTION
				"TYPE: - Display
				 PAGE: - Audio- Mix 2
					O/P Clip  cmdID= 37801  format=   "
		::= { iqmux43CmdEntry 37801 }


	iqmux43Mix3RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 1  cmdID= 37608
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37608 }


	iqmux43Mix3RoutingInvert1 OBJECT-TYPE
		SYNTAX		INTEGER { disable(0), enable(1) }
		MAX-ACCESS		read-write
		STATUS			current
		DESCRIPTION
				"TYPE: - Checkbox
				 PAGE: - Audio- Mix 3
					Invert 1  cmdID= 37728 "
		::= { iqmux43CmdEntry 37728 }


	iqmux43Mix3RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 2  cmdID= 37609
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37609 }


	iqmux43Mix3RoutingInvert2 OBJECT-TYPE
		SYNTAX		INTEGER { disable(0), enable(1) }
		MAX-ACCESS		read-write
		STATUS			current
		DESCRIPTION
				"TYPE: - Checkbox
				 PAGE: - Audio- Mix 3
					Invert 2  cmdID= 37729 "
		::= { iqmux43CmdEntry 37729 }


	iqmux43Mix3RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 3  cmdID= 37610
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37610 }


	iqmux43Mix3RoutingInvert3 OBJECT-TYPE
		SYNTAX		INTEGER { disable(0), enable(1) }
		MAX-ACCESS		read-write
		STATUS			current
		DESCRIPTION
				"TYPE: - Checkbox
				 PAGE: - Audio- Mix 3
					Invert 3  cmdID= 37730 "
		::= { iqmux43CmdEntry 37730 }


	iqmux43Mix3RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 4  cmdID= 37611
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37611 }


	iqmux43Mix3RoutingInvert4 OBJECT-TYPE
		SYNTAX		INTEGER { disable(0), enable(1) }
		MAX-ACCESS		read-write
		STATUS			current
		DESCRIPTION
				"TYPE: - Checkbox
				 PAGE: - Audio- Mix 3
					Invert 4  cmdID= 37731 "
		::= { iqmux43CmdEntry 37731 }


	iqmux43Mix3GainGain1 OBJECT-TYPE
		SYNTAX		INTEGER
		MAX-ACCESS		read-write
		STATUS			current
		DESCRIPTION
				"TYPE: - Number
				 PAGE: - Audio- Mix 3
					Gain 1  cmdID= 37648  min= -360  max= 120  step= 1  format= %0.1f dB  div_scale= 10
					Min = -36.0 dB  Max = 12.0 dB  Step = 0.1 dB "
		::= { iqmux43CmdEntry 37648 }


	iqmux43Mix3GainMute1 OBJECT-TYPE
		SYNTAX		INTEGER { disable(0), enable(1) }
		MAX-ACCESS		read-write
		STATUS			current
		DESCRIPTION
				"TYPE: - Checkbox
				 PAGE: - Audio- Mix 3
					Mute 1  cmdID= 37688 "
		::= { iqmux43CmdEntry 37688 }


	iqmux43Mix3GainGain2 OBJECT-TYPE
		SYNTAX		INTEGER
		MAX-ACCESS		read-write
		STATUS			current
		DESCRIPTION
				"TYPE: - Number
				 PAGE: - Audio- Mix 3
					Gain 2  cmdID= 37649  min= -360  max= 120  step= 1  format= %0.1f dB  div_scale= 10
					Min = -36.0 dB  Max = 12.0 dB  Step = 0.1 dB "
		::= { iqmux43CmdEntry 37649 }


	iqmux43Mix3GainMute2 OBJECT-TYPE
		SYNTAX		INTEGER { disable(0), enable(1) }
		MAX-ACCESS		read-write
		STATUS			current
		DESCRIPTION
				"TYPE: - Checkbox
				 PAGE: - Audio- Mix 3
					Mute 2  cmdID= 37689 "
		::= { iqmux43CmdEntry 37689 }


	iqmux43Mix3GainGain3 OBJECT-TYPE
		SYNTAX		INTEGER
		MAX-ACCESS		read-write
		STATUS			current
		DESCRIPTION
				"TYPE: - Number
				 PAGE: - Audio- Mix 3
					Gain 3  cmdID= 37650  min= -360  max= 120  step= 1  format= %0.1f dB  div_scale= 10
					Min = -36.0 dB  Max = 12.0 dB  Step = 0.1 dB "
		::= { iqmux43CmdEntry 37650 }


	iqmux43Mix3GainMute3 OBJECT-TYPE
		SYNTAX		INTEGER { disable(0), enable(1) }
		MAX-ACCESS		read-write
		STATUS			current
		DESCRIPTION
				"TYPE: - Checkbox
				 PAGE: - Audio- Mix 3
					Mute 3  cmdID= 37690 "
		::= { iqmux43CmdEntry 37690 }


	iqmux43Mix3GainGain4 OBJECT-TYPE
		SYNTAX		INTEGER
		MAX-ACCESS		read-write
		STATUS			current
		DESCRIPTION
				"TYPE: - Number
				 PAGE: - Audio- Mix 3
					Gain 4  cmdID= 37651  min= -360  max= 120  step= 1  format= %0.1f dB  div_scale= 10
					Min = -36.0 dB  Max = 12.0 dB  Step = 0.1 dB "
		::= { iqmux43CmdEntry 37651 }


	iqmux43Mix3GainMute4 OBJECT-TYPE
		SYNTAX		INTEGER { disable(0), enable(1) }
		MAX-ACCESS		read-write
		STATUS			current
		DESCRIPTION
				"TYPE: - Checkbox
				 PAGE: - Audio- Mix 3
					Mute 4  cmdID= 37691 "
		::= { iqmux43CmdEntry 37691 }


	iqmux43Mix3GainInp1Clip OBJECT-TYPE
		SYNTAX		RollCallString
		MAX-ACCESS		read-only
		STATUS			current
		DESCRIPTION
				"TYPE: - Display
				 PAGE: - Audio- Mix 3
					Inp1 Clip  cmdID= 37768  format=   "
		::= { iqmux43CmdEntry 37768 }


	iqmux43Mix3GainInp2Clip OBJECT-TYPE
		SYNTAX		RollCallString
		MAX-ACCESS		read-only
		STATUS			current
		DESCRIPTION
				"TYPE: - Display
				 PAGE: - Audio- Mix 3
					Inp2 Clip  cmdID= 37769  format=   "
		::= { iqmux43CmdEntry 37769 }


	iqmux43Mix3GainInp3Clip OBJECT-TYPE
		SYNTAX		RollCallString
		MAX-ACCESS		read-only
		STATUS			current
		DESCRIPTION
				"TYPE: - Display
				 PAGE: - Audio- Mix 3
					Inp3 Clip  cmdID= 37770  format=   "
		::= { iqmux43CmdEntry 37770 }


	iqmux43Mix3GainInp4Clip OBJECT-TYPE
		SYNTAX		RollCallString
		MAX-ACCESS		read-only
		STATUS			current
		DESCRIPTION
				"TYPE: - Display
				 PAGE: - Audio- Mix 3
					Inp4 Clip  cmdID= 37771  format=   "
		::= { iqmux43CmdEntry 37771 }


	iqmux43Mix3GainOPClip OBJECT-TYPE
		SYNTAX		RollCallString
		MAX-ACCESS		read-only
		STATUS			current
		DESCRIPTION
				"TYPE: - Display
				 PAGE: - Audio- Mix 3
					O/P Clip  cmdID= 37802  format=   "
		::= { iqmux43CmdEntry 37802 }


	iqmux43Mix4RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 1  cmdID= 37612
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37612 }


	iqmux43Mix4RoutingInvert1 OBJECT-TYPE
		SYNTAX		INTEGER { disable(0), enable(1) }
		MAX-ACCESS		read-write
		STATUS			current
		DESCRIPTION
				"TYPE: - Checkbox
				 PAGE: - Audio- Mix 4
					Invert 1  cmdID= 37732 "
		::= { iqmux43CmdEntry 37732 }


	iqmux43Mix4RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 2  cmdID= 37613
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37613 }


	iqmux43Mix4RoutingInvert2 OBJECT-TYPE
		SYNTAX		INTEGER { disable(0), enable(1) }
		MAX-ACCESS		read-write
		STATUS			current
		DESCRIPTION
				"TYPE: - Checkbox
				 PAGE: - Audio- Mix 4
					Invert 2  cmdID= 37733 "
		::= { iqmux43CmdEntry 37733 }


	iqmux43Mix4RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 3  cmdID= 37614
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37614 }


	iqmux43Mix4RoutingInvert3 OBJECT-TYPE
		SYNTAX		INTEGER { disable(0), enable(1) }
		MAX-ACCESS		read-write
		STATUS			current
		DESCRIPTION
				"TYPE: - Checkbox
				 PAGE: - Audio- Mix 4
					Invert 3  cmdID= 37734 "
		::= { iqmux43CmdEntry 37734 }


	iqmux43Mix4RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 4  cmdID= 37615
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 37615 }


	iqmux43Mix4RoutingInvert4 OBJECT-TYPE
		SYNTAX		INTEGER { disable(0), enable(1) }
		MAX-ACCESS		read-write
		STATUS			current
		DESCRIPTION
				"TYPE: - Checkbox
				 PAGE: - Audio- Mix 4
					Invert 4  cmdID= 37735 "
		::= { iqmux43CmdEntry 37735 }


	iqmux43Mix4GainGain1 OBJECT-TYPE
		SYNTAX		INTEGER
		MAX-ACCESS		read-write
		STATUS			current
		DESCRIPTION
				"TYPE: - Number
				 PAGE: - Audio- Mix 4
					Gain 1  cmdID= 37652  min= -360  max= 120  step= 1  format= %0.1f dB  div_scale= 10
					Min = -36.0 dB  Max = 12.0 dB  Step = 0.1 dB "
		::= { iqmux43CmdEntry 37652 }


	iqmux43Mix4GainMute1 OBJECT-TYPE
		SYNTAX		INTEGER { disable(0), enable(1) }
		MAX-ACCESS		read-write
		STATUS			current
		DESCRIPTION
				"TYPE: - Checkbox
				 PAGE: - Audio- Mix 4
					Mute 1  cmdID= 37692 "
		::= { iqmux43CmdEntry 37692 }


	iqmux43Mix4GainGain2 OBJECT-TYPE
		SYNTAX		INTEGER
		MAX-ACCESS		read-write
		STATUS			current
		DESCRIPTION
				"TYPE: - Number
				 PAGE: - Audio- Mix 4
					Gain 2  cmdID= 37653  min= -360  max= 120  step= 1  format= %0.1f dB  div_scale= 10
					Min = -36.0 dB  Max = 12.0 dB  Step = 0.1 dB "
		::= { iqmux43CmdEntry 37653 }


	iqmux43Mix4GainMute2 OBJECT-TYPE
		SYNTAX		INTEGER { disable(0), enable(1) }
		MAX-ACCESS		read-write
		STATUS			current
		DESCRIPTION
				"TYPE: - Checkbox
				 PAGE: - Audio- Mix 4
					Mute 2  cmdID= 37693 "
		::= { iqmux43CmdEntry 37693 }


	iqmux43Mix4GainGain3 OBJECT-TYPE
		SYNTAX		INTEGER
		MAX-ACCESS		read-write
		STATUS			current
		DESCRIPTION
				"TYPE: - Number
				 PAGE: - Audio- Mix 4
					Gain 3  cmdID= 37654  min= -360  max= 120  step= 1  format= %0.1f dB  div_scale= 10
					Min = -36.0 dB  Max = 12.0 dB  Step = 0.1 dB "
		::= { iqmux43CmdEntry 37654 }


	iqmux43Mix4GainMute3 OBJECT-TYPE
		SYNTAX		INTEGER { disable(0), enable(1) }
		MAX-ACCESS		read-write
		STATUS			current
		DESCRIPTION
				"TYPE: - Checkbox
				 PAGE: - Audio- Mix 4
					Mute 3  cmdID= 37694 "
		::= { iqmux43CmdEntry 37694 }


	iqmux43Mix4GainGain4 OBJECT-TYPE
		SYNTAX		INTEGER
		MAX-ACCESS		read-write
		STATUS			current
		DESCRIPTION
				"TYPE: - Number
				 PAGE: - Audio- Mix 4
					Gain 4  cmdID= 37655  min= -360  max= 120  step= 1  format= %0.1f dB  div_scale= 10
					Min = -36.0 dB  Max = 12.0 dB  Step = 0.1 dB "
		::= { iqmux43CmdEntry 37655 }


	iqmux43Mix4GainMute4 OBJECT-TYPE
		SYNTAX		INTEGER { disable(0), enable(1) }
		MAX-ACCESS		read-write
		STATUS			current
		DESCRIPTION
				"TYPE: - Checkbox
				 PAGE: - Audio- Mix 4
					Mute 4  cmdID= 37695 "
		::= { iqmux43CmdEntry 37695 }


	iqmux43Mix4GainInp1Clip OBJECT-TYPE
		SYNTAX		RollCallString
		MAX-ACCESS		read-only
		STATUS			current
		DESCRIPTION
				"TYPE: - Display
				 PAGE: - Audio- Mix 4
					Inp1 Clip  cmdID= 37772  format=   "
		::= { iqmux43CmdEntry 37772 }


	iqmux43Mix4GainInp2Clip OBJECT-TYPE
		SYNTAX		RollCallString
		MAX-ACCESS		read-only
		STATUS			current
		DESCRIPTION
				"TYPE: - Display
				 PAGE: - Audio- Mix 4
					Inp2 Clip  cmdID= 37773  format=   "
		::= { iqmux43CmdEntry 37773 }


	iqmux43Mix4GainInp3Clip OBJECT-TYPE
		SYNTAX		RollCallString
		MAX-ACCESS		read-only
		STATUS			current
		DESCRIPTION
				"TYPE: - Display
				 PAGE: - Audio- Mix 4
					Inp3 Clip  cmdID= 37774  format=   "
		::= { iqmux43CmdEntry 37774 }


	iqmux43Mix4GainInp4Clip OBJECT-TYPE
		SYNTAX		RollCallString
		MAX-ACCESS		read-only
		STATUS			current
		DESCRIPTION
				"TYPE: - Display
				 PAGE: - Audio- Mix 4
					Inp4 Clip  cmdID= 37775  format=   "
		::= { iqmux43CmdEntry 37775 }


	iqmux43Mix4GainOPClip OBJECT-TYPE
		SYNTAX		RollCallString
		MAX-ACCESS		read-only
		STATUS			current
		DESCRIPTION
				"TYPE: - Display
				 PAGE: - Audio- Mix 4
					O/P Clip  cmdID= 37803  format=   "
		::= { iqmux43CmdEntry 37803 }


	iqmux43AESGainOut1AESOut1MuteL OBJECT-TYPE
		SYNTAX		INTEGER { disable(0), enable(1) }
		MAX-ACCESS		read-write
		STATUS			current
		DESCRIPTION
				"TYPE: - Checkbox
				 PAGE: - Audio- AES Ports- AES Gain
					AES Out 1 Mute L  cmdID= 38280 "
		::= { iqmux43CmdEntry 38280 }


	iqmux43AESGainOut1AESOut1MuteR OBJECT-TYPE
		SYNTAX		INTEGER { disable(0), enable(1) }
		MAX-ACCESS		read-write
		STATUS			current
		DESCRIPTION
				"TYPE: - Checkbox
				 PAGE: - Audio- AES Ports- AES Gain
					AES Out 1 Mute R  cmdID= 38281 "
		::= { iqmux43CmdEntry 38281 }


	iqmux43AESGainOut1AESOut1LGain OBJECT-TYPE
		SYNTAX		INTEGER
		MAX-ACCESS		read-write
		STATUS			current
		DESCRIPTION
				"TYPE: - Number
				 PAGE: - Audio- AES Ports- AES Gain
					AES Out 1 L Gain  cmdID= 38240  min= -661  max= 120  step= 1  format= %0.1f dB  div_scale= 10
					Min = -66.1 dB  Max = 12.0 dB  Step = 0.1 dB "
		::= { iqmux43CmdEntry 38240 }


	iqmux43AESGainOut1AESOut1RGain OBJECT-TYPE
		SYNTAX		INTEGER
		MAX-ACCESS		read-write
		STATUS			current
		DESCRIPTION
				"TYPE: - Number
				 PAGE: - Audio- AES Ports- AES Gain
					AES Out 1 R Gain  cmdID= 38241  min= -661  max= 120  step= 1  format= %0.1f dB  div_scale= 10
					Min = -66.1 dB  Max = 12.0 dB  Step = 0.1 dB "
		::= { iqmux43CmdEntry 38241 }


	iqmux43AESGainOut1Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38360 "
		::= { iqmux43CmdEntry 38360 }


	iqmux43AESGainOut1AESOut1InvertL OBJECT-TYPE
		SYNTAX		INTEGER { disable(0), enable(1) }
		MAX-ACCESS		read-write
		STATUS			current
		DESCRIPTION
				"TYPE: - Checkbox
				 PAGE: - Audio- AES Ports- AES Gain
					AES Out 1 Invert L  cmdID= 38320 "
		::= { iqmux43CmdEntry 38320 }


	iqmux43AESGainOut1AESOut1InvertR OBJECT-TYPE
		SYNTAX		INTEGER { disable(0), enable(1) }
		MAX-ACCESS		read-write
		STATUS			current
		DESCRIPTION
				"TYPE: - Checkbox
				 PAGE: - Audio- AES Ports- AES Gain
					AES Out 1 Invert R  cmdID= 38321 "
		::= { iqmux43CmdEntry 38321 }


	iqmux43AESGainOut1AESOut1LClip OBJECT-TYPE
		SYNTAX		RollCallString
		MAX-ACCESS		read-only
		STATUS			current
		DESCRIPTION
				"TYPE: - Display
				 PAGE: - Audio- AES Ports- AES Gain
					AES Out 1-L Clip  cmdID= 38520  format=   "
		::= { iqmux43CmdEntry 38520 }


	iqmux43AESGainOut1AESOut1RClip OBJECT-TYPE
		SYNTAX		RollCallString
		MAX-ACCESS		read-only
		STATUS			current
		DESCRIPTION
				"TYPE: - Display
				 PAGE: - Audio- AES Ports- AES Gain
					AES Out 1-R Clip  cmdID= 38521  format=   "
		::= { iqmux43CmdEntry 38521 }


	iqmux43AESGainOut2AESOut2MuteL OBJECT-TYPE
		SYNTAX		INTEGER { disable(0), enable(1) }
		MAX-ACCESS		read-write
		STATUS			current
		DESCRIPTION
				"TYPE: - Checkbox
				 PAGE: - Audio- AES Ports- AES Gain
					AES Out 2 Mute L  cmdID= 38282 "
		::= { iqmux43CmdEntry 38282 }


	iqmux43AESGainOut2AESOut2MuteR OBJECT-TYPE
		SYNTAX		INTEGER { disable(0), enable(1) }
		MAX-ACCESS		read-write
		STATUS			current
		DESCRIPTION
				"TYPE: - Checkbox
				 PAGE: - Audio- AES Ports- AES Gain
					AES Out 2 Mute R  cmdID= 38283 "
		::= { iqmux43CmdEntry 38283 }


	iqmux43AESGainOut2AESOut2LGain OBJECT-TYPE
		SYNTAX		INTEGER
		MAX-ACCESS		read-write
		STATUS			current
		DESCRIPTION
				"TYPE: - Number
				 PAGE: - Audio- AES Ports- AES Gain
					AES Out 2 L Gain  cmdID= 38242  min= -661  max= 120  step= 1  format= %0.1f dB  div_scale= 10
					Min = -66.1 dB  Max = 12.0 dB  Step = 0.1 dB "
		::= { iqmux43CmdEntry 38242 }


	iqmux43AESGainOut2AESOut2RGain OBJECT-TYPE
		SYNTAX		INTEGER
		MAX-ACCESS		read-write
		STATUS			current
		DESCRIPTION
				"TYPE: - Number
				 PAGE: - Audio- AES Ports- AES Gain
					AES Out 2 R Gain  cmdID= 38243  min= -661  max= 120  step= 1  format= %0.1f dB  div_scale= 10
					Min = -66.1 dB  Max = 12.0 dB  Step = 0.1 dB "
		::= { iqmux43CmdEntry 38243 }


	iqmux43AESGainOut2Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38361 "
		::= { iqmux43CmdEntry 38361 }


	iqmux43AESGainOut2AESOut2InvertL OBJECT-TYPE
		SYNTAX		INTEGER { disable(0), enable(1) }
		MAX-ACCESS		read-write
		STATUS			current
		DESCRIPTION
				"TYPE: - Checkbox
				 PAGE: - Audio- AES Ports- AES Gain
					AES Out 2 Invert L  cmdID= 38322 "
		::= { iqmux43CmdEntry 38322 }


	iqmux43AESGainOut2AESOut2InvertR OBJECT-TYPE
		SYNTAX		INTEGER { disable(0), enable(1) }
		MAX-ACCESS		read-write
		STATUS			current
		DESCRIPTION
				"TYPE: - Checkbox
				 PAGE: - Audio- AES Ports- AES Gain
					AES Out 2 Invert R  cmdID= 38323 "
		::= { iqmux43CmdEntry 38323 }


	iqmux43AESGainOut2AESOut2LClip OBJECT-TYPE
		SYNTAX		RollCallString
		MAX-ACCESS		read-only
		STATUS			current
		DESCRIPTION
				"TYPE: - Display
				 PAGE: - Audio- AES Ports- AES Gain
					AES Out 2-L Clip  cmdID= 38522  format=   "
		::= { iqmux43CmdEntry 38522 }


	iqmux43AESGainOut2AESOut2RClip OBJECT-TYPE
		SYNTAX		RollCallString
		MAX-ACCESS		read-only
		STATUS			current
		DESCRIPTION
				"TYPE: - Display
				 PAGE: - Audio- AES Ports- AES Gain
					AES Out 2-R Clip  cmdID= 38523  format=   "
		::= { iqmux43CmdEntry 38523 }


	iqmux43AESGainOut3AESOut3MuteL OBJECT-TYPE
		SYNTAX		INTEGER { disable(0), enable(1) }
		MAX-ACCESS		read-write
		STATUS			current
		DESCRIPTION
				"TYPE: - Checkbox
				 PAGE: - Audio- AES Ports- AES Gain
					AES Out 3 Mute L  cmdID= 38284 "
		::= { iqmux43CmdEntry 38284 }


	iqmux43AESGainOut3AESOut3MuteR OBJECT-TYPE
		SYNTAX		INTEGER { disable(0), enable(1) }
		MAX-ACCESS		read-write
		STATUS			current
		DESCRIPTION
				"TYPE: - Checkbox
				 PAGE: - Audio- AES Ports- AES Gain
					AES Out 3 Mute R  cmdID= 38285 "
		::= { iqmux43CmdEntry 38285 }


	iqmux43AESGainOut3AESOut3LGain OBJECT-TYPE
		SYNTAX		INTEGER
		MAX-ACCESS		read-write
		STATUS			current
		DESCRIPTION
				"TYPE: - Number
				 PAGE: - Audio- AES Ports- AES Gain
					AES Out 3 L Gain  cmdID= 38244  min= -661  max= 120  step= 1  format= %0.1f dB  div_scale= 10
					Min = -66.1 dB  Max = 12.0 dB  Step = 0.1 dB "
		::= { iqmux43CmdEntry 38244 }


	iqmux43AESGainOut3AESOut3RGain OBJECT-TYPE
		SYNTAX		INTEGER
		MAX-ACCESS		read-write
		STATUS			current
		DESCRIPTION
				"TYPE: - Number
				 PAGE: - Audio- AES Ports- AES Gain
					AES Out 3 R Gain  cmdID= 38245  min= -661  max= 120  step= 1  format= %0.1f dB  div_scale= 10
					Min = -66.1 dB  Max = 12.0 dB  Step = 0.1 dB "
		::= { iqmux43CmdEntry 38245 }


	iqmux43AESGainOut3Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38362 "
		::= { iqmux43CmdEntry 38362 }


	iqmux43AESGainOut3AESOut3InvertL OBJECT-TYPE
		SYNTAX		INTEGER { disable(0), enable(1) }
		MAX-ACCESS		read-write
		STATUS			current
		DESCRIPTION
				"TYPE: - Checkbox
				 PAGE: - Audio- AES Ports- AES Gain
					AES Out 3 Invert L  cmdID= 38324 "
		::= { iqmux43CmdEntry 38324 }


	iqmux43AESGainOut3AESOut3InvertR OBJECT-TYPE
		SYNTAX		INTEGER { disable(0), enable(1) }
		MAX-ACCESS		read-write
		STATUS			current
		DESCRIPTION
				"TYPE: - Checkbox
				 PAGE: - Audio- AES Ports- AES Gain
					AES Out 3 Invert R  cmdID= 38325 "
		::= { iqmux43CmdEntry 38325 }


	iqmux43AESGainOut3AESOut3LClip OBJECT-TYPE
		SYNTAX		RollCallString
		MAX-ACCESS		read-only
		STATUS			current
		DESCRIPTION
				"TYPE: - Display
				 PAGE: - Audio- AES Ports- AES Gain
					AES Out 3-L Clip  cmdID= 38524  format=   "
		::= { iqmux43CmdEntry 38524 }


	iqmux43AESGainOut3AESOut3RClip OBJECT-TYPE
		SYNTAX		RollCallString
		MAX-ACCESS		read-only
		STATUS			current
		DESCRIPTION
				"TYPE: - Display
				 PAGE: - Audio- AES Ports- AES Gain
					AES Out 3-R Clip  cmdID= 38525  format=   "
		::= { iqmux43CmdEntry 38525 }


	iqmux43AESGainOut4AESOut4MuteL OBJECT-TYPE
		SYNTAX		INTEGER { disable(0), enable(1) }
		MAX-ACCESS		read-write
		STATUS			current
		DESCRIPTION
				"TYPE: - Checkbox
				 PAGE: - Audio- AES Ports- AES Gain
					AES Out 4 Mute L  cmdID= 38286 "
		::= { iqmux43CmdEntry 38286 }


	iqmux43AESGainOut4AESOut4MuteR OBJECT-TYPE
		SYNTAX		INTEGER { disable(0), enable(1) }
		MAX-ACCESS		read-write
		STATUS			current
		DESCRIPTION
				"TYPE: - Checkbox
				 PAGE: - Audio- AES Ports- AES Gain
					AES Out 4 Mute R  cmdID= 38287 "
		::= { iqmux43CmdEntry 38287 }


	iqmux43AESGainOut4AESOut4LGain OBJECT-TYPE
		SYNTAX		INTEGER
		MAX-ACCESS		read-write
		STATUS			current
		DESCRIPTION
				"TYPE: - Number
				 PAGE: - Audio- AES Ports- AES Gain
					AES Out 4 L Gain  cmdID= 38246  min= -661  max= 120  step= 1  format= %0.1f dB  div_scale= 10
					Min = -66.1 dB  Max = 12.0 dB  Step = 0.1 dB "
		::= { iqmux43CmdEntry 38246 }


	iqmux43AESGainOut4AESOut4RGain OBJECT-TYPE
		SYNTAX		INTEGER
		MAX-ACCESS		read-write
		STATUS			current
		DESCRIPTION
				"TYPE: - Number
				 PAGE: - Audio- AES Ports- AES Gain
					AES Out 4 R Gain  cmdID= 38247  min= -661  max= 120  step= 1  format= %0.1f dB  div_scale= 10
					Min = -66.1 dB  Max = 12.0 dB  Step = 0.1 dB "
		::= { iqmux43CmdEntry 38247 }


	iqmux43AESGainOut4Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38363 "
		::= { iqmux43CmdEntry 38363 }


	iqmux43AESGainOut4AESOut4InvertL OBJECT-TYPE
		SYNTAX		INTEGER { disable(0), enable(1) }
		MAX-ACCESS		read-write
		STATUS			current
		DESCRIPTION
				"TYPE: - Checkbox
				 PAGE: - Audio- AES Ports- AES Gain
					AES Out 4 Invert L  cmdID= 38326 "
		::= { iqmux43CmdEntry 38326 }


	iqmux43AESGainOut4AESOut4InvertR OBJECT-TYPE
		SYNTAX		INTEGER { disable(0), enable(1) }
		MAX-ACCESS		read-write
		STATUS			current
		DESCRIPTION
				"TYPE: - Checkbox
				 PAGE: - Audio- AES Ports- AES Gain
					AES Out 4 Invert R  cmdID= 38327 "
		::= { iqmux43CmdEntry 38327 }


	iqmux43AESGainOut4AESOut4LClip OBJECT-TYPE
		SYNTAX		RollCallString
		MAX-ACCESS		read-only
		STATUS			current
		DESCRIPTION
				"TYPE: - Display
				 PAGE: - Audio- AES Ports- AES Gain
					AES Out 4-L Clip  cmdID= 38526  format=   "
		::= { iqmux43CmdEntry 38526 }


	iqmux43AESGainOut4AESOut4RClip OBJECT-TYPE
		SYNTAX		RollCallString
		MAX-ACCESS		read-only
		STATUS			current
		DESCRIPTION
				"TYPE: - Display
				 PAGE: - Audio- AES Ports- AES Gain
					AES Out 4-R Clip  cmdID= 38527  format=   "
		::= { iqmux43CmdEntry 38527 }


	iqmux43AESGainOut5AESOut5MuteL OBJECT-TYPE
		SYNTAX		INTEGER { disable(0), enable(1) }
		MAX-ACCESS		read-write
		STATUS			current
		DESCRIPTION
				"TYPE: - Checkbox
				 PAGE: - Audio- AES Ports- AES Gain
					AES Out 5 Mute L  cmdID= 38288 "
		::= { iqmux43CmdEntry 38288 }


	iqmux43AESGainOut5AESOut5MuteR OBJECT-TYPE
		SYNTAX		INTEGER { disable(0), enable(1) }
		MAX-ACCESS		read-write
		STATUS			current
		DESCRIPTION
				"TYPE: - Checkbox
				 PAGE: - Audio- AES Ports- AES Gain
					AES Out 5 Mute R  cmdID= 38289 "
		::= { iqmux43CmdEntry 38289 }


	iqmux43AESGainOut5AESOut5LGain OBJECT-TYPE
		SYNTAX		INTEGER
		MAX-ACCESS		read-write
		STATUS			current
		DESCRIPTION
				"TYPE: - Number
				 PAGE: - Audio- AES Ports- AES Gain
					AES Out 5 L Gain  cmdID= 38248  min= -661  max= 120  step= 1  format= %0.1f dB  div_scale= 10
					Min = -66.1 dB  Max = 12.0 dB  Step = 0.1 dB "
		::= { iqmux43CmdEntry 38248 }


	iqmux43AESGainOut5AESOut5RGain OBJECT-TYPE
		SYNTAX		INTEGER
		MAX-ACCESS		read-write
		STATUS			current
		DESCRIPTION
				"TYPE: - Number
				 PAGE: - Audio- AES Ports- AES Gain
					AES Out 5 R Gain  cmdID= 38249  min= -661  max= 120  step= 1  format= %0.1f dB  div_scale= 10
					Min = -66.1 dB  Max = 12.0 dB  Step = 0.1 dB "
		::= { iqmux43CmdEntry 38249 }


	iqmux43AESGainOut5Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38364 "
		::= { iqmux43CmdEntry 38364 }


	iqmux43AESGainOut5AESOut5InvertL OBJECT-TYPE
		SYNTAX		INTEGER { disable(0), enable(1) }
		MAX-ACCESS		read-write
		STATUS			current
		DESCRIPTION
				"TYPE: - Checkbox
				 PAGE: - Audio- AES Ports- AES Gain
					AES Out 5 Invert L  cmdID= 38328 "
		::= { iqmux43CmdEntry 38328 }


	iqmux43AESGainOut5AESOut5InvertR OBJECT-TYPE
		SYNTAX		INTEGER { disable(0), enable(1) }
		MAX-ACCESS		read-write
		STATUS			current
		DESCRIPTION
				"TYPE: - Checkbox
				 PAGE: - Audio- AES Ports- AES Gain
					AES Out 5 Invert R  cmdID= 38329 "
		::= { iqmux43CmdEntry 38329 }


	iqmux43AESGainOut5AESOut5LClip OBJECT-TYPE
		SYNTAX		RollCallString
		MAX-ACCESS		read-only
		STATUS			current
		DESCRIPTION
				"TYPE: - Display
				 PAGE: - Audio- AES Ports- AES Gain
					AES Out 5-L Clip  cmdID= 38528  format=   "
		::= { iqmux43CmdEntry 38528 }


	iqmux43AESGainOut5AESOut5RClip OBJECT-TYPE
		SYNTAX		RollCallString
		MAX-ACCESS		read-only
		STATUS			current
		DESCRIPTION
				"TYPE: - Display
				 PAGE: - Audio- AES Ports- AES Gain
					AES Out 5-R Clip  cmdID= 38529  format=   "
		::= { iqmux43CmdEntry 38529 }


	iqmux43AESGainOut6AESOut6MuteL OBJECT-TYPE
		SYNTAX		INTEGER { disable(0), enable(1) }
		MAX-ACCESS		read-write
		STATUS			current
		DESCRIPTION
				"TYPE: - Checkbox
				 PAGE: - Audio- AES Ports- AES Gain
					AES Out 6 Mute L  cmdID= 38290 "
		::= { iqmux43CmdEntry 38290 }


	iqmux43AESGainOut6AESOut6MuteR OBJECT-TYPE
		SYNTAX		INTEGER { disable(0), enable(1) }
		MAX-ACCESS		read-write
		STATUS			current
		DESCRIPTION
				"TYPE: - Checkbox
				 PAGE: - Audio- AES Ports- AES Gain
					AES Out 6 Mute R  cmdID= 38291 "
		::= { iqmux43CmdEntry 38291 }


	iqmux43AESGainOut6AESOut6LGain OBJECT-TYPE
		SYNTAX		INTEGER
		MAX-ACCESS		read-write
		STATUS			current
		DESCRIPTION
				"TYPE: - Number
				 PAGE: - Audio- AES Ports- AES Gain
					AES Out 6 L Gain  cmdID= 38250  min= -661  max= 120  step= 1  format= %0.1f dB  div_scale= 10
					Min = -66.1 dB  Max = 12.0 dB  Step = 0.1 dB "
		::= { iqmux43CmdEntry 38250 }


	iqmux43AESGainOut6AESOut6RGain OBJECT-TYPE
		SYNTAX		INTEGER
		MAX-ACCESS		read-write
		STATUS			current
		DESCRIPTION
				"TYPE: - Number
				 PAGE: - Audio- AES Ports- AES Gain
					AES Out 6 R Gain  cmdID= 38251  min= -661  max= 120  step= 1  format= %0.1f dB  div_scale= 10
					Min = -66.1 dB  Max = 12.0 dB  Step = 0.1 dB "
		::= { iqmux43CmdEntry 38251 }


	iqmux43AESGainOut6Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38365 "
		::= { iqmux43CmdEntry 38365 }


	iqmux43AESGainOut6AESOut6InvertL OBJECT-TYPE
		SYNTAX		INTEGER { disable(0), enable(1) }
		MAX-ACCESS		read-write
		STATUS			current
		DESCRIPTION
				"TYPE: - Checkbox
				 PAGE: - Audio- AES Ports- AES Gain
					AES Out 6 Invert L  cmdID= 38330 "
		::= { iqmux43CmdEntry 38330 }


	iqmux43AESGainOut6AESOut6InvertR OBJECT-TYPE
		SYNTAX		INTEGER { disable(0), enable(1) }
		MAX-ACCESS		read-write
		STATUS			current
		DESCRIPTION
				"TYPE: - Checkbox
				 PAGE: - Audio- AES Ports- AES Gain
					AES Out 6 Invert R  cmdID= 38331 "
		::= { iqmux43CmdEntry 38331 }


	iqmux43AESGainOut6AESOut6LClip OBJECT-TYPE
		SYNTAX		RollCallString
		MAX-ACCESS		read-only
		STATUS			current
		DESCRIPTION
				"TYPE: - Display
				 PAGE: - Audio- AES Ports- AES Gain
					AES Out 6-L Clip  cmdID= 38530  format=   "
		::= { iqmux43CmdEntry 38530 }


	iqmux43AESGainOut6AESOut6RClip OBJECT-TYPE
		SYNTAX		RollCallString
		MAX-ACCESS		read-only
		STATUS			current
		DESCRIPTION
				"TYPE: - Display
				 PAGE: - Audio- AES Ports- AES Gain
					AES Out 6-R Clip  cmdID= 38531  format=   "
		::= { iqmux43CmdEntry 38531 }


	iqmux43AESGainOut7AESOut7MuteL OBJECT-TYPE
		SYNTAX		INTEGER { disable(0), enable(1) }
		MAX-ACCESS		read-write
		STATUS			current
		DESCRIPTION
				"TYPE: - Checkbox
				 PAGE: - Audio- AES Ports- AES Gain
					AES Out 7 Mute L  cmdID= 38292 "
		::= { iqmux43CmdEntry 38292 }


	iqmux43AESGainOut7AESOut7MuteR OBJECT-TYPE
		SYNTAX		INTEGER { disable(0), enable(1) }
		MAX-ACCESS		read-write
		STATUS			current
		DESCRIPTION
				"TYPE: - Checkbox
				 PAGE: - Audio- AES Ports- AES Gain
					AES Out 7 Mute R  cmdID= 38293 "
		::= { iqmux43CmdEntry 38293 }


	iqmux43AESGainOut7AESOut7LGain OBJECT-TYPE
		SYNTAX		INTEGER
		MAX-ACCESS		read-write
		STATUS			current
		DESCRIPTION
				"TYPE: - Number
				 PAGE: - Audio- AES Ports- AES Gain
					AES Out 7 L Gain  cmdID= 38252  min= -661  max= 120  step= 1  format= %0.1f dB  div_scale= 10
					Min = -66.1 dB  Max = 12.0 dB  Step = 0.1 dB "
		::= { iqmux43CmdEntry 38252 }


	iqmux43AESGainOut7AESOut7RGain OBJECT-TYPE
		SYNTAX		INTEGER
		MAX-ACCESS		read-write
		STATUS			current
		DESCRIPTION
				"TYPE: - Number
				 PAGE: - Audio- AES Ports- AES Gain
					AES Out 7 R Gain  cmdID= 38253  min= -661  max= 120  step= 1  format= %0.1f dB  div_scale= 10
					Min = -66.1 dB  Max = 12.0 dB  Step = 0.1 dB "
		::= { iqmux43CmdEntry 38253 }


	iqmux43AESGainOut7Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38366 "
		::= { iqmux43CmdEntry 38366 }


	iqmux43AESGainOut7AESOut7InvertL OBJECT-TYPE
		SYNTAX		INTEGER { disable(0), enable(1) }
		MAX-ACCESS		read-write
		STATUS			current
		DESCRIPTION
				"TYPE: - Checkbox
				 PAGE: - Audio- AES Ports- AES Gain
					AES Out 7 Invert L  cmdID= 38332 "
		::= { iqmux43CmdEntry 38332 }


	iqmux43AESGainOut7AESOut7InvertR OBJECT-TYPE
		SYNTAX		INTEGER { disable(0), enable(1) }
		MAX-ACCESS		read-write
		STATUS			current
		DESCRIPTION
				"TYPE: - Checkbox
				 PAGE: - Audio- AES Ports- AES Gain
					AES Out 7 Invert R  cmdID= 38333 "
		::= { iqmux43CmdEntry 38333 }


	iqmux43AESGainOut7AESOut7LClip OBJECT-TYPE
		SYNTAX		RollCallString
		MAX-ACCESS		read-only
		STATUS			current
		DESCRIPTION
				"TYPE: - Display
				 PAGE: - Audio- AES Ports- AES Gain
					AES Out 7-L Clip  cmdID= 38532  format=   "
		::= { iqmux43CmdEntry 38532 }


	iqmux43AESGainOut7AESOut7RClip OBJECT-TYPE
		SYNTAX		RollCallString
		MAX-ACCESS		read-only
		STATUS			current
		DESCRIPTION
				"TYPE: - Display
				 PAGE: - Audio- AES Ports- AES Gain
					AES Out 7-R Clip  cmdID= 38533  format=   "
		::= { iqmux43CmdEntry 38533 }


	iqmux43AESGainOut8AESOut8MuteL OBJECT-TYPE
		SYNTAX		INTEGER { disable(0), enable(1) }
		MAX-ACCESS		read-write
		STATUS			current
		DESCRIPTION
				"TYPE: - Checkbox
				 PAGE: - Audio- AES Ports- AES Gain
					AES Out 8 Mute L  cmdID= 38294 "
		::= { iqmux43CmdEntry 38294 }


	iqmux43AESGainOut8AESOut8MuteR OBJECT-TYPE
		SYNTAX		INTEGER { disable(0), enable(1) }
		MAX-ACCESS		read-write
		STATUS			current
		DESCRIPTION
				"TYPE: - Checkbox
				 PAGE: - Audio- AES Ports- AES Gain
					AES Out 8 Mute R  cmdID= 38295 "
		::= { iqmux43CmdEntry 38295 }


	iqmux43AESGainOut8AESOut8LGain OBJECT-TYPE
		SYNTAX		INTEGER
		MAX-ACCESS		read-write
		STATUS			current
		DESCRIPTION
				"TYPE: - Number
				 PAGE: - Audio- AES Ports- AES Gain
					AES Out 8 L Gain  cmdID= 38254  min= -661  max= 120  step= 1  format= %0.1f dB  div_scale= 10
					Min = -66.1 dB  Max = 12.0 dB  Step = 0.1 dB "
		::= { iqmux43CmdEntry 38254 }


	iqmux43AESGainOut8AESOut8RGain OBJECT-TYPE
		SYNTAX		INTEGER
		MAX-ACCESS		read-write
		STATUS			current
		DESCRIPTION
				"TYPE: - Number
				 PAGE: - Audio- AES Ports- AES Gain
					AES Out 8 R Gain  cmdID= 38255  min= -661  max= 120  step= 1  format= %0.1f dB  div_scale= 10
					Min = -66.1 dB  Max = 12.0 dB  Step = 0.1 dB "
		::= { iqmux43CmdEntry 38255 }


	iqmux43AESGainOut8Stereo OBJECT-TYPE
		SYNTAX		INTEGER { disable(0), enable(1) }
		MAX-ACCESS		read-write
		STATUS			current
		DESCRIPTION
				"TYPE: - Checkbox
				 PAGE: - Audio- AES Ports- AES Gain
					Stereo  cmdID= 38367 "
		::= { iqmux43CmdEntry 38367 }


	iqmux43AESGainOut8AESOut8InvertL OBJECT-TYPE
		SYNTAX		INTEGER { disable(0), enable(1) }
		MAX-ACCESS		read-write
		STATUS			current
		DESCRIPTION
				"TYPE: - Checkbox
				 PAGE: - Audio- AES Ports- AES Gain
					AES Out 8 Invert L  cmdID= 38334 "
		::= { iqmux43CmdEntry 38334 }


	iqmux43AESGainOut8AESOut8InvertR OBJECT-TYPE
		SYNTAX		INTEGER { disable(0), enable(1) }
		MAX-ACCESS		read-write
		STATUS			current
		DESCRIPTION
				"TYPE: - Checkbox
				 PAGE: - Audio- AES Ports- AES Gain
					AES Out 8 Invert R  cmdID= 38335 "
		::= { iqmux43CmdEntry 38335 }


	iqmux43AESGainOut8AESOut8LClip OBJECT-TYPE
		SYNTAX		RollCallString
		MAX-ACCESS		read-only
		STATUS			current
		DESCRIPTION
				"TYPE: - Display
				 PAGE: - Audio- AES Ports- AES Gain
					AES Out 8-L Clip  cmdID= 38534  format=   "
		::= { iqmux43CmdEntry 38534 }


	iqmux43AESGainOut8AESOut8RClip OBJECT-TYPE
		SYNTAX		RollCallString
		MAX-ACCESS		read-only
		STATUS			current
		DESCRIPTION
				"TYPE: - Display
				 PAGE: - Audio- AES Ports- AES Gain
					AES Out 8-R Clip  cmdID= 38535  format=   "
		::= { iqmux43CmdEntry 38535 }


	iqmux43AESOut1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 1
					Left  cmdID= 38200
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38200 }


	iqmux43AESOut1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 1
					Right  cmdID= 38201
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38201 }


	iqmux43AESOut1LinkLRSelection OBJECT-TYPE
		SYNTAX		INTEGER { disable(0), enable(1) }
		MAX-ACCESS		read-write
		STATUS			current
		DESCRIPTION
				"TYPE: - Checkbox
				 PAGE: - Audio- AES Ports- AES Out 1
					Link L+R Selection  cmdID= 38380 "
		::= { iqmux43CmdEntry 38380 }


	iqmux43AESOut2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 2
					Left  cmdID= 38202
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38202 }


	iqmux43AESOut2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 2
					Right  cmdID= 38203
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38203 }


	iqmux43AESOut2LinkLRSelection OBJECT-TYPE
		SYNTAX		INTEGER { disable(0), enable(1) }
		MAX-ACCESS		read-write
		STATUS			current
		DESCRIPTION
				"TYPE: - Checkbox
				 PAGE: - Audio- AES Ports- AES Out 2
					Link L+R Selection  cmdID= 38381 "
		::= { iqmux43CmdEntry 38381 }


	iqmux43AESOut3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 3
					Left  cmdID= 38204
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38204 }


	iqmux43AESOut3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 3
					Right  cmdID= 38205
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38205 }


	iqmux43AESOut3LinkLRSelection OBJECT-TYPE
		SYNTAX		INTEGER { disable(0), enable(1) }
		MAX-ACCESS		read-write
		STATUS			current
		DESCRIPTION
				"TYPE: - Checkbox
				 PAGE: - Audio- AES Ports- AES Out 3
					Link L+R Selection  cmdID= 38382 "
		::= { iqmux43CmdEntry 38382 }


	iqmux43AESOut4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 4
					Left  cmdID= 38206
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38206 }


	iqmux43AESOut4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 4
					Right  cmdID= 38207
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38207 }


	iqmux43AESOut4LinkLRSelection OBJECT-TYPE
		SYNTAX		INTEGER { disable(0), enable(1) }
		MAX-ACCESS		read-write
		STATUS			current
		DESCRIPTION
				"TYPE: - Checkbox
				 PAGE: - Audio- AES Ports- AES Out 4
					Link L+R Selection  cmdID= 38383 "
		::= { iqmux43CmdEntry 38383 }


	iqmux43AESOut5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 5
					Left  cmdID= 38208
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38208 }


	iqmux43AESOut5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 5
					Right  cmdID= 38209
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38209 }


	iqmux43AESOut5LinkLRSelection OBJECT-TYPE
		SYNTAX		INTEGER { disable(0), enable(1) }
		MAX-ACCESS		read-write
		STATUS			current
		DESCRIPTION
				"TYPE: - Checkbox
				 PAGE: - Audio- AES Ports- AES Out 5
					Link L+R Selection  cmdID= 38384 "
		::= { iqmux43CmdEntry 38384 }


	iqmux43AESOut6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 6
					Left  cmdID= 38210
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38210 }


	iqmux43AESOut6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 6
					Right  cmdID= 38211
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38211 }


	iqmux43AESOut6LinkLRSelection OBJECT-TYPE
		SYNTAX		INTEGER { disable(0), enable(1) }
		MAX-ACCESS		read-write
		STATUS			current
		DESCRIPTION
				"TYPE: - Checkbox
				 PAGE: - Audio- AES Ports- AES Out 6
					Link L+R Selection  cmdID= 38385 "
		::= { iqmux43CmdEntry 38385 }


	iqmux43AESOut7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 7
					Left  cmdID= 38212
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38212 }


	iqmux43AESOut7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 7
					Right  cmdID= 38213
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38213 }


	iqmux43AESOut7LinkLRSelection OBJECT-TYPE
		SYNTAX		INTEGER { disable(0), enable(1) }
		MAX-ACCESS		read-write
		STATUS			current
		DESCRIPTION
				"TYPE: - Checkbox
				 PAGE: - Audio- AES Ports- AES Out 7
					Link L+R Selection  cmdID= 38386 "
		::= { iqmux43CmdEntry 38386 }


	iqmux43AESOut8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 8
					Left  cmdID= 38214
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38214 }


	iqmux43AESOut8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- AES Out 8
					Right  cmdID= 38215
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38215 }


	iqmux43AESOut8LinkLRSelection OBJECT-TYPE
		SYNTAX		INTEGER { disable(0), enable(1) }
		MAX-ACCESS		read-write
		STATUS			current
		DESCRIPTION
				"TYPE: - Checkbox
				 PAGE: - Audio- AES Ports- AES Out 8
					Link L+R Selection  cmdID= 38387 "
		::= { iqmux43CmdEntry 38387 }


	iqmux43AESOutMonitoropLeft OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- Monitor o/p
					Left  cmdID= 38641
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38641 }


	iqmux43AESOutMonitoropRight OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- AES Ports- Monitor o/p
					Right  cmdID= 38642
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqmux43CmdEntry 38642 }


	iqmux43AESOutMonitoropLinkLRSelection OBJECT-TYPE
		SYNTAX		INTEGER { disable(0), enable(1) }
		MAX-ACCESS		read-write
		STATUS			current
		DESCRIPTION
				"TYPE: - Checkbox
				 PAGE: - Audio- AES Ports- Monitor o/p
					Link L+R Selection  cmdID= 38640 "
		::= { iqmux43CmdEntry 38640 }


	iqmux43AESOutPortNamesAESPort1Stereo OBJECT-TYPE
		SYNTAX		INTEGER { disable(0), enable(1) }
		MAX-ACCESS		read-write
		STATUS			current
		DESCRIPTION
				"TYPE: - Checkbox
				 PAGE: - Audio- AES Ports- AES Port Names
					AES Port 1 Stereo  cmdID= 38448 "
		::= { iqmux43CmdEntry 38448 }


	iqmux43AESOutPortNamesAESPort1L OBJECT-TYPE
		SYNTAX		RollCallString
		MAX-ACCESS		read-write
		STATUS			current
		DESCRIPTION
				"TYPE: - Editstring
				 PAGE: - Audio- AES Ports- AES Port Names
					AES Port 1-L  cmdID= 38496  "
		::= { iqmux43CmdEntry 38496 }


	iqmux43AESOutPortNamesAESPort1R OBJECT-TYPE
		SYNTAX		RollCallString
		MAX-ACCESS		read-write
		STATUS			current
		DESCRIPTION
				"TYPE: - Editstring
				 PAGE: - Audio- AES Ports- AES Port Names
					AES Port 1-R  cmdID= 38497  "
		::= { iqmux43CmdEntry 38497 }


	iqmux43AESOutPortNamesAESPort2Stereo OBJECT-TYPE
		SYNTAX		INTEGER { disable(0), enable(1) }
		MAX-ACCESS		read-write
		STATUS			current
		DESCRIPTION
				"TYPE: - Checkbox
				 PAGE: - Audio- AES Ports- AES Port Names
					AES Port 2 Stereo  cmdID= 38449 "
		::= { iqmux43CmdEntry 38449 }


	iqmux43AESOutPortNamesAESPort2L OBJECT-TYPE
		SYNTAX		RollCallString
		MAX-ACCESS		read-write
		STATUS			current
		DESCRIPTION
				"TYPE: - Editstring
				 PAGE: - Audio- AES Ports- AES Port Names
					AES Port 2-L  cmdID= 38498  "
		::= { iqmux43CmdEntry 38498 }


	iqmux43AESOutPortNamesAESPort2R OBJECT-TYPE
		SYNTAX		RollCallString
		MAX-ACCESS		read-write
		STATUS			current
		DESCRIPTION
				"TYPE: - Editstring
				 PAGE: - Audio- AES Ports- AES Port Names
					AES Port 2-R  cmdID= 38499  "
		::= { iqmux43CmdEntry 38499 }


	iqmux43AESOutPortNamesAESPort3Stereo OBJECT-TYPE
		SYNTAX		INTEGER { disable(0), enable(1) }
		MAX-ACCESS		read-write
		STATUS			current
		DESCRIPTION
				"TYPE: - Checkbox
				 PAGE: - Audio- AES Ports- AES Port Names
					AES Port 3 Stereo  cmdID= 38450 "
		::= { iqmux43CmdEntry 38450 }


	iqmux43AESOutPortNamesAESPort3L OBJECT-TYPE
		SYNTAX		RollCallString
		MAX-ACCESS		read-write
		STATUS			current
		DESCRIPTION
				"TYPE: - Editstring
				 PAGE: - Audio- AES Ports- AES Port Names
					AES Port 3-L  cmdID= 38500  "
		::= { iqmux43CmdEntry 38500 }


	iqmux43AESOutPortNamesAESPort3R OBJECT-TYPE
		SYNTAX		RollCallString
		MAX-ACCESS		read-write
		STATUS			current
		DESCRIPTION
				"TYPE: - Editstring
				 PAGE: - Audio- AES Ports- AES Port Names
					AES Port 3-R  cmdID= 38501  "
		::= { iqmux43CmdEntry 38501 }


	iqmux43AESOutPortNamesAESPort4Stereo OBJECT-TYPE
		SYNTAX		INTEGER { disable(0), enable(1) }
		MAX-ACCESS		read-write
		STATUS			current
		DESCRIPTION
				"TYPE: - Checkbox
				 PAGE: - Audio- AES Ports- AES Port Names
					AES Port 4 Stereo  cmdID= 38451 "
		::= { iqmux43CmdEntry 38451 }


	iqmux43AESOutPortNamesAESPort4L OBJECT-TYPE
		SYNTAX		RollCallString
		MAX-ACCESS		read-write
		STATUS			current
		DESCRIPTION
				"TYPE: - Editstring
				 PAGE: - Audio- AES Ports- AES Port Names
					AES Port 4-L  cmdID= 38502  "
		::= { iqmux43CmdEntry 38502 }


	iqmux43AESOutPortNamesAESPort4R OBJECT-TYPE
		SYNTAX		RollCallString
		MAX-ACCESS		read-write
		STATUS			current
		DESCRIPTION
				"TYPE: - Editstring
				 PAGE: - Audio- AES Ports- AES Port Names
					AES Port 4-R  cmdID= 38503  "
		::= { iqmux43CmdEntry 38503 }


	iqmux43AESOutPortNamesAESPort5Stereo OBJECT-TYPE
		SYNTAX		INTEGER { disable(0), enable(1) }
		MAX-ACCESS		read-write
		STATUS			current
		DESCRIPTION
				"TYPE: - Checkbox
				 PAGE: - Audio- AES Ports- AES Port Names
					AES Port 5 Stereo  cmdID= 38452 "
		::= { iqmux43CmdEntry 38452 }


	iqmux43AESOutPortNamesAESPort5L OBJECT-TYPE
		SYNTAX		RollCallString
		MAX-ACCESS		read-write
		STATUS			current
		DESCRIPTION
				"TYPE: - Editstring
				 PAGE: - Audio- AES Ports- AES Port Names
					AES Port 5-L  cmdID= 38504  "
		::= { iqmux43CmdEntry 38504 }


	iqmux43AESOutPortNamesAESPort5R OBJECT-TYPE
		SYNTAX		RollCallString
		MAX-ACCESS		read-write
		STATUS			current
		DESCRIPTION
				"TYPE: - Editstring
				 PAGE: - Audio- AES Ports- AES Port Names
					AES Port 5-R  cmdID= 38505  "
		::= { iqmux43CmdEntry 38505 }


	iqmux43AESOutPortNamesAESPort6Stereo OBJECT-TYPE
		SYNTAX		INTEGER { disable(0), enable(1) }
		MAX-ACCESS		read-write
		STATUS			current
		DESCRIPTION
				"TYPE: - Checkbox
				 PAGE: - Audio- AES Ports- AES Port Names
					AES Port 6 Stereo  cmdID= 38453 "
		::= { iqmux43CmdEntry 38453 }


	iqmux43AESOutPortNamesAESPort6L OBJECT-TYPE
		SYNTAX		RollCallString
		MAX-ACCESS		read-write
		STATUS			current
		DESCRIPTION
				"TYPE: - Editstring
				 PAGE: - Audio- AES Ports- AES Port Names
					AES Port 6-L  cmdID= 38506  "
		::= { iqmux43CmdEntry 38506 }


	iqmux43AESOutPortNamesAESPort6R OBJECT-TYPE
		SYNTAX		RollCallString
		MAX-ACCESS		read-write
		STATUS			current
		DESCRIPTION
				"TYPE: - Editstring
				 PAGE: - Audio- AES Ports- AES Port Names
					AES Port 6-R  cmdID= 38507  "
		::= { iqmux43CmdEntry 38507 }


	iqmux43AESOutPortNamesAESPort7Stereo OBJECT-TYPE
		SYNTAX		INTEGER { disable(0), enable(1) }
		MAX-ACCESS		read-write
		STATUS			current
		DESCRIPTION
				"TYPE: - Checkbox
				 PAGE: - Audio- AES Ports- AES Port Names
					AES Port 7 Stereo  cmdID= 38454 "
		::= { iqmux43CmdEntry 38454 }


	iqmux43AESOutPortNamesAESPort7L OBJECT-TYPE
		SYNTAX		RollCallString
		MAX-ACCESS		read-write
		STATUS			current
		DESCRIPTION
				"TYPE: - Editstring
				 PAGE: - Audio- AES Ports- AES Port Names
					AES Port 7-L  cmdID= 38508  "
		::= { iqmux43CmdEntry 38508 }


	iqmux43AESOutPortNamesAESPort7R OBJECT-TYPE
		SYNTAX		RollCallString
		MAX-ACCESS		read-write
		STATUS			current
		DESCRIPTION
				"TYPE: - Editstring
				 PAGE: - Audio- AES Ports- AES Port Names
					AES Port 7-R  cmdID= 38509  "
		::= { iqmux43CmdEntry 38509 }


	iqmux43AESOutPortNamesAESPort8Stereo OBJECT-TYPE
		SYNTAX		INTEGER { disable(0), enable(1) }
		MAX-ACCESS		read-write
		STATUS			current
		DESCRIPTION
				"TYPE: - Checkbox
				 PAGE: - Audio- AES Ports- AES Port Names
					AES Port 8 Stereo  cmdID= 38455 "
		::= { iqmux43CmdEntry 38455 }


	iqmux43AESOutPortNamesAESPort8L OBJECT-TYPE
		SYNTAX		RollCallString
		MAX-ACCESS		read-write
		STATUS			current
		DESCRIPTION
				"TYPE: - Editstring
				 PAGE: - Audio- AES Ports- AES Port Names
					AES Port 8-L  cmdID= 38510  "
		::= { iqmux43CmdEntry 38510 }


	iqmux43AESOutPortNamesAESPort8R OBJECT-TYPE
		SYNTAX		RollCallString
		MAX-ACCESS		read-write
		STATUS			current
		DESCRIPTION
				"TYPE: - Editstring
				 PAGE: - Audio- AES Ports- AES Port Names
					AES Port 8-R  cmdID= 38511  "
		::= { iqmux43CmdEntry 38511 }


	iqmux43AESBusDataModeInput1 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 1  cmdID= 38400
					PCM  value= 0
					Data  value= 1
					Mixed  value= 2  "
		::= { iqmux43CmdEntry 38400 }


	iqmux43AESBusDataModeInput2 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 2  cmdID= 38401
					PCM  value= 0
					Data  value= 1
					Mixed  value= 2  "
		::= { iqmux43CmdEntry 38401 }


	iqmux43AESBusDataModeInput3 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 3  cmdID= 38402
					PCM  value= 0
					Data  value= 1
					Mixed  value= 2  "
		::= { iqmux43CmdEntry 38402 }


	iqmux43AESBusDataModeInput4 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 4  cmdID= 38403
					PCM  value= 0
					Data  value= 1
					Mixed  value= 2  "
		::= { iqmux43CmdEntry 38403 }


	iqmux43AESBusDataModeInput5 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 5  cmdID= 38404
					PCM  value= 0
					Data  value= 1
					Mixed  value= 2  "
		::= { iqmux43CmdEntry 38404 }


	iqmux43AESBusDataModeInput6 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 6  cmdID= 38405
					PCM  value= 0
					Data  value= 1
					Mixed  value= 2  "
		::= { iqmux43CmdEntry 38405 }


	iqmux43AESBusDataModeInput7 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 7  cmdID= 38406
					PCM  value= 0
					Data  value= 1
					Mixed  value= 2  "
		::= { iqmux43CmdEntry 38406 }


	iqmux43AESBusDataModeInput8 OBJECT-TYPE
		SYNTAX		INTEGER {
							val_PCM(0),
							val_Data(1),
							val_Mixed(2)
							}
		MAX-ACCESS		read-write
		STATUS			current
		DESCRIPTION
				"TYPE: - RadiobuttonList
				 PAGE: - Audio- AES Ports- AES Bus
					Input 8  cmdID= 38407
					PCM  value= 0
					Data  value= 1
					Mixed  value= 2  "
		::= { iqmux43CmdEntry 38407 }


	iqmux43AESBusNamesAESBus1Stereo OBJECT-TYPE
		SYNTAX		INTEGER { disable(0), enable(1) }
		MAX-ACCESS		read-write
		STATUS			current
		DESCRIPTION
				"TYPE: - Checkbox
				 PAGE: - Audio- AES Ports- AES Bus
					AES Bus 1 Stereo  cmdID= 38440 "
		::= { iqmux43CmdEntry 38440 }


	iqmux43AESBusNamesAESBus1 OBJECT-TYPE
		SYNTAX		RollCallString
		MAX-ACCESS		read-write
		STATUS			current
		DESCRIPTION
				"TYPE: - Editstring
				 PAGE: - Audio- AES Ports- AES Bus
					AES Bus 1  cmdID= 38480  "
		::= { iqmux43CmdEntry 38480 }


	iqmux43AESBusNamesAESBus1R OBJECT-TYPE
		SYNTAX		RollCallString
		MAX-ACCESS		read-write
		STATUS			current
		DESCRIPTION
				"TYPE: - Editstring
				 PAGE: - Audio- AES Ports- AES Bus
					AES Bus 1-R  cmdID= 38481  "
		::= { iqmux43CmdEntry 38481 }


	iqmux43AESBusNamesAESBus2Stereo OBJECT-TYPE
		SYNTAX		INTEGER { disable(0), enable(1) }
		MAX-ACCESS		read-write
		STATUS			current
		DESCRIPTION
				"TYPE: - Checkbox
				 PAGE: - Audio- AES Ports- AES Bus
					AES Bus 2 Stereo  cmdID= 38441 "
		::= { iqmux43CmdEntry 38441 }


	iqmux43AESBusNamesAESBus2 OBJECT-TYPE
		SYNTAX		RollCallString
		MAX-ACCESS		read-write
		STATUS			current
		DESCRIPTION
				"TYPE: - Editstring
				 PAGE: - Audio- AES Ports- AES Bus
					AES Bus 2  cmdID= 38482  "
		::= { iqmux43CmdEntry 38482 }


	iqmux43AESBusNamesAESBus2R OBJECT-TYPE
		SYNTAX		RollCallString
		MAX-ACCESS		read-write
		STATUS			current
		DESCRIPTION
				"TYPE: - Editstring
				 PAGE: - Audio- AES Ports- AES Bus
					AES Bus 2-R  cmdID= 38483  "
		::= { iqmux43CmdEntry 38483 }


	iqmux43AESBusNamesAESBus3Stereo OBJECT-TYPE
		SYNTAX		INTEGER { disable(0), enable(1) }
		MAX-ACCESS		read-write
		STATUS			current
		DESCRIPTION
				"TYPE: - Checkbox
				 PAGE: - Audio- AES Ports- AES Bus
					AES Bus 3 Stereo  cmdID= 38442 "
		::= { iqmux43CmdEntry 38442 }


	iqmux43AESBusNamesAESBus3 OBJECT-TYPE
		SYNTAX		RollCallString
		MAX-ACCESS		read-write
		STATUS			current
		DESCRIPTION
				"TYPE: - Editstring
				 PAGE: - Audio- AES Ports- AES Bus
					AES Bus 3  cmdID= 38484  "
		::= { iqmux43CmdEntry 38484 }


	iqmux43AESBusNamesAESBus3R OBJECT-TYPE
		SYNTAX		RollCallString
		MAX-ACCESS		read-write
		STATUS			current
		DESCRIPTION
				"TYPE: - Editstring
				 PAGE: - Audio- AES Ports- AES Bus
					AES Bus 3-R  cmdID= 38485  "
		::= { iqmux43CmdEntry 38485 }


	iqmux43AESBusNamesAESBus4Stereo OBJECT-TYPE
		SYNTAX		INTEGER { disable(0), enable(1) }
		MAX-ACCESS		read-write
		STATUS			current
		DESCRIPTION
				"TYPE: - Checkbox
				 PAGE: - Audio- AES Ports- AES Bus
					AES Bus 4 Stereo  cmdID= 38443 "
		::= { iqmux43CmdEntry 38443 }


	iqmux43AESBusNamesAESBus4 OBJECT-TYPE
		SYNTAX		RollCallString
		MAX-ACCESS		read-write
		STATUS			current
		DESCRIPTION
				"TYPE: - Editstring
				 PAGE: - Audio- AES Ports- AES Bus
					AES Bus 4  cmdID= 38486  "
		::= { iqmux43CmdEntry 38486 }


	iqmux43AESBusNamesAESBus4R OBJECT-TYPE
		SYNTAX		RollCallString
		MAX-ACCESS		read-write
		STATUS			current
		DESCRIPTION
				"TYPE: - Editstring
				 PAGE: - Audio- AES Ports- AES Bus
					AES Bus 4-R  cmdID= 38487  "
		::= { iqmux43CmdEntry 38487 }


	iqmux43AESBusNamesAESBus5Stereo OBJECT-TYPE
		SYNTAX		INTEGER { disable(0), enable(1) }
		MAX-ACCESS		read-write
		STATUS			current
		DESCRIPTION
				"TYPE: - Checkbox
				 PAGE: - Audio- AES Ports- AES Bus
					AES Bus 5 Stereo  cmdID= 38444 "
		::= { iqmux43CmdEntry 38444 }


	iqmux43AESBusNamesAESBus5 OBJECT-TYPE
		SYNTAX		RollCallString
		MAX-ACCESS		read-write
		STATUS			current
		DESCRIPTION
				"TYPE: - Editstring
				 PAGE: - Audio- AES Ports- AES Bus
					AES Bus 5  cmdID= 38488  "
		::= { iqmux43CmdEntry 38488 }


	iqmux43AESBusNamesAESBus5R OBJECT-TYPE
		SYNTAX		RollCallString
		MAX-ACCESS		read-write
		STATUS			current
		DESCRIPTION
				"TYPE: - Editstring
				 PAGE: - Audio- AES Ports- AES Bus
					AES Bus 5-R  cmdID= 38489  "
		::= { iqmux43CmdEntry 38489 }


	iqmux43AESBusNamesAESBus6Stereo OBJECT-TYPE
		SYNTAX		INTEGER { disable(0), enable(1) }
		MAX-ACCESS		read-write
		STATUS			current
		DESCRIPTION
				"TYPE: - Checkbox
				 PAGE: - Audio- AES Ports- AES Bus
					AES Bus 6 Stereo  cmdID= 38445 "
		::= { iqmux43CmdEntry 38445 }


	iqmux43AESBusNamesAESBus6 OBJECT-TYPE
		SYNTAX		RollCallString
		MAX-ACCESS		read-write
		STATUS			current
		DESCRIPTION
				"TYPE: - Editstring
				 PAGE: - Audio- AES Ports- AES Bus
					AES Bus 6  cmdID= 38490  "
		::= { iqmux43CmdEntry 38490 }


	iqmux43AESBusNamesAESBus6R OBJECT-TYPE
		SYNTAX		RollCallString
		MAX-ACCESS		read-write
		STATUS			current
		DESCRIPTION
				"TYPE: - Editstring
				 PAGE: - Audio- AES Ports- AES Bus
					AES Bus 6-R  cmdID= 38491  "
		::= { iqmux43CmdEntry 38491 }


	iqmux43AESBusNamesAESBus7Stereo OBJECT-TYPE
		SYNTAX		INTEGER { disable(0), enable(1) }
		MAX-ACCESS		read-write
		STATUS			current
		DESCRIPTION
				"TYPE: - Checkbox
				 PAGE: - Audio- AES Ports- AES Bus
					AES Bus 7 Stereo  cmdID= 38446 "
		::= { iqmux43CmdEntry 38446 }


	iqmux43AESBusNamesAESBus7 OBJECT-TYPE
		SYNTAX		RollCallString
		MAX-ACCESS		read-write
		STATUS			current
		DESCRIPTION
				"TYPE: - Editstring
				 PAGE: - Audio- AES Ports- AES Bus
					AES Bus 7  cmdID= 38492  "
		::= { iqmux43CmdEntry 38492 }


	iqmux43AESBusNamesAESBus7R OBJECT-TYPE
		SYNTAX		RollCallString
		MAX-ACCESS		read-write
		STATUS			current
		DESCRIPTION
				"TYPE: - Editstring
				 PAGE: - Audio- AES Ports- AES Bus
					AES Bus 7-R  cmdID= 38493  "
		::= { iqmux43CmdEntry 38493 }


	iqmux43AESBusNamesAESBus8Stereo OBJECT-TYPE
		SYNTAX		INTEGER { disable(0), enable(1) }
		MAX-ACCESS		read-write
		STATUS			current
		DESCRIPTION
				"TYPE: - Checkbox
				 PAGE: - Audio- AES Ports- AES Bus
					AES Bus 8 Stereo  cmdID= 38447 "
		::= { iqmux43CmdEntry 38447 }


	iqmux43AESBusNamesAESBus8 OBJECT-TYPE
		SYNTAX		RollCallString
		MAX-ACCESS		read-write
		STATUS			current
		DESCRIPTION
				"TYPE: - Editstring
				 PAGE: - Audio- AES Ports- AES Bus
					AES Bus 8  cmdID= 38494  "
		::= { iqmux43CmdEntry 38494 }


	iqmux43AESBusNamesAESBus8R OBJECT-TYPE
		SYNTAX		RollCallString
		MAX-ACCESS		read-write
		STATUS			current
		DESCRIPTION
				"TYPE: - Editstring
				 PAGE: - Audio- AES Ports- AES Bus
					AES Bus 8-R  cmdID= 38495  "
		::= { iqmux43CmdEntry 38495 }


	iqmux43AESBusRoutingSource1 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 1  cmdID= 38560
					AES Port 1  value= 1
					AES Port 2  value= 2
					AES Port 3  value= 3
					AES Port 4  value= 4
					AES Port 5  value= 5
					AES Port 6  value= 6
					AES Port 7  value= 7
					AES Port 8  value= 8  "
		::= { iqmux43CmdEntry 38560 }


	iqmux43AESBusRoutingSource2 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 2  cmdID= 38561
					AES Port 1  value= 1
					AES Port 2  value= 2
					AES Port 3  value= 3
					AES Port 4  value= 4
					AES Port 5  value= 5
					AES Port 6  value= 6
					AES Port 7  value= 7
					AES Port 8  value= 8  "
		::= { iqmux43CmdEntry 38561 }


	iqmux43AESBusRoutingSource3 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 3  cmdID= 38562
					AES Port 1  value= 1
					AES Port 2  value= 2
					AES Port 3  value= 3
					AES Port 4  value= 4
					AES Port 5  value= 5
					AES Port 6  value= 6
					AES Port 7  value= 7
					AES Port 8  value= 8  "
		::= { iqmux43CmdEntry 38562 }


	iqmux43AESBusRoutingSource4 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 4  cmdID= 38563
					AES Port 1  value= 1
					AES Port 2  value= 2
					AES Port 3  value= 3
					AES Port 4  value= 4
					AES Port 5  value= 5
					AES Port 6  value= 6
					AES Port 7  value= 7
					AES Port 8  value= 8  "
		::= { iqmux43CmdEntry 38563 }


	iqmux43AESBusRoutingSource5 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 5  cmdID= 38564
					AES Port 1  value= 1
					AES Port 2  value= 2
					AES Port 3  value= 3
					AES Port 4  value= 4
					AES Port 5  value= 5
					AES Port 6  value= 6
					AES Port 7  value= 7
					AES Port 8  value= 8  "
		::= { iqmux43CmdEntry 38564 }


	iqmux43AESBusRoutingSource6 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 6  cmdID= 38565
					AES Port 1  value= 1
					AES Port 2  value= 2
					AES Port 3  value= 3
					AES Port 4  value= 4
					AES Port 5  value= 5
					AES Port 6  value= 6
					AES Port 7  value= 7
					AES Port 8  value= 8  "
		::= { iqmux43CmdEntry 38565 }


	iqmux43AESBusRoutingSource7 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 7  cmdID= 38566
					AES Port 1  value= 1
					AES Port 2  value= 2
					AES Port 3  value= 3
					AES Port 4  value= 4
					AES Port 5  value= 5
					AES Port 6  value= 6
					AES Port 7  value= 7
					AES Port 8  value= 8  "
		::= { iqmux43CmdEntry 38566 }


	iqmux43AESBusRoutingSource8 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - Audio- AES Ports- AES Bus
					Source 8  cmdID= 38567
					AES Port 1  value= 1
					AES Port 2  value= 2
					AES Port 3  value= 3
					AES Port 4  value= 4
					AES Port 5  value= 5
					AES Port 6  value= 6
					AES Port 7  value= 7
					AES Port 8  value= 8  "
		::= { iqmux43CmdEntry 38567 }


	iqmux43AESPortsDirectionAES1Out OBJECT-TYPE
		SYNTAX		INTEGER {
							val_Input(0),
							val_Output(1)
							}
		MAX-ACCESS		read-write
		STATUS			current
		DESCRIPTION
				"TYPE: - RadiobuttonList
				 PAGE: - Audio- AES Ports
					AES Port 1 Dir  cmdID= 38420
					Input  value= 0
					Output  value= 1  "
		::= { iqmux43CmdEntry 38420 }


	iqmux43AESPortsDirectionAES2Out OBJECT-TYPE
		SYNTAX		INTEGER {
							val_Input(0),
							val_Output(1)
							}
		MAX-ACCESS		read-write
		STATUS			current
		DESCRIPTION
				"TYPE: - RadiobuttonList
				 PAGE: - Audio- AES Ports
					AES Port 2 Dir  cmdID= 38421
					Input  value= 0
					Output  value= 1  "
		::= { iqmux43CmdEntry 38421 }


	iqmux43AESPortsDirectionAES3Out OBJECT-TYPE
		SYNTAX		INTEGER {
							val_Input(0),
							val_Output(1)
							}
		MAX-ACCESS		read-write
		STATUS			current
		DESCRIPTION
				"TYPE: - RadiobuttonList
				 PAGE: - Audio- AES Ports
					AES Port 3 Dir  cmdID= 38422
					Input  value= 0
					Output  value= 1  "
		::= { iqmux43CmdEntry 38422 }


	iqmux43AESPortsDirectionAES4Out OBJECT-TYPE
		SYNTAX		INTEGER {
							val_Input(0),
							val_Output(1)
							}
		MAX-ACCESS		read-write
		STATUS			current
		DESCRIPTION
				"TYPE: - RadiobuttonList
				 PAGE: - Audio- AES Ports
					AES Port 4 Dir  cmdID= 38423
					Input  value= 0
					Output  value= 1  "
		::= { iqmux43CmdEntry 38423 }


	iqmux43AESPortsDirectionAES5Out OBJECT-TYPE
		SYNTAX		INTEGER {
							val_Input(0),
							val_Output(1)
							}
		MAX-ACCESS		read-write
		STATUS			current
		DESCRIPTION
				"TYPE: - RadiobuttonList
				 PAGE: - Audio- AES Ports
					AES Port 5 Dir  cmdID= 38424
					Input  value= 0
					Output  value= 1  "
		::= { iqmux43CmdEntry 38424 }


	iqmux43AESPortsDirectionAES6Out OBJECT-TYPE
		SYNTAX		INTEGER {
							val_Input(0),
							val_Output(1)
							}
		MAX-ACCESS		read-write
		STATUS			current
		DESCRIPTION
				"TYPE: - RadiobuttonList
				 PAGE: - Audio- AES Ports
					AES Port 6 Dir  cmdID= 38425
					Input  value= 0
					Output  value= 1  "
		::= { iqmux43CmdEntry 38425 }


	iqmux43AESPortsDirectionAES7Out OBJECT-TYPE
		SYNTAX		INTEGER {
							val_Input(0),
							val_Output(1)
							}
		MAX-ACCESS		read-write
		STATUS			current
		DESCRIPTION
				"TYPE: - RadiobuttonList
				 PAGE: - Audio- AES Ports
					AES Port 7 Dir  cmdID= 38426
					Input  value= 0
					Output  value= 1  "
		::= { iqmux43CmdEntry 38426 }


	iqmux43AESPortsDirectionAES8Out OBJECT-TYPE
		SYNTAX		INTEGER {
							val_Input(0),
							val_Output(1)
							}
		MAX-ACCESS		read-write
		STATUS			current
		DESCRIPTION
				"TYPE: - RadiobuttonList
				 PAGE: - Audio- AES Ports
					AES Port 8 Dir  cmdID= 38427
					Input  value= 0
					Output  value= 1  "
		::= { iqmux43CmdEntry 38427 }


	iqmux43AudioDolbyETimingSelAudioPair OBJECT-TYPE
		SYNTAX		INTEGER
		MAX-ACCESS		read-write
		STATUS			current
		DESCRIPTION
				"TYPE: - Number
				 PAGE: - Audio
					Sel Audio Pair  cmdID= 38650  min= 1  max= 8  step= 1  format= %0.0f  div_scale= 1
					Min = 1  Max = 8  Step = 1 "
		::= { iqmux43CmdEntry 38650 }


	iqmux43AudioDolbyETimingRelativeTiming OBJECT-TYPE
		SYNTAX		RollCallString
		MAX-ACCESS		read-only
		STATUS			current
		DESCRIPTION
				"TYPE: - Display
				 PAGE: - Audio
					Relative Timing  cmdID= 38653  format=   "
		::= { iqmux43CmdEntry 38653 }


	iqmux43AudioDolbyETimingStatus OBJECT-TYPE
		SYNTAX		RollCallString
		MAX-ACCESS		read-only
		STATUS			current
		DESCRIPTION
				"TYPE: - Display
				 PAGE: - Audio
					Status  cmdID= 38652  format=   "
		::= { iqmux43CmdEntry 38652 }


	iqmux43AudioDolbyETimingError OBJECT-TYPE
		SYNTAX		RollCallString
		MAX-ACCESS		read-only
		STATUS			current
		DESCRIPTION
				"TYPE: - Display
				 PAGE: - Audio
					Error  cmdID= 38654  format=   "
		::= { iqmux43CmdEntry 38654 }


	iqmux43DolbyETimingLineStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Audio
					Standard  cmdID= 38655
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux43CmdEntry 38655 }


	iqmux43DolbyETimingLineAutoLineNo OBJECT-TYPE
		SYNTAX		INTEGER
		MAX-ACCESS		read-write
		STATUS			current
		DESCRIPTION
				"TYPE: - Number
				 PAGE: - Audio
					Auto Line No.  cmdID= 38656  min= 1  max= 10000  step= 1  format= %0.0f  div_scale= 1
					Min = 1  Max = 10000  Step = 1 "
		::= { iqmux43CmdEntry 38656 }


	iqmux43DolbyELineUserDolbyELinePair1 OBJECT-TYPE
		SYNTAX		INTEGER {
							val_User_Line(1),
							val_Standard_Line(0)
							}
		MAX-ACCESS		read-write
		STATUS			current
		DESCRIPTION
				"TYPE: - RadiobuttonList
				 PAGE: - Audio
					Pair 1  cmdID= 38670
					User Line  value= 1
					Standard Line  value= 0  "
		::= { iqmux43CmdEntry 38670 }


	iqmux43DolbyELineUserDolbyELinePair2 OBJECT-TYPE
		SYNTAX		INTEGER {
							val_User_Line(1),
							val_Standard_Line(0)
							}
		MAX-ACCESS		read-write
		STATUS			current
		DESCRIPTION
				"TYPE: - RadiobuttonList
				 PAGE: - Audio
					Pair 2  cmdID= 38671
					User Line  value= 1
					Standard Line  value= 0  "
		::= { iqmux43CmdEntry 38671 }


	iqmux43DolbyELineUserDolbyELinePair3 OBJECT-TYPE
		SYNTAX		INTEGER {
							val_User_Line(1),
							val_Standard_Line(0)
							}
		MAX-ACCESS		read-write
		STATUS			current
		DESCRIPTION
				"TYPE: - RadiobuttonList
				 PAGE: - Audio
					Pair 3  cmdID= 38672
					User Line  value= 1
					Standard Line  value= 0  "
		::= { iqmux43CmdEntry 38672 }


	iqmux43DolbyELineUserDolbyELinePair4 OBJECT-TYPE
		SYNTAX		INTEGER {
							val_User_Line(1),
							val_Standard_Line(0)
							}
		MAX-ACCESS		read-write
		STATUS			current
		DESCRIPTION
				"TYPE: - RadiobuttonList
				 PAGE: - Audio
					Pair 4  cmdID= 38673
					User Line  value= 1
					Standard Line  value= 0  "
		::= { iqmux43CmdEntry 38673 }


	iqmux43DolbyELineUserDolbyELinePair5 OBJECT-TYPE
		SYNTAX		INTEGER {
							val_User_Line(1),
							val_Standard_Line(0)
							}
		MAX-ACCESS		read-write
		STATUS			current
		DESCRIPTION
				"TYPE: - RadiobuttonList
				 PAGE: - Audio
					Pair 5  cmdID= 38674
					User Line  value= 1
					Standard Line  value= 0  "
		::= { iqmux43CmdEntry 38674 }


	iqmux43DolbyELineUserDolbyELinePair6 OBJECT-TYPE
		SYNTAX		INTEGER {
							val_User_Line(1),
							val_Standard_Line(0)
							}
		MAX-ACCESS		read-write
		STATUS			current
		DESCRIPTION
				"TYPE: - RadiobuttonList
				 PAGE: - Audio
					Pair 6  cmdID= 38675
					User Line  value= 1
					Standard Line  value= 0  "
		::= { iqmux43CmdEntry 38675 }


	iqmux43DolbyELineUserDolbyELinePair7 OBJECT-TYPE
		SYNTAX		INTEGER {
							val_User_Line(1),
							val_Standard_Line(0)
							}
		MAX-ACCESS		read-write
		STATUS			current
		DESCRIPTION
				"TYPE: - RadiobuttonList
				 PAGE: - Audio
					Pair 7  cmdID= 38676
					User Line  value= 1
					Standard Line  value= 0  "
		::= { iqmux43CmdEntry 38676 }


	iqmux43DolbyELineUserDolbyELinePair8 OBJECT-TYPE
		SYNTAX		INTEGER {
							val_User_Line(1),
							val_Standard_Line(0)
							}
		MAX-ACCESS		read-write
		STATUS			current
		DESCRIPTION
				"TYPE: - RadiobuttonList
				 PAGE: - Audio
					Pair 8  cmdID= 38677
					User Line  value= 1
					Standard Line  value= 0  "
		::= { iqmux43CmdEntry 38677 }


	iqmux43VidDelayInternalDelay OBJECT-TYPE
		SYNTAX		RollCallString
		MAX-ACCESS		read-only
		STATUS			current
		DESCRIPTION
				"TYPE: - Display
				 PAGE: - Vid. Delay
					Internal Delay  cmdID= 33025  format=   "
		::= { iqmux43CmdEntry 33025 }


	iqmux43VidDelayDelayMode OBJECT-TYPE
		SYNTAX		INTEGER {
							val_Minimum_Audio(3),
							val_Frames(4),
							val_Manual_H_V(5),
							val_Manual_ms(6)
							}
		MAX-ACCESS		read-write
		STATUS			current
		DESCRIPTION
				"TYPE: - RadiobuttonList
				 PAGE: - Vid. Delay
					Delay Mode  cmdID= 33026
					Minimum Audio  value= 3
					Frames  value= 4
					Manual H/V  value= 5
					Manual ms  value= 6  "
		::= { iqmux43CmdEntry 33026 }


	iqmux43VidSetDelayDelayFrames OBJECT-TYPE
		SYNTAX		INTEGER
		MAX-ACCESS		read-write
		STATUS			current
		DESCRIPTION
				"TYPE: - Number
				 PAGE: - Vid. Delay
					Delay Frames  cmdID= 33024  min= 0  max= 11  step= 1  format= %0.0f frames  div_scale= 1
					Min = 0 frames  Max = 11 frames  Step = 1 frames "
		::= { iqmux43CmdEntry 33024 }


	iqmux43VidSetDelayVerticalTiming OBJECT-TYPE
		SYNTAX		INTEGER
		MAX-ACCESS		read-write
		STATUS			current
		DESCRIPTION
				"TYPE: - Number
				 PAGE: - Vid. Delay
					Vertical Timing  cmdID= 33022  min= -1500  max= 1500  step= 1  format= %0.0f lines  div_scale= 1
					Min = -1500 lines  Max = 1500 lines  Step = 1 lines "
		::= { iqmux43CmdEntry 33022 }


	iqmux43VidSetDelayHorizontalTiming OBJECT-TYPE
		SYNTAX		INTEGER
		MAX-ACCESS		read-write
		STATUS			current
		DESCRIPTION
				"TYPE: - Number
				 PAGE: - Vid. Delay
					Horizontal Timing  cmdID= 33021  min= -3000  max= 3000  step= 1  format= %0.0f pixels  div_scale= 1
					Min = -3000 pixels  Max = 3000 pixels  Step = 1 pixels "
		::= { iqmux43CmdEntry 33021 }


	iqmux43VidSetDelayDelayms OBJECT-TYPE
		SYNTAX		INTEGER
		MAX-ACCESS		read-write
		STATUS			current
		DESCRIPTION
				"TYPE: - Number
				 PAGE: - Vid. Delay
					Delay ms  cmdID= 33027  min= -48000  max= 48000  step= 5  format= %0.2f ms  div_scale= 100
					Min = -480.00 ms  Max = 480.00 ms  Step = 0.05 ms "
		::= { iqmux43CmdEntry 33027 }


	iqmux43UtilsPatternsPatternEnable OBJECT-TYPE
		SYNTAX		INTEGER { disable(0), enable(1) }
		MAX-ACCESS		read-write
		STATUS			current
		DESCRIPTION
				"TYPE: - Checkbox
				 PAGE: - Utils
					Pattern Enable  cmdID= 33038 "
		::= { iqmux43CmdEntry 33038 }


	iqmux43UtilsPatternsScrollPattern OBJECT-TYPE
		SYNTAX		INTEGER { disable(0), enable(1) }
		MAX-ACCESS		read-write
		STATUS			current
		DESCRIPTION
				"TYPE: - Checkbox
				 PAGE: - Utils
					Scroll Pattern  cmdID= 33040 "
		::= { iqmux43CmdEntry 33040 }


	iqmux43UtilsPatternsPatternType OBJECT-TYPE
		SYNTAX		INTEGER {
							val_100_Color_Bars(1),
							val_75_Color_Bars(2),
							val_SMPTE_Bars(3),
							val_Tartan_Bars(4),
							val_Pluge(5),
							val_Ramp(6),
							val_Sweep(7),
							val_Pulse_Bar(8),
							val_Burst(9),
							val_Black(10)
							}
		MAX-ACCESS		read-write
		STATUS			current
		DESCRIPTION
				"TYPE: - RadiobuttonList
				 PAGE: - Utils
					Pattern Type  cmdID= 33039
					100% Color Bars  value= 1
					75% Color Bars  value= 2
					SMPTE Bars  value= 3
					Tartan Bars  value= 4
					Pluge  value= 5
					Ramp  value= 6
					Sweep  value= 7
					Pulse & Bar  value= 8
					Burst  value= 9
					Black  value= 10  "
		::= { iqmux43CmdEntry 33039 }


	iqmux43UtilsANCblankonMismat OBJECT-TYPE
		SYNTAX		INTEGER { disable(0), enable(1) }
		MAX-ACCESS		read-write
		STATUS			current
		DESCRIPTION
				"TYPE: - Checkbox
				 PAGE: - Utils
					ANC blank on Mismat  cmdID= 33036 "
		::= { iqmux43CmdEntry 33036 }


	iqmux43UtilsFreezeForceFreeze OBJECT-TYPE
		SYNTAX		INTEGER { disable(0), enable(1) }
		MAX-ACCESS		read-write
		STATUS			current
		DESCRIPTION
				"TYPE: - Checkbox
				 PAGE: - Utils
					Force Freeze  cmdID= 33032 "
		::= { iqmux43CmdEntry 33032 }


	iqmux43UtilsFreezeFreezeType OBJECT-TYPE
		SYNTAX		INTEGER {
							val_Frame(0),
							val_Field(1)
							}
		MAX-ACCESS		read-write
		STATUS			current
		DESCRIPTION
				"TYPE: - RadiobuttonList
				 PAGE: - Utils
					Freeze Type  cmdID= 33033
					Frame  value= 0
					Field  value= 1  "
		::= { iqmux43CmdEntry 33033 }


	iqmux43UtilsMonochrome OBJECT-TYPE
		SYNTAX		INTEGER { disable(0), enable(1) }
		MAX-ACCESS		read-write
		STATUS			current
		DESCRIPTION
				"TYPE: - Checkbox
				 PAGE: - Utils
					Monochrome  cmdID= 33034 "
		::= { iqmux43CmdEntry 33034 }


	iqmux43UtilsMonochromeMonochromeType OBJECT-TYPE
		SYNTAX		INTEGER {
							val_Y_only(0),
							val_C_only(1)
							}
		MAX-ACCESS		read-write
		STATUS			current
		DESCRIPTION
				"TYPE: - RadiobuttonList
				 PAGE: - Utils
					Monochrome Type  cmdID= 33035
					Y only  value= 0
					C only  value= 1  "
		::= { iqmux43CmdEntry 33035 }


	iqmux43UtilsVBIBlankingANCMode OBJECT-TYPE
		SYNTAX		INTEGER {
							val_Pass_Input_ANC(0),
							val_Blank_HANC(2),
							val_Blank_All_ANC(1)
							}
		MAX-ACCESS		read-write
		STATUS			current
		DESCRIPTION
				"TYPE: - RadiobuttonList
				 PAGE: - Utils
					ANC Mode  cmdID= 33037
					Pass Input ANC  value= 0
					Blank HANC  value= 2
					Blank All ANC  value= 1  "
		::= { iqmux43CmdEntry 33037 }


	iqmux43UtilsVBIBlankingStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Utils
					Standard  cmdID= 37200
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqmux43CmdEntry 37200 }


	iqmux43UtilsVBIBlankingBlankAll OBJECT-TYPE
		SYNTAX		INTEGER { noAction(0),val_Blank_All(1) }
		MAX-ACCESS		read-write
		STATUS			current
		DESCRIPTION
				"TYPE: - Button
				 PAGE: - Utils
					Blank All  cmdID= 37201  value= 1  "
		::= { iqmux43CmdEntry 37201 }


	iqmux43UtilsVBIBlankingPassAll OBJECT-TYPE
		SYNTAX		INTEGER { noAction(0),val_Pass_All(1) }
		MAX-ACCESS		read-write
		STATUS			current
		DESCRIPTION
				"TYPE: - Button
				 PAGE: - Utils
					Pass All  cmdID= 37202  value= 1  "
		::= { iqmux43CmdEntry 37202 }


	iqmux43UtilsVBIBlankingBlank1 OBJECT-TYPE
		SYNTAX		INTEGER { disable(0), enable(1) }
		MAX-ACCESS		read-write
		STATUS			current
		DESCRIPTION
				"TYPE: - Checkbox
				 PAGE: - Utils
					Blank 1  cmdID= 37210 "
		::= { iqmux43CmdEntry 37210 }


	iqmux43UtilsVBIBlankingBlank2 OBJECT-TYPE
		SYNTAX		INTEGER { disable(0), enable(1) }
		MAX-ACCESS		read-write
		STATUS			current
		DESCRIPTION
				"TYPE: - Checkbox
				 PAGE: - Utils
					Blank 2  cmdID= 37211 "
		::= { iqmux43CmdEntry 37211 }


	iqmux43UtilsVBIBlankingBlank3 OBJECT-TYPE
		SYNTAX		INTEGER { disable(0), enable(1) }
		MAX-ACCESS		read-write
		STATUS			current
		DESCRIPTION
				"TYPE: - Checkbox
				 PAGE: - Utils
					Blank 3  cmdID= 37212 "
		::= { iqmux43CmdEntry 37212 }


	iqmux43UtilsVBIBlankingBlank4 OBJECT-TYPE
		SYNTAX		INTEGER { disable(0), enable(1) }
		MAX-ACCESS		read-write
		STATUS			current
		DESCRIPTION
				"TYPE: - Checkbox
				 PAGE: - Utils
					Blank 4  cmdID= 37213 "
		::= { iqmux43CmdEntry 37213 }


	iqmux43UtilsVBIBlankingBlank5 OBJECT-TYPE
		SYNTAX		INTEGER { disable(0), enable(1) }
		MAX-ACCESS		read-write
		STATUS			current
		DESCRIPTION
				"TYPE: - Checkbox
				 PAGE: - Utils
					Blank 5  cmdID= 37214 "
		::= { iqmux43CmdEntry 37214 }


	iqmux43UtilsVBIBlankingBlank6 OBJECT-TYPE
		SYNTAX		INTEGER { disable(0), enable(1) }
		MAX-ACCESS		read-write
		STATUS			current
		DESCRIPTION
				"TYPE: - Checkbox
				 PAGE: - Utils
					Blank 6  cmdID= 37215 "
		::= { iqmux43CmdEntry 37215 }


	iqmux43UtilsVBIBlankingBlank7 OBJECT-TYPE
		SYNTAX		INTEGER { disable(0), enable(1) }
		MAX-ACCESS		read-write
		STATUS			current
		DESCRIPTION
				"TYPE: - Checkbox
				 PAGE: - Utils
					Blank 7  cmdID= 37216 "
		::= { iqmux43CmdEntry 37216 }


	iqmux43UtilsVBIBlankingBlank8 OBJECT-TYPE
		SYNTAX		INTEGER { disable(0), enable(1) }
		MAX-ACCESS		read-write
		STATUS			current
		DESCRIPTION
				"TYPE: - Checkbox
				 PAGE: - Utils
					Blank 8  cmdID= 37217 "
		::= { iqmux43CmdEntry 37217 }


	iqmux43UtilsVBIBlankingBlank9 OBJECT-TYPE
		SYNTAX		INTEGER { disable(0), enable(1) }
		MAX-ACCESS		read-write
		STATUS			current
		DESCRIPTION
				"TYPE: - Checkbox
				 PAGE: - Utils
					Blank 9  cmdID= 37218 "
		::= { iqmux43CmdEntry 37218 }


	iqmux43UtilsVBIBlankingBlank10 OBJECT-TYPE
		SYNTAX		INTEGER { disable(0), enable(1) }
		MAX-ACCESS		read-write
		STATUS			current
		DESCRIPTION
				"TYPE: - Checkbox
				 PAGE: - Utils
					Blank 10  cmdID= 37219 "
		::= { iqmux43CmdEntry 37219 }


	iqmux43UtilsVBIBlankingBlank11 OBJECT-TYPE
		SYNTAX		INTEGER { disable(0), enable(1) }
		MAX-ACCESS		read-write
		STATUS			current
		DESCRIPTION
				"TYPE: - Checkbox
				 PAGE: - Utils
					Blank 11  cmdID= 37220 "
		::= { iqmux43CmdEntry 37220 }


	iqmux43UtilsVBIBlankingBlank12 OBJECT-TYPE
		SYNTAX		INTEGER { disable(0), enable(1) }
		MAX-ACCESS		read-write
		STATUS			current
		DESCRIPTION
				"TYPE: - Checkbox
				 PAGE: - Utils
					Blank 12  cmdID= 37221 "
		::= { iqmux43CmdEntry 37221 }


	iqmux43UtilsVBIBlankingBlank13 OBJECT-TYPE
		SYNTAX		INTEGER { disable(0), enable(1) }
		MAX-ACCESS		read-write
		STATUS			current
		DESCRIPTION
				"TYPE: - Checkbox
				 PAGE: - Utils
					Blank 13  cmdID= 37222 "
		::= { iqmux43CmdEntry 37222 }


	iqmux43UtilsVBIBlankingBlank14 OBJECT-TYPE
		SYNTAX		INTEGER { disable(0), enable(1) }
		MAX-ACCESS		read-write
		STATUS			current
		DESCRIPTION
				"TYPE: - Checkbox
				 PAGE: - Utils
					Blank 14  cmdID= 37223 "
		::= { iqmux43CmdEntry 37223 }


	iqmux43UtilsVBIBlankingBlank15 OBJECT-TYPE
		SYNTAX		INTEGER { disable(0), enable(1) }
		MAX-ACCESS		read-write
		STATUS			current
		DESCRIPTION
				"TYPE: - Checkbox
				 PAGE: - Utils
					Blank 15  cmdID= 37224 "
		::= { iqmux43CmdEntry 37224 }


	iqmux43UtilsVBIBlankingBlank16 OBJECT-TYPE
		SYNTAX		INTEGER { disable(0), enable(1) }
		MAX-ACCESS		read-write
		STATUS			current
		DESCRIPTION
				"TYPE: - Checkbox
				 PAGE: - Utils
					Blank 16  cmdID= 37225 "
		::= { iqmux43CmdEntry 37225 }


	iqmux43UtilsVBIBlankingBlank17 OBJECT-TYPE
		SYNTAX		INTEGER { disable(0), enable(1) }
		MAX-ACCESS		read-write
		STATUS			current
		DESCRIPTION
				"TYPE: - Checkbox
				 PAGE: - Utils
					Blank 17  cmdID= 37226 "
		::= { iqmux43CmdEntry 37226 }


	iqmux43UtilsVBIBlankingBlank18 OBJECT-TYPE
		SYNTAX		INTEGER { disable(0), enable(1) }
		MAX-ACCESS		read-write
		STATUS			current
		DESCRIPTION
				"TYPE: - Checkbox
				 PAGE: - Utils
					Blank 18  cmdID= 37227 "
		::= { iqmux43CmdEntry 37227 }


	iqmux43UtilsVBIBlankingBlank19 OBJECT-TYPE
		SYNTAX		INTEGER { disable(0), enable(1) }
		MAX-ACCESS		read-write
		STATUS			current
		DESCRIPTION
				"TYPE: - Checkbox
				 PAGE: - Utils
					Blank 19  cmdID= 37228 "
		::= { iqmux43CmdEntry 37228 }


	iqmux43UtilsVBIBlankingBlank20 OBJECT-TYPE
		SYNTAX		INTEGER { disable(0), enable(1) }
		MAX-ACCESS		read-write
		STATUS			current
		DESCRIPTION
				"TYPE: - Checkbox
				 PAGE: - Utils
					Blank 20  cmdID= 37229 "
		::= { iqmux43CmdEntry 37229 }


	iqmux43UtilsVBIBlankingBlank21 OBJECT-TYPE
		SYNTAX		INTEGER { disable(0), enable(1) }
		MAX-ACCESS		read-write
		STATUS			current
		DESCRIPTION
				"TYPE: - Checkbox
				 PAGE: - Utils
					Blank 21  cmdID= 37230 "
		::= { iqmux43CmdEntry 37230 }


	iqmux43UtilsVBIBlankingBlank22 OBJECT-TYPE
		SYNTAX		INTEGER { disable(0), enable(1) }
		MAX-ACCESS		read-write
		STATUS			current
		DESCRIPTION
				"TYPE: - Checkbox
				 PAGE: - Utils
					Blank 22  cmdID= 37231 "
		::= { iqmux43CmdEntry 37231 }


	iqmux43UtilsVBIBlankingBlank23 OBJECT-TYPE
		SYNTAX		INTEGER { disable(0), enable(1) }
		MAX-ACCESS		read-write
		STATUS			current
		DESCRIPTION
				"TYPE: - Checkbox
				 PAGE: - Utils
					Blank 23  cmdID= 37232 "
		::= { iqmux43CmdEntry 37232 }


	iqmux43UtilsVBIBlankingBlank24 OBJECT-TYPE
		SYNTAX		INTEGER { disable(0), enable(1) }
		MAX-ACCESS		read-write
		STATUS			current
		DESCRIPTION
				"TYPE: - Checkbox
				 PAGE: - Utils
					Blank 24  cmdID= 37233 "
		::= { iqmux43CmdEntry 37233 }


	iqmux43UtilsVBIBlankingBlank25 OBJECT-TYPE
		SYNTAX		INTEGER { disable(0), enable(1) }
		MAX-ACCESS		read-write
		STATUS			current
		DESCRIPTION
				"TYPE: - Checkbox
				 PAGE: - Utils
					Blank 25  cmdID= 37234 "
		::= { iqmux43CmdEntry 37234 }


	iqmux43UtilsVBIBlankingBlank26 OBJECT-TYPE
		SYNTAX		INTEGER { disable(0), enable(1) }
		MAX-ACCESS		read-write
		STATUS			current
		DESCRIPTION
				"TYPE: - Checkbox
				 PAGE: - Utils
					Blank 26  cmdID= 37235 "
		::= { iqmux43CmdEntry 37235 }


	iqmux43UtilsVBIBlankingBlank27 OBJECT-TYPE
		SYNTAX		INTEGER { disable(0), enable(1) }
		MAX-ACCESS		read-write
		STATUS			current
		DESCRIPTION
				"TYPE: - Checkbox
				 PAGE: - Utils
					Blank 27  cmdID= 37236 "
		::= { iqmux43CmdEntry 37236 }


	iqmux43UtilsVBIBlankingBlank28 OBJECT-TYPE
		SYNTAX		INTEGER { disable(0), enable(1) }
		MAX-ACCESS		read-write
		STATUS			current
		DESCRIPTION
				"TYPE: - Checkbox
				 PAGE: - Utils
					Blank 28  cmdID= 37237 "
		::= { iqmux43CmdEntry 37237 }


	iqmux43UtilsVBIBlankingBlank29 OBJECT-TYPE
		SYNTAX		INTEGER { disable(0), enable(1) }
		MAX-ACCESS		read-write
		STATUS			current
		DESCRIPTION
				"TYPE: - Checkbox
				 PAGE: - Utils
					Blank 29  cmdID= 37238 "
		::= { iqmux43CmdEntry 37238 }


	iqmux43UtilsVBIBlankingBlank30 OBJECT-TYPE
		SYNTAX		INTEGER { disable(0), enable(1) }
		MAX-ACCESS		read-write
		STATUS			current
		DESCRIPTION
				"TYPE: - Checkbox
				 PAGE: - Utils
					Blank 30  cmdID= 37239 "
		::= { iqmux43CmdEntry 37239 }


	iqmux43UtilsVBIBlankingBlank31 OBJECT-TYPE
		SYNTAX		INTEGER { disable(0), enable(1) }
		MAX-ACCESS		read-write
		STATUS			current
		DESCRIPTION
				"TYPE: - Checkbox
				 PAGE: - Utils
					Blank 31  cmdID= 37240 "
		::= { iqmux43CmdEntry 37240 }


	iqmux43UtilsVBIBlankingBlank32 OBJECT-TYPE
		SYNTAX		INTEGER { disable(0), enable(1) }
		MAX-ACCESS		read-write
		STATUS			current
		DESCRIPTION
				"TYPE: - Checkbox
				 PAGE: - Utils
					Blank 32  cmdID= 37241 "
		::= { iqmux43CmdEntry 37241 }


	iqmux43UtilsVBIBlankingBlank33 OBJECT-TYPE
		SYNTAX		INTEGER { disable(0), enable(1) }
		MAX-ACCESS		read-write
		STATUS			current
		DESCRIPTION
				"TYPE: - Checkbox
				 PAGE: - Utils
					Blank 33  cmdID= 37242 "
		::= { iqmux43CmdEntry 37242 }


	iqmux43UtilsVBIBlankingBlank34 OBJECT-TYPE
		SYNTAX		INTEGER { disable(0), enable(1) }
		MAX-ACCESS		read-write
		STATUS			current
		DESCRIPTION
				"TYPE: - Checkbox
				 PAGE: - Utils
					Blank 34  cmdID= 37243 "
		::= { iqmux43CmdEntry 37243 }


	iqmux43MemoriesRecallMemory OBJECT-TYPE
		SYNTAX		INTEGER {
							val_None_Selected(0),
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Recall Memory  cmdID= 37100
					None Selected  value= 0
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqmux43CmdEntry 37100 }


	iqmux43MemoriesSelMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqmux43CmdEntry 37101 }


	iqmux43SaveMemories OBJECT-TYPE
		SYNTAX		INTEGER { noAction(0),val_Save_Memory(1) }
		MAX-ACCESS		read-write
		STATUS			current
		DESCRIPTION
				"TYPE: - Button
				 PAGE: - Memories
					Save Memory  cmdID= 37102  value= 1 "
		::= { iqmux43CmdEntry 37102 }


	iqmux43ClearMemories OBJECT-TYPE
		SYNTAX		INTEGER { noAction(0),val_Clear_Memory(1) }
		MAX-ACCESS		read-write
		STATUS			current
		DESCRIPTION
				"TYPE: - Button
				 PAGE: - Memories
					Clear Memory  cmdID= 37105  value= 1 "
		::= { iqmux43CmdEntry 37105 }


	iqmux43MemoriesMemoryNameChangeName OBJECT-TYPE
		SYNTAX		RollCallString
		MAX-ACCESS		read-write
		STATUS			current
		DESCRIPTION
				"TYPE: - Editstring
				 PAGE: - Memories
					Change Name  cmdID= 37103  "
		::= { iqmux43CmdEntry 37103 }


	iqmux43MemoriesLastUserMemory OBJECT-TYPE
		SYNTAX		RollCallString
		MAX-ACCESS		read-only
		STATUS			current
		DESCRIPTION
				"TYPE: - Display
				 PAGE: - Memories
					Last User Memory  cmdID= 37104  format=   "
		::= { iqmux43CmdEntry 37104 }


	iqmux43MemoriesMemoryName1 OBJECT-TYPE
		SYNTAX		RollCallString
		MAX-ACCESS		read-only
		STATUS			current
		DESCRIPTION
				"TYPE: - Display
				 PAGE: - Memories
					Memory Name1  cmdID= 37106  format=   "
		::= { iqmux43CmdEntry 37106 }


	iqmux43MemoriesMemoryName2 OBJECT-TYPE
		SYNTAX		RollCallString
		MAX-ACCESS		read-only
		STATUS			current
		DESCRIPTION
				"TYPE: - Display
				 PAGE: - Memories
					Memory Name2  cmdID= 37107  format=   "
		::= { iqmux43CmdEntry 37107 }


	iqmux43MemoriesMemoryName3 OBJECT-TYPE
		SYNTAX		RollCallString
		MAX-ACCESS		read-only
		STATUS			current
		DESCRIPTION
				"TYPE: - Display
				 PAGE: - Memories
					Memory Name3  cmdID= 37108  format=   "
		::= { iqmux43CmdEntry 37108 }


	iqmux43MemoriesMemoryName4 OBJECT-TYPE
		SYNTAX		RollCallString
		MAX-ACCESS		read-only
		STATUS			current
		DESCRIPTION
				"TYPE: - Display
				 PAGE: - Memories
					Memory Name4  cmdID= 37109  format=   "
		::= { iqmux43CmdEntry 37109 }


	iqmux43MemoriesMemoryName5 OBJECT-TYPE
		SYNTAX		RollCallString
		MAX-ACCESS		read-only
		STATUS			current
		DESCRIPTION
				"TYPE: - Display
				 PAGE: - Memories
					Memory Name5  cmdID= 37110  format=   "
		::= { iqmux43CmdEntry 37110 }


	iqmux43MemoriesMemoryName6 OBJECT-TYPE
		SYNTAX		RollCallString
		MAX-ACCESS		read-only
		STATUS			current
		DESCRIPTION
				"TYPE: - Display
				 PAGE: - Memories
					Memory Name6  cmdID= 37111  format=   "
		::= { iqmux43CmdEntry 37111 }


	iqmux43MemoriesMemoryName7 OBJECT-TYPE
		SYNTAX		RollCallString
		MAX-ACCESS		read-only
		STATUS			current
		DESCRIPTION
				"TYPE: - Display
				 PAGE: - Memories
					Memory Name7  cmdID= 37112  format=   "
		::= { iqmux43CmdEntry 37112 }


	iqmux43MemoriesMemoryName8 OBJECT-TYPE
		SYNTAX		RollCallString
		MAX-ACCESS		read-only
		STATUS			current
		DESCRIPTION
				"TYPE: - Display
				 PAGE: - Memories
					Memory Name8  cmdID= 37113  format=   "
		::= { iqmux43CmdEntry 37113 }


	iqmux43MemoriesMemoryName9 OBJECT-TYPE
		SYNTAX		RollCallString
		MAX-ACCESS		read-only
		STATUS			current
		DESCRIPTION
				"TYPE: - Display
				 PAGE: - Memories
					Memory Name9  cmdID= 37114  format=   "
		::= { iqmux43CmdEntry 37114 }


	iqmux43MemoriesMemoryName10 OBJECT-TYPE
		SYNTAX		RollCallString
		MAX-ACCESS		read-only
		STATUS			current
		DESCRIPTION
				"TYPE: - Display
				 PAGE: - Memories
					Memory Name10  cmdID= 37115  format=   "
		::= { iqmux43CmdEntry 37115 }


	iqmux43MemoriesMemoryName11 OBJECT-TYPE
		SYNTAX		RollCallString
		MAX-ACCESS		read-only
		STATUS			current
		DESCRIPTION
				"TYPE: - Display
				 PAGE: - Memories
					Memory Name11  cmdID= 37116  format=   "
		::= { iqmux43CmdEntry 37116 }


	iqmux43MemoriesMemoryName12 OBJECT-TYPE
		SYNTAX		RollCallString
		MAX-ACCESS		read-only
		STATUS			current
		DESCRIPTION
				"TYPE: - Display
				 PAGE: - Memories
					Memory Name12  cmdID= 37117  format=   "
		::= { iqmux43CmdEntry 37117 }


	iqmux43MemoriesMemoryName13 OBJECT-TYPE
		SYNTAX		RollCallString
		MAX-ACCESS		read-only
		STATUS			current
		DESCRIPTION
				"TYPE: - Display
				 PAGE: - Memories
					Memory Name13  cmdID= 37118  format=   "
		::= { iqmux43CmdEntry 37118 }


	iqmux43MemoriesMemoryName14 OBJECT-TYPE
		SYNTAX		RollCallString
		MAX-ACCESS		read-only
		STATUS			current
		DESCRIPTION
				"TYPE: - Display
				 PAGE: - Memories
					Memory Name14  cmdID= 37119  format=   "
		::= { iqmux43CmdEntry 37119 }


	iqmux43MemoriesMemoryName15 OBJECT-TYPE
		SYNTAX		RollCallString
		MAX-ACCESS		read-only
		STATUS			current
		DESCRIPTION
				"TYPE: - Display
				 PAGE: - Memories
					Memory Name15  cmdID= 37120  format=   "
		::= { iqmux43CmdEntry 37120 }


	iqmux43MemoriesMemoryName16 OBJECT-TYPE
		SYNTAX		RollCallString
		MAX-ACCESS		read-only
		STATUS			current
		DESCRIPTION
				"TYPE: - Display
				 PAGE: - Memories
					Memory Name16  cmdID= 37121  format=   "
		::= { iqmux43CmdEntry 37121 }





	iqmux43LoggingVideoLogInput1Type OBJECT-TYPE
		SYNTAX		INTEGER { disable(0), enable(1) }
		MAX-ACCESS		read-write
		STATUS			current
		DESCRIPTION
				"TYPE: - Checkbox
				 PAGE: - RollCall- Logging
					Log Input 1 Type  cmdID= 35017 "
		::= { iqmux43CmdEntry 35017 }


	iqmux43LoggingVideoInput1Type OBJECT-TYPE
		SYNTAX		RollCallString
		MAX-ACCESS		read-only
		STATUS			current
		DESCRIPTION
				"TYPE: - Display
				 PAGE: - RollCall- Logging
					Input 1 Type=  cmdID= 36017  format=   "
		::= { iqmux43CmdEntry 36017 }


	iqmux43LoggingVideoLogInput1Status OBJECT-TYPE
		SYNTAX		INTEGER { disable(0), enable(1) }
		MAX-ACCESS		read-write
		STATUS			current
		DESCRIPTION
				"TYPE: - Checkbox
				 PAGE: - RollCall- Logging
					Log Input 1 Status  cmdID= 35005 "
		::= { iqmux43CmdEntry 35005 }


	iqmux43LoggingVideoInput1Status OBJECT-TYPE
		SYNTAX		RollCallString
		MAX-ACCESS		read-only
		STATUS			current
		DESCRIPTION
				"TYPE: - Display
				 PAGE: - RollCall- Logging
					Input 1 Status=  cmdID= 36005  format=   "
		::= { iqmux43CmdEntry 36005 }


	iqmux43LoggingVideoLogInput1Std OBJECT-TYPE
		SYNTAX		INTEGER { disable(0), enable(1) }
		MAX-ACCESS		read-write
		STATUS			current
		DESCRIPTION
				"TYPE: - Checkbox
				 PAGE: - RollCall- Logging
					Log Input 1 Std.  cmdID= 35016 "
		::= { iqmux43CmdEntry 35016 }


	iqmux43LoggingVideoInput1Std OBJECT-TYPE
		SYNTAX		RollCallString
		MAX-ACCESS		read-only
		STATUS			current
		DESCRIPTION
				"TYPE: - Display
				 PAGE: - RollCall- Logging
					Input 1 Std.=  cmdID= 36016  format=   "
		::= { iqmux43CmdEntry 36016 }


	iqmux43LoggingVideoLogInput1Errors OBJECT-TYPE
		SYNTAX		INTEGER { disable(0), enable(1) }
		MAX-ACCESS		read-write
		STATUS			current
		DESCRIPTION
				"TYPE: - Checkbox
				 PAGE: - RollCall- Logging
					Log Input 1 Errors  cmdID= 35002 "
		::= { iqmux43CmdEntry 35002 }


	iqmux43LoggingVideoInput1Errors OBJECT-TYPE
		SYNTAX		RollCallString
		MAX-ACCESS		read-only
		STATUS			current
		DESCRIPTION
				"TYPE: - Display
				 PAGE: - RollCall- Logging
					Input 1 Errors=  cmdID= 36002  format=   "
		::= { iqmux43CmdEntry 36002 }


	iqmux43LoggingVideoLogInput1ErrSecs OBJECT-TYPE
		SYNTAX		INTEGER { disable(0), enable(1) }
		MAX-ACCESS		read-write
		STATUS			current
		DESCRIPTION
				"TYPE: - Checkbox
				 PAGE: - RollCall- Logging
					Log Input 1 ErrSecs  cmdID= 35003 "
		::= { iqmux43CmdEntry 35003 }


	iqmux43LoggingVideoInput1ErrSecs OBJECT-TYPE
		SYNTAX		RollCallString
		MAX-ACCESS		read-only
		STATUS			current
		DESCRIPTION
				"TYPE: - Display
				 PAGE: - RollCall- Logging
					Input 1 ErrSecs=  cmdID= 36003  format=   "
		::= { iqmux43CmdEntry 36003 }


	iqmux43LoggingVideoLogInput1ANCErr35000 OBJECT-TYPE
		SYNTAX		INTEGER { disable(0), enable(1) }
		MAX-ACCESS		read-write
		STATUS			current
		DESCRIPTION
				"TYPE: - Checkbox
				 PAGE: - RollCall- Logging
					Log Input 1 ANC Err  cmdID= 35000 "
		::= { iqmux43CmdEntry 35000 }


	iqmux43LoggingVideoInput1ANCErrors OBJECT-TYPE
		SYNTAX		RollCallString
		MAX-ACCESS		read-only
		STATUS			current
		DESCRIPTION
				"TYPE: - Display
				 PAGE: - RollCall- Logging
					Input 1 ANC Errors=  cmdID= 36000  format=   "
		::= { iqmux43CmdEntry 36000 }


	iqmux43LoggingVideoLogInput1ANCErr35001 OBJECT-TYPE
		SYNTAX		INTEGER { disable(0), enable(1) }
		MAX-ACCESS		read-write
		STATUS			current
		DESCRIPTION
				"TYPE: - Checkbox
				 PAGE: - RollCall- Logging
					Log Input 1 ANC Err  cmdID= 35001 "
		::= { iqmux43CmdEntry 35001 }


	iqmux43LoggingVideoInput1ANCErrSecs OBJECT-TYPE
		SYNTAX		RollCallString
		MAX-ACCESS		read-only
		STATUS			current
		DESCRIPTION
				"TYPE: - Display
				 PAGE: - RollCall- Logging
					Input 1 ANC ErrSecs  cmdID= 36001  format=   "
		::= { iqmux43CmdEntry 36001 }


	iqmux43LoggingVideoLogOutputState OBJECT-TYPE
		SYNTAX		INTEGER { disable(0), enable(1) }
		MAX-ACCESS		read-write
		STATUS			current
		DESCRIPTION
				"TYPE: - Checkbox
				 PAGE: - RollCall- Logging
					Log Output State  cmdID= 35941 "
		::= { iqmux43CmdEntry 35941 }


	iqmux43LoggingVideoOutputState OBJECT-TYPE
		SYNTAX		RollCallString
		MAX-ACCESS		read-only
		STATUS			current
		DESCRIPTION
				"TYPE: - Display
				 PAGE: - RollCall- Logging
					Output State=  cmdID= 36941  format=   "
		::= { iqmux43CmdEntry 36941 }


	iqmux43LoggingVideoLogOutputType OBJECT-TYPE
		SYNTAX		INTEGER { disable(0), enable(1) }
		MAX-ACCESS		read-write
		STATUS			current
		DESCRIPTION
				"TYPE: - Checkbox
				 PAGE: - RollCall- Logging
					Log Output Type  cmdID= 35942 "
		::= { iqmux43CmdEntry 35942 }


	iqmux43LoggingVideoOutputType OBJECT-TYPE
		SYNTAX		RollCallString
		MAX-ACCESS		read-only
		STATUS			current
		DESCRIPTION
				"TYPE: - Display
				 PAGE: - RollCall- Logging
					Output Type=  cmdID= 36942  format=   "
		::= { iqmux43CmdEntry 36942 }


	iqmux43LoggingVideoLogOutputStandard OBJECT-TYPE
		SYNTAX		INTEGER { disable(0), enable(1) }
		MAX-ACCESS		read-write
		STATUS			current
		DESCRIPTION
				"TYPE: - Checkbox
				 PAGE: - RollCall- Logging
					Log Output Standard  cmdID= 35940 "
		::= { iqmux43CmdEntry 35940 }


	iqmux43LoggingVideoOutputStandard OBJECT-TYPE
		SYNTAX		RollCallString
		MAX-ACCESS		read-only
		STATUS			current
		DESCRIPTION
				"TYPE: - Display
				 PAGE: - RollCall- Logging
					Output Standard=  cmdID= 36940  format=   "
		::= { iqmux43CmdEntry 36940 }


	iqmux43LoggingVideoLogoutputANCstat OBJECT-TYPE
		SYNTAX		INTEGER { disable(0), enable(1) }
		MAX-ACCESS		read-write
		STATUS			current
		DESCRIPTION
				"TYPE: - Checkbox
				 PAGE: - RollCall- Logging
					Log output ANC stat  cmdID= 35946 "
		::= { iqmux43CmdEntry 35946 }


	iqmux43LoggingVideoOutputANCstate OBJECT-TYPE
		SYNTAX		RollCallString
		MAX-ACCESS		read-only
		STATUS			current
		DESCRIPTION
				"TYPE: - Display
				 PAGE: - RollCall- Logging
					Output ANC state=  cmdID= 36946  format=   "
		::= { iqmux43CmdEntry 36946 }


	iqmux43LoggingEmbedAudioLogInp1Emb1stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 stat  cmdID= 35006 "
		::= { iqmux43CmdEntry 35006 }


	iqmux43LoggingEmbedAudioInp1Emb1state OBJECT-TYPE
		SYNTAX		RollCallString
		MAX-ACCESS		read-only
		STATUS			current
		DESCRIPTION
				"TYPE: - Display
				 PAGE: - RollCall- Logging- Emb.Aud Logging
					Inp1 Emb.1 state=  cmdID= 36006  format=   "
		::= { iqmux43CmdEntry 36006 }


	iqmux43LoggingEmbedAudioLogInp1Emb2stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 stat  cmdID= 35007 "
		::= { iqmux43CmdEntry 35007 }


	iqmux43LoggingEmbedAudioInp1Emb2state OBJECT-TYPE
		SYNTAX		RollCallString
		MAX-ACCESS		read-only
		STATUS			current
		DESCRIPTION
				"TYPE: - Display
				 PAGE: - RollCall- Logging- Emb.Aud Logging
					Inp1 Emb.2 state=  cmdID= 36007  format=   "
		::= { iqmux43CmdEntry 36007 }


	iqmux43LoggingEmbedAudioLogInp1Emb3stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 stat  cmdID= 35008 "
		::= { iqmux43CmdEntry 35008 }


	iqmux43LoggingEmbedAudioInp1Emb3state OBJECT-TYPE
		SYNTAX		RollCallString
		MAX-ACCESS		read-only
		STATUS			current
		DESCRIPTION
				"TYPE: - Display
				 PAGE: - RollCall- Logging- Emb.Aud Logging
					Inp1 Emb.3 state=  cmdID= 36008  format=   "
		::= { iqmux43CmdEntry 36008 }


	iqmux43LoggingEmbedAudioLogInp1Emb4stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 stat  cmdID= 35009 "
		::= { iqmux43CmdEntry 35009 }


	iqmux43LoggingEmbedAudioInp1Emb4state OBJECT-TYPE
		SYNTAX		RollCallString
		MAX-ACCESS		read-only
		STATUS			current
		DESCRIPTION
				"TYPE: - Display
				 PAGE: - RollCall- Logging- Emb.Aud Logging
					Inp1 Emb.4 state=  cmdID= 36009  format=   "
		::= { iqmux43CmdEntry 36009 }


	iqmux43LoggingEmbedAudioLogInp1Emb5stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 stat  cmdID= 35010 "
		::= { iqmux43CmdEntry 35010 }


	iqmux43LoggingEmbedAudioInp1Emb5state OBJECT-TYPE
		SYNTAX		RollCallString
		MAX-ACCESS		read-only
		STATUS			current
		DESCRIPTION
				"TYPE: - Display
				 PAGE: - RollCall- Logging- Emb.Aud Logging
					Inp1 Emb.5 state=  cmdID= 36010  format=   "
		::= { iqmux43CmdEntry 36010 }


	iqmux43LoggingEmbedAudioLogInp1Emb6stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 stat  cmdID= 35011 "
		::= { iqmux43CmdEntry 35011 }


	iqmux43LoggingEmbedAudioInp1Emb6state OBJECT-TYPE
		SYNTAX		RollCallString
		MAX-ACCESS		read-only
		STATUS			current
		DESCRIPTION
				"TYPE: - Display
				 PAGE: - RollCall- Logging- Emb.Aud Logging
					Inp1 Emb.6 state=  cmdID= 36011  format=   "
		::= { iqmux43CmdEntry 36011 }


	iqmux43LoggingEmbedAudioLogInp1Emb7stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 stat  cmdID= 35012 "
		::= { iqmux43CmdEntry 35012 }


	iqmux43LoggingEmbedAudioInp1Emb7state OBJECT-TYPE
		SYNTAX		RollCallString
		MAX-ACCESS		read-only
		STATUS			current
		DESCRIPTION
				"TYPE: - Display
				 PAGE: - RollCall- Logging- Emb.Aud Logging
					Inp1 Emb.7 state=  cmdID= 36012  format=   "
		::= { iqmux43CmdEntry 36012 }


	iqmux43LoggingEmbedAudioLogInp1Emb8stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 stat  cmdID= 35013 "
		::= { iqmux43CmdEntry 35013 }


	iqmux43LoggingEmbedAudioInp1Emb8state OBJECT-TYPE
		SYNTAX		RollCallString
		MAX-ACCESS		read-only
		STATUS			current
		DESCRIPTION
				"TYPE: - Display
				 PAGE: - RollCall- Logging- Emb.Aud Logging
					Inp1 Emb.8 state=  cmdID= 36013  format=   "
		::= { iqmux43CmdEntry 36013 }


	iqmux43LoggingEmbedAudioLogInp1Emb1type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 type  cmdID= 35018 "
		::= { iqmux43CmdEntry 35018 }


	iqmux43LoggingEmbedAudioInp1Emb1type OBJECT-TYPE
		SYNTAX		RollCallString
		MAX-ACCESS		read-only
		STATUS			current
		DESCRIPTION
				"TYPE: - Display
				 PAGE: - RollCall- Logging- Emb.Aud Logging
					Inp1 Emb.1 type=  cmdID= 36018  format=   "
		::= { iqmux43CmdEntry 36018 }


	iqmux43LoggingEmbedAudioLogInp1Emb2type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 type  cmdID= 35019 "
		::= { iqmux43CmdEntry 35019 }


	iqmux43LoggingEmbedAudioInp1Emb2type OBJECT-TYPE
		SYNTAX		RollCallString
		MAX-ACCESS		read-only
		STATUS			current
		DESCRIPTION
				"TYPE: - Display
				 PAGE: - RollCall- Logging- Emb.Aud Logging
					Inp1 Emb.2 type=  cmdID= 36019  format=   "
		::= { iqmux43CmdEntry 36019 }


	iqmux43LoggingEmbedAudioLogInp1Emb3type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 type  cmdID= 35020 "
		::= { iqmux43CmdEntry 35020 }


	iqmux43LoggingEmbedAudioInp1Emb3type OBJECT-TYPE
		SYNTAX		RollCallString
		MAX-ACCESS		read-only
		STATUS			current
		DESCRIPTION
				"TYPE: - Display
				 PAGE: - RollCall- Logging- Emb.Aud Logging
					Inp1 Emb.3 type=  cmdID= 36020  format=   "
		::= { iqmux43CmdEntry 36020 }


	iqmux43LoggingEmbedAudioLogInp1Emb4type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 type  cmdID= 35021 "
		::= { iqmux43CmdEntry 35021 }


	iqmux43LoggingEmbedAudioInp1Emb4type OBJECT-TYPE
		SYNTAX		RollCallString
		MAX-ACCESS		read-only
		STATUS			current
		DESCRIPTION
				"TYPE: - Display
				 PAGE: - RollCall- Logging- Emb.Aud Logging
					Inp1 Emb.4 type=  cmdID= 36021  format=   "
		::= { iqmux43CmdEntry 36021 }


	iqmux43LoggingEmbedAudioLogInp1Emb5type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 type  cmdID= 35022 "
		::= { iqmux43CmdEntry 35022 }


	iqmux43LoggingEmbedAudioInp1Emb5type OBJECT-TYPE
		SYNTAX		RollCallString
		MAX-ACCESS		read-only
		STATUS			current
		DESCRIPTION
				"TYPE: - Display
				 PAGE: - RollCall- Logging- Emb.Aud Logging
					Inp1 Emb.5 type=  cmdID= 36022  format=   "
		::= { iqmux43CmdEntry 36022 }


	iqmux43LoggingEmbedAudioLogInp1Emb6type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 type  cmdID= 35023 "
		::= { iqmux43CmdEntry 35023 }


	iqmux43LoggingEmbedAudioInp1Emb6type OBJECT-TYPE
		SYNTAX		RollCallString
		MAX-ACCESS		read-only
		STATUS			current
		DESCRIPTION
				"TYPE: - Display
				 PAGE: - RollCall- Logging- Emb.Aud Logging
					Inp1 Emb.6 type=  cmdID= 36023  format=   "
		::= { iqmux43CmdEntry 36023 }


	iqmux43LoggingEmbedAudioLogInp1Emb7type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 type  cmdID= 35024 "
		::= { iqmux43CmdEntry 35024 }


	iqmux43LoggingEmbedAudioInp1Emb7type OBJECT-TYPE
		SYNTAX		RollCallString
		MAX-ACCESS		read-only
		STATUS			current
		DESCRIPTION
				"TYPE: - Display
				 PAGE: - RollCall- Logging- Emb.Aud Logging
					Inp1 Emb.7 type=  cmdID= 36024  format=   "
		::= { iqmux43CmdEntry 36024 }


	iqmux43LoggingEmbedAudioLogInp1Emb8type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 type  cmdID= 35025 "
		::= { iqmux43CmdEntry 35025 }


	iqmux43LoggingEmbedAudioInp1Emb8type OBJECT-TYPE
		SYNTAX		RollCallString
		MAX-ACCESS		read-only
		STATUS			current
		DESCRIPTION
				"TYPE: - Display
				 PAGE: - RollCall- Logging- Emb.Aud Logging
					Inp1 Emb.8 type=  cmdID= 36025  format=   "
		::= { iqmux43CmdEntry 36025 }


	iqmux43LoggingOPAudioLogOutEmb1state OBJECT-TYPE
		SYNTAX		INTEGER { disable(0), enable(1) }
		MAX-ACCESS		read-write
		STATUS			current
		DESCRIPTION
				"TYPE: - Checkbox
				 PAGE: - RollCall- Logging
					Log Out Emb.1 state  cmdID= 35920 "
		::= { iqmux43CmdEntry 35920 }


	iqmux43LoggingOPAudioOutEmb1state OBJECT-TYPE
		SYNTAX		RollCallString
		MAX-ACCESS		read-only
		STATUS			current
		DESCRIPTION
				"TYPE: - Display
				 PAGE: - RollCall- Logging
					Out Emb.1 state=  cmdID= 36920  format=   "
		::= { iqmux43CmdEntry 36920 }


	iqmux43LoggingOPAudioLogOutEmb2state OBJECT-TYPE
		SYNTAX		INTEGER { disable(0), enable(1) }
		MAX-ACCESS		read-write
		STATUS			current
		DESCRIPTION
				"TYPE: - Checkbox
				 PAGE: - RollCall- Logging
					Log Out Emb.2 state  cmdID= 35921 "
		::= { iqmux43CmdEntry 35921 }


	iqmux43LoggingOPAudioOutEmb2state OBJECT-TYPE
		SYNTAX		RollCallString
		MAX-ACCESS		read-only
		STATUS			current
		DESCRIPTION
				"TYPE: - Display
				 PAGE: - RollCall- Logging
					Out Emb.2 state=  cmdID= 36921  format=   "
		::= { iqmux43CmdEntry 36921 }


	iqmux43LoggingOPAudioLogOutEmb3state OBJECT-TYPE
		SYNTAX		INTEGER { disable(0), enable(1) }
		MAX-ACCESS		read-write
		STATUS			current
		DESCRIPTION
				"TYPE: - Checkbox
				 PAGE: - RollCall- Logging
					Log Out Emb.3 state  cmdID= 35922 "
		::= { iqmux43CmdEntry 35922 }


	iqmux43LoggingOPAudioOutEmb3state OBJECT-TYPE
		SYNTAX		RollCallString
		MAX-ACCESS		read-only
		STATUS			current
		DESCRIPTION
				"TYPE: - Display
				 PAGE: - RollCall- Logging
					Out Emb.3 state=  cmdID= 36922  format=   "
		::= { iqmux43CmdEntry 36922 }


	iqmux43LoggingOPAudioLogOutEmb4state OBJECT-TYPE
		SYNTAX		INTEGER { disable(0), enable(1) }
		MAX-ACCESS		read-write
		STATUS			current
		DESCRIPTION
				"TYPE: - Checkbox
				 PAGE: - RollCall- Logging
					Log Out Emb.4 state  cmdID= 35923 "
		::= { iqmux43CmdEntry 35923 }


	iqmux43LoggingOPAudioOutEmb4state OBJECT-TYPE
		SYNTAX		RollCallString
		MAX-ACCESS		read-only
		STATUS			current
		DESCRIPTION
				"TYPE: - Display
				 PAGE: - RollCall- Logging
					Out Emb.4 state=  cmdID= 36923  format=   "
		::= { iqmux43CmdEntry 36923 }


	iqmux43LoggingOPAudioLogOutEmb5state OBJECT-TYPE
		SYNTAX		INTEGER { disable(0), enable(1) }
		MAX-ACCESS		read-write
		STATUS			current
		DESCRIPTION
				"TYPE: - Checkbox
				 PAGE: - RollCall- Logging
					Log Out Emb.5 state  cmdID= 35924 "
		::= { iqmux43CmdEntry 35924 }


	iqmux43LoggingOPAudioOutEmb5state OBJECT-TYPE
		SYNTAX		RollCallString
		MAX-ACCESS		read-only
		STATUS			current
		DESCRIPTION
				"TYPE: - Display
				 PAGE: - RollCall- Logging
					Out Emb.5 state=  cmdID= 36924  format=   "
		::= { iqmux43CmdEntry 36924 }


	iqmux43LoggingOPAudioLogOutEmb6state OBJECT-TYPE
		SYNTAX		INTEGER { disable(0), enable(1) }
		MAX-ACCESS		read-write
		STATUS			current
		DESCRIPTION
				"TYPE: - Checkbox
				 PAGE: - RollCall- Logging
					Log Out Emb.6 state  cmdID= 35925 "
		::= { iqmux43CmdEntry 35925 }


	iqmux43LoggingOPAudioOutEmb6state OBJECT-TYPE
		SYNTAX		RollCallString
		MAX-ACCESS		read-only
		STATUS			current
		DESCRIPTION
				"TYPE: - Display
				 PAGE: - RollCall- Logging
					Out Emb.6 state=  cmdID= 36925  format=   "
		::= { iqmux43CmdEntry 36925 }


	iqmux43LoggingOPAudioLogOutEmb7state OBJECT-TYPE
		SYNTAX		INTEGER { disable(0), enable(1) }
		MAX-ACCESS		read-write
		STATUS			current
		DESCRIPTION
				"TYPE: - Checkbox
				 PAGE: - RollCall- Logging
					Log Out Emb.7 state  cmdID= 35926 "
		::= { iqmux43CmdEntry 35926 }


	iqmux43LoggingOPAudioOutEmb7state OBJECT-TYPE
		SYNTAX		RollCallString
		MAX-ACCESS		read-only
		STATUS			current
		DESCRIPTION
				"TYPE: - Display
				 PAGE: - RollCall- Logging
					Out Emb.7 state=  cmdID= 36926  format=   "
		::= { iqmux43CmdEntry 36926 }


	iqmux43LoggingOPAudioLogOutEmb8state OBJECT-TYPE
		SYNTAX		INTEGER { disable(0), enable(1) }
		MAX-ACCESS		read-write
		STATUS			current
		DESCRIPTION
				"TYPE: - Checkbox
				 PAGE: - RollCall- Logging
					Log Out Emb.8 state  cmdID= 35927 "
		::= { iqmux43CmdEntry 35927 }


	iqmux43LoggingOPAudioOutEmb8state OBJECT-TYPE
		SYNTAX		RollCallString
		MAX-ACCESS		read-only
		STATUS			current
		DESCRIPTION
				"TYPE: - Display
				 PAGE: - RollCall- Logging
					Out Emb.8 state=  cmdID= 36927  format=   "
		::= { iqmux43CmdEntry 36927 }


	iqmux43LoggingOPAudioLogOutEmb1type OBJECT-TYPE
		SYNTAX		INTEGER { disable(0), enable(1) }
		MAX-ACCESS		read-write
		STATUS			current
		DESCRIPTION
				"TYPE: - Checkbox
				 PAGE: - RollCall- Logging
					Log Out Emb.1 type  cmdID= 35930 "
		::= { iqmux43CmdEntry 35930 }


	iqmux43LoggingOPAudioOutEmb1type OBJECT-TYPE
		SYNTAX		RollCallString
		MAX-ACCESS		read-only
		STATUS			current
		DESCRIPTION
				"TYPE: - Display
				 PAGE: - RollCall- Logging
					Out Emb.1 type=  cmdID= 36930  format=   "
		::= { iqmux43CmdEntry 36930 }


	iqmux43LoggingOPAudioLogOutEmb2type OBJECT-TYPE
		SYNTAX		INTEGER { disable(0), enable(1) }
		MAX-ACCESS		read-write
		STATUS			current
		DESCRIPTION
				"TYPE: - Checkbox
				 PAGE: - RollCall- Logging
					Log Out Emb.2 type  cmdID= 35931 "
		::= { iqmux43CmdEntry 35931 }


	iqmux43LoggingOPAudioOutEmb2type OBJECT-TYPE
		SYNTAX		RollCallString
		MAX-ACCESS		read-only
		STATUS			current
		DESCRIPTION
				"TYPE: - Display
				 PAGE: - RollCall- Logging
					Out Emb.2 type=  cmdID= 36931  format=   "
		::= { iqmux43CmdEntry 36931 }


	iqmux43LoggingOPAudioLogOutEmb3type OBJECT-TYPE
		SYNTAX		INTEGER { disable(0), enable(1) }
		MAX-ACCESS		read-write
		STATUS			current
		DESCRIPTION
				"TYPE: - Checkbox
				 PAGE: - RollCall- Logging
					Log Out Emb.3 type  cmdID= 35932 "
		::= { iqmux43CmdEntry 35932 }


	iqmux43LoggingOPAudioOutEmb3type OBJECT-TYPE
		SYNTAX		RollCallString
		MAX-ACCESS		read-only
		STATUS			current
		DESCRIPTION
				"TYPE: - Display
				 PAGE: - RollCall- Logging
					Out Emb.3 type=  cmdID= 36932  format=   "
		::= { iqmux43CmdEntry 36932 }


	iqmux43LoggingOPAudioLogOutEmb4type OBJECT-TYPE
		SYNTAX		INTEGER { disable(0), enable(1) }
		MAX-ACCESS		read-write
		STATUS			current
		DESCRIPTION
				"TYPE: - Checkbox
				 PAGE: - RollCall- Logging
					Log Out Emb.4 type  cmdID= 35933 "
		::= { iqmux43CmdEntry 35933 }


	iqmux43LoggingOPAudioOutEmb4type OBJECT-TYPE
		SYNTAX		RollCallString
		MAX-ACCESS		read-only
		STATUS			current
		DESCRIPTION
				"TYPE: - Display
				 PAGE: - RollCall- Logging
					Out Emb.4 type=  cmdID= 36933  format=   "
		::= { iqmux43CmdEntry 36933 }


	iqmux43LoggingOPAudioLogOutEmb5type OBJECT-TYPE
		SYNTAX		INTEGER { disable(0), enable(1) }
		MAX-ACCESS		read-write
		STATUS			current
		DESCRIPTION
				"TYPE: - Checkbox
				 PAGE: - RollCall- Logging
					Log Out Emb.5 type  cmdID= 35934 "
		::= { iqmux43CmdEntry 35934 }


	iqmux43LoggingOPAudioOutEmb5type OBJECT-TYPE
		SYNTAX		RollCallString
		MAX-ACCESS		read-only
		STATUS			current
		DESCRIPTION
				"TYPE: - Display
				 PAGE: - RollCall- Logging
					Out Emb.5 type=  cmdID= 36934  format=   "
		::= { iqmux43CmdEntry 36934 }


	iqmux43LoggingOPAudioLogOutEmb6type OBJECT-TYPE
		SYNTAX		INTEGER { disable(0), enable(1) }
		MAX-ACCESS		read-write
		STATUS			current
		DESCRIPTION
				"TYPE: - Checkbox
				 PAGE: - RollCall- Logging
					Log Out Emb.6 type  cmdID= 35935 "
		::= { iqmux43CmdEntry 35935 }


	iqmux43LoggingOPAudioOutEmb6type OBJECT-TYPE
		SYNTAX		RollCallString
		MAX-ACCESS		read-only
		STATUS			current
		DESCRIPTION
				"TYPE: - Display
				 PAGE: - RollCall- Logging
					Out Emb.6 type=  cmdID= 36935  format=   "
		::= { iqmux43CmdEntry 36935 }


	iqmux43LoggingOPAudioLogOutEmb7type OBJECT-TYPE
		SYNTAX		INTEGER { disable(0), enable(1) }
		MAX-ACCESS		read-write
		STATUS			current
		DESCRIPTION
				"TYPE: - Checkbox
				 PAGE: - RollCall- Logging
					Log Out Emb.7 type  cmdID= 35936 "
		::= { iqmux43CmdEntry 35936 }


	iqmux43LoggingOPAudioOutEmb7type OBJECT-TYPE
		SYNTAX		RollCallString
		MAX-ACCESS		read-only
		STATUS			current
		DESCRIPTION
				"TYPE: - Display
				 PAGE: - RollCall- Logging
					Out Emb.7 type=  cmdID= 36936  format=   "
		::= { iqmux43CmdEntry 36936 }


	iqmux43LoggingOPAudioLogOutEmb8type OBJECT-TYPE
		SYNTAX		INTEGER { disable(0), enable(1) }
		MAX-ACCESS		read-write
		STATUS			current
		DESCRIPTION
				"TYPE: - Checkbox
				 PAGE: - RollCall- Logging
					Log Out Emb.8 type  cmdID= 35937 "
		::= { iqmux43CmdEntry 35937 }


	iqmux43LoggingOPAudioOutEmb8type OBJECT-TYPE
		SYNTAX		RollCallString
		MAX-ACCESS		read-only
		STATUS			current
		DESCRIPTION
				"TYPE: - Display
				 PAGE: - RollCall- Logging
					Out Emb.8 type=  cmdID= 36937  format=   "
		::= { iqmux43CmdEntry 36937 }


	iqmux43LoggingOPAudioLevelLogOutEmb1LLev OBJECT-TYPE
		SYNTAX		INTEGER { disable(0), enable(1) }
		MAX-ACCESS		read-write
		STATUS			current
		DESCRIPTION
				"TYPE: - Checkbox
				 PAGE: - RollCall- Logging
					Log Out Emb.1-L Lev  cmdID= 35900 "
		::= { iqmux43CmdEntry 35900 }


	iqmux43LoggingOPAudioLevelOutEmb1LLevel OBJECT-TYPE
		SYNTAX		RollCallString
		MAX-ACCESS		read-only
		STATUS			current
		DESCRIPTION
				"TYPE: - Display
				 PAGE: - RollCall- Logging
					Out Emb.1-L Level=  cmdID= 36900  format=   "
		::= { iqmux43CmdEntry 36900 }


	iqmux43LoggingOPAudioLevelLogOutEmb1RLev OBJECT-TYPE
		SYNTAX		INTEGER { disable(0), enable(1) }
		MAX-ACCESS		read-write
		STATUS			current
		DESCRIPTION
				"TYPE: - Checkbox
				 PAGE: - RollCall- Logging
					Log Out Emb.1-R Lev  cmdID= 35901 "
		::= { iqmux43CmdEntry 35901 }


	iqmux43LoggingOPAudioLevelOutEmb1RLevel OBJECT-TYPE
		SYNTAX		RollCallString
		MAX-ACCESS		read-only
		STATUS			current
		DESCRIPTION
				"TYPE: - Display
				 PAGE: - RollCall- Logging
					Out Emb.1-R Level=  cmdID= 36901  format=   "
		::= { iqmux43CmdEntry 36901 }


	iqmux43LoggingOPAudioLevelLogOutEmb2LLev OBJECT-TYPE
		SYNTAX		INTEGER { disable(0), enable(1) }
		MAX-ACCESS		read-write
		STATUS			current
		DESCRIPTION
				"TYPE: - Checkbox
				 PAGE: - RollCall- Logging
					Log Out Emb.2-L Lev  cmdID= 35902 "
		::= { iqmux43CmdEntry 35902 }


	iqmux43LoggingOPAudioLevelOutEmb2LLevel OBJECT-TYPE
		SYNTAX		RollCallString
		MAX-ACCESS		read-only
		STATUS			current
		DESCRIPTION
				"TYPE: - Display
				 PAGE: - RollCall- Logging
					Out Emb.2-L Level=  cmdID= 36902  format=   "
		::= { iqmux43CmdEntry 36902 }


	iqmux43LoggingOPAudioLevelLogOutEmb2RLev OBJECT-TYPE
		SYNTAX		INTEGER { disable(0), enable(1) }
		MAX-ACCESS		read-write
		STATUS			current
		DESCRIPTION
				"TYPE: - Checkbox
				 PAGE: - RollCall- Logging
					Log Out Emb.2-R Lev  cmdID= 35903 "
		::= { iqmux43CmdEntry 35903 }


	iqmux43LoggingOPAudioLevelOutEmb2RLevel OBJECT-TYPE
		SYNTAX		RollCallString
		MAX-ACCESS		read-only
		STATUS			current
		DESCRIPTION
				"TYPE: - Display
				 PAGE: - RollCall- Logging
					Out Emb.2-R Level=  cmdID= 36903  format=   "
		::= { iqmux43CmdEntry 36903 }


	iqmux43LoggingOPAudioLevelLogOutEmb3LLev OBJECT-TYPE
		SYNTAX		INTEGER { disable(0), enable(1) }
		MAX-ACCESS		read-write
		STATUS			current
		DESCRIPTION
				"TYPE: - Checkbox
				 PAGE: - RollCall- Logging
					Log Out Emb.3-L Lev  cmdID= 35904 "
		::= { iqmux43CmdEntry 35904 }


	iqmux43LoggingOPAudioLevelOutEmb3LLevel OBJECT-TYPE
		SYNTAX		RollCallString
		MAX-ACCESS		read-only
		STATUS			current
		DESCRIPTION
				"TYPE: - Display
				 PAGE: - RollCall- Logging
					Out Emb.3-L Level=  cmdID= 36904  format=   "
		::= { iqmux43CmdEntry 36904 }


	iqmux43LoggingOPAudioLevelLogOutEmb3RLev OBJECT-TYPE
		SYNTAX		INTEGER { disable(0), enable(1) }
		MAX-ACCESS		read-write
		STATUS			current
		DESCRIPTION
				"TYPE: - Checkbox
				 PAGE: - RollCall- Logging
					Log Out Emb.3-R Lev  cmdID= 35905 "
		::= { iqmux43CmdEntry 35905 }


	iqmux43LoggingOPAudioLevelOutEmb3RLevel OBJECT-TYPE
		SYNTAX		RollCallString
		MAX-ACCESS		read-only
		STATUS			current
		DESCRIPTION
				"TYPE: - Display
				 PAGE: - RollCall- Logging
					Out Emb.3-R Level=  cmdID= 36905  format=   "
		::= { iqmux43CmdEntry 36905 }


	iqmux43LoggingOPAudioLevelLogOutEmb4LLev OBJECT-TYPE
		SYNTAX		INTEGER { disable(0), enable(1) }
		MAX-ACCESS		read-write
		STATUS			current
		DESCRIPTION
				"TYPE: - Checkbox
				 PAGE: - RollCall- Logging
					Log Out Emb.4-L Lev  cmdID= 35906 "
		::= { iqmux43CmdEntry 35906 }


	iqmux43LoggingOPAudioLevelOutEmb4LLevel OBJECT-TYPE
		SYNTAX		RollCallString
		MAX-ACCESS		read-only
		STATUS			current
		DESCRIPTION
				"TYPE: - Display
				 PAGE: - RollCall- Logging
					Out Emb.4-L Level=  cmdID= 36906  format=   "
		::= { iqmux43CmdEntry 36906 }


	iqmux43LoggingOPAudioLevelLogOutEmb4RLev OBJECT-TYPE
		SYNTAX		INTEGER { disable(0), enable(1) }
		MAX-ACCESS		read-write
		STATUS			current
		DESCRIPTION
				"TYPE: - Checkbox
				 PAGE: - RollCall- Logging
					Log Out Emb.4-R Lev  cmdID= 35907 "
		::= { iqmux43CmdEntry 35907 }


	iqmux43LoggingOPAudioLevelOutEmb4RLevel OBJECT-TYPE
		SYNTAX		RollCallString
		MAX-ACCESS		read-only
		STATUS			current
		DESCRIPTION
				"TYPE: - Display
				 PAGE: - RollCall- Logging
					Out Emb.4-R Level=  cmdID= 36907  format=   "
		::= { iqmux43CmdEntry 36907 }


	iqmux43LoggingOPAudioLevelLogOutEmb5LLev OBJECT-TYPE
		SYNTAX		INTEGER { disable(0), enable(1) }
		MAX-ACCESS		read-write
		STATUS			current
		DESCRIPTION
				"TYPE: - Checkbox
				 PAGE: - RollCall- Logging
					Log Out Emb.5-L Lev  cmdID= 35908 "
		::= { iqmux43CmdEntry 35908 }


	iqmux43LoggingOPAudioLevelOutEmb5LLevel OBJECT-TYPE
		SYNTAX		RollCallString
		MAX-ACCESS		read-only
		STATUS			current
		DESCRIPTION
				"TYPE: - Display
				 PAGE: - RollCall- Logging
					Out Emb.5-L Level=  cmdID= 36908  format=   "
		::= { iqmux43CmdEntry 36908 }


	iqmux43LoggingOPAudioLevelLogOutEmb5RLev OBJECT-TYPE
		SYNTAX		INTEGER { disable(0), enable(1) }
		MAX-ACCESS		read-write
		STATUS			current
		DESCRIPTION
				"TYPE: - Checkbox
				 PAGE: - RollCall- Logging
					Log Out Emb.5-R Lev  cmdID= 35909 "
		::= { iqmux43CmdEntry 35909 }


	iqmux43LoggingOPAudioLevelOutEmb5RLevel OBJECT-TYPE
		SYNTAX		RollCallString
		MAX-ACCESS		read-only
		STATUS			current
		DESCRIPTION
				"TYPE: - Display
				 PAGE: - RollCall- Logging
					Out Emb.5-R Level=  cmdID= 36909  format=   "
		::= { iqmux43CmdEntry 36909 }


	iqmux43LoggingOPAudioLevelLogOutEmb6LLev OBJECT-TYPE
		SYNTAX		INTEGER { disable(0), enable(1) }
		MAX-ACCESS		read-write
		STATUS			current
		DESCRIPTION
				"TYPE: - Checkbox
				 PAGE: - RollCall- Logging
					Log Out Emb.6-L Lev  cmdID= 35910 "
		::= { iqmux43CmdEntry 35910 }


	iqmux43LoggingOPAudioLevelOutEmb6LLevel OBJECT-TYPE
		SYNTAX		RollCallString
		MAX-ACCESS		read-only
		STATUS			current
		DESCRIPTION
				"TYPE: - Display
				 PAGE: - RollCall- Logging
					Out Emb.6-L Level=  cmdID= 36910  format=   "
		::= { iqmux43CmdEntry 36910 }


	iqmux43LoggingOPAudioLevelLogOutEmb6RLev OBJECT-TYPE
		SYNTAX		INTEGER { disable(0), enable(1) }
		MAX-ACCESS		read-write
		STATUS			current
		DESCRIPTION
				"TYPE: - Checkbox
				 PAGE: - RollCall- Logging
					Log Out Emb.6-R Lev  cmdID= 35911 "
		::= { iqmux43CmdEntry 35911 }


	iqmux43LoggingOPAudioLevelOutEmb6RLevel OBJECT-TYPE
		SYNTAX		RollCallString
		MAX-ACCESS		read-only
		STATUS			current
		DESCRIPTION
				"TYPE: - Display
				 PAGE: - RollCall- Logging
					Out Emb.6-R Level=  cmdID= 36911  format=   "
		::= { iqmux43CmdEntry 36911 }


	iqmux43LoggingOPAudioLevelLogOutEmb7LLev OBJECT-TYPE
		SYNTAX		INTEGER { disable(0), enable(1) }
		MAX-ACCESS		read-write
		STATUS			current
		DESCRIPTION
				"TYPE: - Checkbox
				 PAGE: - RollCall- Logging
					Log Out Emb.7-L Lev  cmdID= 35912 "
		::= { iqmux43CmdEntry 35912 }


	iqmux43LoggingOPAudioLevelOutEmb7LLevel OBJECT-TYPE
		SYNTAX		RollCallString
		MAX-ACCESS		read-only
		STATUS			current
		DESCRIPTION
				"TYPE: - Display
				 PAGE: - RollCall- Logging
					Out Emb.7-L Level=  cmdID= 36912  format=   "
		::= { iqmux43CmdEntry 36912 }


	iqmux43LoggingOPAudioLevelLogOutEmb7RLev OBJECT-TYPE
		SYNTAX		INTEGER { disable(0), enable(1) }
		MAX-ACCESS		read-write
		STATUS			current
		DESCRIPTION
				"TYPE: - Checkbox
				 PAGE: - RollCall- Logging
					Log Out Emb.7-R Lev  cmdID= 35913 "
		::= { iqmux43CmdEntry 35913 }


	iqmux43LoggingOPAudioLevelOutEmb7RLevel OBJECT-TYPE
		SYNTAX		RollCallString
		MAX-ACCESS		read-only
		STATUS			current
		DESCRIPTION
				"TYPE: - Display
				 PAGE: - RollCall- Logging
					Out Emb.7-R Level=  cmdID= 36913  format=   "
		::= { iqmux43CmdEntry 36913 }


	iqmux43LoggingOPAudioLevelLogOutEmb8LLev OBJECT-TYPE
		SYNTAX		INTEGER { disable(0), enable(1) }
		MAX-ACCESS		read-write
		STATUS			current
		DESCRIPTION
				"TYPE: - Checkbox
				 PAGE: - RollCall- Logging
					Log Out Emb.8-L Lev  cmdID= 35914 "
		::= { iqmux43CmdEntry 35914 }


	iqmux43LoggingOPAudioLevelOutEmb8LLevel OBJECT-TYPE
		SYNTAX		RollCallString
		MAX-ACCESS		read-only
		STATUS			current
		DESCRIPTION
				"TYPE: - Display
				 PAGE: - RollCall- Logging
					Out Emb.8-L Level=  cmdID= 36914  format=   "
		::= { iqmux43CmdEntry 36914 }


	iqmux43LoggingOPAudioLevelLogOutEmb8RLev OBJECT-TYPE
		SYNTAX		INTEGER { disable(0), enable(1) }
		MAX-ACCESS		read-write
		STATUS			current
		DESCRIPTION
				"TYPE: - Checkbox
				 PAGE: - RollCall- Logging
					Log Out Emb.8-R Lev  cmdID= 35915 "
		::= { iqmux43CmdEntry 35915 }


	iqmux43LoggingOPAudioLevelOutEmb8RLevel OBJECT-TYPE
		SYNTAX		RollCallString
		MAX-ACCESS		read-only
		STATUS			current
		DESCRIPTION
				"TYPE: - Display
				 PAGE: - RollCall- Logging
					Out Emb.8-R Level=  cmdID= 36915  format=   "
		::= { iqmux43CmdEntry 36915 }


	iqmux43LoggingOPDolbyELogEmbDolbyE1 OBJECT-TYPE
		SYNTAX		INTEGER { disable(0), enable(1) }
		MAX-ACCESS		read-write
		STATUS			current
		DESCRIPTION
				"TYPE: - Checkbox
				 PAGE: - RollCall- Logging
					Log Emb DolbyE 1  cmdID= 35950 "
		::= { iqmux43CmdEntry 35950 }


	iqmux43LoggingOPDolbyEEmbDolbyE1 OBJECT-TYPE
		SYNTAX		RollCallString
		MAX-ACCESS		read-only
		STATUS			current
		DESCRIPTION
				"TYPE: - Display
				 PAGE: - RollCall- Logging
					Emb DolbyE 1=  cmdID= 36950  format=   "
		::= { iqmux43CmdEntry 36950 }


	iqmux43LoggingOPDolbyELogEmbDolbyE2 OBJECT-TYPE
		SYNTAX		INTEGER { disable(0), enable(1) }
		MAX-ACCESS		read-write
		STATUS			current
		DESCRIPTION
				"TYPE: - Checkbox
				 PAGE: - RollCall- Logging
					Log Emb DolbyE 2  cmdID= 35951 "
		::= { iqmux43CmdEntry 35951 }


	iqmux43LoggingOPDolbyEEmbDolbyE2 OBJECT-TYPE
		SYNTAX		RollCallString
		MAX-ACCESS		read-only
		STATUS			current
		DESCRIPTION
				"TYPE: - Display
				 PAGE: - RollCall- Logging
					Emb DolbyE 2=  cmdID= 36951  format=   "
		::= { iqmux43CmdEntry 36951 }


	iqmux43LoggingOPDolbyELogEmbDolbyE3 OBJECT-TYPE
		SYNTAX		INTEGER { disable(0), enable(1) }
		MAX-ACCESS		read-write
		STATUS			current
		DESCRIPTION
				"TYPE: - Checkbox
				 PAGE: - RollCall- Logging
					Log Emb DolbyE 3  cmdID= 35952 "
		::= { iqmux43CmdEntry 35952 }


	iqmux43LoggingOPDolbyEEmbDolbyE3 OBJECT-TYPE
		SYNTAX		RollCallString
		MAX-ACCESS		read-only
		STATUS			current
		DESCRIPTION
				"TYPE: - Display
				 PAGE: - RollCall- Logging
					Emb DolbyE 3=  cmdID= 36952  format=   "
		::= { iqmux43CmdEntry 36952 }


	iqmux43LoggingOPDolbyELogEmbDolbyE4 OBJECT-TYPE
		SYNTAX		INTEGER { disable(0), enable(1) }
		MAX-ACCESS		read-write
		STATUS			current
		DESCRIPTION
				"TYPE: - Checkbox
				 PAGE: - RollCall- Logging
					Log Emb DolbyE 4  cmdID= 35953 "
		::= { iqmux43CmdEntry 35953 }


	iqmux43LoggingOPDolbyEEmbDolbyE4 OBJECT-TYPE
		SYNTAX		RollCallString
		MAX-ACCESS		read-only
		STATUS			current
		DESCRIPTION
				"TYPE: - Display
				 PAGE: - RollCall- Logging
					Emb DolbyE 4=  cmdID= 36953  format=   "
		::= { iqmux43CmdEntry 36953 }


	iqmux43LoggingOPDolbyELogEmbDolbyE5 OBJECT-TYPE
		SYNTAX		INTEGER { disable(0), enable(1) }
		MAX-ACCESS		read-write
		STATUS			current
		DESCRIPTION
				"TYPE: - Checkbox
				 PAGE: - RollCall- Logging
					Log Emb DolbyE 5  cmdID= 35954 "
		::= { iqmux43CmdEntry 35954 }


	iqmux43LoggingOPDolbyEEmbDolbyE5 OBJECT-TYPE
		SYNTAX		RollCallString
		MAX-ACCESS		read-only
		STATUS			current
		DESCRIPTION
				"TYPE: - Display
				 PAGE: - RollCall- Logging
					Emb DolbyE 5=  cmdID= 36954  format=   "
		::= { iqmux43CmdEntry 36954 }


	iqmux43LoggingOPDolbyELogEmbDolbyE6 OBJECT-TYPE
		SYNTAX		INTEGER { disable(0), enable(1) }
		MAX-ACCESS		read-write
		STATUS			current
		DESCRIPTION
				"TYPE: - Checkbox
				 PAGE: - RollCall- Logging
					Log Emb DolbyE 6  cmdID= 35955 "
		::= { iqmux43CmdEntry 35955 }


	iqmux43LoggingOPDolbyEEmbDolbyE6 OBJECT-TYPE
		SYNTAX		RollCallString
		MAX-ACCESS		read-only
		STATUS			current
		DESCRIPTION
				"TYPE: - Display
				 PAGE: - RollCall- Logging
					Emb DolbyE 6=  cmdID= 36955  format=   "
		::= { iqmux43CmdEntry 36955 }


	iqmux43LoggingOPDolbyELogEmbDolbyE7 OBJECT-TYPE
		SYNTAX		INTEGER { disable(0), enable(1) }
		MAX-ACCESS		read-write
		STATUS			current
		DESCRIPTION
				"TYPE: - Checkbox
				 PAGE: - RollCall- Logging
					Log Emb DolbyE 7  cmdID= 35956 "
		::= { iqmux43CmdEntry 35956 }


	iqmux43LoggingOPDolbyEEmbDolbyE7 OBJECT-TYPE
		SYNTAX		RollCallString
		MAX-ACCESS		read-only
		STATUS			current
		DESCRIPTION
				"TYPE: - Display
				 PAGE: - RollCall- Logging
					Emb DolbyE 7=  cmdID= 36956  format=   "
		::= { iqmux43CmdEntry 36956 }


	iqmux43LoggingOPDolbyELogEmbDolbyE8 OBJECT-TYPE
		SYNTAX		INTEGER { disable(0), enable(1) }
		MAX-ACCESS		read-write
		STATUS			current
		DESCRIPTION
				"TYPE: - Checkbox
				 PAGE: - RollCall- Logging
					Log Emb DolbyE 8  cmdID= 35957 "
		::= { iqmux43CmdEntry 35957 }


	iqmux43LoggingOPDolbyEEmbDolbyE8 OBJECT-TYPE
		SYNTAX		RollCallString
		MAX-ACCESS		read-only
		STATUS			current
		DESCRIPTION
				"TYPE: - Display
				 PAGE: - RollCall- Logging
					Emb DolbyE 8=  cmdID= 36957  format=   "
		::= { iqmux43CmdEntry 36957 }


	iqmux43LoggingAESInputLogAESInput1sta OBJECT-TYPE
		SYNTAX		INTEGER { disable(0), enable(1) }
		MAX-ACCESS		read-write
		STATUS			current
		DESCRIPTION
				"TYPE: - Checkbox
				 PAGE: - RollCall- Logging
					Log AES Input 1 sta  cmdID= 35600 "
		::= { iqmux43CmdEntry 35600 }


	iqmux43LoggingAESInputAESInput1state OBJECT-TYPE
		SYNTAX		RollCallString
		MAX-ACCESS		read-only
		STATUS			current
		DESCRIPTION
				"TYPE: - Display
				 PAGE: - RollCall- Logging
					AES Input 1 state=  cmdID= 36600  format=   "
		::= { iqmux43CmdEntry 36600 }


	iqmux43LoggingAESInputLogAESInput2sta OBJECT-TYPE
		SYNTAX		INTEGER { disable(0), enable(1) }
		MAX-ACCESS		read-write
		STATUS			current
		DESCRIPTION
				"TYPE: - Checkbox
				 PAGE: - RollCall- Logging
					Log AES Input 2 sta  cmdID= 35601 "
		::= { iqmux43CmdEntry 35601 }


	iqmux43LoggingAESInputAESInput2state OBJECT-TYPE
		SYNTAX		RollCallString
		MAX-ACCESS		read-only
		STATUS			current
		DESCRIPTION
				"TYPE: - Display
				 PAGE: - RollCall- Logging
					AES Input 2 state=  cmdID= 36601  format=   "
		::= { iqmux43CmdEntry 36601 }


	iqmux43LoggingAESInputLogAESInput3sta OBJECT-TYPE
		SYNTAX		INTEGER { disable(0), enable(1) }
		MAX-ACCESS		read-write
		STATUS			current
		DESCRIPTION
				"TYPE: - Checkbox
				 PAGE: - RollCall- Logging
					Log AES Input 3 sta  cmdID= 35602 "
		::= { iqmux43CmdEntry 35602 }


	iqmux43LoggingAESInputAESInput3state OBJECT-TYPE
		SYNTAX		RollCallString
		MAX-ACCESS		read-only
		STATUS			current
		DESCRIPTION
				"TYPE: - Display
				 PAGE: - RollCall- Logging
					AES Input 3 state=  cmdID= 36602  format=   "
		::= { iqmux43CmdEntry 36602 }


	iqmux43LoggingAESInputLogAESInput4sta OBJECT-TYPE
		SYNTAX		INTEGER { disable(0), enable(1) }
		MAX-ACCESS		read-write
		STATUS			current
		DESCRIPTION
				"TYPE: - Checkbox
				 PAGE: - RollCall- Logging
					Log AES Input 4 sta  cmdID= 35603 "
		::= { iqmux43CmdEntry 35603 }


	iqmux43LoggingAESInputAESInput4state OBJECT-TYPE
		SYNTAX		RollCallString
		MAX-ACCESS		read-only
		STATUS			current
		DESCRIPTION
				"TYPE: - Display
				 PAGE: - RollCall- Logging
					AES Input 4 state=  cmdID= 36603  format=   "
		::= { iqmux43CmdEntry 36603 }


	iqmux43LoggingAESInputLogAESInput5sta OBJECT-TYPE
		SYNTAX		INTEGER { disable(0), enable(1) }
		MAX-ACCESS		read-write
		STATUS			current
		DESCRIPTION
				"TYPE: - Checkbox
				 PAGE: - RollCall- Logging
					Log AES Input 5 sta  cmdID= 35604 "
		::= { iqmux43CmdEntry 35604 }


	iqmux43LoggingAESInputAESInput5state OBJECT-TYPE
		SYNTAX		RollCallString
		MAX-ACCESS		read-only
		STATUS			current
		DESCRIPTION
				"TYPE: - Display
				 PAGE: - RollCall- Logging
					AES Input 5 state=  cmdID= 36604  format=   "
		::= { iqmux43CmdEntry 36604 }


	iqmux43LoggingAESInputLogAESInput6sta OBJECT-TYPE
		SYNTAX		INTEGER { disable(0), enable(1) }
		MAX-ACCESS		read-write
		STATUS			current
		DESCRIPTION
				"TYPE: - Checkbox
				 PAGE: - RollCall- Logging
					Log AES Input 6 sta  cmdID= 35605 "
		::= { iqmux43CmdEntry 35605 }


	iqmux43LoggingAESInputAESInput6state OBJECT-TYPE
		SYNTAX		RollCallString
		MAX-ACCESS		read-only
		STATUS			current
		DESCRIPTION
				"TYPE: - Display
				 PAGE: - RollCall- Logging
					AES Input 6 state=  cmdID= 36605  format=   "
		::= { iqmux43CmdEntry 36605 }


	iqmux43LoggingAESInputLogAESInput7sta OBJECT-TYPE
		SYNTAX		INTEGER { disable(0), enable(1) }
		MAX-ACCESS		read-write
		STATUS			current
		DESCRIPTION
				"TYPE: - Checkbox
				 PAGE: - RollCall- Logging
					Log AES Input 7 sta  cmdID= 35606 "
		::= { iqmux43CmdEntry 35606 }


	iqmux43LoggingAESInputAESInput7state OBJECT-TYPE
		SYNTAX		RollCallString
		MAX-ACCESS		read-only
		STATUS			current
		DESCRIPTION
				"TYPE: - Display
				 PAGE: - RollCall- Logging
					AES Input 7 state=  cmdID= 36606  format=   "
		::= { iqmux43CmdEntry 36606 }


	iqmux43LoggingAESInputLogAESInput8sta OBJECT-TYPE
		SYNTAX		INTEGER { disable(0), enable(1) }
		MAX-ACCESS		read-write
		STATUS			current
		DESCRIPTION
				"TYPE: - Checkbox
				 PAGE: - RollCall- Logging
					Log AES Input 8 sta  cmdID= 35607 "
		::= { iqmux43CmdEntry 35607 }


	iqmux43LoggingAESInputAESInput8state OBJECT-TYPE
		SYNTAX		RollCallString
		MAX-ACCESS		read-only
		STATUS			current
		DESCRIPTION
				"TYPE: - Display
				 PAGE: - RollCall- Logging
					AES Input 8 state=  cmdID= 36607  format=   "
		::= { iqmux43CmdEntry 36607 }


	iqmux43LoggingAESInputLogAESInput1typ OBJECT-TYPE
		SYNTAX		INTEGER { disable(0), enable(1) }
		MAX-ACCESS		read-write
		STATUS			current
		DESCRIPTION
				"TYPE: - Checkbox
				 PAGE: - RollCall- Logging
					Log AES Input 1 typ  cmdID= 35640 "
		::= { iqmux43CmdEntry 35640 }


	iqmux43LoggingAESInputAESInput1type OBJECT-TYPE
		SYNTAX		RollCallString
		MAX-ACCESS		read-only
		STATUS			current
		DESCRIPTION
				"TYPE: - Display
				 PAGE: - RollCall- Logging
					AES Input 1 type=  cmdID= 36640  format=   "
		::= { iqmux43CmdEntry 36640 }


	iqmux43LoggingAESInputLogAESInput2typ OBJECT-TYPE
		SYNTAX		INTEGER { disable(0), enable(1) }
		MAX-ACCESS		read-write
		STATUS			current
		DESCRIPTION
				"TYPE: - Checkbox
				 PAGE: - RollCall- Logging
					Log AES Input 2 typ  cmdID= 35641 "
		::= { iqmux43CmdEntry 35641 }


	iqmux43LoggingAESInputAESInput2type OBJECT-TYPE
		SYNTAX		RollCallString
		MAX-ACCESS		read-only
		STATUS			current
		DESCRIPTION
				"TYPE: - Display
				 PAGE: - RollCall- Logging
					AES Input 2 type=  cmdID= 36641  format=   "
		::= { iqmux43CmdEntry 36641 }


	iqmux43LoggingAESInputLogAESInput3typ OBJECT-TYPE
		SYNTAX		INTEGER { disable(0), enable(1) }
		MAX-ACCESS		read-write
		STATUS			current
		DESCRIPTION
				"TYPE: - Checkbox
				 PAGE: - RollCall- Logging
					Log AES Input 3 typ  cmdID= 35642 "
		::= { iqmux43CmdEntry 35642 }


	iqmux43LoggingAESInputAESInput3type OBJECT-TYPE
		SYNTAX		RollCallString
		MAX-ACCESS		read-only
		STATUS			current
		DESCRIPTION
				"TYPE: - Display
				 PAGE: - RollCall- Logging
					AES Input 3 type=  cmdID= 36642  format=   "
		::= { iqmux43CmdEntry 36642 }


	iqmux43LoggingAESInputLogAESInput4typ OBJECT-TYPE
		SYNTAX		INTEGER { disable(0), enable(1) }
		MAX-ACCESS		read-write
		STATUS			current
		DESCRIPTION
				"TYPE: - Checkbox
				 PAGE: - RollCall- Logging
					Log AES Input 4 typ  cmdID= 35643 "
		::= { iqmux43CmdEntry 35643 }


	iqmux43LoggingAESInputAESInput4type OBJECT-TYPE
		SYNTAX		RollCallString
		MAX-ACCESS		read-only
		STATUS			current
		DESCRIPTION
				"TYPE: - Display
				 PAGE: - RollCall- Logging
					AES Input 4 type=  cmdID= 36643  format=   "
		::= { iqmux43CmdEntry 36643 }


	iqmux43LoggingAESInputLogAESInput5typ OBJECT-TYPE
		SYNTAX		INTEGER { disable(0), enable(1) }
		MAX-ACCESS		read-write
		STATUS			current
		DESCRIPTION
				"TYPE: - Checkbox
				 PAGE: - RollCall- Logging
					Log AES Input 5 typ  cmdID= 35644 "
		::= { iqmux43CmdEntry 35644 }


	iqmux43LoggingAESInputAESInput5type OBJECT-TYPE
		SYNTAX		RollCallString
		MAX-ACCESS		read-only
		STATUS			current
		DESCRIPTION
				"TYPE: - Display
				 PAGE: - RollCall- Logging
					AES Input 5 type=  cmdID= 36644  format=   "
		::= { iqmux43CmdEntry 36644 }


	iqmux43LoggingAESInputLogAESInput6typ OBJECT-TYPE
		SYNTAX		INTEGER { disable(0), enable(1) }
		MAX-ACCESS		read-write
		STATUS			current
		DESCRIPTION
				"TYPE: - Checkbox
				 PAGE: - RollCall- Logging
					Log AES Input 6 typ  cmdID= 35645 "
		::= { iqmux43CmdEntry 35645 }


	iqmux43LoggingAESInputAESInput6type OBJECT-TYPE
		SYNTAX		RollCallString
		MAX-ACCESS		read-only
		STATUS			current
		DESCRIPTION
				"TYPE: - Display
				 PAGE: - RollCall- Logging
					AES Input 6 type=  cmdID= 36645  format=   "
		::= { iqmux43CmdEntry 36645 }


	iqmux43LoggingAESInputLogAESInput7typ OBJECT-TYPE
		SYNTAX		INTEGER { disable(0), enable(1) }
		MAX-ACCESS		read-write
		STATUS			current
		DESCRIPTION
				"TYPE: - Checkbox
				 PAGE: - RollCall- Logging
					Log AES Input 7 typ  cmdID= 35646 "
		::= { iqmux43CmdEntry 35646 }


	iqmux43LoggingAESInputAESInput7type OBJECT-TYPE
		SYNTAX		RollCallString
		MAX-ACCESS		read-only
		STATUS			current
		DESCRIPTION
				"TYPE: - Display
				 PAGE: - RollCall- Logging
					AES Input 7 type=  cmdID= 36646  format=   "
		::= { iqmux43CmdEntry 36646 }


	iqmux43LoggingAESInputLogAESInput8typ OBJECT-TYPE
		SYNTAX		INTEGER { disable(0), enable(1) }
		MAX-ACCESS		read-write
		STATUS			current
		DESCRIPTION
				"TYPE: - Checkbox
				 PAGE: - RollCall- Logging
					Log AES Input 8 typ  cmdID= 35647 "
		::= { iqmux43CmdEntry 35647 }


	iqmux43LoggingAESInputAESInput8type OBJECT-TYPE
		SYNTAX		RollCallString
		MAX-ACCESS		read-only
		STATUS			current
		DESCRIPTION
				"TYPE: - Display
				 PAGE: - RollCall- Logging
					AES Input 8 type=  cmdID= 36647  format=   "
		::= { iqmux43CmdEntry 36647 }


	iqmux43LoggingAESOutputLogAESOutput1st OBJECT-TYPE
		SYNTAX		INTEGER { disable(0), enable(1) }
		MAX-ACCESS		read-write
		STATUS			current
		DESCRIPTION
				"TYPE: - Checkbox
				 PAGE: - RollCall- Logging
					Log AES Output 1 st  cmdID= 35620 "
		::= { iqmux43CmdEntry 35620 }


	iqmux43LoggingAESOutputAESOutput1state OBJECT-TYPE
		SYNTAX		RollCallString
		MAX-ACCESS		read-only
		STATUS			current
		DESCRIPTION
				"TYPE: - Display
				 PAGE: - RollCall- Logging
					AES Output 1 state=  cmdID= 36620  format=   "
		::= { iqmux43CmdEntry 36620 }


	iqmux43LoggingAESOutputLogAESOutput2st OBJECT-TYPE
		SYNTAX		INTEGER { disable(0), enable(1) }
		MAX-ACCESS		read-write
		STATUS			current
		DESCRIPTION
				"TYPE: - Checkbox
				 PAGE: - RollCall- Logging
					Log AES Output 2 st  cmdID= 35621 "
		::= { iqmux43CmdEntry 35621 }


	iqmux43LoggingAESOutputAESOutput2state OBJECT-TYPE
		SYNTAX		RollCallString
		MAX-ACCESS		read-only
		STATUS			current
		DESCRIPTION
				"TYPE: - Display
				 PAGE: - RollCall- Logging
					AES Output 2 state=  cmdID= 36621  format=   "
		::= { iqmux43CmdEntry 36621 }


	iqmux43LoggingAESOutputLogAESOutput3st OBJECT-TYPE
		SYNTAX		INTEGER { disable(0), enable(1) }
		MAX-ACCESS		read-write
		STATUS			current
		DESCRIPTION
				"TYPE: - Checkbox
				 PAGE: - RollCall- Logging
					Log AES Output 3 st  cmdID= 35622 "
		::= { iqmux43CmdEntry 35622 }


	iqmux43LoggingAESOutputAESOutput3state OBJECT-TYPE
		SYNTAX		RollCallString
		MAX-ACCESS		read-only
		STATUS			current
		DESCRIPTION
				"TYPE: - Display
				 PAGE: - RollCall- Logging
					AES Output 3 state=  cmdID= 36622  format=   "
		::= { iqmux43CmdEntry 36622 }


	iqmux43LoggingAESOutputLogAESOutput4st OBJECT-TYPE
		SYNTAX		INTEGER { disable(0), enable(1) }
		MAX-ACCESS		read-write
		STATUS			current
		DESCRIPTION
				"TYPE: - Checkbox
				 PAGE: - RollCall- Logging
					Log AES Output 4 st  cmdID= 35623 "
		::= { iqmux43CmdEntry 35623 }


	iqmux43LoggingAESOutputAESOutput4state OBJECT-TYPE
		SYNTAX		RollCallString
		MAX-ACCESS		read-only
		STATUS			current
		DESCRIPTION
				"TYPE: - Display
				 PAGE: - RollCall- Logging
					AES Output 4 state=  cmdID= 36623  format=   "
		::= { iqmux43CmdEntry 36623 }


	iqmux43LoggingAESOutputLogAESOutput5st OBJECT-TYPE
		SYNTAX		INTEGER { disable(0), enable(1) }
		MAX-ACCESS		read-write
		STATUS			current
		DESCRIPTION
				"TYPE: - Checkbox
				 PAGE: - RollCall- Logging
					Log AES Output 5 st  cmdID= 35624 "
		::= { iqmux43CmdEntry 35624 }


	iqmux43LoggingAESOutputAESOutput5state OBJECT-TYPE
		SYNTAX		RollCallString
		MAX-ACCESS		read-only
		STATUS			current
		DESCRIPTION
				"TYPE: - Display
				 PAGE: - RollCall- Logging
					AES Output 5 state=  cmdID= 36624  format=   "
		::= { iqmux43CmdEntry 36624 }


	iqmux43LoggingAESOutputLogAESOutput6st OBJECT-TYPE
		SYNTAX		INTEGER { disable(0), enable(1) }
		MAX-ACCESS		read-write
		STATUS			current
		DESCRIPTION
				"TYPE: - Checkbox
				 PAGE: - RollCall- Logging
					Log AES Output 6 st  cmdID= 35625 "
		::= { iqmux43CmdEntry 35625 }


	iqmux43LoggingAESOutputAESOutput6state OBJECT-TYPE
		SYNTAX		RollCallString
		MAX-ACCESS		read-only
		STATUS			current
		DESCRIPTION
				"TYPE: - Display
				 PAGE: - RollCall- Logging
					AES Output 6 state=  cmdID= 36625  format=   "
		::= { iqmux43CmdEntry 36625 }


	iqmux43LoggingAESOutputLogAESOutput7st OBJECT-TYPE
		SYNTAX		INTEGER { disable(0), enable(1) }
		MAX-ACCESS		read-write
		STATUS			current
		DESCRIPTION
				"TYPE: - Checkbox
				 PAGE: - RollCall- Logging
					Log AES Output 7 st  cmdID= 35626 "
		::= { iqmux43CmdEntry 35626 }


	iqmux43LoggingAESOutputAESOutput7state OBJECT-TYPE
		SYNTAX		RollCallString
		MAX-ACCESS		read-only
		STATUS			current
		DESCRIPTION
				"TYPE: - Display
				 PAGE: - RollCall- Logging
					AES Output 7 state=  cmdID= 36626  format=   "
		::= { iqmux43CmdEntry 36626 }


	iqmux43LoggingAESOutputLogAESOutput8st OBJECT-TYPE
		SYNTAX		INTEGER { disable(0), enable(1) }
		MAX-ACCESS		read-write
		STATUS			current
		DESCRIPTION
				"TYPE: - Checkbox
				 PAGE: - RollCall- Logging
					Log AES Output 8 st  cmdID= 35627 "
		::= { iqmux43CmdEntry 35627 }


	iqmux43LoggingAESOutputAESOutput8state OBJECT-TYPE
		SYNTAX		RollCallString
		MAX-ACCESS		read-only
		STATUS			current
		DESCRIPTION
				"TYPE: - Display
				 PAGE: - RollCall- Logging
					AES Output 8 state=  cmdID= 36627  format=   "
		::= { iqmux43CmdEntry 36627 }


	iqmux43LoggingAESOutputLogAESOutput1ty OBJECT-TYPE
		SYNTAX		INTEGER { disable(0), enable(1) }
		MAX-ACCESS		read-write
		STATUS			current
		DESCRIPTION
				"TYPE: - Checkbox
				 PAGE: - RollCall- Logging
					Log AES Output 1 ty  cmdID= 35660 "
		::= { iqmux43CmdEntry 35660 }


	iqmux43LoggingAESOutputAESOutput1type OBJECT-TYPE
		SYNTAX		RollCallString
		MAX-ACCESS		read-only
		STATUS			current
		DESCRIPTION
				"TYPE: - Display
				 PAGE: - RollCall- Logging
					AES Output 1 type=  cmdID= 36660  format=   "
		::= { iqmux43CmdEntry 36660 }


	iqmux43LoggingAESOutputLogAESOutput2ty OBJECT-TYPE
		SYNTAX		INTEGER { disable(0), enable(1) }
		MAX-ACCESS		read-write
		STATUS			current
		DESCRIPTION
				"TYPE: - Checkbox
				 PAGE: - RollCall- Logging
					Log AES Output 2 ty  cmdID= 35661 "
		::= { iqmux43CmdEntry 35661 }


	iqmux43LoggingAESOutputAESOutput2type OBJECT-TYPE
		SYNTAX		RollCallString
		MAX-ACCESS		read-only
		STATUS			current
		DESCRIPTION
				"TYPE: - Display
				 PAGE: - RollCall- Logging
					AES Output 2 type=  cmdID= 36661  format=   "
		::= { iqmux43CmdEntry 36661 }


	iqmux43LoggingAESOutputLogAESOutput3ty OBJECT-TYPE
		SYNTAX		INTEGER { disable(0), enable(1) }
		MAX-ACCESS		read-write
		STATUS			current
		DESCRIPTION
				"TYPE: - Checkbox
				 PAGE: - RollCall- Logging
					Log AES Output 3 ty  cmdID= 35662 "
		::= { iqmux43CmdEntry 35662 }


	iqmux43LoggingAESOutputAESOutput3type OBJECT-TYPE
		SYNTAX		RollCallString
		MAX-ACCESS		read-only
		STATUS			current
		DESCRIPTION
				"TYPE: - Display
				 PAGE: - RollCall- Logging
					AES Output 3 type=  cmdID= 36662  format=   "
		::= { iqmux43CmdEntry 36662 }


	iqmux43LoggingAESOutputLogAESOutput4ty OBJECT-TYPE
		SYNTAX		INTEGER { disable(0), enable(1) }
		MAX-ACCESS		read-write
		STATUS			current
		DESCRIPTION
				"TYPE: - Checkbox
				 PAGE: - RollCall- Logging
					Log AES Output 4 ty  cmdID= 35663 "
		::= { iqmux43CmdEntry 35663 }


	iqmux43LoggingAESOutputAESOutput4type OBJECT-TYPE
		SYNTAX		RollCallString
		MAX-ACCESS		read-only
		STATUS			current
		DESCRIPTION
				"TYPE: - Display
				 PAGE: - RollCall- Logging
					AES Output 4 type=  cmdID= 36663  format=   "
		::= { iqmux43CmdEntry 36663 }


	iqmux43LoggingAESOutputLogAESOutput5ty OBJECT-TYPE
		SYNTAX		INTEGER { disable(0), enable(1) }
		MAX-ACCESS		read-write
		STATUS			current
		DESCRIPTION
				"TYPE: - Checkbox
				 PAGE: - RollCall- Logging
					Log AES Output 5 ty  cmdID= 35664 "
		::= { iqmux43CmdEntry 35664 }


	iqmux43LoggingAESOutputAESOutput5type OBJECT-TYPE
		SYNTAX		RollCallString
		MAX-ACCESS		read-only
		STATUS			current
		DESCRIPTION
				"TYPE: - Display
				 PAGE: - RollCall- Logging
					AES Output 5 type=  cmdID= 36664  format=   "
		::= { iqmux43CmdEntry 36664 }


	iqmux43LoggingAESOutputLogAESOutput6ty OBJECT-TYPE
		SYNTAX		INTEGER { disable(0), enable(1) }
		MAX-ACCESS		read-write
		STATUS			current
		DESCRIPTION
				"TYPE: - Checkbox
				 PAGE: - RollCall- Logging
					Log AES Output 6 ty  cmdID= 35665 "
		::= { iqmux43CmdEntry 35665 }


	iqmux43LoggingAESOutputAESOutput6type OBJECT-TYPE
		SYNTAX		RollCallString
		MAX-ACCESS		read-only
		STATUS			current
		DESCRIPTION
				"TYPE: - Display
				 PAGE: - RollCall- Logging
					AES Output 6 type=  cmdID= 36665  format=   "
		::= { iqmux43CmdEntry 36665 }


	iqmux43LoggingAESOutputLogAESOutput7ty OBJECT-TYPE
		SYNTAX		INTEGER { disable(0), enable(1) }
		MAX-ACCESS		read-write
		STATUS			current
		DESCRIPTION
				"TYPE: - Checkbox
				 PAGE: - RollCall- Logging
					Log AES Output 7 ty  cmdID= 35666 "
		::= { iqmux43CmdEntry 35666 }


	iqmux43LoggingAESOutputAESOutput7type OBJECT-TYPE
		SYNTAX		RollCallString
		MAX-ACCESS		read-only
		STATUS			current
		DESCRIPTION
				"TYPE: - Display
				 PAGE: - RollCall- Logging
					AES Output 7 type=  cmdID= 36666  format=   "
		::= { iqmux43CmdEntry 36666 }


	iqmux43LoggingAESOutputLogAESOutput8ty OBJECT-TYPE
		SYNTAX		INTEGER { disable(0), enable(1) }
		MAX-ACCESS		read-write
		STATUS			current
		DESCRIPTION
				"TYPE: - Checkbox
				 PAGE: - RollCall- Logging
					Log AES Output 8 ty  cmdID= 35667 "
		::= { iqmux43CmdEntry 35667 }


	iqmux43LoggingAESOutputAESOutput8type OBJECT-TYPE
		SYNTAX		RollCallString
		MAX-ACCESS		read-only
		STATUS			current
		DESCRIPTION
				"TYPE: - Display
				 PAGE: - RollCall- Logging
					AES Output 8 type=  cmdID= 36667  format=   "
		::= { iqmux43CmdEntry 36667 }


	iqmux43LoggingMiscLogSerialNo OBJECT-TYPE
		SYNTAX		INTEGER { disable(0), enable(1) }
		MAX-ACCESS		read-write
		STATUS			current
		DESCRIPTION
				"TYPE: - Checkbox
				 PAGE: - RollCall- Logging
					Log Serial No.  cmdID= 35015 "
		::= { iqmux43CmdEntry 35015 }


	iqmux43LoggingMiscSerialNo OBJECT-TYPE
		SYNTAX		RollCallString
		MAX-ACCESS		read-only
		STATUS			current
		DESCRIPTION
				"TYPE: - Display
				 PAGE: - RollCall- Logging
					Serial No.=  cmdID= 36015  format=   "
		::= { iqmux43CmdEntry 36015 }


	iqmux43LoggingMiscLogOSVersion OBJECT-TYPE
		SYNTAX		INTEGER { disable(0), enable(1) }
		MAX-ACCESS		read-write
		STATUS			current
		DESCRIPTION
				"TYPE: - Checkbox
				 PAGE: - RollCall- Logging
					Log OS Version  cmdID= 35993 "
		::= { iqmux43CmdEntry 35993 }


	iqmux43LoggingMiscOSVersion OBJECT-TYPE
		SYNTAX		RollCallString
		MAX-ACCESS		read-only
		STATUS			current
		DESCRIPTION
				"TYPE: - Display
				 PAGE: - RollCall- Logging
					OS Version=  cmdID= 36993  format=   "
		::= { iqmux43CmdEntry 36993 }


	iqmux43LoggingMiscLogBuildNo OBJECT-TYPE
		SYNTAX		INTEGER { disable(0), enable(1) }
		MAX-ACCESS		read-write
		STATUS			current
		DESCRIPTION
				"TYPE: - Checkbox
				 PAGE: - RollCall- Logging
					Log Build No.  cmdID= 35990 "
		::= { iqmux43CmdEntry 35990 }


	iqmux43LoggingMiscBuildNo OBJECT-TYPE
		SYNTAX		RollCallString
		MAX-ACCESS		read-only
		STATUS			current
		DESCRIPTION
				"TYPE: - Display
				 PAGE: - RollCall- Logging
					Build No.=  cmdID= 36990  format=   "
		::= { iqmux43CmdEntry 36990 }


	iqmux43LoggingMiscLogHardwareVer OBJECT-TYPE
		SYNTAX		INTEGER { disable(0), enable(1) }
		MAX-ACCESS		read-write
		STATUS			current
		DESCRIPTION
				"TYPE: - Checkbox
				 PAGE: - RollCall- Logging
					Log Hardware Ver.  cmdID= 35992 "
		::= { iqmux43CmdEntry 35992 }


	iqmux43LoggingMiscHardwareVer OBJECT-TYPE
		SYNTAX		RollCallString
		MAX-ACCESS		read-only
		STATUS			current
		DESCRIPTION
				"TYPE: - Display
				 PAGE: - RollCall- Logging
					Hardware Ver.=  cmdID= 36992  format=   "
		::= { iqmux43CmdEntry 36992 }


	iqmux43LoggingMiscLogFirmwareVer OBJECT-TYPE
		SYNTAX		INTEGER { disable(0), enable(1) }
		MAX-ACCESS		read-write
		STATUS			current
		DESCRIPTION
				"TYPE: - Checkbox
				 PAGE: - RollCall- Logging
					Log Firmware Ver.  cmdID= 35991 "
		::= { iqmux43CmdEntry 35991 }


	iqmux43LoggingMiscFirmwareVer OBJECT-TYPE
		SYNTAX		RollCallString
		MAX-ACCESS		read-only
		STATUS			current
		DESCRIPTION
				"TYPE: - Display
				 PAGE: - RollCall- Logging
					Firmware Ver.=  cmdID= 36991  format=   "
		::= { iqmux43CmdEntry 36991 }


	iqmux43LoggingMiscLogUpTime OBJECT-TYPE
		SYNTAX		INTEGER { disable(0), enable(1) }
		MAX-ACCESS		read-write
		STATUS			current
		DESCRIPTION
				"TYPE: - Checkbox
				 PAGE: - RollCall- Logging
					Log Up Time  cmdID= 35994 "
		::= { iqmux43CmdEntry 35994 }


	iqmux43LoggingMiscUpTime OBJECT-TYPE
		SYNTAX		RollCallString
		MAX-ACCESS		read-only
		STATUS			current
		DESCRIPTION
				"TYPE: - Display
				 PAGE: - RollCall- Logging
					Up Time=  cmdID= 36994  format=   "
		::= { iqmux43CmdEntry 36994 }


	iqmux43RollCallRollTrackDisableAll OBJECT-TYPE
		SYNTAX		INTEGER { disable(0), enable(1) }
		MAX-ACCESS		read-write
		STATUS			current
		DESCRIPTION
				"TYPE: - Checkbox
				 PAGE: - RollCall
					Disable All  cmdID= 36104 "
		::= { iqmux43CmdEntry 36104 }


	iqmux43RollCallRollTrackIndex OBJECT-TYPE
		SYNTAX		INTEGER
		MAX-ACCESS		read-write
		STATUS			current
		DESCRIPTION
				"TYPE: - BarGraph
				 PAGE: - RollCall
					Index  cmdID= 36100  min= 1  max= 16   step= 1  format= %0.0f  div_scale= 1
					Min = 1  Max = 16  Step = 1 "
		::= { iqmux43CmdEntry 36100 }


	iqmux43RollCallRollTrackSource OBJECT-TYPE
		SYNTAX		INTEGER {
							val_Unused(-1),
							val_Video_Delay(0),
							val_Input_Present(1),
							val_Input_Loss(2),
							val_O_p_Freeze(3),
							val_O_p_UnFreeze(4),
							val_Output_1080(53),
							val_Output_720(54),
							val_Output_576_625(55),
							val_Output_480_525(56),
							val_De_embed_1_Data(5),
							val_De_embed_1_Pcm(6),
							val_De_embed_1_Lost(7),
							val_De_embed_2_Data(8),
							val_De_embed_2_Pcm(9),
							val_De_embed_2_Lost(10),
							val_De_embed_3_Data(11),
							val_De_embed_3_Pcm(12),
							val_De_embed_3_Lost(13),
							val_De_embed_4_Data(14),
							val_De_embed_4_Pcm(15),
							val_De_embed_4_Lost(16),
							val_De_embed_5_Data(17),
							val_De_embed_5_Pcm(18),
							val_De_embed_5_Lost(19),
							val_De_embed_6_Data(20),
							val_De_embed_6_Pcm(21),
							val_De_embed_6_Lost(22),
							val_De_embed_7_Data(23),
							val_De_embed_7_Pcm(24),
							val_De_embed_7_Lost(25),
							val_De_embed_8_Data(26),
							val_De_embed_8_Pcm(27),
							val_De_embed_8_Lost(28),
							val_AES_1_Data(29),
							val_AES_1_Pcm(30),
							val_AES_1_Lost(31),
							val_AES_2_Data(32),
							val_AES_2_Pcm(33),
							val_AES_2_Lost(34),
							val_AES_3_Data(35),
							val_AES_3_Pcm(36),
							val_AES_3_Lost(37),
							val_AES_4_Data(38),
							val_AES_4_Pcm(39),
							val_AES_4_Lost(40),
							val_AES_5_Data(41),
							val_AES_5_Pcm(42),
							val_AES_5_Lost(43),
							val_AES_6_Data(44),
							val_AES_6_Pcm(45),
							val_AES_6_Lost(46),
							val_AES_7_Data(47),
							val_AES_7_Pcm(48),
							val_AES_7_Lost(49),
							val_AES_8_Data(50),
							val_AES_8_Pcm(51),
							val_AES_8_Lost(52)
							}
		MAX-ACCESS		read-write
		STATUS			current
		DESCRIPTION
				"TYPE: - RadiobuttonList
				 PAGE: - RollCall
					Source  cmdID= 36101
					Unused  value= -1
					Video Delay  value= 0
					Input Present  value= 1
					Input Loss  value= 2
					O/p Freeze  value= 3
					O/p UnFreeze  value= 4
					Output:1080  value= 53
					Output:720  value= 54
					Output:576(625)  value= 55
					Output:480(525)  value= 56
					De-embed 1 Data  value= 5
					De-embed 1 Pcm  value= 6
					De-embed 1 Lost  value= 7
					De-embed 2 Data  value= 8
					De-embed 2 Pcm  value= 9
					De-embed 2 Lost  value= 10
					De-embed 3 Data  value= 11
					De-embed 3 Pcm  value= 12
					De-embed 3 Lost  value= 13
					De-embed 4 Data  value= 14
					De-embed 4 Pcm  value= 15
					De-embed 4 Lost  value= 16
					De-embed 5 Data  value= 17
					De-embed 5 Pcm  value= 18
					De-embed 5 Lost  value= 19
					De-embed 6 Data  value= 20
					De-embed 6 Pcm  value= 21
					De-embed 6 Lost  value= 22
					De-embed 7 Data  value= 23
					De-embed 7 Pcm  value= 24
					De-embed 7 Lost  value= 25
					De-embed 8 Data  value= 26
					De-embed 8 Pcm  value= 27
					De-embed 8 Lost  value= 28
					AES 1 Data  value= 29
					AES 1 Pcm  value= 30
					AES 1 Lost  value= 31
					AES 2 Data  value= 32
					AES 2 Pcm  value= 33
					AES 2 Lost  value= 34
					AES 3 Data  value= 35
					AES 3 Pcm  value= 36
					AES 3 Lost  value= 37
					AES 4 Data  value= 38
					AES 4 Pcm  value= 39
					AES 4 Lost  value= 40
					AES 5 Data  value= 41
					AES 5 Pcm  value= 42
					AES 5 Lost  value= 43
					AES 6 Data  value= 44
					AES 6 Pcm  value= 45
					AES 6 Lost  value= 46
					AES 7 Data  value= 47
					AES 7 Pcm  value= 48
					AES 7 Lost  value= 49
					AES 8 Data  value= 50
					AES 8 Pcm  value= 51
					AES 8 Lost  value= 52  "
		::= { iqmux43CmdEntry 36101 }


	iqmux43RollCallRollTrackAddress OBJECT-TYPE
		SYNTAX		RollCallString
		MAX-ACCESS		read-write
		STATUS			current
		DESCRIPTION
				"TYPE: - Editstring
				 PAGE: - RollCall
					Address  cmdID= 36102  "
		::= { iqmux43CmdEntry 36102 }


	iqmux43RollCallRollTrackCommand OBJECT-TYPE
		SYNTAX		RollCallString
		MAX-ACCESS		read-write
		STATUS			current
		DESCRIPTION
				"TYPE: - Editstring
				 PAGE: - RollCall
					Command  cmdID= 36103  "
		::= { iqmux43CmdEntry 36103 }


	iqmux43RollCallRollTrackStatus OBJECT-TYPE
		SYNTAX		RollCallString
		MAX-ACCESS		read-only
		STATUS			current
		DESCRIPTION
				"TYPE: - Display
				 PAGE: - RollCall
					Status  cmdID= 36105  format=   "
		::= { iqmux43CmdEntry 36105 }


	iqmux43RollCallRollTrackSending OBJECT-TYPE
		SYNTAX		RollCallString
		MAX-ACCESS		read-only
		STATUS			current
		DESCRIPTION
				"TYPE: - Display
				 PAGE: - RollCall
					Sending  cmdID= 36106  format=   "
		::= { iqmux43CmdEntry 36106 }


	iqmux43SetupProduct OBJECT-TYPE
		SYNTAX		RollCallString
		MAX-ACCESS		read-only
		STATUS			current
		DESCRIPTION
				"TYPE: - Display
					Product  cmdID= 32771  format=   "
		::= { iqmux43CmdEntry 32771 }


	iqmux43SetupRelease OBJECT-TYPE
		SYNTAX		RollCallString
		MAX-ACCESS		read-only
		STATUS			current
		DESCRIPTION
				"TYPE: - Display
					Release  cmdID= 2  format=   "
		::= { iqmux43CmdEntry 2 }


	iqmux43SetupBuild OBJECT-TYPE
		SYNTAX		RollCallString
		MAX-ACCESS		read-only
		STATUS			current
		DESCRIPTION
				"TYPE: - Display
					Build  cmdID= 5  format=   "
		::= { iqmux43CmdEntry 5 }


	iqmux43SetupKOS OBJECT-TYPE
		SYNTAX		RollCallString
		MAX-ACCESS		read-only
		STATUS			current
		DESCRIPTION
				"TYPE: - Display
					KOS  cmdID= 32772  format=   "
		::= { iqmux43CmdEntry 32772 }


	iqmux43SetupSerial OBJECT-TYPE
		SYNTAX		RollCallString
		MAX-ACCESS		read-only
		STATUS			current
		DESCRIPTION
				"TYPE: - Display
					Serial No.  cmdID= 1  format=   "
		::= { iqmux43CmdEntry 1 }


	iqmux43SetupFirmware OBJECT-TYPE
		SYNTAX		RollCallString
		MAX-ACCESS		read-only
		STATUS			current
		DESCRIPTION
				"TYPE: - Display
					Firmware  cmdID= 32769  format=   "
		::= { iqmux43CmdEntry 32769 }


	iqmux43SetupPCB OBJECT-TYPE
		SYNTAX		RollCallString
		MAX-ACCESS		read-only
		STATUS			current
		DESCRIPTION
				"TYPE: - Display
					PCB  cmdID= 32770  format=   "
		::= { iqmux43CmdEntry 32770 }


	iqmux43SetupFactoryDefault OBJECT-TYPE
		SYNTAX		INTEGER { noAction(0),val_Factory_Default(1) }
		MAX-ACCESS		read-write
		STATUS			current
		DESCRIPTION
				"TYPE: - Button
					Factory Default  cmdID= 37002  value= 1  "
		::= { iqmux43CmdEntry 37002 }


	iqmux43SetupRestart OBJECT-TYPE
		SYNTAX		INTEGER { noAction(0),val_Restart(1) }
		MAX-ACCESS		read-write
		STATUS			current
		DESCRIPTION
				"TYPE: - Button
					Restart  cmdID= 4  value= 1  "
		::= { iqmux43CmdEntry 4 }


	iqmux43SetupDefaultSettings OBJECT-TYPE
		SYNTAX		INTEGER { noAction(0),val_Default_Settings(1) }
		MAX-ACCESS		read-write
		STATUS			current
		DESCRIPTION
				"TYPE: - Button
					Default Settings  cmdID= 37001  value= 1  "
		::= { iqmux43CmdEntry 37001 }


	iqmux43SetupDisplay OBJECT-TYPE
		SYNTAX		INTEGER {
							val_Video_Status(0),
							val_Audio_Status(1)
							}
		MAX-ACCESS		read-write
		STATUS			current
		DESCRIPTION
				"TYPE: - RadiobuttonList
					Display  cmdID= 32773
					Video Status  value= 0
					Audio Status  value= 1  "
		::= { iqmux43CmdEntry 32773 }


	iqmux43SetupSerialNumber OBJECT-TYPE
		SYNTAX		RollCallString
		MAX-ACCESS		read-write
		STATUS			current
		DESCRIPTION
				"TYPE: - Editstring
					Serial Number  cmdID= 32774  "
		::= { iqmux43CmdEntry 32774 }


	iqmux43SetupBoardID OBJECT-TYPE
		SYNTAX		INTEGER {
							val_IQMUX43(389),
							val_IQMUX43(390),
							val_IQMUX44(472),
							val_IQMUX45(473),
							val_IQMUX46(494),
							val_IQMUX47(495),
							val_IQMUX48(496),
							val_IQMUX49(497)
							}
		MAX-ACCESS		read-write
		STATUS			current
		DESCRIPTION
				"TYPE: - RadiobuttonList
					BoardID  cmdID= 32776
					IQMUX43  value= 389
					IQMUX43  value= 390
					IQMUX44  value= 472
					IQMUX45  value= 473
					IQMUX46  value= 494
					IQMUX47  value= 495
					IQMUX48  value= 496
					IQMUX49  value= 497  "
		::= { iqmux43CmdEntry 32776 }


	iqmux43SetupSaveID OBJECT-TYPE
		SYNTAX		INTEGER { noAction(0),val_Save_ID(1) }
		MAX-ACCESS		read-write
		STATUS			current
		DESCRIPTION
				"TYPE: - Button
					Save ID  cmdID= 32775  value= 1  "
		::= { iqmux43CmdEntry 32775 }


	iqmux43EngineerPassword OBJECT-TYPE
		SYNTAX		RollCallString
		MAX-ACCESS		read-write
		STATUS			current
		DESCRIPTION
				"TYPE: - Editstring
				 PAGE: - Engineer
					Engineer Password  cmdID= 34011  "
		::= { iqmux43CmdEntry 34011 }


	iqmux43EngineerShowEngineer OBJECT-TYPE
		SYNTAX		INTEGER { disable(0), enable(1) }
		MAX-ACCESS		read-write
		STATUS			current
		DESCRIPTION
				"TYPE: - Checkbox
				 PAGE: - Engineer
					Show Engineer  cmdID= 34012 "
		::= { iqmux43CmdEntry 34012 }


	iqmux43EngineerPageOptionsS134014 OBJECT-TYPE
		SYNTAX		INTEGER { disable(0), enable(1) }
		MAX-ACCESS		read-write
		STATUS			current
		DESCRIPTION
				"TYPE: - Checkbox
				 PAGE: - Engineer
					$S1  cmdID= 34014 "
		::= { iqmux43CmdEntry 34014 }


	iqmux43EngineerPageOptionsS134015 OBJECT-TYPE
		SYNTAX		INTEGER { disable(0), enable(1) }
		MAX-ACCESS		read-write
		STATUS			current
		DESCRIPTION
				"TYPE: - Checkbox
				 PAGE: - Engineer
					$S1  cmdID= 34015 "
		::= { iqmux43CmdEntry 34015 }


	iqmux43EngineerPageOptionsS1 OBJECT-TYPE
		SYNTAX		INTEGER { disable(0), enable(1) }
		MAX-ACCESS		read-write
		STATUS			current
		DESCRIPTION
				"TYPE: - Checkbox
				 PAGE: - Engineer
					$S1  cmdID= 34016 "
		::= { iqmux43CmdEntry 34016 }


	iqmux43EngineerPageUndoChanges OBJECT-TYPE
		SYNTAX		INTEGER { noAction(0),val_Undo_Changes(1) }
		MAX-ACCESS		read-write
		STATUS			current
		DESCRIPTION
				"TYPE: - Button
				 PAGE: - Engineer
					Undo Changes  cmdID= 34013  value= 1  "
		::= { iqmux43CmdEntry 34013 }


	iqmux43EngineerPageLineNumber OBJECT-TYPE
		SYNTAX		RollCallString
		MAX-ACCESS		read-only
		STATUS			current
		DESCRIPTION
				"TYPE: - Display
				 PAGE: - Engineer
					Line Number  cmdID= 38651  format=   "
		::= { iqmux43CmdEntry 38651 }


	iqmux43EngineerPageSampleNumber OBJECT-TYPE
		SYNTAX		RollCallString
		MAX-ACCESS		read-only
		STATUS			current
		DESCRIPTION
				"TYPE: - Display
				 PAGE: - Engineer
					Sample Number  cmdID= 38657  format=   "
		::= { iqmux43CmdEntry 38657 }


	iqmux43EngineerPaAutoalignEmbeddedInputs OBJECT-TYPE
		SYNTAX		INTEGER { disable(0), enable(1) }
		MAX-ACCESS		read-write
		STATUS			current
		DESCRIPTION
				"TYPE: - Checkbox
				 PAGE: - Engineer
					Embedded Inputs  cmdID= 34060 "
		::= { iqmux43CmdEntry 34060 }


	iqmux43EngineerPaAutoalignAESInputs OBJECT-TYPE
		SYNTAX		INTEGER { disable(0), enable(1) }
		MAX-ACCESS		read-write
		STATUS			current
		DESCRIPTION
				"TYPE: - Checkbox
				 PAGE: - Engineer
					AES Inputs  cmdID= 34061 "
		::= { iqmux43CmdEntry 34061 }


	iqmux43ShowEngineer2 OBJECT-TYPE
		SYNTAX		INTEGER { disable(0), enable(1) }
		MAX-ACCESS		read-write
		STATUS			current
		DESCRIPTION
				"TYPE: - Checkbox
					Show Engineer2  cmdID= 34050 "
		::= { iqmux43CmdEntry 34050 }


	iqmux43UseEmbDelayFbac OBJECT-TYPE
		SYNTAX		INTEGER { disable(0), enable(1) }
		MAX-ACCESS		read-write
		STATUS			current
		DESCRIPTION
				"TYPE: - Checkbox
					Use Emb Delay F/bac  cmdID= 34049 "
		::= { iqmux43CmdEntry 34049 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S35034500
--				:
-- Comments		: Serial Number or module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:34:00
--				:
-- Comments		: Uptime in formated date-time string
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number or current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 2001420336
--				:
-- Comments		: String of current Software build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD / SD SDI
--				:
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2010-01-27T10:41:47Z
--				:
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2010-01-27T10:45:05Z
--				:
-- Comments		: Time String of last control modification
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: HD / SD SDI
--				:
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: BLACK
--				: PATTERN
--				: MONO
--				: FROZEN
--				: OK
--				: FAIL
--				: LOGO
--				: PATTERN+LOGO
--				: MONO+LOGO
--				: BLACK+LOGO
--				: FROZEN+LOGO
--				: OK+LOGO
-- Comments		:
--
---------------------------------------------------------------------------------------------------
-- Header		: AES_INPUT_1_TYPE
--
-- MIB ref		: swCardEventLogSlotXX       .16.65.69.83.95.73.78.80.85.84.95.49.95.84.89.80.69
-- absolute OID	: 1.3.6.1.4.1.7995.2.6.1.1.XX.16.65.69.83.95.73.78.80.85.84.95.49.95.84.89.80.69
-- Vary			: YES
--
-- Value(s)		: Unknown
--				: NONPCM
--              : PCM
--              : WARN: No Input
-- Comments		:
--
---------------------------------------------------------------------------------------------------
-- Header		: AES_INPUT_2_TYPE
--
-- MIB ref		: swCardEventLogSlotXX       .16.65.69.83.95.73.78.80.85.84.95.50.95.84.89.80.69
-- absolute OID	: 1.3.6.1.4.1.7995.2.6.1.1.XX.16.65.69.83.95.73.78.80.85.84.95.50.95.84.89.80.69
-- Vary			: YES
--
-- Value(s)		: Unknown
--				: NONPCM
--              : PCM
--              : WARN: No Input
-- Comments		:
--
---------------------------------------------------------------------------------------------------
-- Header		: AES_INPUT_3_TYPE
--
-- MIB ref		: swCardEventLogSlotXX       .16.65.69.83.95.73.78.80.85.84.95.51.95.84.89.80.69
-- absolute OID	: 1.3.6.1.4.1.7995.2.6.1.1.XX.16.65.69.83.95.73.78.80.85.84.95.51.95.84.89.80.69
-- Vary			: YES
--
-- Value(s)		: Unknown
--				: NONPCM
--              : PCM
--              : WARN: No Input
-- Comments		:
--
---------------------------------------------------------------------------------------------------
-- Header		: AES_INPUT_4_TYPE
--
-- MIB ref		: swCardEventLogSlotXX       .16.65.69.83.95.73.78.80.85.84.95.52.95.84.89.80.69
-- absolute OID	: 1.3.6.1.4.1.7995.2.6.1.1.XX.16.65.69.83.95.73.78.80.85.84.95.52.95.84.89.80.69
-- Vary			: YES
--
-- Value(s)		: Unknown
--				: NONPCM
--              : PCM
--              : WARN: No Input
-- Comments		:
--
---------------------------------------------------------------------------------------------------
-- Header		: AES_INPUT_5_TYPE
--
-- MIB ref		: swCardEventLogSlotXX       .16.65.69.83.95.73.78.80.85.84.95.53.95.84.89.80.69
-- absolute OID	: 1.3.6.1.4.1.7995.2.6.1.1.XX.16.65.69.83.95.73.78.80.85.84.95.53.95.84.89.80.69
-- Vary			: YES
--
-- Value(s)		: Unknown
--				: NONPCM
--              : PCM
--              : WARN: No Input
-- Comments		:
--
---------------------------------------------------------------------------------------------------
-- Header		: AES_INPUT_6_TYPE
--
-- MIB ref		: swCardEventLogSlotXX       .16.65.69.83.95.73.78.80.85.84.95.54.95.84.89.80.69
-- absolute OID	: 1.3.6.1.4.1.7995.2.6.1.1.XX.16.65.69.83.95.73.78.80.85.84.95.54.95.84.89.80.69
-- Vary			: YES
--
-- Value(s)		: Unknown
--				: NONPCM
--              : PCM
--              : WARN: No Input
-- Comments		:
--
---------------------------------------------------------------------------------------------------
-- Header		: AES_INPUT_7_TYPE
--
-- MIB ref		: swCardEventLogSlotXX       .16.65.69.83.95.73.78.80.85.84.95.55.95.84.89.80.69
-- absolute OID	: 1.3.6.1.4.1.7995.2.6.1.1.XX.16.65.69.83.95.73.78.80.85.84.95.55.95.84.89.80.69
-- Vary			: YES
--
-- Value(s)		: Unknown
--				: NONPCM
--              : PCM
--              : WARN: No Input
-- Comments		:
--
---------------------------------------------------------------------------------------------------
-- Header		: AES_INPUT_8_TYPE
--
-- MIB ref		: swCardEventLogSlotXX       .16.65.69.83.95.73.78.80.85.84.95.56.95.84.89.80.69
-- absolute OID	: 1.3.6.1.4.1.7995.2.6.1.1.XX.16.65.69.83.95.73.78.80.85.84.95.56.95.84.89.80.69
-- Vary			: YES
--
-- Value(s)		: Unknown
--				: NONPCM
--              : PCM
--              : WARN: No Input
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 2.193
--				:
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RDAUD1Y.001
--				:
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: NONE
--              : WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
-- Vary			: YES
--
-- Value(s)		: LOST
--				: FAIL:Lost
--              : OK
--              : Unknown
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
-- Vary			: YES
--
-- Value(s)		: LOST
--				: FAIL:Lost
--              : OK
--              : Unknown
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
-- Vary			: YES
--
-- Value(s)		: LOST
--				: FAIL:Lost
--              : OK
--              : Unknown
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
-- Vary			: YES
--
-- Value(s)		: LOST
--				: FAIL:Lost
--              : OK
--              : Unknown
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
-- Vary			: YES
--
-- Value(s)		: LOST
--				: FAIL:Lost
--              : OK
--              : Unknown
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
-- Vary			: YES
--
-- Value(s)		: LOST
--				: FAIL:Lost
--              : OK
--              : Unknown
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
-- Vary			: YES
--
-- Value(s)		: LOST
--				: FAIL:Lost
--              : OK
--              : Unknown
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
-- Vary			: YES
--
-- Value(s)		: LOST
--				: FAIL:Lost
--              : OK
--              : Unknown
-- Comments		:
--
---------------------------------------------------------------------------------------------------
-- Header		: AES_OUTPUT_1_TYPE
--
-- MIB ref		: swCardEventLogSlotXX       .17.65.69.83.95.79.85.84.80.85.84.95.49.95.84.89.80.69
-- absolute OID	: 1.3.6.1.4.1.7995.2.6.1.1.XX.17.65.69.83.95.79.85.84.80.85.84.95.49.95.84.89.80.69
-- Vary			: YES
--
-- Value(s)		: Unknown
--				: PCM
--              : NONPCM
--              : WARN: No Input
-- Comments		:
--
---------------------------------------------------------------------------------------------------
-- Header		: AES_OUTPUT_2_TYPE
--
-- MIB ref		: swCardEventLogSlotXX       .17.65.69.83.95.79.85.84.80.85.84.95.50.95.84.89.80.69
-- absolute OID	: 1.3.6.1.4.1.7995.2.6.1.1.XX.17.65.69.83.95.79.85.84.80.85.84.95.50.95.84.89.80.69
-- Vary			: YES
--
-- Value(s)		: Unknown
--				: PCM
--              : NONPCM
--              : WARN: No Input
-- Comments		:
--
---------------------------------------------------------------------------------------------------
-- Header		: AES_OUTPUT_3_TYPE
--
-- MIB ref		: swCardEventLogSlotXX       .17.65.69.83.95.79.85.84.80.85.84.95.51.95.84.89.80.69
-- absolute OID	: 1.3.6.1.4.1.7995.2.6.1.1.XX.17.65.69.83.95.79.85.84.80.85.84.95.51.95.84.89.80.69
-- Vary			: YES
--
-- Value(s)		: Unknown
--				: PCM
--              : NONPCM
--              : WARN: No Input
-- Comments		:
--
---------------------------------------------------------------------------------------------------
-- Header		: AES_OUTPUT_4_TYPE
--
-- MIB ref		: swCardEventLogSlotXX       .17.65.69.83.95.79.85.84.80.85.84.95.52.95.84.89.80.69
-- absolute OID	: 1.3.6.1.4.1.7995.2.6.1.1.XX.17.65.69.83.95.79.85.84.80.85.84.95.52.95.84.89.80.69
-- Vary			: YES
--
-- Value(s)		: Unknown
--				: PCM
--              : NONPCM
--              : WARN: No Input
-- Comments		:
--
---------------------------------------------------------------------------------------------------
-- Header		: AES_OUTPUT_5_TYPE
--
-- MIB ref		: swCardEventLogSlotXX       .17.65.69.83.95.79.85.84.80.85.84.95.53.95.84.89.80.69
-- absolute OID	: 1.3.6.1.4.1.7995.2.6.1.1.XX.17.65.69.83.95.79.85.84.80.85.84.95.53.95.84.89.80.69
-- Vary			: YES
--
-- Value(s)		: Unknown
--				: PCM
--              : NONPCM
--              : WARN: No Input
-- Comments		:
--
---------------------------------------------------------------------------------------------------
-- Header		: AES_OUTPUT_6_TYPE
--
-- MIB ref		: swCardEventLogSlotXX       .17.65.69.83.95.79.85.84.80.85.84.95.54.95.84.89.80.69
-- absolute OID	: 1.3.6.1.4.1.7995.2.6.1.1.XX.17.65.69.83.95.79.85.84.80.85.84.95.54.95.84.89.80.69
-- Vary			: YES
--
-- Value(s)		: Unknown
--				: PCM
--              : NONPCM
--              : WARN: No Input
-- Comments		:
--
---------------------------------------------------------------------------------------------------
-- Header		: AES_OUTPUT_7_TYPE
--
-- MIB ref		: swCardEventLogSlotXX       .17.65.69.83.95.79.85.84.80.85.84.95.55.95.84.89.80.69
-- absolute OID	: 1.3.6.1.4.1.7995.2.6.1.1.XX.17.65.69.83.95.79.85.84.80.85.84.95.55.95.84.89.80.69
-- Vary			: YES
--
-- Value(s)		: Unknown
--				: PCM
--              : NONPCM
--              : WARN: No Input
-- Comments		:
--
---------------------------------------------------------------------------------------------------
-- Header		: AES_OUTPUT_8_TYPE
--
-- MIB ref		: swCardEventLogSlotXX       .17.65.69.83.95.79.85.84.80.85.84.95.56.95.84.89.80.69
-- absolute OID	: 1.3.6.1.4.1.7995.2.6.1.1.XX.17.65.69.83.95.79.85.84.80.85.84.95.56.95.84.89.80.69
-- Vary			: YES
--
-- Value(s)		: Unknown
--				: PCM
--              : NONPCM
--              : WARN: No Input
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_OUTPUT_1_STATE
--
-- MIB ref		: swCardEventLogSlotXX       .18.65.69.83.95.79.85.84.80.85.84.95.49.95.83.84.65.84.69
-- absolute OID	: 1.3.6.1.4.1.7995.2.6.1.1.XX.18.65.69.83.95.79.85.84.80.85.84.95.49.95.83.84.65.84.69
-- Vary			: YES
--
-- Value(s)		: LOST
--				: FAIL:Lost
--              : OK
--              : Unknown
-- Comments		:
--
---------------------------------------------------------------------------------------------------
-- Header		: AES_OUTPUT_2_STATE
--
-- MIB ref		: swCardEventLogSlotXX       .18.65.69.83.95.79.85.84.80.85.84.95.50.95.83.84.65.84.69
-- absolute OID	: 1.3.6.1.4.1.7995.2.6.1.1.XX.18.65.69.83.95.79.85.84.80.85.84.95.50.95.83.84.65.84.69
-- Vary			: YES
--
-- Value(s)		: LOST
--				: FAIL:Lost
--              : OK
--              : Unknown
-- Comments		:
--
---------------------------------------------------------------------------------------------------
-- Header		: AES_OUTPUT_3_STATE
--
-- MIB ref		: swCardEventLogSlotXX       .18.65.69.83.95.79.85.84.80.85.84.95.51.95.83.84.65.84.69
-- absolute OID	: 1.3.6.1.4.1.7995.2.6.1.1.XX.18.65.69.83.95.79.85.84.80.85.84.95.51.95.83.84.65.84.69
-- Vary			: YES
--
-- Value(s)		: LOST
--				: FAIL:Lost
--              : OK
--              : Unknown
-- Comments		:
--
---------------------------------------------------------------------------------------------------
-- Header		: AES_OUTPUT_4_STATE
--
-- MIB ref		: swCardEventLogSlotXX       .18.65.69.83.95.79.85.84.80.85.84.95.52.95.83.84.65.84.69
-- absolute OID	: 1.3.6.1.4.1.7995.2.6.1.1.XX.18.65.69.83.95.79.85.84.80.85.84.95.52.95.83.84.65.84.69
-- Vary			: YES
--
-- Value(s)		: LOST
--				: FAIL:Lost
--              : OK
--              : Unknown
-- Comments		:
--
---------------------------------------------------------------------------------------------------
-- Header		: AES_OUTPUT_5_STATE
--
-- MIB ref		: swCardEventLogSlotXX       .18.65.69.83.95.79.85.84.80.85.84.95.53.95.83.84.65.84.69
-- absolute OID	: 1.3.6.1.4.1.7995.2.6.1.1.XX.18.65.69.83.95.79.85.84.80.85.84.95.53.95.83.84.65.84.69
-- Vary			: YES
--
-- Value(s)		: LOST
--				: FAIL:Lost
--              : OK
--              : Unknown
-- Comments		:
--
---------------------------------------------------------------------------------------------------
-- Header		: AES_OUTPUT_6_STATE
--
-- MIB ref		: swCardEventLogSlotXX       .18.65.69.83.95.79.85.84.80.85.84.95.54.95.83.84.65.84.69
-- absolute OID	: 1.3.6.1.4.1.7995.2.6.1.1.XX.18.65.69.83.95.79.85.84.80.85.84.95.54.95.83.84.65.84.69
-- Vary			: YES
--
-- Value(s)		: LOST
--				: FAIL:Lost
--              : OK
--              : Unknown
-- Comments		:
--
---------------------------------------------------------------------------------------------------
-- Header		: AES_OUTPUT_7_STATE
--
-- MIB ref		: swCardEventLogSlotXX       .18.65.69.83.95.79.85.84.80.85.84.95.55.95.83.84.65.84.69
-- absolute OID	: 1.3.6.1.4.1.7995.2.6.1.1.XX.18.65.69.83.95.79.85.84.80.85.84.95.55.95.83.84.65.84.69
-- Vary			: YES
--
-- Value(s)		: LOST
--				: FAIL:Lost
--              : OK
--              : Unknown
-- Comments		:
--
---------------------------------------------------------------------------------------------------
-- Header		: AES_OUTPUT_8_STATE
--
-- MIB ref		: swCardEventLogSlotXX       .18.65.69.83.95.79.85.84.80.85.84.95.56.95.83.84.65.84.69
-- absolute OID	: 1.3.6.1.4.1.7995.2.6.1.1.XX.18.65.69.83.95.79.85.84.80.85.84.95.56.95.83.84.65.84.69
-- Vary			: YES
--
-- Value(s)		: LOST
--				: FAIL:Lost
--              : OK
--              : Unknown
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				:
-- Comments		: Number
--
---------------------------------------------------------------------------------------------------
-- Header		: OUTPUT_1_ANC_STATE
--
-- MIB ref		: swCardEventLogSlotXX       .18.79.85.84.80.85.84.95.49.95.65.78.67.95.83.84.65.84.69
-- absolute OID	: 1.3.6.1.4.1.7995.2.6.1.1.XX.18.79.85.84.80.85.84.95.49.95.65.78.67.95.83.84.65.84.69
-- Vary			: YES
--
-- Value(s)		:
--				: ANC FULL
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: NONE
--              : WARN
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				:
-- Comments		: Number
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: OUTPUT_1_EMBEDDED_AUDIO_2_DOLBY
--
-- MIB ref		: swCardEventLogSlotXX       .31.79.85.84.80.85.84.95.49.95.69.77.66.69.68.68.69.68.95.65.85.68.73.79.95.50.95.68.79.76.66.89
-- absolute OID	: 1.3.6.1.4.1.7995.2.6.1.1.XX.31.79.85.84.80.85.84.95.49.95.69.77.66.69.68.68.69.68.95.65.85.68.73.79.95.50.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: OUTPUT_1_EMBEDDED_AUDIO_3_DOLBY
--
-- MIB ref		: swCardEventLogSlotXX       .31.79.85.84.80.85.84.95.49.95.69.77.66.69.68.68.69.68.95.65.85.68.73.79.95.51.95.68.79.76.66.89
-- absolute OID	: 1.3.6.1.4.1.7995.2.6.1.1.XX.31.79.85.84.80.85.84.95.49.95.69.77.66.69.68.68.69.68.95.65.85.68.73.79.95.51.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: OUTPUT_1_EMBEDDED_AUDIO_4_DOLBY
--
-- MIB ref		: swCardEventLogSlotXX       .31.79.85.84.80.85.84.95.49.95.69.77.66.69.68.68.69.68.95.65.85.68.73.79.95.52.95.68.79.76.66.89
-- absolute OID	: 1.3.6.1.4.1.7995.2.6.1.1.XX.31.79.85.84.80.85.84.95.49.95.69.77.66.69.68.68.69.68.95.65.85.68.73.79.95.52.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: LOST
--				: FAIL:Lost
--              : OK
--              : Unknown
-- Comments		:
-- Comments		:
--
---------------------------------------------------------------------------------------------------
-- Header		: OUTPUT_1_EMBEDDED_AUDIO_5_DOLBY
--
-- MIB ref		: swCardEventLogSlotXX       .31.79.85.84.80.85.84.95.49.95.69.77.66.69.68.68.69.68.95.65.85.68.73.79.95.53.95.68.79.76.66.89
-- absolute OID	: 1.3.6.1.4.1.7995.2.6.1.1.XX.31.79.85.84.80.85.84.95.49.95.69.77.66.69.68.68.69.68.95.65.85.68.73.79.95.53.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: OUTPUT_1_EMBEDDED_AUDIO_6_DOLBY
--
-- MIB ref		: swCardEventLogSlotXX       .31.79.85.84.80.85.84.95.49.95.69.77.66.69.68.68.69.68.95.65.85.68.73.79.95.54.95.68.79.76.66.89
-- absolute OID	: 1.3.6.1.4.1.7995.2.6.1.1.XX.31.79.85.84.80.85.84.95.49.95.69.77.66.69.68.68.69.68.95.65.85.68.73.79.95.54.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
--				: FAIL:Lost
--              : OK
--              : Unknown
-- Comments		:
-- Comments		:
--
---------------------------------------------------------------------------------------------------
-- Header		: OUTPUT_1_EMBEDDED_AUDIO_7_DOLBY
--
-- MIB ref		: swCardEventLogSlotXX       .31.79.85.84.80.85.84.95.49.95.69.77.66.69.68.68.69.68.95.65.85.68.73.79.95.55.95.68.79.76.66.89
-- absolute OID	: 1.3.6.1.4.1.7995.2.6.1.1.XX.31.79.85.84.80.85.84.95.49.95.69.77.66.69.68.68.69.68.95.65.85.68.73.79.95.55.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: LOST
--				: FAIL:Lost
--              : OK
--              : Unknown
-- Comments		:
---------------------------------------------------------------------------------------------------
-- Header		: OUTPUT_1_EMBEDDED_AUDIO_8_DOLBY
--
-- MIB ref		: swCardEventLogSlotXX       .31.79.85.84.80.85.84.95.49.95.69.77.66.69.68.68.69.68.95.65.85.68.73.79.95.56.95.68.79.76.66.89
-- absolute OID	: 1.3.6.1.4.1.7995.2.6.1.1.XX.31.79.85.84.80.85.84.95.49.95.69.77.66.69.68.68.69.68.95.65.85.68.73.79.95.56.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
-- Vary			: YES
--
-- Value(s)		: OK
--				:
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
-- Vary			: YES
--
-- Value(s)		: OK
--				:
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
-- Vary			: YES
--
-- Value(s)		: OK
--				: WARN:Silent
--              : WARN:Quiet
--              : WARN:Loud
--              : WARN:Overflow
-- Comments		:
--
---------------------------------------------------------------------------------------------------
