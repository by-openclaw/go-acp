-- ************************************************************************************
-- Snell&Wilcox Card:IQBDAC
--        Module Id#:52
--       Command Set:7
--          Filename:SNELL-IQBDAC-CMD-MIB.mib
--            Author:Jonathan Riches
--              Date:29/06/2005
--              Time:10:23
--
-- Copyright (c) 2005 Snell & Wilcox Ltd
-- All rights reserved.
--
-- ************************************************************************************

SNELL-IQBDAC-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQBDAC,
    moduleIQBDACMIB
        FROM SNELL-WILCOX-PRODUCT-REG;

 moduleIQBDACCmdMi MODULE-IDENTITY
    LAST-UPDATED "0506291023Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQBDACMIB 1 }




--********************************************************************************
--*
--*  Snell Wilcox Card:
--*  command set:
--*  list commands/menus:
--*
--******************************************************************************
	iqbdacCmdTable OBJECT-TYPE
		SYNTAX			SEQUENCE OF IqbdacCmdEntry
		MAX-ACCESS		not-accessible
		STATUS			current
		DESCRIPTION
				"Note the instance of this table is relected in the command set Version"
		::= { moduleIQBDAC 1 }

	iqbdacCmdEntry OBJECT-TYPE
		SYNTAX		IqbdacCmdEntry
		MAX-ACCESS		not-accessible
		STATUS			current
		DESCRIPTION
				"Entry in command table."
		INDEX	{ iqbdacSlotIndex }
		::= { iqbdacCmdTable 1 }

	IqbdacCmdEntry ::=
		SEQUENCE {
			iqbdacSlotIndex
				Unsigned32,
			iqbdacDelayManualDelayTime
				INTEGER,
			iqbdacDelayManualDelay
				INTEGER,
			iqbdacDelayRollTrack
				INTEGER,
			iqbdacDelayExternalDelay
				INTEGER,
			iqbdacAttenuator
				INTEGER,
			iqbdacMute
				INTEGER,
			iqbdacSetupExtDelayPolarity
				INTEGER,
			iqbdacSetupPresetUnit
				INTEGER,
			iqbdacSetupLoggingInputStatus
				INTEGER,
			iqbdacSetupLoggingOverflow
				INTEGER,
			iqbdacSetupSoftwareVersion
				RollCallString,
			iqbdacSetupSerialNo
				RollCallString,
			iqbdacExtDelay1
				INTEGER,
			iqbdacExtDelay2
				INTEGER,
			iqbdacExtDelay3
				INTEGER,
			iqbdacExtDelay4
				INTEGER,
			iqbdacExtDelay5
				INTEGER
		}

	iqbdacSlotIndex OBJECT-TYPE
		SYNTAX		Unsigned32
		MAX-ACCESS		not-accessible
		STATUS			current
		DESCRIPTION
				"The unique Index value for each slot.  Its value
					ranges between 1 and the value of slotNumber."
		::= { iqbdacCmdEntry 0 }


	iqbdacDelayManualDelayTime OBJECT-TYPE
		SYNTAX		INTEGER
		MAX-ACCESS		read-write
		STATUS			current
		DESCRIPTION
				"TYPE: - Number
					Manual_Delay_Time  cmdID= 7  min= -1800  max= 1800  step= 1  format= %.0f ms  div_scale= 1 
					Min = -1800 ms  Max = 1800 ms  Step = 1 ms "
		::= { iqbdacCmdEntry 7 }


	iqbdacDelayManualDelay OBJECT-TYPE
		SYNTAX		INTEGER { disable(0), enable(1) }
		MAX-ACCESS		read-write
		STATUS			current
		DESCRIPTION
				"TYPE: - Checkbox
					Manual_Delay  cmdID= 22 "
		::= { iqbdacCmdEntry 22 }


	iqbdacDelayRollTrack OBJECT-TYPE
		SYNTAX		INTEGER { disable(0), enable(1) }
		MAX-ACCESS		read-write
		STATUS			current
		DESCRIPTION
				"TYPE: - Checkbox
					RollTrack  cmdID= 21 "
		::= { iqbdacCmdEntry 21 }


	iqbdacDelayExternalDelay OBJECT-TYPE
		SYNTAX		INTEGER { disable(0), enable(1) }
		MAX-ACCESS		read-write
		STATUS			current
		DESCRIPTION
				"TYPE: - Checkbox
					External_Delay  cmdID= 8 "
		::= { iqbdacCmdEntry 8 }


	iqbdacAttenuator OBJECT-TYPE
		SYNTAX		INTEGER {
							val_18dBu(18),
							val_21dBu(21),
							val_24dBu(24)
							}
		MAX-ACCESS		read-write
		STATUS			current
		DESCRIPTION
				"TYPE: - RadiobuttonList
					Attenuator  cmdID= 5 
					18dBu  value= 18  
					21dBu  value= 21  
					24dBu  value= 24  "
		::= { iqbdacCmdEntry 5 }


	iqbdacMute OBJECT-TYPE
		SYNTAX		INTEGER { disable(0), enable(1) }
		MAX-ACCESS		read-write
		STATUS			current
		DESCRIPTION
				"TYPE: - Checkbox
					Mute  cmdID= 6 "
		::= { iqbdacCmdEntry 6 }


	iqbdacSetupExtDelayPolarity OBJECT-TYPE
		SYNTAX		INTEGER {
							val_Positive(1),
							val_Negative(0)
							}
		MAX-ACCESS		read-write
		STATUS			current
		DESCRIPTION
				"TYPE: - RadiobuttonList
					Ext_Delay_Polarity  cmdID= 20 
					Positive  value= 1  
					Negative  value= 0  "
		::= { iqbdacCmdEntry 20 }


	iqbdacSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqbdacCmdEntry 3 }


	iqbdacSetupLoggingInputStatus OBJECT-TYPE
		SYNTAX		INTEGER { disable(0), enable(1) }
		MAX-ACCESS		read-write
		STATUS			current
		DESCRIPTION
				"TYPE: - Checkbox
					Input_Status  cmdID= 10 "
		::= { iqbdacCmdEntry 10 }


	iqbdacSetupLoggingOverflow OBJECT-TYPE
		SYNTAX		INTEGER { disable(0), enable(1) }
		MAX-ACCESS		read-write
		STATUS			current
		DESCRIPTION
				"TYPE: - Checkbox
					Overflow  cmdID= 11 "
		::= { iqbdacCmdEntry 11 }


	iqbdacSetupSoftwareVersion OBJECT-TYPE
		SYNTAX		RollCallString
		MAX-ACCESS		read-only
		STATUS			current
		DESCRIPTION
				"TYPE: - Display
					Software_Version  cmdID= 2  format=   "
		::= { iqbdacCmdEntry 2 }


	iqbdacSetupSerialNo OBJECT-TYPE
		SYNTAX		RollCallString
		MAX-ACCESS		read-only
		STATUS			current
		DESCRIPTION
				"TYPE: - Display
					Serial_No  cmdID= 1  format=   "
		::= { iqbdacCmdEntry 1 }


	iqbdacExtDelay1 OBJECT-TYPE
		SYNTAX		INTEGER
		MAX-ACCESS		read-write
		STATUS			current
		DESCRIPTION
				"TYPE: - Number
					Ext_Delay_1  cmdID= 14  min= 0  max= 1600  step= 1  format= %1.0f ms  div_scale= 1 
					Min = 0 ms  Max = 1600 ms  Step = 1 ms "
		::= { iqbdacCmdEntry 14 }


	iqbdacExtDelay2 OBJECT-TYPE
		SYNTAX		INTEGER
		MAX-ACCESS		read-write
		STATUS			current
		DESCRIPTION
				"TYPE: - Number
					Ext_Delay_2  cmdID= 15  min= 0  max= 1600  step= 1  format= %1.0f ms  div_scale= 1 
					Min = 0 ms  Max = 1600 ms  Step = 1 ms "
		::= { iqbdacCmdEntry 15 }


	iqbdacExtDelay3 OBJECT-TYPE
		SYNTAX		INTEGER
		MAX-ACCESS		read-write
		STATUS			current
		DESCRIPTION
				"TYPE: - Number
					Ext_Delay_3  cmdID= 16  min= 0  max= 1600  step= 1  format= %1.0f ms  div_scale= 1 
					Min = 0 ms  Max = 1600 ms  Step = 1 ms "
		::= { iqbdacCmdEntry 16 }


	iqbdacExtDelay4 OBJECT-TYPE
		SYNTAX		INTEGER
		MAX-ACCESS		read-write
		STATUS			current
		DESCRIPTION
				"TYPE: - Number
					Ext_Delay_4  cmdID= 17  min= 0  max= 1600  step= 1  format= %1.0f ms  div_scale= 1 
					Min = 0 ms  Max = 1600 ms  Step = 1 ms "
		::= { iqbdacCmdEntry 17 }


	iqbdacExtDelay5 OBJECT-TYPE
		SYNTAX		INTEGER
		MAX-ACCESS		read-write
		STATUS			current
		DESCRIPTION
				"TYPE: - Number
					Ext_Delay_5  cmdID= 18  min= 0  max= 1600  step= 1  format= %1.0f ms  div_scale= 1 
					Min = 0 ms  Max = 1600 ms  Step = 1 ms "
		::= { iqbdacCmdEntry 18 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		:             
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: LOST
--				: 625
--				: 525
--				: OK
--				: N/A
-- Comments		: 
--
---------------------------------------------------------------------------------------------------
-- Header		: CH-LEFT
--
-- MIB ref		: swCardEventLogSlotXX       .7.67.72.45.76.69.70.84
-- absolute OID	: 1.3.6.1.4.1.7995.2.6.1.1.XX.7.67.72.45.76.69.70.84
-- Vary			: YES
--
-- Value(s)		: OK
--				: OVERFLOW
--				: LOST
-- Comments		: 
--
---------------------------------------------------------------------------------------------------
-- Header		: CH-RIGHT
--
-- MIB ref		: swCardEventLogSlotXX       .8.67.72.45.82.73.71.72.84
-- absolute OID	: 1.3.6.1.4.1.7995.2.6.1.1.XX.8.67.72.45.82.73.71.72.84
-- Vary			: YES
--
-- Value(s)		: OK
--				: OVERFLOW
--				: LOST
-- Comments		: 
--
---------------------------------------------------------------------------------------------------
