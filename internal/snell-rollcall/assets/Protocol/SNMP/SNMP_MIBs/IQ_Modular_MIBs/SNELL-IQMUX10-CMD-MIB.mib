-- ************************************************************************************
-- Snell&Wilcox Card:IQMUX10
--        Module Id#:358
--       Command Set:5
--          Filename:SNELL-IQMUX10-CMD-MIB.mib
--            Author:Jonathan Riches
--              Date:08/06/2005
--              Time:15:35
--
-- Copyright (c) 2005 Snell & Wilcox Ltd
-- All rights reserved.
--
-- ************************************************************************************

SNELL-IQMUX10-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQMUX10,
    moduleIQMUX10MIB
        FROM SNELL-WILCOX-PRODUCT-REG;

 moduleIQMUX10CmdMi MODULE-IDENTITY
    LAST-UPDATED "0506081535Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQMUX10MIB 1 }




--********************************************************************************
--*
--*  Snell Wilcox Card:
--*  command set:
--*  list commands/menus:
--*
--******************************************************************************
	iqmux10CmdTable OBJECT-TYPE
		SYNTAX			SEQUENCE OF Iqmux10CmdEntry
		MAX-ACCESS		not-accessible
		STATUS			current
		DESCRIPTION
				"Note the instance of this table is relected in the command set Version"
		::= { moduleIQMUX10 1 }

	iqmux10CmdEntry OBJECT-TYPE
		SYNTAX		Iqmux10CmdEntry
		MAX-ACCESS		not-accessible
		STATUS			current
		DESCRIPTION
				"Entry in command table."
		INDEX	{ iqmux10SlotIndex }
		::= { iqmux10CmdTable 1 }

	Iqmux10CmdEntry ::=
		SEQUENCE {
			iqmux10SlotIndex
				Unsigned32,
			iqmux10VideoInput
				INTEGER,
			iqmux10VideoInput525
				INTEGER,
			iqmux10VideoInput625
				INTEGER,
			iqmux10VideoProcAmp1In1ProcAmpEnable
				INTEGER,
			iqmux10VideoProcAmp1LumaGain
				INTEGER,
			iqmux10VideoProcAmp1ChromaGain
				INTEGER,
			iqmux10VideoProcAmp1BlackLevel
				INTEGER,
			iqmux10VideoProcAmp1PicturePosition
				INTEGER,
			iqmux10VideoProcAmp1YCTiming
				INTEGER,
			iqmux10VideoProcAmp2In2ProcAmpEnable
				INTEGER,
			iqmux10VideoProcAmp2LumaGain
				INTEGER,
			iqmux10VideoProcAmp2ChromaGain
				INTEGER,
			iqmux10VideoProcAmp2BlackLevel
				INTEGER,
			iqmux10VideoProcAmp2PicturePosition
				INTEGER,
			iqmux10VideoProcAmp2YCTiming
				INTEGER,
			iqmux10AudioDeembed
				INTEGER,
			iqmux10AudioProcAmpStereo1
				INTEGER,
			iqmux10ProcAmpDeembed1LGainDeembed1L
				INTEGER,
			iqmux10ProcAmpDeembed1LInvert
				INTEGER,
			iqmux10ProcAmpDeembed1LMute
				INTEGER,
			iqmux10ProcAmpDeembed1RGainDeembed1R
				INTEGER,
			iqmux10ProcAmpDeembed1RInvert
				INTEGER,
			iqmux10ProcAmpDeembed1RMute
				INTEGER,
			iqmux10AudioProcAmpStereo2
				INTEGER,
			iqmux10ProcAmpDeembed2LGainDeembed2L
				INTEGER,
			iqmux10ProcAmpDeembed2LInvert
				INTEGER,
			iqmux10ProcAmpDeembed2LMute
				INTEGER,
			iqmux10ProcAmpDeembed2RGainDeembed2R
				INTEGER,
			iqmux10ProcAmpDeembed2RInvert
				INTEGER,
			iqmux10ProcAmpDeembed2RMute
				INTEGER,
			iqmux10AudioProcAmpStereo3
				INTEGER,
			iqmux10ProcAmpDeembed3LGainDeembed3L
				INTEGER,
			iqmux10ProcAmpDeembed3LInvert
				INTEGER,
			iqmux10ProcAmpDeembed3LMute
				INTEGER,
			iqmux10ProcAmpDeembed3RGainDeembed3R
				INTEGER,
			iqmux10ProcAmpDeembed3RInvert
				INTEGER,
			iqmux10ProcAmpDeembed3RMute
				INTEGER,
			iqmux10AudioProcAmpStereo4
				INTEGER,
			iqmux10ProcAmpDeembed4LGainDeembed4L
				INTEGER,
			iqmux10ProcAmpDeembed4LInvert
				INTEGER,
			iqmux10ProcAmpDeembed4LMute
				INTEGER,
			iqmux10ProcAmpDeembed4RGainDeembed4R
				INTEGER,
			iqmux10ProcAmpDeembed4RInvert
				INTEGER,
			iqmux10ProcAmpDeembed4RMute
				INTEGER,
			iqmux10AudioProcAmpStereo5
				INTEGER,
			iqmux10ProcAmpDeembed5LGainDeembed5L
				INTEGER,
			iqmux10ProcAmpDeembed5LInvert
				INTEGER,
			iqmux10ProcAmpDeembed5LMute
				INTEGER,
			iqmux10ProcAmpDeembed5RGainDeembed5R
				INTEGER,
			iqmux10ProcAmpDeembed5RInvert
				INTEGER,
			iqmux10ProcAmpDeembed5RMute
				INTEGER,
			iqmux10AudioProcAmpStereo6
				INTEGER,
			iqmux10ProcAmpDeembed6LGainDeembed6L
				INTEGER,
			iqmux10ProcAmpDeembed6LInvert
				INTEGER,
			iqmux10ProcAmpDeembed6LMute
				INTEGER,
			iqmux10ProcAmpDeembed6RGainDeembed6R
				INTEGER,
			iqmux10ProcAmpDeembed6RInvert
				INTEGER,
			iqmux10ProcAmpDeembed6RMute
				INTEGER,
			iqmux10AudioProcAmpStereo7
				INTEGER,
			iqmux10ProcAmpDeembed7LGainDeembed7L
				INTEGER,
			iqmux10ProcAmpDeembed7LInvert
				INTEGER,
			iqmux10ProcAmpDeembed7LMute
				INTEGER,
			iqmux10ProcAmpDeembed7RGainDeembed7R
				INTEGER,
			iqmux10ProcAmpDeembed7RInvert
				INTEGER,
			iqmux10ProcAmpDeembed7RMute
				INTEGER,
			iqmux10AudioProcAmpStereo8
				INTEGER,
			iqmux10ProcAmpDeembed8LGainDeembed8L
				INTEGER,
			iqmux10ProcAmpDeembed8LInvert
				INTEGER,
			iqmux10ProcAmpDeembed8LMute
				INTEGER,
			iqmux10ProcAmpDeembed8RGainDeembed8R
				INTEGER,
			iqmux10ProcAmpDeembed8RInvert
				INTEGER,
			iqmux10ProcAmpDeembed8RMute
				INTEGER,
			iqmux10ProcAmpAES1Stereo
				INTEGER,
			iqmux10ProcAmpAES1LGainAES1L
				INTEGER,
			iqmux10ProcAmpAES1LInvert
				INTEGER,
			iqmux10ProcAmpAES1LMute
				INTEGER,
			iqmux10ProcAmpAES1RGainAES1R
				INTEGER,
			iqmux10ProcAmpAES1RInvert
				INTEGER,
			iqmux10ProcAmpAES1RMute
				INTEGER,
			iqmux10ProcAmpAES2Stereo
				INTEGER,
			iqmux10ProcAmpAES2LGainAES2L
				INTEGER,
			iqmux10ProcAmpAES2LInvert
				INTEGER,
			iqmux10ProcAmpAES2LMute
				INTEGER,
			iqmux10ProcAmpAES2RGainAES2R
				INTEGER,
			iqmux10ProcAmpAES2RInvert
				INTEGER,
			iqmux10ProcAmpAES2RMute
				INTEGER,
			iqmux10ProcAmpAES3Stereo
				INTEGER,
			iqmux10ProcAmpAES3LGainAES3L
				INTEGER,
			iqmux10ProcAmpAES3LInvert
				INTEGER,
			iqmux10ProcAmpAES3LMute
				INTEGER,
			iqmux10ProcAmpAES3RGainAES3R
				INTEGER,
			iqmux10ProcAmpAES3RInvert
				INTEGER,
			iqmux10ProcAmpAES3RMute
				INTEGER,
			iqmux10ProcAmpAES4Stereo
				INTEGER,
			iqmux10ProcAmpAES4LGainAES4L
				INTEGER,
			iqmux10ProcAmpAES4LInvert
				INTEGER,
			iqmux10ProcAmpAES4LMute
				INTEGER,
			iqmux10ProcAmpAES4RGainAES4R
				INTEGER,
			iqmux10ProcAmpAES4RInvert
				INTEGER,
			iqmux10ProcAmpAES4RMute
				INTEGER,
			iqmux10EmbedEmbedder1Embed1Source
				INTEGER,
			iqmux10EmbedEmbedder1PairSelection
				INTEGER,
			iqmux10EmbedEmbedder1Disable
				INTEGER,
			iqmux10EmbedEmbedder2Embed2Source
				INTEGER,
			iqmux10EmbedEmbedder2PairSelection
				INTEGER,
			iqmux10EmbedEmbedder2Disable
				INTEGER,
			iqmux10EmbedEmbedder3Embed3Source
				INTEGER,
			iqmux10EmbedEmbedder3PairSelection
				INTEGER,
			iqmux10EmbedEmbedder3Disable
				INTEGER,
			iqmux10EmbedEmbedder4Embed4Source
				INTEGER,
			iqmux10EmbedEmbedder4PairSelection
				INTEGER,
			iqmux10EmbedEmbedder4Disable
				INTEGER,
			iqmux10Mixer1Mix1Source1
				INTEGER,
			iqmux10MixMixer1Gain1
				INTEGER,
			iqmux10Mixer1Mix1Source2
				INTEGER,
			iqmux10MixMixer1Gain2
				INTEGER,
			iqmux10Mixer1Mix1Source3
				INTEGER,
			iqmux10MixMixer1Gain3
				INTEGER,
			iqmux10Mixer1Mix1Source4
				INTEGER,
			iqmux10MixMixer1Gain4
				INTEGER,
			iqmux10Mixer2Mix2Source1
				INTEGER,
			iqmux10MixMixer2Gain1
				INTEGER,
			iqmux10Mixer2Mix2Source2
				INTEGER,
			iqmux10MixMixer2Gain2
				INTEGER,
			iqmux10Mixer2Mix2Source3
				INTEGER,
			iqmux10MixMixer2Gain3
				INTEGER,
			iqmux10Mixer2Mix2Source4
				INTEGER,
			iqmux10MixMixer2Gain4
				INTEGER,
			iqmux10Mixer3Mix3Source1
				INTEGER,
			iqmux10MixMixer3Gain1
				INTEGER,
			iqmux10Mixer3Mix3Source2
				INTEGER,
			iqmux10MixMixer3Gain2
				INTEGER,
			iqmux10Mixer3Mix3Source3
				INTEGER,
			iqmux10MixMixer3Gain3
				INTEGER,
			iqmux10Mixer3Mix3Source4
				INTEGER,
			iqmux10MixMixer3Gain4
				INTEGER,
			iqmux10Mixer4Mix4Source1
				INTEGER,
			iqmux10MixMixer4Gain1
				INTEGER,
			iqmux10Mixer4Mix4Source2
				INTEGER,
			iqmux10MixMixer4Gain2
				INTEGER,
			iqmux10Mixer4Mix4Source3
				INTEGER,
			iqmux10MixMixer4Gain3
				INTEGER,
			iqmux10Mixer4Mix4Source4
				INTEGER,
			iqmux10MixMixer4Gain4
				INTEGER,
			iqmux10BusSourceBusALSource
				INTEGER,
			iqmux10BusSourceBusARSource
				INTEGER,
			iqmux10BusSourceBusBLSource
				INTEGER,
			iqmux10BusSourceBusBRSource
				INTEGER,
			iqmux10BusSourceBusCLSource
				INTEGER,
			iqmux10BusSourceBusCRSource
				INTEGER,
			iqmux10BusSourceBusDLSource
				INTEGER,
			iqmux10BusSourceBusDRSource
				INTEGER,
			iqmux10BusesBusProcAmpStereoA
				INTEGER,
			iqmux10BusProcAmpBusALGainBusAL
				INTEGER,
			iqmux10BusProcAmpBusALInvert
				INTEGER,
			iqmux10BusProcAmpBusALMute
				INTEGER,
			iqmux10BusProcAmpBusARGainBusAR
				INTEGER,
			iqmux10BusProcAmpBusARInvert
				INTEGER,
			iqmux10BusProcAmpBusARMute
				INTEGER,
			iqmux10BusesBusProcAmpStereoB
				INTEGER,
			iqmux10BusProcAmpBusBLGainBusBL
				INTEGER,
			iqmux10BusProcAmpBusBLInvert
				INTEGER,
			iqmux10BusProcAmpBusBLMute
				INTEGER,
			iqmux10BusProcAmpBusBRGainBusBR
				INTEGER,
			iqmux10BusProcAmpBusBRInvert
				INTEGER,
			iqmux10BusProcAmpBusBRMute
				INTEGER,
			iqmux10BusesBusProcAmpStereoC
				INTEGER,
			iqmux10BusProcAmpBusCLGainBusCL
				INTEGER,
			iqmux10BusProcAmpBusCLInvert
				INTEGER,
			iqmux10BusProcAmpBusCLMute
				INTEGER,
			iqmux10BusProcAmpBusCRGainBusCR
				INTEGER,
			iqmux10BusProcAmpBusCRInvert
				INTEGER,
			iqmux10BusProcAmpBusCRMute
				INTEGER,
			iqmux10BusesBusProcAmpStereoD
				INTEGER,
			iqmux10BusProcAmpBusDLGainBusDL
				INTEGER,
			iqmux10BusProcAmpBusDLInvert
				INTEGER,
			iqmux10BusProcAmpBusDLMute
				INTEGER,
			iqmux10BusProcAmpBusDRGainBusDR
				INTEGER,
			iqmux10BusProcAmpBusDRInvert
				INTEGER,
			iqmux10BusProcAmpBusDRMute
				INTEGER,
			iqmux10AudioDelayAESInput1Delay
				INTEGER,
			iqmux10AudioDelayAESInput2Delay
				INTEGER,
			iqmux10AudioDelayAESInput3Delay
				INTEGER,
			iqmux10AudioDelayAESInput4Delay
				INTEGER,
			iqmux10DelayDelaySelectInternal
				INTEGER,
			iqmux10DelayDelaySelectManual
				INTEGER,
			iqmux10DelayDelaySelectRolltrack14
				INTEGER,
			iqmux10DelayDelaySelectRolltrack15
				INTEGER,
			iqmux10DelayDelaySelectRolltrack16
				INTEGER,
			iqmux10DelayDelaySelectRolltrack17
				INTEGER,
			iqmux10DelayDelaySelectGPIDelaySelect
				INTEGER,
			iqmux10DelayDelayStatusManual
				INTEGER,
			iqmux10DelayDelayStatusInternal
				RollCallString,
			iqmux10DelayDelayStatusRolltrack14
				RollCallString,
			iqmux10DelayDelayStatusRolltrack15
				RollCallString,
			iqmux10DelayDelayStatusRolltrack16
				RollCallString,
			iqmux10DelayDelayStatusRolltrack17
				RollCallString,
			iqmux10DelayDelayStatusGPIDelayDisplay
				RollCallString,
			iqmux10DelayDelayStatusTotalDelayDisplay
				RollCallString,
			iqmux10AudioMonitorSilenceLevel
				INTEGER,
			iqmux10AudioMonitorLowLevel
				INTEGER,
			iqmux10AudioMonitorHighLevel
				INTEGER,
			iqmux10AudioMonitorOverloadLevel
				INTEGER,
			iqmux10AudioMonitorWarningTimer
				INTEGER,
			iqmux10Freeze
				INTEGER,
			iqmux10Genlock
				INTEGER,
			iqmux10GenlockGenlockPhase625HPhase
				INTEGER,
			iqmux10GenlockGenlockPhase625VPhase
				INTEGER,
			iqmux10GenlockGenlockPhase525HPhase
				INTEGER,
			iqmux10GenlockGenlockPhase525VPhase
				INTEGER,
			iqmux10GenlockFreerunFreq
				INTEGER,
			iqmux10GenlockFrameDelay
				INTEGER,
			iqmux10GenlockDelayPhase625HPhase
				INTEGER,
			iqmux10GenlockDelayPhase625VPhase
				INTEGER,
			iqmux10GenlockDelayPhase525HPhase
				INTEGER,
			iqmux10GenlockDelayPhase525VPhase
				INTEGER,
			iqmux10UserMemMemory1Save1
				INTEGER,
			iqmux10UserMemMemory1Recall1
				INTEGER,
			iqmux10UserMemMemory1Clear1
				INTEGER,
			iqmux10UserMemMemory1Name1
				RollCallString,
			iqmux10UserMemMemory2Save2
				INTEGER,
			iqmux10UserMemMemory2Recall2
				INTEGER,
			iqmux10UserMemMemory2Clear2
				INTEGER,
			iqmux10UserMemMemory2Name2
				RollCallString,
			iqmux10UserMemMemory3Save3
				INTEGER,
			iqmux10UserMemMemory3Recall3
				INTEGER,
			iqmux10UserMemMemory3Clear3
				INTEGER,
			iqmux10UserMemMemory3Name3
				RollCallString,
			iqmux10UserMemMemory4Save4
				INTEGER,
			iqmux10UserMemMemory4Recall4
				INTEGER,
			iqmux10UserMemMemory4Clear4
				INTEGER,
			iqmux10UserMemMemory4Name4
				RollCallString,
			iqmux10UserMemMemory5Save5
				INTEGER,
			iqmux10UserMemMemory5Recall5
				INTEGER,
			iqmux10UserMemMemory5Clear5
				INTEGER,
			iqmux10UserMemMemory5Name5
				RollCallString,
			iqmux10UserMemMemory6Save6
				INTEGER,
			iqmux10UserMemMemory6Recall6
				INTEGER,
			iqmux10UserMemMemory6Clear6
				INTEGER,
			iqmux10UserMemMemory6Name6
				RollCallString,
			iqmux10UserMemMemory7Save7
				INTEGER,
			iqmux10UserMemMemory7Recall7
				INTEGER,
			iqmux10UserMemMemory7Clear7
				INTEGER,
			iqmux10UserMemMemory7Name7
				RollCallString,
			iqmux10UserMemMemory8Save8
				INTEGER,
			iqmux10UserMemMemory8Recall8
				INTEGER,
			iqmux10UserMemMemory8Clear8
				INTEGER,
			iqmux10UserMemMemory8Name8
				RollCallString,
			iqmux10SetupPatternAnimatedPattern
				INTEGER,
			iqmux10SetupPatternEnablePattern
				INTEGER,
			iqmux10SetupPattern
				INTEGER,
			iqmux10SetupCaptionEditCaption
				RollCallString,
			iqmux10SetupCaption
				INTEGER,
			iqmux10BlankingVIPass525BlankAll
				INTEGER,
			iqmux10BlankingVIPass525PassAll
				INTEGER,
			iqmux10BlankingVIPass525Line11
				INTEGER,
			iqmux10BlankingVIPass525Line274
				INTEGER,
			iqmux10BlankingVIPass525Line12
				INTEGER,
			iqmux10BlankingVIPass525Line275
				INTEGER,
			iqmux10BlankingVIPass525Line13
				INTEGER,
			iqmux10BlankingVIPass525Line276
				INTEGER,
			iqmux10BlankingVIPass525Line14
				INTEGER,
			iqmux10BlankingVIPass525Line277
				INTEGER,
			iqmux10BlankingVIPass525Line15
				INTEGER,
			iqmux10BlankingVIPass525Line278
				INTEGER,
			iqmux10BlankingVIPass525Line16
				INTEGER,
			iqmux10BlankingVIPass525Line279
				INTEGER,
			iqmux10BlankingVIPass525Line17
				INTEGER,
			iqmux10BlankingVIPass525Line280
				INTEGER,
			iqmux10BlankingVIPass525Line18
				INTEGER,
			iqmux10BlankingVIPass525Line281
				INTEGER,
			iqmux10BlankingVIPass525Line19
				INTEGER,
			iqmux10BlankingVIPass525Line282
				INTEGER,
			iqmux10BlankingVIPass525Line20
				INTEGER,
			iqmux10BlankingVIPass525Line283
				INTEGER,
			iqmux10BlankingVIPass525Line21
				INTEGER,
			iqmux10BlankingVIPass625BlankAll
				INTEGER,
			iqmux10BlankingVIPass625PassAll
				INTEGER,
			iqmux10BlankingVIPass625Line7
				INTEGER,
			iqmux10BlankingVIPass625Line320
				INTEGER,
			iqmux10BlankingVIPass625Line8
				INTEGER,
			iqmux10BlankingVIPass625Line321
				INTEGER,
			iqmux10BlankingVIPass625Line9
				INTEGER,
			iqmux10BlankingVIPass625Line322
				INTEGER,
			iqmux10BlankingVIPass625Line10
				INTEGER,
			iqmux10BlankingVIPass625Line323
				INTEGER,
			iqmux10BlankingVIPass625Line11
				INTEGER,
			iqmux10BlankingVIPass625Line324
				INTEGER,
			iqmux10BlankingVIPass625Line12
				INTEGER,
			iqmux10BlankingVIPass625Line325
				INTEGER,
			iqmux10BlankingVIPass625Line13
				INTEGER,
			iqmux10BlankingVIPass625Line326
				INTEGER,
			iqmux10BlankingVIPass625Line14
				INTEGER,
			iqmux10BlankingVIPass625Line327
				INTEGER,
			iqmux10BlankingVIPass625Line15
				INTEGER,
			iqmux10BlankingVIPass625Line328
				INTEGER,
			iqmux10BlankingVIPass625Line16
				INTEGER,
			iqmux10BlankingVIPass625Line329
				INTEGER,
			iqmux10BlankingVIPass625Line17
				INTEGER,
			iqmux10BlankingVIPass625Line330
				INTEGER,
			iqmux10BlankingVIPass625Line18
				INTEGER,
			iqmux10BlankingVIPass625Line331
				INTEGER,
			iqmux10BlankingVIPass625Line19
				INTEGER,
			iqmux10BlankingVIPass625Line332
				INTEGER,
			iqmux10BlankingVIPass625Line20
				INTEGER,
			iqmux10BlankingVIPass625Line333
				INTEGER,
			iqmux10BlankingVIPass625Line21
				INTEGER,
			iqmux10BlankingVIPass625Line334
				INTEGER,
			iqmux10BlankingVIPass625Line22
				INTEGER,
			iqmux10BlankingVIPass625Line335
				INTEGER,
			iqmux10BlankingVIPass625Line23
				INTEGER,
			iqmux10SetupBlankingHancBlank
				INTEGER,
			iqmux10SetupAudioToneIdentEnable
				INTEGER,
			iqmux10SetupAudioToneFrequency
				INTEGER,
			iqmux10SetupAudioToneFrequencyR
				INTEGER,
			iqmux10SetupAudioToneHeadRoom
				INTEGER,
			iqmux10SetupSlewRate
				INTEGER,
			iqmux10SetupChannelStatus
				RollCallString,
			iqmux10GPIIOGPIInputDisableInputs
				INTEGER,
			iqmux10GPIIOGPIInputInputTimerEnable
				INTEGER,
			iqmux10GPIIOGPIInputTimerActiveHigh
				INTEGER,
			iqmux10GPIIOGPIInputInputSelection
				INTEGER,
			iqmux10GPIIOGPIInputGPIInStatus
				RollCallString,
			iqmux10GPIIOGPIOutputOutActiveHigh
				INTEGER,
			iqmux10GPIIOGPIOutputOutputSelection
				INTEGER,
			iqmux10GPIIOGPIOutputGPIOutStatus
				RollCallString,
			iqmux10GPIIOGPIInputOutputGPIO1
				INTEGER,
			iqmux10SetupGPIIOInputSelection
				INTEGER,
			iqmux10SetupGPIIOOutputSelection
				INTEGER,
			iqmux10SetupRollTrackRollTrackIndex
				INTEGER,
			iqmux10SetupRollTrackRollTrackSource
				INTEGER,
			iqmux10SetupRollTrackRollTrackDisable
				INTEGER,
			iqmux10SetupRollTrackRollTrackAddress
				RollCallString,
			iqmux10SetupRollTrackRollTrackCommand
				RollCallString,
			iqmux10SetupRollTrackRollTrackSending
				RollCallString,
			iqmux10SetupRollTrackRollTrackStatus
				RollCallString,
			iqmux10SetupRollTrackRollTrack_Index
				INTEGER,
			iqmux10SetupRollTrackRollTrack_Source
				INTEGER,
			iqmux10SetupRollTrackRollTrack_Address
				RollCallString,
			iqmux10SetupRollTrackRollTrack_Command
				RollCallString,
			iqmux10SetupLoggingInput
				INTEGER,
			iqmux10SetupLoggingStd
				INTEGER,
			iqmux10SetupLoggingInput1
				INTEGER,
			iqmux10SetupLoggingStd1
				INTEGER,
			iqmux10SetupLoggingInput2
				INTEGER,
			iqmux10SetupLoggingStd2
				INTEGER,
			iqmux10SetupLoggingReference
				INTEGER,
			iqmux10SetupLoggingEDH
				INTEGER,
			iqmux10SetupLoggingEDHErrors
				INTEGER,
			iqmux10SetupLoggingRollTrack
				INTEGER,
			iqmux10SetupLoggingDeembed1
				INTEGER,
			iqmux10SetupLoggingDeembed2
				INTEGER,
			iqmux10SetupLoggingDeembed3
				INTEGER,
			iqmux10SetupLoggingDeembed4
				INTEGER,
			iqmux10SetupLoggingDeembed5
				INTEGER,
			iqmux10SetupLoggingDeembed6
				INTEGER,
			iqmux10SetupLoggingDeembed7
				INTEGER,
			iqmux10SetupLoggingDeembed8
				INTEGER,
			iqmux10SetupLoggingnPCM1
				INTEGER,
			iqmux10SetupLoggingnPCM2
				INTEGER,
			iqmux10SetupLoggingnPCM3
				INTEGER,
			iqmux10SetupLoggingnPCM4
				INTEGER,
			iqmux10SetupLoggingnPCM5
				INTEGER,
			iqmux10SetupLoggingnPCM6
				INTEGER,
			iqmux10SetupLoggingnPCM7
				INTEGER,
			iqmux10SetupLoggingnPCM8
				INTEGER,
			iqmux10SetupLoggingAES1
				INTEGER,
			iqmux10SetupLoggingAES2
				INTEGER,
			iqmux10SetupLoggingAES3
				INTEGER,
			iqmux10SetupLoggingAES4
				INTEGER,
			iqmux10SetupLoggingBusAL
				INTEGER,
			iqmux10SetupLoggingBusAR
				INTEGER,
			iqmux10SetupLoggingBusBL
				INTEGER,
			iqmux10SetupLoggingBusBR
				INTEGER,
			iqmux10SetupLoggingBusCL
				INTEGER,
			iqmux10SetupLoggingBusCR
				INTEGER,
			iqmux10SetupLoggingBusDL
				INTEGER,
			iqmux10SetupLoggingBusDR
				INTEGER,
			iqmux10SetupLoggingFault
				INTEGER,
			iqmux10SetupLoggingStatusINPUT
				RollCallString,
			iqmux10SetupLoggingStatusSTD
				RollCallString,
			iqmux10SetupLoggingStatusINPUT1
				RollCallString,
			iqmux10SetupLoggingStatusSTD1
				RollCallString,
			iqmux10SetupLoggingStatusINPUT2
				RollCallString,
			iqmux10SetupLoggingStatusSTD2
				RollCallString,
			iqmux10SetupLoggingStatusEXTREF
				RollCallString,
			iqmux10SetupLoggingStatusEDH
				RollCallString,
			iqmux10SetupLoggingStatusERRSEC
				RollCallString,
			iqmux10SetupLoggingStatusROLLTRACK
				RollCallString,
			iqmux10SetupLoggingStatusDEEMBED1
				RollCallString,
			iqmux10SetupLoggingStatusDEEMBED2
				RollCallString,
			iqmux10SetupLoggingStatusDEEMBED3
				RollCallString,
			iqmux10SetupLoggingStatusDEEMBED4
				RollCallString,
			iqmux10SetupLoggingStatusDEEMBED5
				RollCallString,
			iqmux10SetupLoggingStatusDEEMBED6
				RollCallString,
			iqmux10SetupLoggingStatusDEEMBED7
				RollCallString,
			iqmux10SetupLoggingStatusDEEMBED8
				RollCallString,
			iqmux10SetupLoggingStatusNPCM1
				RollCallString,
			iqmux10SetupLoggingStatusNPCM2
				RollCallString,
			iqmux10SetupLoggingStatusNPCM3
				RollCallString,
			iqmux10SetupLoggingStatusNPCM4
				RollCallString,
			iqmux10SetupLoggingStatusNPCM5
				RollCallString,
			iqmux10SetupLoggingStatusNPCM6
				RollCallString,
			iqmux10SetupLoggingStatusNPCM7
				RollCallString,
			iqmux10SetupLoggingStatusNPCM8
				RollCallString,
			iqmux10SetupLoggingStatusAES1
				RollCallString,
			iqmux10SetupLoggingStatusAES2
				RollCallString,
			iqmux10SetupLoggingStatusAES3
				RollCallString,
			iqmux10SetupLoggingStatusAES4
				RollCallString,
			iqmux10SetupLoggingStatusBUSAL
				RollCallString,
			iqmux10SetupLoggingStatusBUSAR
				RollCallString,
			iqmux10SetupLoggingStatusBUSBL
				RollCallString,
			iqmux10SetupLoggingStatusBUSBR
				RollCallString,
			iqmux10SetupLoggingStatusBUSCL
				RollCallString,
			iqmux10SetupLoggingStatusBUSCR
				RollCallString,
			iqmux10SetupLoggingStatusBUSDL
				RollCallString,
			iqmux10SetupLoggingStatusBUSDR
				RollCallString,
			iqmux10SetupLoggingStatusFAULT
				RollCallString,
			iqmux10SetupInformationWindow
				INTEGER,
			iqmux10SetupInformationWindowResetErrors
				INTEGER,
			iqmux10SetupDefaultOutput
				INTEGER,
			iqmux10SetupDefaultOutputPattern
				INTEGER,
			iqmux10SetupUnitSoftwareVersion
				RollCallString,
			iqmux10SetupUnitSerialNo
				RollCallString,
			iqmux10SetupUnitPresetUnit
				INTEGER,
			iqmux10SetupUnitRestart
				INTEGER,
			iqmux10SetupUnitBuildNo
				RollCallString
		}

	iqmux10SlotIndex OBJECT-TYPE
		SYNTAX		Unsigned32
		MAX-ACCESS		not-accessible
		STATUS			current
		DESCRIPTION
				"The unique Index value for each slot.  Its value
					ranges between 1 and the value of slotNumber."
		::= { iqmux10CmdEntry 0 }


	iqmux10VideoInput OBJECT-TYPE
		SYNTAX		INTEGER {
							val_Input_1_SDI(0),
							val_Input_2_SDI(1)
							}
		MAX-ACCESS		read-write
		STATUS			current
		DESCRIPTION
				"TYPE: - Button
				 PAGE: - Video- Input
					Input 1 SDI  cmdID= 2251  value= 0  
					Input 2 SDI  cmdID= 2251  value= 1  "
		::= { iqmux10CmdEntry 2251 }


	iqmux10VideoInput525 OBJECT-TYPE
		SYNTAX		INTEGER { disable(0), enable(1) }
		MAX-ACCESS		read-write
		STATUS			current
		DESCRIPTION
				"TYPE: - Checkbox
				 PAGE: - Video- Input
					525  cmdID= 1405 "
		::= { iqmux10CmdEntry 1405 }


	iqmux10VideoInput625 OBJECT-TYPE
		SYNTAX		INTEGER { disable(0), enable(1) }
		MAX-ACCESS		read-write
		STATUS			current
		DESCRIPTION
				"TYPE: - Checkbox
				 PAGE: - Video- Input
					625  cmdID= 1406 "
		::= { iqmux10CmdEntry 1406 }


	iqmux10VideoProcAmp1In1ProcAmpEnable OBJECT-TYPE
		SYNTAX		INTEGER { disable(0), enable(1) }
		MAX-ACCESS		read-write
		STATUS			current
		DESCRIPTION
				"TYPE: - Checkbox
				 PAGE: - Video- ProcAmp 1
					In1 ProcAmp Enable  cmdID= 2864 "
		::= { iqmux10CmdEntry 2864 }


	iqmux10VideoProcAmp1LumaGain OBJECT-TYPE
		SYNTAX		INTEGER
		MAX-ACCESS		read-write
		STATUS			current
		DESCRIPTION
				"TYPE: - Number
				 PAGE: - Video- ProcAmp 1
					Luma Gain  cmdID= 2707  min= -60  max= 60  step= 1  format= %1.1f dB  div_scale= 10 
					Min = -6.0 dB  Max = 6.0 dB  Step = 0.1 dB "
		::= { iqmux10CmdEntry 2707 }


	iqmux10VideoProcAmp1ChromaGain OBJECT-TYPE
		SYNTAX		INTEGER
		MAX-ACCESS		read-write
		STATUS			current
		DESCRIPTION
				"TYPE: - Number
				 PAGE: - Video- ProcAmp 1
					Chroma Gain  cmdID= 2706  min= -60  max= 60  step= 1  format= %1.1f dB  div_scale= 10 
					Min = -6.0 dB  Max = 6.0 dB  Step = 0.1 dB "
		::= { iqmux10CmdEntry 2706 }


	iqmux10VideoProcAmp1BlackLevel OBJECT-TYPE
		SYNTAX		INTEGER
		MAX-ACCESS		read-write
		STATUS			current
		DESCRIPTION
				"TYPE: - Number
				 PAGE: - Video- ProcAmp 1
					Black Level  cmdID= 2708  min= -1000  max= 1000  step= 8  format= %1.1f mV  div_scale= 10 
					Min = -100.0 mV  Max = 100.0 mV  Step = 0.8 mV "
		::= { iqmux10CmdEntry 2708 }


	iqmux10VideoProcAmp1PicturePosition OBJECT-TYPE
		SYNTAX		INTEGER
		MAX-ACCESS		read-write
		STATUS			current
		DESCRIPTION
				"TYPE: - Number
				 PAGE: - Video- ProcAmp 1
					Picture Position  cmdID= 2709  min= -592  max= 592  step= 148  format= %3.0f ns  div_scale= 1 
					Min = -592 ns  Max = 592 ns  Step = 148 ns "
		::= { iqmux10CmdEntry 2709 }


	iqmux10VideoProcAmp1YCTiming OBJECT-TYPE
		SYNTAX		INTEGER
		MAX-ACCESS		read-write
		STATUS			current
		DESCRIPTION
				"TYPE: - Number
				 PAGE: - Video- ProcAmp 1
					Y/C Timing  cmdID= 2924  min= -592  max= 592  step= 148  format= %3.0fns  div_scale= 1 
					Min = -592ns  Max = 592ns  Step = 148ns "
		::= { iqmux10CmdEntry 2924 }


	iqmux10VideoProcAmp2In2ProcAmpEnable OBJECT-TYPE
		SYNTAX		INTEGER { disable(0), enable(1) }
		MAX-ACCESS		read-write
		STATUS			current
		DESCRIPTION
				"TYPE: - Checkbox
				 PAGE: - Video- ProcAmp 2
					In2 ProcAmp Enable  cmdID= 2865 "
		::= { iqmux10CmdEntry 2865 }


	iqmux10VideoProcAmp2LumaGain OBJECT-TYPE
		SYNTAX		INTEGER
		MAX-ACCESS		read-write
		STATUS			current
		DESCRIPTION
				"TYPE: - Number
				 PAGE: - Video- ProcAmp 2
					Luma Gain  cmdID= 2711  min= -60  max= 60  step= 1  format= %1.1f dB  div_scale= 10 
					Min = -6.0 dB  Max = 6.0 dB  Step = 0.1 dB "
		::= { iqmux10CmdEntry 2711 }


	iqmux10VideoProcAmp2ChromaGain OBJECT-TYPE
		SYNTAX		INTEGER
		MAX-ACCESS		read-write
		STATUS			current
		DESCRIPTION
				"TYPE: - Number
				 PAGE: - Video- ProcAmp 2
					Chroma Gain  cmdID= 2710  min= -60  max= 60  step= 1  format= %1.1f dB  div_scale= 10 
					Min = -6.0 dB  Max = 6.0 dB  Step = 0.1 dB "
		::= { iqmux10CmdEntry 2710 }


	iqmux10VideoProcAmp2BlackLevel OBJECT-TYPE
		SYNTAX		INTEGER
		MAX-ACCESS		read-write
		STATUS			current
		DESCRIPTION
				"TYPE: - Number
				 PAGE: - Video- ProcAmp 2
					Black Level  cmdID= 2712  min= -1000  max= 1000  step= 8  format= %1.1f mV  div_scale= 10 
					Min = -100.0 mV  Max = 100.0 mV  Step = 0.8 mV "
		::= { iqmux10CmdEntry 2712 }


	iqmux10VideoProcAmp2PicturePosition OBJECT-TYPE
		SYNTAX		INTEGER
		MAX-ACCESS		read-write
		STATUS			current
		DESCRIPTION
				"TYPE: - Number
				 PAGE: - Video- ProcAmp 2
					Picture Position  cmdID= 2713  min= -592  max= 592  step= 148  format= %3.0f ns  div_scale= 1 
					Min = -592 ns  Max = 592 ns  Step = 148 ns "
		::= { iqmux10CmdEntry 2713 }


	iqmux10VideoProcAmp2YCTiming OBJECT-TYPE
		SYNTAX		INTEGER
		MAX-ACCESS		read-write
		STATUS			current
		DESCRIPTION
				"TYPE: - Number
				 PAGE: - Video- ProcAmp 2
					Y/C Timing  cmdID= 2925  min= -592  max= 592  step= 148  format= %3.0fns  div_scale= 1 
					Min = -592ns  Max = 592ns  Step = 148ns "
		::= { iqmux10CmdEntry 2925 }


	iqmux10AudioDeembed OBJECT-TYPE
		SYNTAX		INTEGER {
							val_Input_1_SDI(0),
							val_Input_2_SDI(1),
							val_Follow_Video(2)
							}
		MAX-ACCESS		read-write
		STATUS			current
		DESCRIPTION
				"TYPE: - Button
				 PAGE: - Audio- De-embed
					Input 1 SDI  cmdID= 2923  value= 0  
					Input 2 SDI  cmdID= 2923  value= 1  
					Follow Video  cmdID= 2923  value= 2  "
		::= { iqmux10CmdEntry 2923 }


	iqmux10AudioProcAmpStereo1 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqmux10CmdEntry 3324 }


	iqmux10ProcAmpDeembed1LGainDeembed1L OBJECT-TYPE
		SYNTAX		INTEGER
		MAX-ACCESS		read-write
		STATUS			current
		DESCRIPTION
				"TYPE: - Number
				 PAGE: - Audio- ProcAmp
					Gain De-embed 1L  cmdID= 3088  min= -180  max= 180  step= 1  format= %0.1fdB  div_scale= 10 
					Min = -18.0dB  Max = 18.0dB  Step = 0.1dB "
		::= { iqmux10CmdEntry 3088 }


	iqmux10ProcAmpDeembed1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqmux10CmdEntry 3168 }


	iqmux10ProcAmpDeembed1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqmux10CmdEntry 3248 }


	iqmux10ProcAmpDeembed1RGainDeembed1R OBJECT-TYPE
		SYNTAX		INTEGER
		MAX-ACCESS		read-write
		STATUS			current
		DESCRIPTION
				"TYPE: - Number
				 PAGE: - Audio- ProcAmp
					Gain De-embed 1R  cmdID= 3089  min= -180  max= 180  step= 1  format= %0.1fdB  div_scale= 10 
					Min = -18.0dB  Max = 18.0dB  Step = 0.1dB "
		::= { iqmux10CmdEntry 3089 }


	iqmux10ProcAmpDeembed1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqmux10CmdEntry 3169 }


	iqmux10ProcAmpDeembed1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqmux10CmdEntry 3249 }


	iqmux10AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqmux10CmdEntry 3325 }


	iqmux10ProcAmpDeembed2LGainDeembed2L OBJECT-TYPE
		SYNTAX		INTEGER
		MAX-ACCESS		read-write
		STATUS			current
		DESCRIPTION
				"TYPE: - Number
				 PAGE: - Audio- ProcAmp
					Gain De-embed 2L  cmdID= 3090  min= -180  max= 180  step= 1  format= %0.1fdB  div_scale= 10 
					Min = -18.0dB  Max = 18.0dB  Step = 0.1dB "
		::= { iqmux10CmdEntry 3090 }


	iqmux10ProcAmpDeembed2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqmux10CmdEntry 3170 }


	iqmux10ProcAmpDeembed2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqmux10CmdEntry 3250 }


	iqmux10ProcAmpDeembed2RGainDeembed2R OBJECT-TYPE
		SYNTAX		INTEGER
		MAX-ACCESS		read-write
		STATUS			current
		DESCRIPTION
				"TYPE: - Number
				 PAGE: - Audio- ProcAmp
					Gain De-embed 2R  cmdID= 3091  min= -180  max= 180  step= 1  format= %0.1fdB  div_scale= 10 
					Min = -18.0dB  Max = 18.0dB  Step = 0.1dB "
		::= { iqmux10CmdEntry 3091 }


	iqmux10ProcAmpDeembed2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqmux10CmdEntry 3171 }


	iqmux10ProcAmpDeembed2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqmux10CmdEntry 3251 }


	iqmux10AudioProcAmpStereo3 OBJECT-TYPE
		SYNTAX		INTEGER { disable(0), enable(1) }
		MAX-ACCESS		read-write
		STATUS			current
		DESCRIPTION
				"TYPE: - Checkbox
				 PAGE: - Audio- ProcAmp
					Stereo 3  cmdID= 3326 "
		::= { iqmux10CmdEntry 3326 }


	iqmux10ProcAmpDeembed3LGainDeembed3L OBJECT-TYPE
		SYNTAX		INTEGER
		MAX-ACCESS		read-write
		STATUS			current
		DESCRIPTION
				"TYPE: - Number
				 PAGE: - Audio- ProcAmp
					Gain De-embed 3L  cmdID= 3092  min= -180  max= 180  step= 1  format= %0.1fdB  div_scale= 10 
					Min = -18.0dB  Max = 18.0dB  Step = 0.1dB "
		::= { iqmux10CmdEntry 3092 }


	iqmux10ProcAmpDeembed3LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqmux10CmdEntry 3172 }


	iqmux10ProcAmpDeembed3LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqmux10CmdEntry 3252 }


	iqmux10ProcAmpDeembed3RGainDeembed3R OBJECT-TYPE
		SYNTAX		INTEGER
		MAX-ACCESS		read-write
		STATUS			current
		DESCRIPTION
				"TYPE: - Number
				 PAGE: - Audio- ProcAmp
					Gain De-embed 3R  cmdID= 3093  min= -180  max= 180  step= 1  format= %0.1fdB  div_scale= 10 
					Min = -18.0dB  Max = 18.0dB  Step = 0.1dB "
		::= { iqmux10CmdEntry 3093 }


	iqmux10ProcAmpDeembed3RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqmux10CmdEntry 3173 }


	iqmux10ProcAmpDeembed3RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqmux10CmdEntry 3253 }


	iqmux10AudioProcAmpStereo4 OBJECT-TYPE
		SYNTAX		INTEGER { disable(0), enable(1) }
		MAX-ACCESS		read-write
		STATUS			current
		DESCRIPTION
				"TYPE: - Checkbox
				 PAGE: - Audio- ProcAmp
					Stereo 4  cmdID= 3327 "
		::= { iqmux10CmdEntry 3327 }


	iqmux10ProcAmpDeembed4LGainDeembed4L OBJECT-TYPE
		SYNTAX		INTEGER
		MAX-ACCESS		read-write
		STATUS			current
		DESCRIPTION
				"TYPE: - Number
				 PAGE: - Audio- ProcAmp
					Gain De-embed 4L  cmdID= 3094  min= -180  max= 180  step= 1  format= %0.1fdB  div_scale= 10 
					Min = -18.0dB  Max = 18.0dB  Step = 0.1dB "
		::= { iqmux10CmdEntry 3094 }


	iqmux10ProcAmpDeembed4LInvert OBJECT-TYPE
		SYNTAX		INTEGER { disable(0), enable(1) }
		MAX-ACCESS		read-write
		STATUS			current
		DESCRIPTION
				"TYPE: - Checkbox
				 PAGE: - Audio- ProcAmp
					Invert  cmdID= 3174 "
		::= { iqmux10CmdEntry 3174 }


	iqmux10ProcAmpDeembed4LMute OBJECT-TYPE
		SYNTAX		INTEGER { disable(0), enable(1) }
		MAX-ACCESS		read-write
		STATUS			current
		DESCRIPTION
				"TYPE: - Checkbox
				 PAGE: - Audio- ProcAmp
					Mute  cmdID= 3254 "
		::= { iqmux10CmdEntry 3254 }


	iqmux10ProcAmpDeembed4RGainDeembed4R OBJECT-TYPE
		SYNTAX		INTEGER
		MAX-ACCESS		read-write
		STATUS			current
		DESCRIPTION
				"TYPE: - Number
				 PAGE: - Audio- ProcAmp
					Gain De-embed 4R  cmdID= 3095  min= -180  max= 180  step= 1  format= %0.1fdB  div_scale= 10 
					Min = -18.0dB  Max = 18.0dB  Step = 0.1dB "
		::= { iqmux10CmdEntry 3095 }


	iqmux10ProcAmpDeembed4RInvert OBJECT-TYPE
		SYNTAX		INTEGER { disable(0), enable(1) }
		MAX-ACCESS		read-write
		STATUS			current
		DESCRIPTION
				"TYPE: - Checkbox
				 PAGE: - Audio- ProcAmp
					Invert  cmdID= 3175 "
		::= { iqmux10CmdEntry 3175 }


	iqmux10ProcAmpDeembed4RMute OBJECT-TYPE
		SYNTAX		INTEGER { disable(0), enable(1) }
		MAX-ACCESS		read-write
		STATUS			current
		DESCRIPTION
				"TYPE: - Checkbox
				 PAGE: - Audio- ProcAmp
					Mute  cmdID= 3255 "
		::= { iqmux10CmdEntry 3255 }


	iqmux10AudioProcAmpStereo5 OBJECT-TYPE
		SYNTAX		INTEGER { disable(0), enable(1) }
		MAX-ACCESS		read-write
		STATUS			current
		DESCRIPTION
				"TYPE: - Checkbox
				 PAGE: - Audio- ProcAmp
					Stereo 5  cmdID= 3328 "
		::= { iqmux10CmdEntry 3328 }


	iqmux10ProcAmpDeembed5LGainDeembed5L OBJECT-TYPE
		SYNTAX		INTEGER
		MAX-ACCESS		read-write
		STATUS			current
		DESCRIPTION
				"TYPE: - Number
				 PAGE: - Audio- ProcAmp
					Gain De-embed 5L  cmdID= 3096  min= -180  max= 180  step= 1  format= %0.1fdB  div_scale= 10 
					Min = -18.0dB  Max = 18.0dB  Step = 0.1dB "
		::= { iqmux10CmdEntry 3096 }


	iqmux10ProcAmpDeembed5LInvert OBJECT-TYPE
		SYNTAX		INTEGER { disable(0), enable(1) }
		MAX-ACCESS		read-write
		STATUS			current
		DESCRIPTION
				"TYPE: - Checkbox
				 PAGE: - Audio- ProcAmp
					Invert  cmdID= 3176 "
		::= { iqmux10CmdEntry 3176 }


	iqmux10ProcAmpDeembed5LMute OBJECT-TYPE
		SYNTAX		INTEGER { disable(0), enable(1) }
		MAX-ACCESS		read-write
		STATUS			current
		DESCRIPTION
				"TYPE: - Checkbox
				 PAGE: - Audio- ProcAmp
					Mute  cmdID= 3256 "
		::= { iqmux10CmdEntry 3256 }


	iqmux10ProcAmpDeembed5RGainDeembed5R OBJECT-TYPE
		SYNTAX		INTEGER
		MAX-ACCESS		read-write
		STATUS			current
		DESCRIPTION
				"TYPE: - Number
				 PAGE: - Audio- ProcAmp
					Gain De-embed 5R  cmdID= 3097  min= -180  max= 180  step= 1  format= %0.1fdB  div_scale= 10 
					Min = -18.0dB  Max = 18.0dB  Step = 0.1dB "
		::= { iqmux10CmdEntry 3097 }


	iqmux10ProcAmpDeembed5RInvert OBJECT-TYPE
		SYNTAX		INTEGER { disable(0), enable(1) }
		MAX-ACCESS		read-write
		STATUS			current
		DESCRIPTION
				"TYPE: - Checkbox
				 PAGE: - Audio- ProcAmp
					Invert  cmdID= 3177 "
		::= { iqmux10CmdEntry 3177 }


	iqmux10ProcAmpDeembed5RMute OBJECT-TYPE
		SYNTAX		INTEGER { disable(0), enable(1) }
		MAX-ACCESS		read-write
		STATUS			current
		DESCRIPTION
				"TYPE: - Checkbox
				 PAGE: - Audio- ProcAmp
					Mute  cmdID= 3257 "
		::= { iqmux10CmdEntry 3257 }


	iqmux10AudioProcAmpStereo6 OBJECT-TYPE
		SYNTAX		INTEGER { disable(0), enable(1) }
		MAX-ACCESS		read-write
		STATUS			current
		DESCRIPTION
				"TYPE: - Checkbox
				 PAGE: - Audio- ProcAmp
					Stereo 6  cmdID= 3329 "
		::= { iqmux10CmdEntry 3329 }


	iqmux10ProcAmpDeembed6LGainDeembed6L OBJECT-TYPE
		SYNTAX		INTEGER
		MAX-ACCESS		read-write
		STATUS			current
		DESCRIPTION
				"TYPE: - Number
				 PAGE: - Audio- ProcAmp
					Gain De-embed 6L  cmdID= 3098  min= -180  max= 180  step= 1  format= %0.1fdB  div_scale= 10 
					Min = -18.0dB  Max = 18.0dB  Step = 0.1dB "
		::= { iqmux10CmdEntry 3098 }


	iqmux10ProcAmpDeembed6LInvert OBJECT-TYPE
		SYNTAX		INTEGER { disable(0), enable(1) }
		MAX-ACCESS		read-write
		STATUS			current
		DESCRIPTION
				"TYPE: - Checkbox
				 PAGE: - Audio- ProcAmp
					Invert  cmdID= 3178 "
		::= { iqmux10CmdEntry 3178 }


	iqmux10ProcAmpDeembed6LMute OBJECT-TYPE
		SYNTAX		INTEGER { disable(0), enable(1) }
		MAX-ACCESS		read-write
		STATUS			current
		DESCRIPTION
				"TYPE: - Checkbox
				 PAGE: - Audio- ProcAmp
					Mute  cmdID= 3258 "
		::= { iqmux10CmdEntry 3258 }


	iqmux10ProcAmpDeembed6RGainDeembed6R OBJECT-TYPE
		SYNTAX		INTEGER
		MAX-ACCESS		read-write
		STATUS			current
		DESCRIPTION
				"TYPE: - Number
				 PAGE: - Audio- ProcAmp
					Gain De-embed 6R  cmdID= 3099  min= -180  max= 180  step= 1  format= %0.1fdB  div_scale= 10 
					Min = -18.0dB  Max = 18.0dB  Step = 0.1dB "
		::= { iqmux10CmdEntry 3099 }


	iqmux10ProcAmpDeembed6RInvert OBJECT-TYPE
		SYNTAX		INTEGER { disable(0), enable(1) }
		MAX-ACCESS		read-write
		STATUS			current
		DESCRIPTION
				"TYPE: - Checkbox
				 PAGE: - Audio- ProcAmp
					Invert  cmdID= 3179 "
		::= { iqmux10CmdEntry 3179 }


	iqmux10ProcAmpDeembed6RMute OBJECT-TYPE
		SYNTAX		INTEGER { disable(0), enable(1) }
		MAX-ACCESS		read-write
		STATUS			current
		DESCRIPTION
				"TYPE: - Checkbox
				 PAGE: - Audio- ProcAmp
					Mute  cmdID= 3259 "
		::= { iqmux10CmdEntry 3259 }


	iqmux10AudioProcAmpStereo7 OBJECT-TYPE
		SYNTAX		INTEGER { disable(0), enable(1) }
		MAX-ACCESS		read-write
		STATUS			current
		DESCRIPTION
				"TYPE: - Checkbox
				 PAGE: - Audio- ProcAmp
					Stereo 7  cmdID= 3330 "
		::= { iqmux10CmdEntry 3330 }


	iqmux10ProcAmpDeembed7LGainDeembed7L OBJECT-TYPE
		SYNTAX		INTEGER
		MAX-ACCESS		read-write
		STATUS			current
		DESCRIPTION
				"TYPE: - Number
				 PAGE: - Audio- ProcAmp
					Gain De-embed 7L  cmdID= 3100  min= -180  max= 180  step= 1  format= %0.1fdB  div_scale= 10 
					Min = -18.0dB  Max = 18.0dB  Step = 0.1dB "
		::= { iqmux10CmdEntry 3100 }


	iqmux10ProcAmpDeembed7LInvert OBJECT-TYPE
		SYNTAX		INTEGER { disable(0), enable(1) }
		MAX-ACCESS		read-write
		STATUS			current
		DESCRIPTION
				"TYPE: - Checkbox
				 PAGE: - Audio- ProcAmp
					Invert  cmdID= 3180 "
		::= { iqmux10CmdEntry 3180 }


	iqmux10ProcAmpDeembed7LMute OBJECT-TYPE
		SYNTAX		INTEGER { disable(0), enable(1) }
		MAX-ACCESS		read-write
		STATUS			current
		DESCRIPTION
				"TYPE: - Checkbox
				 PAGE: - Audio- ProcAmp
					Mute  cmdID= 3260 "
		::= { iqmux10CmdEntry 3260 }


	iqmux10ProcAmpDeembed7RGainDeembed7R OBJECT-TYPE
		SYNTAX		INTEGER
		MAX-ACCESS		read-write
		STATUS			current
		DESCRIPTION
				"TYPE: - Number
				 PAGE: - Audio- ProcAmp
					Gain De-embed 7R  cmdID= 3101  min= -180  max= 180  step= 1  format= %0.1fdB  div_scale= 10 
					Min = -18.0dB  Max = 18.0dB  Step = 0.1dB "
		::= { iqmux10CmdEntry 3101 }


	iqmux10ProcAmpDeembed7RInvert OBJECT-TYPE
		SYNTAX		INTEGER { disable(0), enable(1) }
		MAX-ACCESS		read-write
		STATUS			current
		DESCRIPTION
				"TYPE: - Checkbox
				 PAGE: - Audio- ProcAmp
					Invert  cmdID= 3181 "
		::= { iqmux10CmdEntry 3181 }


	iqmux10ProcAmpDeembed7RMute OBJECT-TYPE
		SYNTAX		INTEGER { disable(0), enable(1) }
		MAX-ACCESS		read-write
		STATUS			current
		DESCRIPTION
				"TYPE: - Checkbox
				 PAGE: - Audio- ProcAmp
					Mute  cmdID= 3261 "
		::= { iqmux10CmdEntry 3261 }


	iqmux10AudioProcAmpStereo8 OBJECT-TYPE
		SYNTAX		INTEGER { disable(0), enable(1) }
		MAX-ACCESS		read-write
		STATUS			current
		DESCRIPTION
				"TYPE: - Checkbox
				 PAGE: - Audio- ProcAmp
					Stereo 8  cmdID= 3331 "
		::= { iqmux10CmdEntry 3331 }


	iqmux10ProcAmpDeembed8LGainDeembed8L OBJECT-TYPE
		SYNTAX		INTEGER
		MAX-ACCESS		read-write
		STATUS			current
		DESCRIPTION
				"TYPE: - Number
				 PAGE: - Audio- ProcAmp
					Gain De-embed 8L  cmdID= 3102  min= -180  max= 180  step= 1  format= %0.1fdB  div_scale= 10 
					Min = -18.0dB  Max = 18.0dB  Step = 0.1dB "
		::= { iqmux10CmdEntry 3102 }


	iqmux10ProcAmpDeembed8LInvert OBJECT-TYPE
		SYNTAX		INTEGER { disable(0), enable(1) }
		MAX-ACCESS		read-write
		STATUS			current
		DESCRIPTION
				"TYPE: - Checkbox
				 PAGE: - Audio- ProcAmp
					Invert  cmdID= 3182 "
		::= { iqmux10CmdEntry 3182 }


	iqmux10ProcAmpDeembed8LMute OBJECT-TYPE
		SYNTAX		INTEGER { disable(0), enable(1) }
		MAX-ACCESS		read-write
		STATUS			current
		DESCRIPTION
				"TYPE: - Checkbox
				 PAGE: - Audio- ProcAmp
					Mute  cmdID= 3262 "
		::= { iqmux10CmdEntry 3262 }


	iqmux10ProcAmpDeembed8RGainDeembed8R OBJECT-TYPE
		SYNTAX		INTEGER
		MAX-ACCESS		read-write
		STATUS			current
		DESCRIPTION
				"TYPE: - Number
				 PAGE: - Audio- ProcAmp
					Gain De-embed 8R  cmdID= 3103  min= -180  max= 180  step= 1  format= %0.1fdB  div_scale= 10 
					Min = -18.0dB  Max = 18.0dB  Step = 0.1dB "
		::= { iqmux10CmdEntry 3103 }


	iqmux10ProcAmpDeembed8RInvert OBJECT-TYPE
		SYNTAX		INTEGER { disable(0), enable(1) }
		MAX-ACCESS		read-write
		STATUS			current
		DESCRIPTION
				"TYPE: - Checkbox
				 PAGE: - Audio- ProcAmp
					Invert  cmdID= 3183 "
		::= { iqmux10CmdEntry 3183 }


	iqmux10ProcAmpDeembed8RMute OBJECT-TYPE
		SYNTAX		INTEGER { disable(0), enable(1) }
		MAX-ACCESS		read-write
		STATUS			current
		DESCRIPTION
				"TYPE: - Checkbox
				 PAGE: - Audio- ProcAmp
					Mute  cmdID= 3263 "
		::= { iqmux10CmdEntry 3263 }


	iqmux10ProcAmpAES1Stereo OBJECT-TYPE
		SYNTAX		INTEGER { disable(0), enable(1) }
		MAX-ACCESS		read-write
		STATUS			current
		DESCRIPTION
				"TYPE: - Checkbox
				 PAGE: - Audio- ProcAmp
					Stereo 1  cmdID= 3332 "
		::= { iqmux10CmdEntry 3332 }


	iqmux10ProcAmpAES1LGainAES1L OBJECT-TYPE
		SYNTAX		INTEGER
		MAX-ACCESS		read-write
		STATUS			current
		DESCRIPTION
				"TYPE: - Number
				 PAGE: - Audio- ProcAmp
					Gain AES 1L  cmdID= 3104  min= -180  max= 180  step= 1  format= %0.1fdB  div_scale= 10 
					Min = -18.0dB  Max = 18.0dB  Step = 0.1dB "
		::= { iqmux10CmdEntry 3104 }


	iqmux10ProcAmpAES1LInvert OBJECT-TYPE
		SYNTAX		INTEGER { disable(0), enable(1) }
		MAX-ACCESS		read-write
		STATUS			current
		DESCRIPTION
				"TYPE: - Checkbox
				 PAGE: - Audio- ProcAmp
					Invert  cmdID= 3184 "
		::= { iqmux10CmdEntry 3184 }


	iqmux10ProcAmpAES1LMute OBJECT-TYPE
		SYNTAX		INTEGER { disable(0), enable(1) }
		MAX-ACCESS		read-write
		STATUS			current
		DESCRIPTION
				"TYPE: - Checkbox
				 PAGE: - Audio- ProcAmp
					Mute  cmdID= 3264 "
		::= { iqmux10CmdEntry 3264 }


	iqmux10ProcAmpAES1RGainAES1R OBJECT-TYPE
		SYNTAX		INTEGER
		MAX-ACCESS		read-write
		STATUS			current
		DESCRIPTION
				"TYPE: - Number
				 PAGE: - Audio- ProcAmp
					Gain AES 1R  cmdID= 3105  min= -180  max= 180  step= 1  format= %0.1fdB  div_scale= 10 
					Min = -18.0dB  Max = 18.0dB  Step = 0.1dB "
		::= { iqmux10CmdEntry 3105 }


	iqmux10ProcAmpAES1RInvert OBJECT-TYPE
		SYNTAX		INTEGER { disable(0), enable(1) }
		MAX-ACCESS		read-write
		STATUS			current
		DESCRIPTION
				"TYPE: - Checkbox
				 PAGE: - Audio- ProcAmp
					Invert  cmdID= 3185 "
		::= { iqmux10CmdEntry 3185 }


	iqmux10ProcAmpAES1RMute OBJECT-TYPE
		SYNTAX		INTEGER { disable(0), enable(1) }
		MAX-ACCESS		read-write
		STATUS			current
		DESCRIPTION
				"TYPE: - Checkbox
				 PAGE: - Audio- ProcAmp
					Mute  cmdID= 3265 "
		::= { iqmux10CmdEntry 3265 }


	iqmux10ProcAmpAES2Stereo OBJECT-TYPE
		SYNTAX		INTEGER { disable(0), enable(1) }
		MAX-ACCESS		read-write
		STATUS			current
		DESCRIPTION
				"TYPE: - Checkbox
				 PAGE: - Audio- ProcAmp
					Stereo 2  cmdID= 3333 "
		::= { iqmux10CmdEntry 3333 }


	iqmux10ProcAmpAES2LGainAES2L OBJECT-TYPE
		SYNTAX		INTEGER
		MAX-ACCESS		read-write
		STATUS			current
		DESCRIPTION
				"TYPE: - Number
				 PAGE: - Audio- ProcAmp
					Gain AES 2L  cmdID= 3106  min= -180  max= 180  step= 1  format= %0.1fdB  div_scale= 10 
					Min = -18.0dB  Max = 18.0dB  Step = 0.1dB "
		::= { iqmux10CmdEntry 3106 }


	iqmux10ProcAmpAES2LInvert OBJECT-TYPE
		SYNTAX		INTEGER { disable(0), enable(1) }
		MAX-ACCESS		read-write
		STATUS			current
		DESCRIPTION
				"TYPE: - Checkbox
				 PAGE: - Audio- ProcAmp
					Invert  cmdID= 3186 "
		::= { iqmux10CmdEntry 3186 }


	iqmux10ProcAmpAES2LMute OBJECT-TYPE
		SYNTAX		INTEGER { disable(0), enable(1) }
		MAX-ACCESS		read-write
		STATUS			current
		DESCRIPTION
				"TYPE: - Checkbox
				 PAGE: - Audio- ProcAmp
					Mute  cmdID= 3266 "
		::= { iqmux10CmdEntry 3266 }


	iqmux10ProcAmpAES2RGainAES2R OBJECT-TYPE
		SYNTAX		INTEGER
		MAX-ACCESS		read-write
		STATUS			current
		DESCRIPTION
				"TYPE: - Number
				 PAGE: - Audio- ProcAmp
					Gain AES 2R  cmdID= 3107  min= -180  max= 180  step= 1  format= %0.1fdB  div_scale= 10 
					Min = -18.0dB  Max = 18.0dB  Step = 0.1dB "
		::= { iqmux10CmdEntry 3107 }


	iqmux10ProcAmpAES2RInvert OBJECT-TYPE
		SYNTAX		INTEGER { disable(0), enable(1) }
		MAX-ACCESS		read-write
		STATUS			current
		DESCRIPTION
				"TYPE: - Checkbox
				 PAGE: - Audio- ProcAmp
					Invert  cmdID= 3187 "
		::= { iqmux10CmdEntry 3187 }


	iqmux10ProcAmpAES2RMute OBJECT-TYPE
		SYNTAX		INTEGER { disable(0), enable(1) }
		MAX-ACCESS		read-write
		STATUS			current
		DESCRIPTION
				"TYPE: - Checkbox
				 PAGE: - Audio- ProcAmp
					Mute  cmdID= 3267 "
		::= { iqmux10CmdEntry 3267 }


	iqmux10ProcAmpAES3Stereo OBJECT-TYPE
		SYNTAX		INTEGER { disable(0), enable(1) }
		MAX-ACCESS		read-write
		STATUS			current
		DESCRIPTION
				"TYPE: - Checkbox
				 PAGE: - Audio- ProcAmp
					Stereo 3  cmdID= 3334 "
		::= { iqmux10CmdEntry 3334 }


	iqmux10ProcAmpAES3LGainAES3L OBJECT-TYPE
		SYNTAX		INTEGER
		MAX-ACCESS		read-write
		STATUS			current
		DESCRIPTION
				"TYPE: - Number
				 PAGE: - Audio- ProcAmp
					Gain AES 3L  cmdID= 3108  min= -180  max= 180  step= 1  format= %0.1fdB  div_scale= 10 
					Min = -18.0dB  Max = 18.0dB  Step = 0.1dB "
		::= { iqmux10CmdEntry 3108 }


	iqmux10ProcAmpAES3LInvert OBJECT-TYPE
		SYNTAX		INTEGER { disable(0), enable(1) }
		MAX-ACCESS		read-write
		STATUS			current
		DESCRIPTION
				"TYPE: - Checkbox
				 PAGE: - Audio- ProcAmp
					Invert  cmdID= 3188 "
		::= { iqmux10CmdEntry 3188 }


	iqmux10ProcAmpAES3LMute OBJECT-TYPE
		SYNTAX		INTEGER { disable(0), enable(1) }
		MAX-ACCESS		read-write
		STATUS			current
		DESCRIPTION
				"TYPE: - Checkbox
				 PAGE: - Audio- ProcAmp
					Mute  cmdID= 3268 "
		::= { iqmux10CmdEntry 3268 }


	iqmux10ProcAmpAES3RGainAES3R OBJECT-TYPE
		SYNTAX		INTEGER
		MAX-ACCESS		read-write
		STATUS			current
		DESCRIPTION
				"TYPE: - Number
				 PAGE: - Audio- ProcAmp
					Gain AES 3R  cmdID= 3109  min= -180  max= 180  step= 1  format= %0.1fdB  div_scale= 10 
					Min = -18.0dB  Max = 18.0dB  Step = 0.1dB "
		::= { iqmux10CmdEntry 3109 }


	iqmux10ProcAmpAES3RInvert OBJECT-TYPE
		SYNTAX		INTEGER { disable(0), enable(1) }
		MAX-ACCESS		read-write
		STATUS			current
		DESCRIPTION
				"TYPE: - Checkbox
				 PAGE: - Audio- ProcAmp
					Invert  cmdID= 3189 "
		::= { iqmux10CmdEntry 3189 }


	iqmux10ProcAmpAES3RMute OBJECT-TYPE
		SYNTAX		INTEGER { disable(0), enable(1) }
		MAX-ACCESS		read-write
		STATUS			current
		DESCRIPTION
				"TYPE: - Checkbox
				 PAGE: - Audio- ProcAmp
					Mute  cmdID= 3269 "
		::= { iqmux10CmdEntry 3269 }


	iqmux10ProcAmpAES4Stereo OBJECT-TYPE
		SYNTAX		INTEGER { disable(0), enable(1) }
		MAX-ACCESS		read-write
		STATUS			current
		DESCRIPTION
				"TYPE: - Checkbox
				 PAGE: - Audio- ProcAmp
					Stereo 4  cmdID= 3335 "
		::= { iqmux10CmdEntry 3335 }


	iqmux10ProcAmpAES4LGainAES4L OBJECT-TYPE
		SYNTAX		INTEGER
		MAX-ACCESS		read-write
		STATUS			current
		DESCRIPTION
				"TYPE: - Number
				 PAGE: - Audio- ProcAmp
					Gain AES 4L  cmdID= 3110  min= -180  max= 180  step= 1  format= %0.1fdB  div_scale= 10 
					Min = -18.0dB  Max = 18.0dB  Step = 0.1dB "
		::= { iqmux10CmdEntry 3110 }


	iqmux10ProcAmpAES4LInvert OBJECT-TYPE
		SYNTAX		INTEGER { disable(0), enable(1) }
		MAX-ACCESS		read-write
		STATUS			current
		DESCRIPTION
				"TYPE: - Checkbox
				 PAGE: - Audio- ProcAmp
					Invert  cmdID= 3190 "
		::= { iqmux10CmdEntry 3190 }


	iqmux10ProcAmpAES4LMute OBJECT-TYPE
		SYNTAX		INTEGER { disable(0), enable(1) }
		MAX-ACCESS		read-write
		STATUS			current
		DESCRIPTION
				"TYPE: - Checkbox
				 PAGE: - Audio- ProcAmp
					Mute  cmdID= 3270 "
		::= { iqmux10CmdEntry 3270 }


	iqmux10ProcAmpAES4RGainAES4R OBJECT-TYPE
		SYNTAX		INTEGER
		MAX-ACCESS		read-write
		STATUS			current
		DESCRIPTION
				"TYPE: - Number
				 PAGE: - Audio- ProcAmp
					Gain AES 4R  cmdID= 3111  min= -180  max= 180  step= 1  format= %0.1fdB  div_scale= 10 
					Min = -18.0dB  Max = 18.0dB  Step = 0.1dB "
		::= { iqmux10CmdEntry 3111 }


	iqmux10ProcAmpAES4RInvert OBJECT-TYPE
		SYNTAX		INTEGER { disable(0), enable(1) }
		MAX-ACCESS		read-write
		STATUS			current
		DESCRIPTION
				"TYPE: - Checkbox
				 PAGE: - Audio- ProcAmp
					Invert  cmdID= 3191 "
		::= { iqmux10CmdEntry 3191 }


	iqmux10ProcAmpAES4RMute OBJECT-TYPE
		SYNTAX		INTEGER { disable(0), enable(1) }
		MAX-ACCESS		read-write
		STATUS			current
		DESCRIPTION
				"TYPE: - Checkbox
				 PAGE: - Audio- ProcAmp
					Mute  cmdID= 3271 "
		::= { iqmux10CmdEntry 3271 }


	iqmux10EmbedEmbedder1Embed1Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- Embed- Embedder 1
					Embed 1 Source  cmdID= 2941 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqmux10CmdEntry 2941 }


	iqmux10EmbedEmbedder1PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 1
					Pair Selection  cmdID= 2531 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqmux10CmdEntry 2531 }


	iqmux10EmbedEmbedder1Disable OBJECT-TYPE
		SYNTAX		INTEGER { disable(0), enable(1) }
		MAX-ACCESS		read-write
		STATUS			current
		DESCRIPTION
				"TYPE: - Checkbox
				 PAGE: - Audio- Embed- Embedder 1
					Disable  cmdID= 2541 "
		::= { iqmux10CmdEntry 2541 }


	iqmux10EmbedEmbedder2Embed2Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- Embed- Embedder 2
					Embed 2 Source  cmdID= 2942 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqmux10CmdEntry 2942 }


	iqmux10EmbedEmbedder2PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 2
					Pair Selection  cmdID= 2532 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqmux10CmdEntry 2532 }


	iqmux10EmbedEmbedder2Disable OBJECT-TYPE
		SYNTAX		INTEGER { disable(0), enable(1) }
		MAX-ACCESS		read-write
		STATUS			current
		DESCRIPTION
				"TYPE: - Checkbox
				 PAGE: - Audio- Embed- Embedder 2
					Disable  cmdID= 2542 "
		::= { iqmux10CmdEntry 2542 }


	iqmux10EmbedEmbedder3Embed3Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- Embed- Embedder 3
					Embed 3 Source  cmdID= 2943 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqmux10CmdEntry 2943 }


	iqmux10EmbedEmbedder3PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 3
					Pair Selection  cmdID= 2533 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqmux10CmdEntry 2533 }


	iqmux10EmbedEmbedder3Disable OBJECT-TYPE
		SYNTAX		INTEGER { disable(0), enable(1) }
		MAX-ACCESS		read-write
		STATUS			current
		DESCRIPTION
				"TYPE: - Checkbox
				 PAGE: - Audio- Embed- Embedder 3
					Disable  cmdID= 2543 "
		::= { iqmux10CmdEntry 2543 }


	iqmux10EmbedEmbedder4Embed4Source OBJECT-TYPE
		SYNTAX		INTEGER {
							val_BUS_A(0),
							val_BUS_B(1),
							val_BUS_C(2),
							val_BUS_D(3),
							val_AES_1_Direct(4),
							val_AES_2_Direct(5),
							val_AES_3_Direct(6),
							val_AES_4_Direct(7),
							val_Test_tone(8),
							val_Silence(9)
							}
		MAX-ACCESS		read-write
		STATUS			current
		DESCRIPTION
				"TYPE: - RadiobuttonList
				 PAGE: - Audio- Embed- Embedder 4
					Embed 4 Source  cmdID= 2944 
					BUS A  value= 0  
					BUS B  value= 1  
					BUS C  value= 2  
					BUS D  value= 3  
					AES 1 Direct  value= 4  
					AES 2 Direct  value= 5  
					AES 3 Direct  value= 6  
					AES 4 Direct  value= 7  
					Test tone  value= 8  
					Silence  value= 9  "
		::= { iqmux10CmdEntry 2944 }


	iqmux10EmbedEmbedder4PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 4
					Pair Selection  cmdID= 2534 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqmux10CmdEntry 2534 }


	iqmux10EmbedEmbedder4Disable OBJECT-TYPE
		SYNTAX		INTEGER { disable(0), enable(1) }
		MAX-ACCESS		read-write
		STATUS			current
		DESCRIPTION
				"TYPE: - Checkbox
				 PAGE: - Audio- Embed- Embedder 4
					Disable  cmdID= 2544 "
		::= { iqmux10CmdEntry 2544 }


	iqmux10Mixer1Mix1Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 1- Mix1 Source1
					Mix1 Source1  cmdID= 3440 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3440 }


	iqmux10MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1 
					Min = -71dB  Max = 0dB  Step = 1dB "
		::= { iqmux10CmdEntry 3360 }


	iqmux10Mixer1Mix1Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 1- Mix1 Source2
					Mix1 Source2  cmdID= 3441 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3441 }


	iqmux10MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1 
					Min = -71dB  Max = 0dB  Step = 1dB "
		::= { iqmux10CmdEntry 3361 }


	iqmux10Mixer1Mix1Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 1- Mix1 Source3
					Mix1 Source3  cmdID= 3442 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3442 }


	iqmux10MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1 
					Min = -71dB  Max = 0dB  Step = 1dB "
		::= { iqmux10CmdEntry 3362 }


	iqmux10Mixer1Mix1Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 1- Mix1 Source4
					Mix1 Source4  cmdID= 3443 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3443 }


	iqmux10MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1 
					Min = -71dB  Max = 0dB  Step = 1dB "
		::= { iqmux10CmdEntry 3363 }


	iqmux10Mixer2Mix2Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 2- Mix2 Source1
					Mix2 Source1  cmdID= 3444 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3444 }


	iqmux10MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1 
					Min = -71dB  Max = 0dB  Step = 1dB "
		::= { iqmux10CmdEntry 3364 }


	iqmux10Mixer2Mix2Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 2- Mix2 Source2
					Mix2 Source2  cmdID= 3445 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3445 }


	iqmux10MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1 
					Min = -71dB  Max = 0dB  Step = 1dB "
		::= { iqmux10CmdEntry 3365 }


	iqmux10Mixer2Mix2Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 2- Mix2 Source3
					Mix2 Source3  cmdID= 3446 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3446 }


	iqmux10MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1 
					Min = -71dB  Max = 0dB  Step = 1dB "
		::= { iqmux10CmdEntry 3366 }


	iqmux10Mixer2Mix2Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 2- Mix2 Source4
					Mix2 Source4  cmdID= 3447 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3447 }


	iqmux10MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1 
					Min = -71dB  Max = 0dB  Step = 1dB "
		::= { iqmux10CmdEntry 3367 }


	iqmux10Mixer3Mix3Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 3- Mix3 Source1
					Mix3 Source1  cmdID= 3448 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3448 }


	iqmux10MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1 
					Min = -71dB  Max = 0dB  Step = 1dB "
		::= { iqmux10CmdEntry 3368 }


	iqmux10Mixer3Mix3Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 3- Mix3 Source2
					Mix3 Source2  cmdID= 3449 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3449 }


	iqmux10MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1 
					Min = -71dB  Max = 0dB  Step = 1dB "
		::= { iqmux10CmdEntry 3369 }


	iqmux10Mixer3Mix3Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 3- Mix3 Source3
					Mix3 Source3  cmdID= 3450 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3450 }


	iqmux10MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1 
					Min = -71dB  Max = 0dB  Step = 1dB "
		::= { iqmux10CmdEntry 3370 }


	iqmux10Mixer3Mix3Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 3- Mix3 Source4
					Mix3 Source4  cmdID= 3451 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3451 }


	iqmux10MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1 
					Min = -71dB  Max = 0dB  Step = 1dB "
		::= { iqmux10CmdEntry 3371 }


	iqmux10Mixer4Mix4Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 4- Mix4 Source1
					Mix4 Source1  cmdID= 3452 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3452 }


	iqmux10MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1 
					Min = -71dB  Max = 0dB  Step = 1dB "
		::= { iqmux10CmdEntry 3372 }


	iqmux10Mixer4Mix4Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 4- Mix4 Source2
					Mix4 Source2  cmdID= 3453 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3453 }


	iqmux10MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1 
					Min = -71dB  Max = 0dB  Step = 1dB "
		::= { iqmux10CmdEntry 3373 }


	iqmux10Mixer4Mix4Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 4- Mix4 Source3
					Mix4 Source3  cmdID= 3454 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3454 }


	iqmux10MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1 
					Min = -71dB  Max = 0dB  Step = 1dB "
		::= { iqmux10CmdEntry 3374 }


	iqmux10Mixer4Mix4Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23)
							}
		MAX-ACCESS		read-write
		STATUS			current
		DESCRIPTION
				"TYPE: - RadiobuttonList
				 PAGE: - Audio- Mix- Mixer 4- Mix4 Source4
					Mix4 Source4  cmdID= 3455 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  "
		::= { iqmux10CmdEntry 3455 }


	iqmux10MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1 
					Min = -71dB  Max = 0dB  Step = 1dB "
		::= { iqmux10CmdEntry 3375 }


	iqmux10BusSourceBusALSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusAL Source
					BusAL Source  cmdID= 3520 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3520 }


	iqmux10BusSourceBusARSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusAR Source
					BusAR Source  cmdID= 3521 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3521 }


	iqmux10BusSourceBusBLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusBL Source
					BusBL Source  cmdID= 3522 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3522 }


	iqmux10BusSourceBusBRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusBR Source
					BusBR Source  cmdID= 3523 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3523 }


	iqmux10BusSourceBusCLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusCL Source
					BusCL Source  cmdID= 3524 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3524 }


	iqmux10BusSourceBusCRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusCR Source
					BusCR Source  cmdID= 3525 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3525 }


	iqmux10BusSourceBusDLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusDL Source
					BusDL Source  cmdID= 3526 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3526 }


	iqmux10BusSourceBusDRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_AES_1L(16),
							val_AES_1R(17),
							val_AES_2L(18),
							val_AES_2R(19),
							val_AES_3L(20),
							val_AES_3R(21),
							val_AES_4L(22),
							val_AES_4R(23),
							val_MIX_1(24),
							val_MIX_2(25),
							val_MIX_3(26),
							val_MIX_4(27)
							}
		MAX-ACCESS		read-write
		STATUS			current
		DESCRIPTION
				"TYPE: - RadiobuttonList
				 PAGE: - Audio- Buses- Bus Source- BusDR Source
					BusDR Source  cmdID= 3527 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					AES 1L  value= 16  
					AES 1R  value= 17  
					AES 2L  value= 18  
					AES 2R  value= 19  
					AES 3L  value= 20  
					AES 3R  value= 21  
					AES 4L  value= 22  
					AES 4R  value= 23  
					MIX 1  value= 24  
					MIX 2  value= 25  
					MIX 3  value= 26  
					MIX 4  value= 27  "
		::= { iqmux10CmdEntry 3527 }


	iqmux10BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqmux10CmdEntry 3320 }


	iqmux10BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10 
					Min = -18.0dB  Max = 18.0dB  Step = 0.1dB "
		::= { iqmux10CmdEntry 3080 }


	iqmux10BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqmux10CmdEntry 3160 }


	iqmux10BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqmux10CmdEntry 3240 }


	iqmux10BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10 
					Min = -18.0dB  Max = 18.0dB  Step = 0.1dB "
		::= { iqmux10CmdEntry 3081 }


	iqmux10BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqmux10CmdEntry 3161 }


	iqmux10BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqmux10CmdEntry 3241 }


	iqmux10BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqmux10CmdEntry 3321 }


	iqmux10BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10 
					Min = -18.0dB  Max = 18.0dB  Step = 0.1dB "
		::= { iqmux10CmdEntry 3082 }


	iqmux10BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqmux10CmdEntry 3162 }


	iqmux10BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqmux10CmdEntry 3242 }


	iqmux10BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10 
					Min = -18.0dB  Max = 18.0dB  Step = 0.1dB "
		::= { iqmux10CmdEntry 3083 }


	iqmux10BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqmux10CmdEntry 3163 }


	iqmux10BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqmux10CmdEntry 3243 }


	iqmux10BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqmux10CmdEntry 3322 }


	iqmux10BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10 
					Min = -18.0dB  Max = 18.0dB  Step = 0.1dB "
		::= { iqmux10CmdEntry 3084 }


	iqmux10BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqmux10CmdEntry 3164 }


	iqmux10BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqmux10CmdEntry 3244 }


	iqmux10BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10 
					Min = -18.0dB  Max = 18.0dB  Step = 0.1dB "
		::= { iqmux10CmdEntry 3085 }


	iqmux10BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqmux10CmdEntry 3165 }


	iqmux10BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqmux10CmdEntry 3245 }


	iqmux10BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqmux10CmdEntry 3323 }


	iqmux10BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10 
					Min = -18.0dB  Max = 18.0dB  Step = 0.1dB "
		::= { iqmux10CmdEntry 3086 }


	iqmux10BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqmux10CmdEntry 3166 }


	iqmux10BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqmux10CmdEntry 3246 }


	iqmux10BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10 
					Min = -18.0dB  Max = 18.0dB  Step = 0.1dB "
		::= { iqmux10CmdEntry 3087 }


	iqmux10BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqmux10CmdEntry 3167 }


	iqmux10BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqmux10CmdEntry 3247 }


	iqmux10AudioDelayAESInput1Delay OBJECT-TYPE
		SYNTAX		INTEGER
		MAX-ACCESS		read-write
		STATUS			current
		DESCRIPTION
				"TYPE: - Number
				 PAGE: - Audio- Delay
					AES Input 1 Delay  cmdID= 2928  min= 0  max= 1500  step= 1  format= %0.0f ms  div_scale= 1 
					Min = 0 ms  Max = 1500 ms  Step = 1 ms "
		::= { iqmux10CmdEntry 2928 }


	iqmux10AudioDelayAESInput2Delay OBJECT-TYPE
		SYNTAX		INTEGER
		MAX-ACCESS		read-write
		STATUS			current
		DESCRIPTION
				"TYPE: - Number
				 PAGE: - Audio- Delay
					AES Input 2 Delay  cmdID= 2929  min= 0  max= 1500  step= 1  format= %0.0f ms  div_scale= 1 
					Min = 0 ms  Max = 1500 ms  Step = 1 ms "
		::= { iqmux10CmdEntry 2929 }


	iqmux10AudioDelayAESInput3Delay OBJECT-TYPE
		SYNTAX		INTEGER
		MAX-ACCESS		read-write
		STATUS			current
		DESCRIPTION
				"TYPE: - Number
				 PAGE: - Audio- Delay
					AES Input 3 Delay  cmdID= 2930  min= 0  max= 1500  step= 1  format= %0.0f ms  div_scale= 1 
					Min = 0 ms  Max = 1500 ms  Step = 1 ms "
		::= { iqmux10CmdEntry 2930 }


	iqmux10AudioDelayAESInput4Delay OBJECT-TYPE
		SYNTAX		INTEGER
		MAX-ACCESS		read-write
		STATUS			current
		DESCRIPTION
				"TYPE: - Number
				 PAGE: - Audio- Delay
					AES Input 4 Delay  cmdID= 2931  min= 0  max= 1500  step= 1  format= %0.0f ms  div_scale= 1 
					Min = 0 ms  Max = 1500 ms  Step = 1 ms "
		::= { iqmux10CmdEntry 2931 }


	iqmux10DelayDelaySelectInternal OBJECT-TYPE
		SYNTAX		INTEGER { disable(0), enable(1) }
		MAX-ACCESS		read-write
		STATUS			current
		DESCRIPTION
				"TYPE: - Checkbox
				 PAGE: - Audio- Delay
					Internal  cmdID= 2567 "
		::= { iqmux10CmdEntry 2567 }


	iqmux10DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqmux10CmdEntry 2568 }


	iqmux10DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqmux10CmdEntry 2569 }


	iqmux10DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqmux10CmdEntry 2570 }


	iqmux10DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqmux10CmdEntry 2571 }


	iqmux10DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqmux10CmdEntry 2572 }


	iqmux10DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqmux10CmdEntry 3051 }


	iqmux10DelayDelayStatusManual OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1 
					Manual  cmdID= 2573  format=   
					Min = -40 ms  Max = 1500 ms  Step =   1 ms "
		::= { iqmux10CmdEntry 2573 }


	iqmux10DelayDelayStatusInternal OBJECT-TYPE
		SYNTAX		RollCallString
		MAX-ACCESS		read-only
		STATUS			current
		DESCRIPTION
				"TYPE: - Display
				 PAGE: - Audio- Delay
					Internal  cmdID= 2574  format=   "
		::= { iqmux10CmdEntry 2574 }


	iqmux10DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqmux10CmdEntry 14 }


	iqmux10DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqmux10CmdEntry 15 }


	iqmux10DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqmux10CmdEntry 16 }


	iqmux10DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqmux10CmdEntry 17 }


	iqmux10DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqmux10CmdEntry 3052 }


	iqmux10DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqmux10CmdEntry 2979 }


	iqmux10AudioMonitorSilenceLevel OBJECT-TYPE
		SYNTAX		INTEGER
		MAX-ACCESS		read-write
		STATUS			current
		DESCRIPTION
				"TYPE: - Number
				 PAGE: - Audio- Monitor
					Silence Level  cmdID= 3056  min= -96  max= 0  step= 1  format= %1.1f dB  div_scale= 1 
					Min = -96.0 dB  Max = 0.0 dB  Step = 1.0 dB "
		::= { iqmux10CmdEntry 3056 }


	iqmux10AudioMonitorLowLevel OBJECT-TYPE
		SYNTAX		INTEGER
		MAX-ACCESS		read-write
		STATUS			current
		DESCRIPTION
				"TYPE: - Number
				 PAGE: - Audio- Monitor
					Low Level  cmdID= 2517  min= -96  max= 0  step= 1  format= %1.1f dB  div_scale= 1 
					Min = -96.0 dB  Max = 0.0 dB  Step = 1.0 dB "
		::= { iqmux10CmdEntry 2517 }


	iqmux10AudioMonitorHighLevel OBJECT-TYPE
		SYNTAX		INTEGER
		MAX-ACCESS		read-write
		STATUS			current
		DESCRIPTION
				"TYPE: - Number
				 PAGE: - Audio- Monitor
					High Level  cmdID= 3057  min= -96  max= 0  step= 1  format= %1.1f dB  div_scale= 1 
					Min = -96.0 dB  Max = 0.0 dB  Step = 1.0 dB "
		::= { iqmux10CmdEntry 3057 }


	iqmux10AudioMonitorOverloadLevel OBJECT-TYPE
		SYNTAX		INTEGER
		MAX-ACCESS		read-write
		STATUS			current
		DESCRIPTION
				"TYPE: - Number
				 PAGE: - Audio- Monitor
					Overload Level  cmdID= 3058  min= -96  max= 0  step= 1  format= %1.1f dB  div_scale= 1 
					Min = -96.0 dB  Max = 0.0 dB  Step = 1.0 dB "
		::= { iqmux10CmdEntry 3058 }


	iqmux10AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1 
					Min = 1 sec  Max = 20 sec  Step = 1 sec "
		::= { iqmux10CmdEntry 2518 }


	iqmux10Freeze OBJECT-TYPE
		SYNTAX		INTEGER { disable(0), enable(1) }
		MAX-ACCESS		read-write
		STATUS			current
		DESCRIPTION
				"TYPE: - Checkbox
					Freeze  cmdID= 1208 "
		::= { iqmux10CmdEntry 1208 }


	iqmux10Genlock OBJECT-TYPE
		SYNTAX		INTEGER {
							val_Lock_to_Reference(0),
							val_Lock_to_Input(1),
							val_Free_Run(2)
							}
		MAX-ACCESS		read-write
		STATUS			current
		DESCRIPTION
				"TYPE: - Button
				 PAGE: - Genlock
					Lock to Reference  cmdID= 1049  value= 0  
					Lock to Input  cmdID= 1049  value= 1  
					Free Run  cmdID= 1049  value= 2  "
		::= { iqmux10CmdEntry 1049 }


	iqmux10GenlockGenlockPhase625HPhase OBJECT-TYPE
		SYNTAX		INTEGER
		MAX-ACCESS		read-write
		STATUS			current
		DESCRIPTION
				"TYPE: - Number
				 PAGE: - Genlock
					625 H Phase  cmdID= 1050  min= -31999968  max= 31962931  step= -28499  format=    %.0fns  div_scale= 1000 
					Min =    -32000ns  Max =    31963ns  Step =    -28ns "
		::= { iqmux10CmdEntry 1050 }


	iqmux10GenlockGenlockPhase625VPhase OBJECT-TYPE
		SYNTAX		INTEGER
		MAX-ACCESS		read-write
		STATUS			current
		DESCRIPTION
				"TYPE: - Number
				 PAGE: - Genlock
					625 V Phase  cmdID= 1051  min= -312  max= 312  step= 1  format=    %.0flines  div_scale= 1 
					Min =    -312lines  Max =    312lines  Step =    1lines "
		::= { iqmux10CmdEntry 1051 }


	iqmux10GenlockGenlockPhase525HPhase OBJECT-TYPE
		SYNTAX		INTEGER
		MAX-ACCESS		read-write
		STATUS			current
		DESCRIPTION
				"TYPE: - Number
				 PAGE: - Genlock
					525 H Phase  cmdID= 1052  min= -31777746  max= 31740709  step= -28499  format=    %.0fns  div_scale= 1000 
					Min =    -31778ns  Max =    31741ns  Step =    -28ns "
		::= { iqmux10CmdEntry 1052 }


	iqmux10GenlockGenlockPhase525VPhase OBJECT-TYPE
		SYNTAX		INTEGER
		MAX-ACCESS		read-write
		STATUS			current
		DESCRIPTION
				"TYPE: - Number
				 PAGE: - Genlock
					525 V Phase  cmdID= 1053  min= -262  max= 262  step= 1  format=    %.0flines  div_scale= 1 
					Min =    -262lines  Max =    262lines  Step =    1lines "
		::= { iqmux10CmdEntry 1053 }


	iqmux10GenlockFreerunFreq OBJECT-TYPE
		SYNTAX		INTEGER
		MAX-ACCESS		read-write
		STATUS			current
		DESCRIPTION
				"TYPE: - Number
				 PAGE: - Genlock
					Freerun Freq  cmdID= 2449  min= -60  max= 60  step= 1  format=   %.0f  div_scale= 1 
					Min =   -60  Max =   60  Step =   1 "
		::= { iqmux10CmdEntry 2449 }


	iqmux10GenlockFrameDelay OBJECT-TYPE
		SYNTAX		INTEGER {
							val_0_Frame_Delay(0),
							val_1_Frame_Delay(1),
							val_2_Frame_Delay(2)
							}
		MAX-ACCESS		read-write
		STATUS			current
		DESCRIPTION
				"TYPE: - Button
				 PAGE: - Genlock
					0 Frame Delay  cmdID= 2973  value= 0  
					1 Frame Delay  cmdID= 2973  value= 1  
					2 Frame Delay  cmdID= 2973  value= 2  "
		::= { iqmux10CmdEntry 2973 }


	iqmux10GenlockDelayPhase625HPhase OBJECT-TYPE
		SYNTAX		INTEGER
		MAX-ACCESS		read-write
		STATUS			current
		DESCRIPTION
				"TYPE: - Number
				 PAGE: - Genlock
					625 H Phase  cmdID= 2974  min= 0  max= 63962899  step= -28499  format=  %.0fns  div_scale= 1000 
					Min =  0ns  Max =  63963ns  Step =  -28ns "
		::= { iqmux10CmdEntry 2974 }


	iqmux10GenlockDelayPhase625VPhase OBJECT-TYPE
		SYNTAX		INTEGER
		MAX-ACCESS		read-write
		STATUS			current
		DESCRIPTION
				"TYPE: - Number
				 PAGE: - Genlock
					625 V Phase  cmdID= 2975  min= 0  max= 624  step= 1  format=  %.0flines  div_scale= 1 
					Min =  0lines  Max =  624lines  Step =  1lines "
		::= { iqmux10CmdEntry 2975 }


	iqmux10GenlockDelayPhase525HPhase OBJECT-TYPE
		SYNTAX		INTEGER
		MAX-ACCESS		read-write
		STATUS			current
		DESCRIPTION
				"TYPE: - Number
				 PAGE: - Genlock
					525 H Phase  cmdID= 2976  min= 0  max= 63518455  step= -28499  format=  %.0fns  div_scale= 1000 
					Min =  0ns  Max =  63518ns  Step =  -28ns "
		::= { iqmux10CmdEntry 2976 }


	iqmux10GenlockDelayPhase525VPhase OBJECT-TYPE
		SYNTAX		INTEGER
		MAX-ACCESS		read-write
		STATUS			current
		DESCRIPTION
				"TYPE: - Number
				 PAGE: - Genlock
					525 V Phase  cmdID= 2977  min= 0  max= 524  step= 1  format=  %.0flines  div_scale= 1 
					Min =  0lines  Max =  524lines  Step =  1lines "
		::= { iqmux10CmdEntry 2977 }


	iqmux10UserMemMemory1Save1 OBJECT-TYPE
		SYNTAX		INTEGER { noAction(0),val_Save_1(1) }
		MAX-ACCESS		read-write
		STATUS			current
		DESCRIPTION
				"TYPE: - Button
				 PAGE: - User Mem
					Save 1  cmdID= 1600  value= 1  "
		::= { iqmux10CmdEntry 1600 }


	iqmux10UserMemMemory1Recall1 OBJECT-TYPE
		SYNTAX		INTEGER { noAction(0),val_Recall_1(1) }
		MAX-ACCESS		read-write
		STATUS			current
		DESCRIPTION
				"TYPE: - Button
				 PAGE: - User Mem
					Recall 1  cmdID= 1601  value= 1  "
		::= { iqmux10CmdEntry 1601 }


	iqmux10UserMemMemory1Clear1 OBJECT-TYPE
		SYNTAX		INTEGER { noAction(0),val_Clear_1(1) }
		MAX-ACCESS		read-write
		STATUS			current
		DESCRIPTION
				"TYPE: - Button
				 PAGE: - User Mem
					Clear 1  cmdID= 1602  value= 1  "
		::= { iqmux10CmdEntry 1602 }


	iqmux10UserMemMemory1Name1 OBJECT-TYPE
		SYNTAX		RollCallString
		MAX-ACCESS		read-write
		STATUS			current
		DESCRIPTION
				"TYPE: - Editstring
				 PAGE: - User Mem
					Name 1  cmdID= 1603  "
		::= { iqmux10CmdEntry 1603 }


	iqmux10UserMemMemory2Save2 OBJECT-TYPE
		SYNTAX		INTEGER { noAction(0),val_Save_2(1) }
		MAX-ACCESS		read-write
		STATUS			current
		DESCRIPTION
				"TYPE: - Button
				 PAGE: - User Mem
					Save 2  cmdID= 1604  value= 1  "
		::= { iqmux10CmdEntry 1604 }


	iqmux10UserMemMemory2Recall2 OBJECT-TYPE
		SYNTAX		INTEGER { noAction(0),val_Recall_2(1) }
		MAX-ACCESS		read-write
		STATUS			current
		DESCRIPTION
				"TYPE: - Button
				 PAGE: - User Mem
					Recall 2  cmdID= 1605  value= 1  "
		::= { iqmux10CmdEntry 1605 }


	iqmux10UserMemMemory2Clear2 OBJECT-TYPE
		SYNTAX		INTEGER { noAction(0),val_Clear_2(1) }
		MAX-ACCESS		read-write
		STATUS			current
		DESCRIPTION
				"TYPE: - Button
				 PAGE: - User Mem
					Clear 2  cmdID= 1606  value= 1  "
		::= { iqmux10CmdEntry 1606 }


	iqmux10UserMemMemory2Name2 OBJECT-TYPE
		SYNTAX		RollCallString
		MAX-ACCESS		read-write
		STATUS			current
		DESCRIPTION
				"TYPE: - Editstring
				 PAGE: - User Mem
					Name 2  cmdID= 1607  "
		::= { iqmux10CmdEntry 1607 }


	iqmux10UserMemMemory3Save3 OBJECT-TYPE
		SYNTAX		INTEGER { noAction(0),val_Save_3(1) }
		MAX-ACCESS		read-write
		STATUS			current
		DESCRIPTION
				"TYPE: - Button
				 PAGE: - User Mem
					Save 3  cmdID= 1608  value= 1  "
		::= { iqmux10CmdEntry 1608 }


	iqmux10UserMemMemory3Recall3 OBJECT-TYPE
		SYNTAX		INTEGER { noAction(0),val_Recall_3(1) }
		MAX-ACCESS		read-write
		STATUS			current
		DESCRIPTION
				"TYPE: - Button
				 PAGE: - User Mem
					Recall 3  cmdID= 1609  value= 1  "
		::= { iqmux10CmdEntry 1609 }


	iqmux10UserMemMemory3Clear3 OBJECT-TYPE
		SYNTAX		INTEGER { noAction(0),val_Clear_3(1) }
		MAX-ACCESS		read-write
		STATUS			current
		DESCRIPTION
				"TYPE: - Button
				 PAGE: - User Mem
					Clear 3  cmdID= 1610  value= 1  "
		::= { iqmux10CmdEntry 1610 }


	iqmux10UserMemMemory3Name3 OBJECT-TYPE
		SYNTAX		RollCallString
		MAX-ACCESS		read-write
		STATUS			current
		DESCRIPTION
				"TYPE: - Editstring
				 PAGE: - User Mem
					Name 3  cmdID= 1611  "
		::= { iqmux10CmdEntry 1611 }


	iqmux10UserMemMemory4Save4 OBJECT-TYPE
		SYNTAX		INTEGER { noAction(0),val_Save_4(1) }
		MAX-ACCESS		read-write
		STATUS			current
		DESCRIPTION
				"TYPE: - Button
				 PAGE: - User Mem
					Save 4  cmdID= 1612  value= 1  "
		::= { iqmux10CmdEntry 1612 }


	iqmux10UserMemMemory4Recall4 OBJECT-TYPE
		SYNTAX		INTEGER { noAction(0),val_Recall_4(1) }
		MAX-ACCESS		read-write
		STATUS			current
		DESCRIPTION
				"TYPE: - Button
				 PAGE: - User Mem
					Recall 4  cmdID= 1613  value= 1  "
		::= { iqmux10CmdEntry 1613 }


	iqmux10UserMemMemory4Clear4 OBJECT-TYPE
		SYNTAX		INTEGER { noAction(0),val_Clear_4(1) }
		MAX-ACCESS		read-write
		STATUS			current
		DESCRIPTION
				"TYPE: - Button
				 PAGE: - User Mem
					Clear 4  cmdID= 1614  value= 1  "
		::= { iqmux10CmdEntry 1614 }


	iqmux10UserMemMemory4Name4 OBJECT-TYPE
		SYNTAX		RollCallString
		MAX-ACCESS		read-write
		STATUS			current
		DESCRIPTION
				"TYPE: - Editstring
				 PAGE: - User Mem
					Name 4  cmdID= 1615  "
		::= { iqmux10CmdEntry 1615 }


	iqmux10UserMemMemory5Save5 OBJECT-TYPE
		SYNTAX		INTEGER { noAction(0),val_Save_5(1) }
		MAX-ACCESS		read-write
		STATUS			current
		DESCRIPTION
				"TYPE: - Button
				 PAGE: - User Mem
					Save 5  cmdID= 1616  value= 1  "
		::= { iqmux10CmdEntry 1616 }


	iqmux10UserMemMemory5Recall5 OBJECT-TYPE
		SYNTAX		INTEGER { noAction(0),val_Recall_5(1) }
		MAX-ACCESS		read-write
		STATUS			current
		DESCRIPTION
				"TYPE: - Button
				 PAGE: - User Mem
					Recall 5  cmdID= 1617  value= 1  "
		::= { iqmux10CmdEntry 1617 }


	iqmux10UserMemMemory5Clear5 OBJECT-TYPE
		SYNTAX		INTEGER { noAction(0),val_Clear_5(1) }
		MAX-ACCESS		read-write
		STATUS			current
		DESCRIPTION
				"TYPE: - Button
				 PAGE: - User Mem
					Clear 5  cmdID= 1618  value= 1  "
		::= { iqmux10CmdEntry 1618 }


	iqmux10UserMemMemory5Name5 OBJECT-TYPE
		SYNTAX		RollCallString
		MAX-ACCESS		read-write
		STATUS			current
		DESCRIPTION
				"TYPE: - Editstring
				 PAGE: - User Mem
					Name 5  cmdID= 1619  "
		::= { iqmux10CmdEntry 1619 }


	iqmux10UserMemMemory6Save6 OBJECT-TYPE
		SYNTAX		INTEGER { noAction(0),val_Save_6(1) }
		MAX-ACCESS		read-write
		STATUS			current
		DESCRIPTION
				"TYPE: - Button
				 PAGE: - User Mem
					Save 6  cmdID= 1620  value= 1  "
		::= { iqmux10CmdEntry 1620 }


	iqmux10UserMemMemory6Recall6 OBJECT-TYPE
		SYNTAX		INTEGER { noAction(0),val_Recall_6(1) }
		MAX-ACCESS		read-write
		STATUS			current
		DESCRIPTION
				"TYPE: - Button
				 PAGE: - User Mem
					Recall 6  cmdID= 1621  value= 1  "
		::= { iqmux10CmdEntry 1621 }


	iqmux10UserMemMemory6Clear6 OBJECT-TYPE
		SYNTAX		INTEGER { noAction(0),val_Clear_6(1) }
		MAX-ACCESS		read-write
		STATUS			current
		DESCRIPTION
				"TYPE: - Button
				 PAGE: - User Mem
					Clear 6  cmdID= 1622  value= 1  "
		::= { iqmux10CmdEntry 1622 }


	iqmux10UserMemMemory6Name6 OBJECT-TYPE
		SYNTAX		RollCallString
		MAX-ACCESS		read-write
		STATUS			current
		DESCRIPTION
				"TYPE: - Editstring
				 PAGE: - User Mem
					Name 6  cmdID= 1623  "
		::= { iqmux10CmdEntry 1623 }


	iqmux10UserMemMemory7Save7 OBJECT-TYPE
		SYNTAX		INTEGER { noAction(0),val_Save_7(1) }
		MAX-ACCESS		read-write
		STATUS			current
		DESCRIPTION
				"TYPE: - Button
				 PAGE: - User Mem
					Save 7  cmdID= 1624  value= 1  "
		::= { iqmux10CmdEntry 1624 }


	iqmux10UserMemMemory7Recall7 OBJECT-TYPE
		SYNTAX		INTEGER { noAction(0),val_Recall_7(1) }
		MAX-ACCESS		read-write
		STATUS			current
		DESCRIPTION
				"TYPE: - Button
				 PAGE: - User Mem
					Recall 7  cmdID= 1625  value= 1  "
		::= { iqmux10CmdEntry 1625 }


	iqmux10UserMemMemory7Clear7 OBJECT-TYPE
		SYNTAX		INTEGER { noAction(0),val_Clear_7(1) }
		MAX-ACCESS		read-write
		STATUS			current
		DESCRIPTION
				"TYPE: - Button
				 PAGE: - User Mem
					Clear 7  cmdID= 1626  value= 1  "
		::= { iqmux10CmdEntry 1626 }


	iqmux10UserMemMemory7Name7 OBJECT-TYPE
		SYNTAX		RollCallString
		MAX-ACCESS		read-write
		STATUS			current
		DESCRIPTION
				"TYPE: - Editstring
				 PAGE: - User Mem
					Name 7  cmdID= 1627  "
		::= { iqmux10CmdEntry 1627 }


	iqmux10UserMemMemory8Save8 OBJECT-TYPE
		SYNTAX		INTEGER { noAction(0),val_Save_8(1) }
		MAX-ACCESS		read-write
		STATUS			current
		DESCRIPTION
				"TYPE: - Button
				 PAGE: - User Mem
					Save 8  cmdID= 1628  value= 1  "
		::= { iqmux10CmdEntry 1628 }


	iqmux10UserMemMemory8Recall8 OBJECT-TYPE
		SYNTAX		INTEGER { noAction(0),val_Recall_8(1) }
		MAX-ACCESS		read-write
		STATUS			current
		DESCRIPTION
				"TYPE: - Button
				 PAGE: - User Mem
					Recall 8  cmdID= 1629  value= 1  "
		::= { iqmux10CmdEntry 1629 }


	iqmux10UserMemMemory8Clear8 OBJECT-TYPE
		SYNTAX		INTEGER { noAction(0),val_Clear_8(1) }
		MAX-ACCESS		read-write
		STATUS			current
		DESCRIPTION
				"TYPE: - Button
				 PAGE: - User Mem
					Clear 8  cmdID= 1630  value= 1  "
		::= { iqmux10CmdEntry 1630 }


	iqmux10UserMemMemory8Name8 OBJECT-TYPE
		SYNTAX		RollCallString
		MAX-ACCESS		read-write
		STATUS			current
		DESCRIPTION
				"TYPE: - Editstring
				 PAGE: - User Mem
					Name 8  cmdID= 1631  "
		::= { iqmux10CmdEntry 1631 }


	iqmux10SetupPatternAnimatedPattern OBJECT-TYPE
		SYNTAX		INTEGER { disable(0), enable(1) }
		MAX-ACCESS		read-write
		STATUS			current
		DESCRIPTION
				"TYPE: - Checkbox
				 PAGE: - Setup- Pattern
					Animated Pattern  cmdID= 2940 "
		::= { iqmux10CmdEntry 2940 }


	iqmux10SetupPatternEnablePattern OBJECT-TYPE
		SYNTAX		INTEGER { disable(0), enable(1) }
		MAX-ACCESS		read-write
		STATUS			current
		DESCRIPTION
				"TYPE: - Checkbox
				 PAGE: - Setup- Pattern
					Enable Pattern  cmdID= 1035 "
		::= { iqmux10CmdEntry 1035 }


	iqmux10SetupPattern OBJECT-TYPE
		SYNTAX		INTEGER {
							val_Black(0),
							val_EBU_Colour_Bars(1),
							val_100_Colour_Bars(2),
							val_Ramp(3),
							val_Multiburst(4),
							val_Pulse_Bar(5)
							}
		MAX-ACCESS		read-write
		STATUS			current
		DESCRIPTION
				"TYPE: - Button
				 PAGE: - Setup- Pattern
					Black  cmdID= 1036  value= 0  
					EBU Colour Bars  cmdID= 1036  value= 1  
					100% Colour Bars  cmdID= 1036  value= 2  
					Ramp  cmdID= 1036  value= 3  
					Multiburst  cmdID= 1036  value= 4  
					Pulse & Bar  cmdID= 1036  value= 5  "
		::= { iqmux10CmdEntry 1036 }


	iqmux10SetupCaptionEditCaption OBJECT-TYPE
		SYNTAX		RollCallString
		MAX-ACCESS		read-write
		STATUS			current
		DESCRIPTION
				"TYPE: - Editstring
				 PAGE: - Setup- Caption
					Edit Caption  cmdID= 1041  "
		::= { iqmux10CmdEntry 1041 }


	iqmux10SetupCaption OBJECT-TYPE
		SYNTAX		INTEGER {
							val_Caption_Off(0),
							val_Caption_On(1)
							}
		MAX-ACCESS		read-write
		STATUS			current
		DESCRIPTION
				"TYPE: - Button
				 PAGE: - Setup- Caption
					Caption Off  cmdID= 1037  value= 0  
					Caption On  cmdID= 1037  value= 1  "
		::= { iqmux10CmdEntry 1037 }


	iqmux10BlankingVIPass525BlankAll OBJECT-TYPE
		SYNTAX		INTEGER { noAction(0),val_Blank_All(1) }
		MAX-ACCESS		read-write
		STATUS			current
		DESCRIPTION
				"TYPE: - Button
				 PAGE: - Setup- Blanking
					Blank All  cmdID= 1298  value= 1  "
		::= { iqmux10CmdEntry 1298 }


	iqmux10BlankingVIPass525PassAll OBJECT-TYPE
		SYNTAX		INTEGER { noAction(0),val_Pass_All(1) }
		MAX-ACCESS		read-write
		STATUS			current
		DESCRIPTION
				"TYPE: - Button
				 PAGE: - Setup- Blanking
					Pass All  cmdID= 1297  value= 1  "
		::= { iqmux10CmdEntry 1297 }


	iqmux10BlankingVIPass525Line11 OBJECT-TYPE
		SYNTAX		INTEGER { disable(0), enable(1) }
		MAX-ACCESS		read-write
		STATUS			current
		DESCRIPTION
				"TYPE: - Checkbox
				 PAGE: - Setup- Blanking
					Line 11  cmdID= 1211 "
		::= { iqmux10CmdEntry 1211 }


	iqmux10BlankingVIPass525Line274 OBJECT-TYPE
		SYNTAX		INTEGER { disable(0), enable(1) }
		MAX-ACCESS		read-write
		STATUS			current
		DESCRIPTION
				"TYPE: - Checkbox
				 PAGE: - Setup- Blanking
					Line 274  cmdID= 1231 "
		::= { iqmux10CmdEntry 1231 }


	iqmux10BlankingVIPass525Line12 OBJECT-TYPE
		SYNTAX		INTEGER { disable(0), enable(1) }
		MAX-ACCESS		read-write
		STATUS			current
		DESCRIPTION
				"TYPE: - Checkbox
				 PAGE: - Setup- Blanking
					Line 12  cmdID= 1212 "
		::= { iqmux10CmdEntry 1212 }


	iqmux10BlankingVIPass525Line275 OBJECT-TYPE
		SYNTAX		INTEGER { disable(0), enable(1) }
		MAX-ACCESS		read-write
		STATUS			current
		DESCRIPTION
				"TYPE: - Checkbox
				 PAGE: - Setup- Blanking
					Line 275  cmdID= 1232 "
		::= { iqmux10CmdEntry 1232 }


	iqmux10BlankingVIPass525Line13 OBJECT-TYPE
		SYNTAX		INTEGER { disable(0), enable(1) }
		MAX-ACCESS		read-write
		STATUS			current
		DESCRIPTION
				"TYPE: - Checkbox
				 PAGE: - Setup- Blanking
					Line 13  cmdID= 1213 "
		::= { iqmux10CmdEntry 1213 }


	iqmux10BlankingVIPass525Line276 OBJECT-TYPE
		SYNTAX		INTEGER { disable(0), enable(1) }
		MAX-ACCESS		read-write
		STATUS			current
		DESCRIPTION
				"TYPE: - Checkbox
				 PAGE: - Setup- Blanking
					Line 276  cmdID= 1233 "
		::= { iqmux10CmdEntry 1233 }


	iqmux10BlankingVIPass525Line14 OBJECT-TYPE
		SYNTAX		INTEGER { disable(0), enable(1) }
		MAX-ACCESS		read-write
		STATUS			current
		DESCRIPTION
				"TYPE: - Checkbox
				 PAGE: - Setup- Blanking
					Line 14  cmdID= 1214 "
		::= { iqmux10CmdEntry 1214 }


	iqmux10BlankingVIPass525Line277 OBJECT-TYPE
		SYNTAX		INTEGER { disable(0), enable(1) }
		MAX-ACCESS		read-write
		STATUS			current
		DESCRIPTION
				"TYPE: - Checkbox
				 PAGE: - Setup- Blanking
					Line 277  cmdID= 1234 "
		::= { iqmux10CmdEntry 1234 }


	iqmux10BlankingVIPass525Line15 OBJECT-TYPE
		SYNTAX		INTEGER { disable(0), enable(1) }
		MAX-ACCESS		read-write
		STATUS			current
		DESCRIPTION
				"TYPE: - Checkbox
				 PAGE: - Setup- Blanking
					Line 15  cmdID= 1215 "
		::= { iqmux10CmdEntry 1215 }


	iqmux10BlankingVIPass525Line278 OBJECT-TYPE
		SYNTAX		INTEGER { disable(0), enable(1) }
		MAX-ACCESS		read-write
		STATUS			current
		DESCRIPTION
				"TYPE: - Checkbox
				 PAGE: - Setup- Blanking
					Line 278  cmdID= 1235 "
		::= { iqmux10CmdEntry 1235 }


	iqmux10BlankingVIPass525Line16 OBJECT-TYPE
		SYNTAX		INTEGER { disable(0), enable(1) }
		MAX-ACCESS		read-write
		STATUS			current
		DESCRIPTION
				"TYPE: - Checkbox
				 PAGE: - Setup- Blanking
					Line 16  cmdID= 1216 "
		::= { iqmux10CmdEntry 1216 }


	iqmux10BlankingVIPass525Line279 OBJECT-TYPE
		SYNTAX		INTEGER { disable(0), enable(1) }
		MAX-ACCESS		read-write
		STATUS			current
		DESCRIPTION
				"TYPE: - Checkbox
				 PAGE: - Setup- Blanking
					Line 279  cmdID= 1236 "
		::= { iqmux10CmdEntry 1236 }


	iqmux10BlankingVIPass525Line17 OBJECT-TYPE
		SYNTAX		INTEGER { disable(0), enable(1) }
		MAX-ACCESS		read-write
		STATUS			current
		DESCRIPTION
				"TYPE: - Checkbox
				 PAGE: - Setup- Blanking
					Line 17  cmdID= 1217 "
		::= { iqmux10CmdEntry 1217 }


	iqmux10BlankingVIPass525Line280 OBJECT-TYPE
		SYNTAX		INTEGER { disable(0), enable(1) }
		MAX-ACCESS		read-write
		STATUS			current
		DESCRIPTION
				"TYPE: - Checkbox
				 PAGE: - Setup- Blanking
					Line 280  cmdID= 1237 "
		::= { iqmux10CmdEntry 1237 }


	iqmux10BlankingVIPass525Line18 OBJECT-TYPE
		SYNTAX		INTEGER { disable(0), enable(1) }
		MAX-ACCESS		read-write
		STATUS			current
		DESCRIPTION
				"TYPE: - Checkbox
				 PAGE: - Setup- Blanking
					Line 18  cmdID= 1218 "
		::= { iqmux10CmdEntry 1218 }


	iqmux10BlankingVIPass525Line281 OBJECT-TYPE
		SYNTAX		INTEGER { disable(0), enable(1) }
		MAX-ACCESS		read-write
		STATUS			current
		DESCRIPTION
				"TYPE: - Checkbox
				 PAGE: - Setup- Blanking
					Line 281  cmdID= 1238 "
		::= { iqmux10CmdEntry 1238 }


	iqmux10BlankingVIPass525Line19 OBJECT-TYPE
		SYNTAX		INTEGER { disable(0), enable(1) }
		MAX-ACCESS		read-write
		STATUS			current
		DESCRIPTION
				"TYPE: - Checkbox
				 PAGE: - Setup- Blanking
					Line 19  cmdID= 1219 "
		::= { iqmux10CmdEntry 1219 }


	iqmux10BlankingVIPass525Line282 OBJECT-TYPE
		SYNTAX		INTEGER { disable(0), enable(1) }
		MAX-ACCESS		read-write
		STATUS			current
		DESCRIPTION
				"TYPE: - Checkbox
				 PAGE: - Setup- Blanking
					Line 282  cmdID= 1239 "
		::= { iqmux10CmdEntry 1239 }


	iqmux10BlankingVIPass525Line20 OBJECT-TYPE
		SYNTAX		INTEGER { disable(0), enable(1) }
		MAX-ACCESS		read-write
		STATUS			current
		DESCRIPTION
				"TYPE: - Checkbox
				 PAGE: - Setup- Blanking
					Line 20  cmdID= 1220 "
		::= { iqmux10CmdEntry 1220 }


	iqmux10BlankingVIPass525Line283 OBJECT-TYPE
		SYNTAX		INTEGER { disable(0), enable(1) }
		MAX-ACCESS		read-write
		STATUS			current
		DESCRIPTION
				"TYPE: - Checkbox
				 PAGE: - Setup- Blanking
					Line 283  cmdID= 1240 "
		::= { iqmux10CmdEntry 1240 }


	iqmux10BlankingVIPass525Line21 OBJECT-TYPE
		SYNTAX		INTEGER { disable(0), enable(1) }
		MAX-ACCESS		read-write
		STATUS			current
		DESCRIPTION
				"TYPE: - Checkbox
				 PAGE: - Setup- Blanking
					Line 21  cmdID= 1221 "
		::= { iqmux10CmdEntry 1221 }


	iqmux10BlankingVIPass625BlankAll OBJECT-TYPE
		SYNTAX		INTEGER { noAction(0),val_Blank_All(1) }
		MAX-ACCESS		read-write
		STATUS			current
		DESCRIPTION
				"TYPE: - Button
				 PAGE: - Setup- Blanking
					Blank All  cmdID= 1296  value= 1  "
		::= { iqmux10CmdEntry 1296 }


	iqmux10BlankingVIPass625PassAll OBJECT-TYPE
		SYNTAX		INTEGER { noAction(0),val_Pass_All(1) }
		MAX-ACCESS		read-write
		STATUS			current
		DESCRIPTION
				"TYPE: - Button
				 PAGE: - Setup- Blanking
					Pass All  cmdID= 1295  value= 1  "
		::= { iqmux10CmdEntry 1295 }


	iqmux10BlankingVIPass625Line7 OBJECT-TYPE
		SYNTAX		INTEGER { disable(0), enable(1) }
		MAX-ACCESS		read-write
		STATUS			current
		DESCRIPTION
				"TYPE: - Checkbox
				 PAGE: - Setup- Blanking
					Line 7  cmdID= 1251 "
		::= { iqmux10CmdEntry 1251 }


	iqmux10BlankingVIPass625Line320 OBJECT-TYPE
		SYNTAX		INTEGER { disable(0), enable(1) }
		MAX-ACCESS		read-write
		STATUS			current
		DESCRIPTION
				"TYPE: - Checkbox
				 PAGE: - Setup- Blanking
					Line 320  cmdID= 1272 "
		::= { iqmux10CmdEntry 1272 }


	iqmux10BlankingVIPass625Line8 OBJECT-TYPE
		SYNTAX		INTEGER { disable(0), enable(1) }
		MAX-ACCESS		read-write
		STATUS			current
		DESCRIPTION
				"TYPE: - Checkbox
				 PAGE: - Setup- Blanking
					Line 8  cmdID= 1252 "
		::= { iqmux10CmdEntry 1252 }


	iqmux10BlankingVIPass625Line321 OBJECT-TYPE
		SYNTAX		INTEGER { disable(0), enable(1) }
		MAX-ACCESS		read-write
		STATUS			current
		DESCRIPTION
				"TYPE: - Checkbox
				 PAGE: - Setup- Blanking
					Line 321  cmdID= 1273 "
		::= { iqmux10CmdEntry 1273 }


	iqmux10BlankingVIPass625Line9 OBJECT-TYPE
		SYNTAX		INTEGER { disable(0), enable(1) }
		MAX-ACCESS		read-write
		STATUS			current
		DESCRIPTION
				"TYPE: - Checkbox
				 PAGE: - Setup- Blanking
					Line 9  cmdID= 1253 "
		::= { iqmux10CmdEntry 1253 }


	iqmux10BlankingVIPass625Line322 OBJECT-TYPE
		SYNTAX		INTEGER { disable(0), enable(1) }
		MAX-ACCESS		read-write
		STATUS			current
		DESCRIPTION
				"TYPE: - Checkbox
				 PAGE: - Setup- Blanking
					Line 322  cmdID= 1274 "
		::= { iqmux10CmdEntry 1274 }


	iqmux10BlankingVIPass625Line10 OBJECT-TYPE
		SYNTAX		INTEGER { disable(0), enable(1) }
		MAX-ACCESS		read-write
		STATUS			current
		DESCRIPTION
				"TYPE: - Checkbox
				 PAGE: - Setup- Blanking
					Line 10  cmdID= 1254 "
		::= { iqmux10CmdEntry 1254 }


	iqmux10BlankingVIPass625Line323 OBJECT-TYPE
		SYNTAX		INTEGER { disable(0), enable(1) }
		MAX-ACCESS		read-write
		STATUS			current
		DESCRIPTION
				"TYPE: - Checkbox
				 PAGE: - Setup- Blanking
					Line 323  cmdID= 1275 "
		::= { iqmux10CmdEntry 1275 }


	iqmux10BlankingVIPass625Line11 OBJECT-TYPE
		SYNTAX		INTEGER { disable(0), enable(1) }
		MAX-ACCESS		read-write
		STATUS			current
		DESCRIPTION
				"TYPE: - Checkbox
				 PAGE: - Setup- Blanking
					Line 11  cmdID= 1255 "
		::= { iqmux10CmdEntry 1255 }


	iqmux10BlankingVIPass625Line324 OBJECT-TYPE
		SYNTAX		INTEGER { disable(0), enable(1) }
		MAX-ACCESS		read-write
		STATUS			current
		DESCRIPTION
				"TYPE: - Checkbox
				 PAGE: - Setup- Blanking
					Line 324  cmdID= 1276 "
		::= { iqmux10CmdEntry 1276 }


	iqmux10BlankingVIPass625Line12 OBJECT-TYPE
		SYNTAX		INTEGER { disable(0), enable(1) }
		MAX-ACCESS		read-write
		STATUS			current
		DESCRIPTION
				"TYPE: - Checkbox
				 PAGE: - Setup- Blanking
					Line 12  cmdID= 1256 "
		::= { iqmux10CmdEntry 1256 }


	iqmux10BlankingVIPass625Line325 OBJECT-TYPE
		SYNTAX		INTEGER { disable(0), enable(1) }
		MAX-ACCESS		read-write
		STATUS			current
		DESCRIPTION
				"TYPE: - Checkbox
				 PAGE: - Setup- Blanking
					Line 325  cmdID= 1277 "
		::= { iqmux10CmdEntry 1277 }


	iqmux10BlankingVIPass625Line13 OBJECT-TYPE
		SYNTAX		INTEGER { disable(0), enable(1) }
		MAX-ACCESS		read-write
		STATUS			current
		DESCRIPTION
				"TYPE: - Checkbox
				 PAGE: - Setup- Blanking
					Line 13  cmdID= 1257 "
		::= { iqmux10CmdEntry 1257 }


	iqmux10BlankingVIPass625Line326 OBJECT-TYPE
		SYNTAX		INTEGER { disable(0), enable(1) }
		MAX-ACCESS		read-write
		STATUS			current
		DESCRIPTION
				"TYPE: - Checkbox
				 PAGE: - Setup- Blanking
					Line 326  cmdID= 1278 "
		::= { iqmux10CmdEntry 1278 }


	iqmux10BlankingVIPass625Line14 OBJECT-TYPE
		SYNTAX		INTEGER { disable(0), enable(1) }
		MAX-ACCESS		read-write
		STATUS			current
		DESCRIPTION
				"TYPE: - Checkbox
				 PAGE: - Setup- Blanking
					Line 14  cmdID= 1258 "
		::= { iqmux10CmdEntry 1258 }


	iqmux10BlankingVIPass625Line327 OBJECT-TYPE
		SYNTAX		INTEGER { disable(0), enable(1) }
		MAX-ACCESS		read-write
		STATUS			current
		DESCRIPTION
				"TYPE: - Checkbox
				 PAGE: - Setup- Blanking
					Line 327  cmdID= 1279 "
		::= { iqmux10CmdEntry 1279 }


	iqmux10BlankingVIPass625Line15 OBJECT-TYPE
		SYNTAX		INTEGER { disable(0), enable(1) }
		MAX-ACCESS		read-write
		STATUS			current
		DESCRIPTION
				"TYPE: - Checkbox
				 PAGE: - Setup- Blanking
					Line 15  cmdID= 1259 "
		::= { iqmux10CmdEntry 1259 }


	iqmux10BlankingVIPass625Line328 OBJECT-TYPE
		SYNTAX		INTEGER { disable(0), enable(1) }
		MAX-ACCESS		read-write
		STATUS			current
		DESCRIPTION
				"TYPE: - Checkbox
				 PAGE: - Setup- Blanking
					Line 328  cmdID= 1280 "
		::= { iqmux10CmdEntry 1280 }


	iqmux10BlankingVIPass625Line16 OBJECT-TYPE
		SYNTAX		INTEGER { disable(0), enable(1) }
		MAX-ACCESS		read-write
		STATUS			current
		DESCRIPTION
				"TYPE: - Checkbox
				 PAGE: - Setup- Blanking
					Line 16  cmdID= 1260 "
		::= { iqmux10CmdEntry 1260 }


	iqmux10BlankingVIPass625Line329 OBJECT-TYPE
		SYNTAX		INTEGER { disable(0), enable(1) }
		MAX-ACCESS		read-write
		STATUS			current
		DESCRIPTION
				"TYPE: - Checkbox
				 PAGE: - Setup- Blanking
					Line 329  cmdID= 1281 "
		::= { iqmux10CmdEntry 1281 }


	iqmux10BlankingVIPass625Line17 OBJECT-TYPE
		SYNTAX		INTEGER { disable(0), enable(1) }
		MAX-ACCESS		read-write
		STATUS			current
		DESCRIPTION
				"TYPE: - Checkbox
				 PAGE: - Setup- Blanking
					Line 17  cmdID= 1261 "
		::= { iqmux10CmdEntry 1261 }


	iqmux10BlankingVIPass625Line330 OBJECT-TYPE
		SYNTAX		INTEGER { disable(0), enable(1) }
		MAX-ACCESS		read-write
		STATUS			current
		DESCRIPTION
				"TYPE: - Checkbox
				 PAGE: - Setup- Blanking
					Line 330  cmdID= 1282 "
		::= { iqmux10CmdEntry 1282 }


	iqmux10BlankingVIPass625Line18 OBJECT-TYPE
		SYNTAX		INTEGER { disable(0), enable(1) }
		MAX-ACCESS		read-write
		STATUS			current
		DESCRIPTION
				"TYPE: - Checkbox
				 PAGE: - Setup- Blanking
					Line 18  cmdID= 1262 "
		::= { iqmux10CmdEntry 1262 }


	iqmux10BlankingVIPass625Line331 OBJECT-TYPE
		SYNTAX		INTEGER { disable(0), enable(1) }
		MAX-ACCESS		read-write
		STATUS			current
		DESCRIPTION
				"TYPE: - Checkbox
				 PAGE: - Setup- Blanking
					Line 331  cmdID= 1283 "
		::= { iqmux10CmdEntry 1283 }


	iqmux10BlankingVIPass625Line19 OBJECT-TYPE
		SYNTAX		INTEGER { disable(0), enable(1) }
		MAX-ACCESS		read-write
		STATUS			current
		DESCRIPTION
				"TYPE: - Checkbox
				 PAGE: - Setup- Blanking
					Line 19  cmdID= 1263 "
		::= { iqmux10CmdEntry 1263 }


	iqmux10BlankingVIPass625Line332 OBJECT-TYPE
		SYNTAX		INTEGER { disable(0), enable(1) }
		MAX-ACCESS		read-write
		STATUS			current
		DESCRIPTION
				"TYPE: - Checkbox
				 PAGE: - Setup- Blanking
					Line 332  cmdID= 1284 "
		::= { iqmux10CmdEntry 1284 }


	iqmux10BlankingVIPass625Line20 OBJECT-TYPE
		SYNTAX		INTEGER { disable(0), enable(1) }
		MAX-ACCESS		read-write
		STATUS			current
		DESCRIPTION
				"TYPE: - Checkbox
				 PAGE: - Setup- Blanking
					Line 20  cmdID= 1264 "
		::= { iqmux10CmdEntry 1264 }


	iqmux10BlankingVIPass625Line333 OBJECT-TYPE
		SYNTAX		INTEGER { disable(0), enable(1) }
		MAX-ACCESS		read-write
		STATUS			current
		DESCRIPTION
				"TYPE: - Checkbox
				 PAGE: - Setup- Blanking
					Line 333  cmdID= 1285 "
		::= { iqmux10CmdEntry 1285 }


	iqmux10BlankingVIPass625Line21 OBJECT-TYPE
		SYNTAX		INTEGER { disable(0), enable(1) }
		MAX-ACCESS		read-write
		STATUS			current
		DESCRIPTION
				"TYPE: - Checkbox
				 PAGE: - Setup- Blanking
					Line 21  cmdID= 1265 "
		::= { iqmux10CmdEntry 1265 }


	iqmux10BlankingVIPass625Line334 OBJECT-TYPE
		SYNTAX		INTEGER { disable(0), enable(1) }
		MAX-ACCESS		read-write
		STATUS			current
		DESCRIPTION
				"TYPE: - Checkbox
				 PAGE: - Setup- Blanking
					Line 334  cmdID= 1286 "
		::= { iqmux10CmdEntry 1286 }


	iqmux10BlankingVIPass625Line22 OBJECT-TYPE
		SYNTAX		INTEGER { disable(0), enable(1) }
		MAX-ACCESS		read-write
		STATUS			current
		DESCRIPTION
				"TYPE: - Checkbox
				 PAGE: - Setup- Blanking
					Line 22  cmdID= 1266 "
		::= { iqmux10CmdEntry 1266 }


	iqmux10BlankingVIPass625Line335 OBJECT-TYPE
		SYNTAX		INTEGER { disable(0), enable(1) }
		MAX-ACCESS		read-write
		STATUS			current
		DESCRIPTION
				"TYPE: - Checkbox
				 PAGE: - Setup- Blanking
					Line 335  cmdID= 1287 "
		::= { iqmux10CmdEntry 1287 }


	iqmux10BlankingVIPass625Line23 OBJECT-TYPE
		SYNTAX		INTEGER { disable(0), enable(1) }
		MAX-ACCESS		read-write
		STATUS			current
		DESCRIPTION
				"TYPE: - Checkbox
				 PAGE: - Setup- Blanking
					Line 23  cmdID= 1267 "
		::= { iqmux10CmdEntry 1267 }


	iqmux10SetupBlankingHancBlank OBJECT-TYPE
		SYNTAX		INTEGER { disable(0), enable(1) }
		MAX-ACCESS		read-write
		STATUS			current
		DESCRIPTION
				"TYPE: - Checkbox
				 PAGE: - Setup- Blanking
					Hanc Blank  cmdID= 2971 "
		::= { iqmux10CmdEntry 2971 }


	iqmux10SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqmux10CmdEntry 2489 }


	iqmux10SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1 
					Min = 100.0 Hz  Max = 15000.0 Hz  Step = 100.0 Hz "
		::= { iqmux10CmdEntry 2487 }


	iqmux10SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1 
					Min = 100.0 Hz  Max = 15000.0 Hz  Step = 100.0 Hz "
		::= { iqmux10CmdEntry 2488 }


	iqmux10SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1 
					Min = 4.0 dB  Max = 24.0 dB  Step = 1.0 dB "
		::= { iqmux10CmdEntry 3055 }


	iqmux10SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972 
					Instant  value= 0  
					Fast  value= 1  
					Medium  value= 2  
					Slow  value= 3  
					Slowest  value= 4  "
		::= { iqmux10CmdEntry 2972 }


	iqmux10SetupChannelStatus OBJECT-TYPE
		SYNTAX		RollCallString
		MAX-ACCESS		read-write
		STATUS			current
		DESCRIPTION
				"TYPE: - Editstring
				 PAGE: - Setup
					Channel Status  cmdID= 3060  "
		::= { iqmux10CmdEntry 3060 }


	iqmux10GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqmux10CmdEntry 2605 }


	iqmux10GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqmux10CmdEntry 3053 }


	iqmux10GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqmux10CmdEntry 3054 }


	iqmux10GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 12  step= 1  format= %.0f  div_scale= 1 
					Min = -1  Max = 12  Step = 1 "
		::= { iqmux10CmdEntry 2011 }


	iqmux10GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqmux10CmdEntry 2048 }


	iqmux10GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqmux10CmdEntry 3540 }


	iqmux10GPIIOGPIOutputOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2013 
					Input Present  value= 0  
					Standard 625  value= 1  
					Video Delay  value= 2  
					Unused  value= 3  "
		::= { iqmux10CmdEntry 2013 }


	iqmux10GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqmux10CmdEntry 2049 }


	iqmux10GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqmux10CmdEntry 2014 }


	iqmux10SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 12  step= 1  format= %.0f  div_scale= 1 
					Min = -1  Max = 12  Step = 1 "
		::= { iqmux10CmdEntry 2875 }


	iqmux10SetupGPIIOOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2877 
					Input Present  value= 0  
					Standard 625  value= 1  
					Video Delay  value= 2  
					Unused  value= 3  "
		::= { iqmux10CmdEntry 2877 }


	iqmux10SetupRollTrackRollTrackIndex OBJECT-TYPE
		SYNTAX		INTEGER
		MAX-ACCESS		read-write
		STATUS			current
		DESCRIPTION
				"TYPE: - Number
				 PAGE: - Setup- RollTrack
					RollTrack Index  cmdID= 1495  min= 0  max= 49  step= 1  format= %.0f  div_scale= 1 
					Min = 0  Max = 49  Step = 1 "
		::= { iqmux10CmdEntry 1495 }


	iqmux10SetupRollTrackRollTrackSource OBJECT-TYPE
		SYNTAX		INTEGER
		MAX-ACCESS		read-write
		STATUS			current
		DESCRIPTION
				"TYPE: - Number
				 PAGE: - Setup- RollTrack
					RollTrack Source  cmdID= 1496  min= -1  max= 43  step= 1  format= %.0f  div_scale= 1 
					Min = -1  Max = 43  Step = 1 "
		::= { iqmux10CmdEntry 1496 }


	iqmux10SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqmux10CmdEntry 1513 }


	iqmux10SetupRollTrackRollTrackAddress OBJECT-TYPE
		SYNTAX		RollCallString
		MAX-ACCESS		read-write
		STATUS			current
		DESCRIPTION
				"TYPE: - Editstring
				 PAGE: - Setup- RollTrack
					RollTrack Address  cmdID= 1497  "
		::= { iqmux10CmdEntry 1497 }


	iqmux10SetupRollTrackRollTrackCommand OBJECT-TYPE
		SYNTAX		RollCallString
		MAX-ACCESS		read-write
		STATUS			current
		DESCRIPTION
				"TYPE: - Editstring
				 PAGE: - Setup- RollTrack
					RollTrack Command  cmdID= 1498  "
		::= { iqmux10CmdEntry 1498 }


	iqmux10SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqmux10CmdEntry 1514 }


	iqmux10SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqmux10CmdEntry 1511 }


	iqmux10SetupRollTrackRollTrack_Index OBJECT-TYPE
		SYNTAX		INTEGER
		MAX-ACCESS		read-write
		STATUS			current
		DESCRIPTION
				"TYPE: - Number
				 PAGE: - Setup- RollTrack
					RollTrack Index  cmdID= 2870  min= 0  max= 49  step= 1  format= %.0f  div_scale= 1 
					Min = 0  Max = 49  Step = 1 "
		::= { iqmux10CmdEntry 2870 }


	iqmux10SetupRollTrackRollTrack_Source OBJECT-TYPE
		SYNTAX		INTEGER
		MAX-ACCESS		read-write
		STATUS			current
		DESCRIPTION
				"TYPE: - Number
				 PAGE: - Setup- RollTrack
					RollTrack Source  cmdID= 2871  min= -1  max= 43  step= 1  format= %.0f  div_scale= 1 
					Min = -1  Max = 43  Step = 1 "
		::= { iqmux10CmdEntry 2871 }


	iqmux10SetupRollTrackRollTrack_Address OBJECT-TYPE
		SYNTAX		RollCallString
		MAX-ACCESS		read-write
		STATUS			current
		DESCRIPTION
				"TYPE: - Editstring
				 PAGE: - Setup- RollTrack
					RollTrack Address  cmdID= 2872  "
		::= { iqmux10CmdEntry 2872 }


	iqmux10SetupRollTrackRollTrack_Command OBJECT-TYPE
		SYNTAX		RollCallString
		MAX-ACCESS		read-write
		STATUS			current
		DESCRIPTION
				"TYPE: - Editstring
				 PAGE: - Setup- RollTrack
					RollTrack Command  cmdID= 2873  "
		::= { iqmux10CmdEntry 2873 }


	iqmux10SetupLoggingInput OBJECT-TYPE
		SYNTAX		INTEGER { disable(0), enable(1) }
		MAX-ACCESS		read-write
		STATUS			current
		DESCRIPTION
				"TYPE: - Checkbox
				 PAGE: - Setup- Logging
					Input  cmdID= 1060 "
		::= { iqmux10CmdEntry 1060 }


	iqmux10SetupLoggingStd OBJECT-TYPE
		SYNTAX		INTEGER { disable(0), enable(1) }
		MAX-ACCESS		read-write
		STATUS			current
		DESCRIPTION
				"TYPE: - Checkbox
				 PAGE: - Setup- Logging
					Std  cmdID= 1061 "
		::= { iqmux10CmdEntry 1061 }


	iqmux10SetupLoggingInput1 OBJECT-TYPE
		SYNTAX		INTEGER { disable(0), enable(1) }
		MAX-ACCESS		read-write
		STATUS			current
		DESCRIPTION
				"TYPE: - Checkbox
				 PAGE: - Setup- Logging
					Input1  cmdID= 1094 "
		::= { iqmux10CmdEntry 1094 }


	iqmux10SetupLoggingStd1 OBJECT-TYPE
		SYNTAX		INTEGER { disable(0), enable(1) }
		MAX-ACCESS		read-write
		STATUS			current
		DESCRIPTION
				"TYPE: - Checkbox
				 PAGE: - Setup- Logging
					Std1  cmdID= 1097 "
		::= { iqmux10CmdEntry 1097 }


	iqmux10SetupLoggingInput2 OBJECT-TYPE
		SYNTAX		INTEGER { disable(0), enable(1) }
		MAX-ACCESS		read-write
		STATUS			current
		DESCRIPTION
				"TYPE: - Checkbox
				 PAGE: - Setup- Logging
					Input2  cmdID= 1095 "
		::= { iqmux10CmdEntry 1095 }


	iqmux10SetupLoggingStd2 OBJECT-TYPE
		SYNTAX		INTEGER { disable(0), enable(1) }
		MAX-ACCESS		read-write
		STATUS			current
		DESCRIPTION
				"TYPE: - Checkbox
				 PAGE: - Setup- Logging
					Std2  cmdID= 1098 "
		::= { iqmux10CmdEntry 1098 }


	iqmux10SetupLoggingReference OBJECT-TYPE
		SYNTAX		INTEGER { disable(0), enable(1) }
		MAX-ACCESS		read-write
		STATUS			current
		DESCRIPTION
				"TYPE: - Checkbox
				 PAGE: - Setup- Logging
					Reference  cmdID= 1062 "
		::= { iqmux10CmdEntry 1062 }


	iqmux10SetupLoggingEDH OBJECT-TYPE
		SYNTAX		INTEGER { disable(0), enable(1) }
		MAX-ACCESS		read-write
		STATUS			current
		DESCRIPTION
				"TYPE: - Checkbox
				 PAGE: - Setup- Logging
					EDH  cmdID= 1064 "
		::= { iqmux10CmdEntry 1064 }


	iqmux10SetupLoggingEDHErrors OBJECT-TYPE
		SYNTAX		INTEGER { disable(0), enable(1) }
		MAX-ACCESS		read-write
		STATUS			current
		DESCRIPTION
				"TYPE: - Checkbox
				 PAGE: - Setup- Logging
					EDH Errors  cmdID= 1070 "
		::= { iqmux10CmdEntry 1070 }


	iqmux10SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqmux10CmdEntry 1106 }


	iqmux10SetupLoggingDeembed1 OBJECT-TYPE
		SYNTAX		INTEGER { disable(0), enable(1) }
		MAX-ACCESS		read-write
		STATUS			current
		DESCRIPTION
				"TYPE: - Checkbox
				 PAGE: - Setup- Logging
					De-embed 1  cmdID= 1120 "
		::= { iqmux10CmdEntry 1120 }


	iqmux10SetupLoggingDeembed2 OBJECT-TYPE
		SYNTAX		INTEGER { disable(0), enable(1) }
		MAX-ACCESS		read-write
		STATUS			current
		DESCRIPTION
				"TYPE: - Checkbox
				 PAGE: - Setup- Logging
					De-embed 2  cmdID= 1121 "
		::= { iqmux10CmdEntry 1121 }


	iqmux10SetupLoggingDeembed3 OBJECT-TYPE
		SYNTAX		INTEGER { disable(0), enable(1) }
		MAX-ACCESS		read-write
		STATUS			current
		DESCRIPTION
				"TYPE: - Checkbox
				 PAGE: - Setup- Logging
					De-embed 3  cmdID= 1122 "
		::= { iqmux10CmdEntry 1122 }


	iqmux10SetupLoggingDeembed4 OBJECT-TYPE
		SYNTAX		INTEGER { disable(0), enable(1) }
		MAX-ACCESS		read-write
		STATUS			current
		DESCRIPTION
				"TYPE: - Checkbox
				 PAGE: - Setup- Logging
					De-embed 4  cmdID= 1123 "
		::= { iqmux10CmdEntry 1123 }


	iqmux10SetupLoggingDeembed5 OBJECT-TYPE
		SYNTAX		INTEGER { disable(0), enable(1) }
		MAX-ACCESS		read-write
		STATUS			current
		DESCRIPTION
				"TYPE: - Checkbox
				 PAGE: - Setup- Logging
					De-embed 5  cmdID= 1124 "
		::= { iqmux10CmdEntry 1124 }


	iqmux10SetupLoggingDeembed6 OBJECT-TYPE
		SYNTAX		INTEGER { disable(0), enable(1) }
		MAX-ACCESS		read-write
		STATUS			current
		DESCRIPTION
				"TYPE: - Checkbox
				 PAGE: - Setup- Logging
					De-embed 6  cmdID= 1125 "
		::= { iqmux10CmdEntry 1125 }


	iqmux10SetupLoggingDeembed7 OBJECT-TYPE
		SYNTAX		INTEGER { disable(0), enable(1) }
		MAX-ACCESS		read-write
		STATUS			current
		DESCRIPTION
				"TYPE: - Checkbox
				 PAGE: - Setup- Logging
					De-embed 7  cmdID= 1126 "
		::= { iqmux10CmdEntry 1126 }


	iqmux10SetupLoggingDeembed8 OBJECT-TYPE
		SYNTAX		INTEGER { disable(0), enable(1) }
		MAX-ACCESS		read-write
		STATUS			current
		DESCRIPTION
				"TYPE: - Checkbox
				 PAGE: - Setup- Logging
					De-embed 8  cmdID= 1127 "
		::= { iqmux10CmdEntry 1127 }


	iqmux10SetupLoggingnPCM1 OBJECT-TYPE
		SYNTAX		INTEGER { disable(0), enable(1) }
		MAX-ACCESS		read-write
		STATUS			current
		DESCRIPTION
				"TYPE: - Checkbox
				 PAGE: - Setup- Logging
					nPCM 1  cmdID= 1128 "
		::= { iqmux10CmdEntry 1128 }


	iqmux10SetupLoggingnPCM2 OBJECT-TYPE
		SYNTAX		INTEGER { disable(0), enable(1) }
		MAX-ACCESS		read-write
		STATUS			current
		DESCRIPTION
				"TYPE: - Checkbox
				 PAGE: - Setup- Logging
					nPCM 2  cmdID= 1129 "
		::= { iqmux10CmdEntry 1129 }


	iqmux10SetupLoggingnPCM3 OBJECT-TYPE
		SYNTAX		INTEGER { disable(0), enable(1) }
		MAX-ACCESS		read-write
		STATUS			current
		DESCRIPTION
				"TYPE: - Checkbox
				 PAGE: - Setup- Logging
					nPCM 3  cmdID= 1130 "
		::= { iqmux10CmdEntry 1130 }


	iqmux10SetupLoggingnPCM4 OBJECT-TYPE
		SYNTAX		INTEGER { disable(0), enable(1) }
		MAX-ACCESS		read-write
		STATUS			current
		DESCRIPTION
				"TYPE: - Checkbox
				 PAGE: - Setup- Logging
					nPCM 4  cmdID= 1131 "
		::= { iqmux10CmdEntry 1131 }


	iqmux10SetupLoggingnPCM5 OBJECT-TYPE
		SYNTAX		INTEGER { disable(0), enable(1) }
		MAX-ACCESS		read-write
		STATUS			current
		DESCRIPTION
				"TYPE: - Checkbox
				 PAGE: - Setup- Logging
					nPCM 5  cmdID= 1132 "
		::= { iqmux10CmdEntry 1132 }


	iqmux10SetupLoggingnPCM6 OBJECT-TYPE
		SYNTAX		INTEGER { disable(0), enable(1) }
		MAX-ACCESS		read-write
		STATUS			current
		DESCRIPTION
				"TYPE: - Checkbox
				 PAGE: - Setup- Logging
					nPCM 6  cmdID= 1133 "
		::= { iqmux10CmdEntry 1133 }


	iqmux10SetupLoggingnPCM7 OBJECT-TYPE
		SYNTAX		INTEGER { disable(0), enable(1) }
		MAX-ACCESS		read-write
		STATUS			current
		DESCRIPTION
				"TYPE: - Checkbox
				 PAGE: - Setup- Logging
					nPCM 7  cmdID= 1134 "
		::= { iqmux10CmdEntry 1134 }


	iqmux10SetupLoggingnPCM8 OBJECT-TYPE
		SYNTAX		INTEGER { disable(0), enable(1) }
		MAX-ACCESS		read-write
		STATUS			current
		DESCRIPTION
				"TYPE: - Checkbox
				 PAGE: - Setup- Logging
					nPCM 8  cmdID= 1135 "
		::= { iqmux10CmdEntry 1135 }


	iqmux10SetupLoggingAES1 OBJECT-TYPE
		SYNTAX		INTEGER { disable(0), enable(1) }
		MAX-ACCESS		read-write
		STATUS			current
		DESCRIPTION
				"TYPE: - Checkbox
				 PAGE: - Setup- Logging
					AES 1  cmdID= 1108 "
		::= { iqmux10CmdEntry 1108 }


	iqmux10SetupLoggingAES2 OBJECT-TYPE
		SYNTAX		INTEGER { disable(0), enable(1) }
		MAX-ACCESS		read-write
		STATUS			current
		DESCRIPTION
				"TYPE: - Checkbox
				 PAGE: - Setup- Logging
					AES 2  cmdID= 1109 "
		::= { iqmux10CmdEntry 1109 }


	iqmux10SetupLoggingAES3 OBJECT-TYPE
		SYNTAX		INTEGER { disable(0), enable(1) }
		MAX-ACCESS		read-write
		STATUS			current
		DESCRIPTION
				"TYPE: - Checkbox
				 PAGE: - Setup- Logging
					AES 3  cmdID= 1110 "
		::= { iqmux10CmdEntry 1110 }


	iqmux10SetupLoggingAES4 OBJECT-TYPE
		SYNTAX		INTEGER { disable(0), enable(1) }
		MAX-ACCESS		read-write
		STATUS			current
		DESCRIPTION
				"TYPE: - Checkbox
				 PAGE: - Setup- Logging
					AES 4  cmdID= 1111 "
		::= { iqmux10CmdEntry 1111 }


	iqmux10SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqmux10CmdEntry 1112 }


	iqmux10SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqmux10CmdEntry 1113 }


	iqmux10SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqmux10CmdEntry 1114 }


	iqmux10SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqmux10CmdEntry 1115 }


	iqmux10SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqmux10CmdEntry 1116 }


	iqmux10SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqmux10CmdEntry 1117 }


	iqmux10SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqmux10CmdEntry 1118 }


	iqmux10SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqmux10CmdEntry 1119 }


	iqmux10SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqmux10CmdEntry 1069 }


	iqmux10SetupLoggingStatusINPUT OBJECT-TYPE
		SYNTAX		RollCallString
		MAX-ACCESS		read-only
		STATUS			current
		DESCRIPTION
				"TYPE: - Display
				 PAGE: - Setup- Logging Status
					INPUT=  cmdID= 2980  format=   "
		::= { iqmux10CmdEntry 2980 }


	iqmux10SetupLoggingStatusSTD OBJECT-TYPE
		SYNTAX		RollCallString
		MAX-ACCESS		read-only
		STATUS			current
		DESCRIPTION
				"TYPE: - Display
				 PAGE: - Setup- Logging Status
					STD=  cmdID= 2981  format=   "
		::= { iqmux10CmdEntry 2981 }


	iqmux10SetupLoggingStatusINPUT1 OBJECT-TYPE
		SYNTAX		RollCallString
		MAX-ACCESS		read-only
		STATUS			current
		DESCRIPTION
				"TYPE: - Display
				 PAGE: - Setup- Logging Status
					INPUT1=  cmdID= 2982  format=   "
		::= { iqmux10CmdEntry 2982 }


	iqmux10SetupLoggingStatusSTD1 OBJECT-TYPE
		SYNTAX		RollCallString
		MAX-ACCESS		read-only
		STATUS			current
		DESCRIPTION
				"TYPE: - Display
				 PAGE: - Setup- Logging Status
					STD1=  cmdID= 2983  format=   "
		::= { iqmux10CmdEntry 2983 }


	iqmux10SetupLoggingStatusINPUT2 OBJECT-TYPE
		SYNTAX		RollCallString
		MAX-ACCESS		read-only
		STATUS			current
		DESCRIPTION
				"TYPE: - Display
				 PAGE: - Setup- Logging Status
					INPUT2=  cmdID= 2984  format=   "
		::= { iqmux10CmdEntry 2984 }


	iqmux10SetupLoggingStatusSTD2 OBJECT-TYPE
		SYNTAX		RollCallString
		MAX-ACCESS		read-only
		STATUS			current
		DESCRIPTION
				"TYPE: - Display
				 PAGE: - Setup- Logging Status
					STD2=  cmdID= 2985  format=   "
		::= { iqmux10CmdEntry 2985 }


	iqmux10SetupLoggingStatusEXTREF OBJECT-TYPE
		SYNTAX		RollCallString
		MAX-ACCESS		read-only
		STATUS			current
		DESCRIPTION
				"TYPE: - Display
				 PAGE: - Setup- Logging Status
					EXTREF=  cmdID= 2986  format=   "
		::= { iqmux10CmdEntry 2986 }


	iqmux10SetupLoggingStatusEDH OBJECT-TYPE
		SYNTAX		RollCallString
		MAX-ACCESS		read-only
		STATUS			current
		DESCRIPTION
				"TYPE: - Display
				 PAGE: - Setup- Logging Status
					EDH=  cmdID= 2987  format=   "
		::= { iqmux10CmdEntry 2987 }


	iqmux10SetupLoggingStatusERRSEC OBJECT-TYPE
		SYNTAX		RollCallString
		MAX-ACCESS		read-only
		STATUS			current
		DESCRIPTION
				"TYPE: - Display
				 PAGE: - Setup- Logging Status
					ERRSEC=  cmdID= 2988  format=   "
		::= { iqmux10CmdEntry 2988 }


	iqmux10SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqmux10CmdEntry 2989 }


	iqmux10SetupLoggingStatusDEEMBED1 OBJECT-TYPE
		SYNTAX		RollCallString
		MAX-ACCESS		read-only
		STATUS			current
		DESCRIPTION
				"TYPE: - Display
				 PAGE: - Setup- Logging Status
					DEEMBED1=  cmdID= 3014  format=   "
		::= { iqmux10CmdEntry 3014 }


	iqmux10SetupLoggingStatusDEEMBED2 OBJECT-TYPE
		SYNTAX		RollCallString
		MAX-ACCESS		read-only
		STATUS			current
		DESCRIPTION
				"TYPE: - Display
				 PAGE: - Setup- Logging Status
					DEEMBED2=  cmdID= 3015  format=   "
		::= { iqmux10CmdEntry 3015 }


	iqmux10SetupLoggingStatusDEEMBED3 OBJECT-TYPE
		SYNTAX		RollCallString
		MAX-ACCESS		read-only
		STATUS			current
		DESCRIPTION
				"TYPE: - Display
				 PAGE: - Setup- Logging Status
					DEEMBED3=  cmdID= 3016  format=   "
		::= { iqmux10CmdEntry 3016 }


	iqmux10SetupLoggingStatusDEEMBED4 OBJECT-TYPE
		SYNTAX		RollCallString
		MAX-ACCESS		read-only
		STATUS			current
		DESCRIPTION
				"TYPE: - Display
				 PAGE: - Setup- Logging Status
					DEEMBED4=  cmdID= 3017  format=   "
		::= { iqmux10CmdEntry 3017 }


	iqmux10SetupLoggingStatusDEEMBED5 OBJECT-TYPE
		SYNTAX		RollCallString
		MAX-ACCESS		read-only
		STATUS			current
		DESCRIPTION
				"TYPE: - Display
				 PAGE: - Setup- Logging Status
					DEEMBED5=  cmdID= 3018  format=   "
		::= { iqmux10CmdEntry 3018 }


	iqmux10SetupLoggingStatusDEEMBED6 OBJECT-TYPE
		SYNTAX		RollCallString
		MAX-ACCESS		read-only
		STATUS			current
		DESCRIPTION
				"TYPE: - Display
				 PAGE: - Setup- Logging Status
					DEEMBED6=  cmdID= 3019  format=   "
		::= { iqmux10CmdEntry 3019 }


	iqmux10SetupLoggingStatusDEEMBED7 OBJECT-TYPE
		SYNTAX		RollCallString
		MAX-ACCESS		read-only
		STATUS			current
		DESCRIPTION
				"TYPE: - Display
				 PAGE: - Setup- Logging Status
					DEEMBED7=  cmdID= 3020  format=   "
		::= { iqmux10CmdEntry 3020 }


	iqmux10SetupLoggingStatusDEEMBED8 OBJECT-TYPE
		SYNTAX		RollCallString
		MAX-ACCESS		read-only
		STATUS			current
		DESCRIPTION
				"TYPE: - Display
				 PAGE: - Setup- Logging Status
					DEEMBED8=  cmdID= 3021  format=   "
		::= { iqmux10CmdEntry 3021 }


	iqmux10SetupLoggingStatusNPCM1 OBJECT-TYPE
		SYNTAX		RollCallString
		MAX-ACCESS		read-only
		STATUS			current
		DESCRIPTION
				"TYPE: - Display
				 PAGE: - Setup- Logging Status
					NPCM1=  cmdID= 3022  format=   "
		::= { iqmux10CmdEntry 3022 }


	iqmux10SetupLoggingStatusNPCM2 OBJECT-TYPE
		SYNTAX		RollCallString
		MAX-ACCESS		read-only
		STATUS			current
		DESCRIPTION
				"TYPE: - Display
				 PAGE: - Setup- Logging Status
					NPCM2=  cmdID= 3023  format=   "
		::= { iqmux10CmdEntry 3023 }


	iqmux10SetupLoggingStatusNPCM3 OBJECT-TYPE
		SYNTAX		RollCallString
		MAX-ACCESS		read-only
		STATUS			current
		DESCRIPTION
				"TYPE: - Display
				 PAGE: - Setup- Logging Status
					NPCM3=  cmdID= 3024  format=   "
		::= { iqmux10CmdEntry 3024 }


	iqmux10SetupLoggingStatusNPCM4 OBJECT-TYPE
		SYNTAX		RollCallString
		MAX-ACCESS		read-only
		STATUS			current
		DESCRIPTION
				"TYPE: - Display
				 PAGE: - Setup- Logging Status
					NPCM4=  cmdID= 3025  format=   "
		::= { iqmux10CmdEntry 3025 }


	iqmux10SetupLoggingStatusNPCM5 OBJECT-TYPE
		SYNTAX		RollCallString
		MAX-ACCESS		read-only
		STATUS			current
		DESCRIPTION
				"TYPE: - Display
				 PAGE: - Setup- Logging Status
					NPCM5=  cmdID= 3026  format=   "
		::= { iqmux10CmdEntry 3026 }


	iqmux10SetupLoggingStatusNPCM6 OBJECT-TYPE
		SYNTAX		RollCallString
		MAX-ACCESS		read-only
		STATUS			current
		DESCRIPTION
				"TYPE: - Display
				 PAGE: - Setup- Logging Status
					NPCM6=  cmdID= 3027  format=   "
		::= { iqmux10CmdEntry 3027 }


	iqmux10SetupLoggingStatusNPCM7 OBJECT-TYPE
		SYNTAX		RollCallString
		MAX-ACCESS		read-only
		STATUS			current
		DESCRIPTION
				"TYPE: - Display
				 PAGE: - Setup- Logging Status
					NPCM7=  cmdID= 3028  format=   "
		::= { iqmux10CmdEntry 3028 }


	iqmux10SetupLoggingStatusNPCM8 OBJECT-TYPE
		SYNTAX		RollCallString
		MAX-ACCESS		read-only
		STATUS			current
		DESCRIPTION
				"TYPE: - Display
				 PAGE: - Setup- Logging Status
					NPCM8=  cmdID= 3029  format=   "
		::= { iqmux10CmdEntry 3029 }


	iqmux10SetupLoggingStatusAES1 OBJECT-TYPE
		SYNTAX		RollCallString
		MAX-ACCESS		read-only
		STATUS			current
		DESCRIPTION
				"TYPE: - Display
				 PAGE: - Setup- Logging Status
					AES1=  cmdID= 2994  format=   "
		::= { iqmux10CmdEntry 2994 }


	iqmux10SetupLoggingStatusAES2 OBJECT-TYPE
		SYNTAX		RollCallString
		MAX-ACCESS		read-only
		STATUS			current
		DESCRIPTION
				"TYPE: - Display
				 PAGE: - Setup- Logging Status
					AES2=  cmdID= 2995  format=   "
		::= { iqmux10CmdEntry 2995 }


	iqmux10SetupLoggingStatusAES3 OBJECT-TYPE
		SYNTAX		RollCallString
		MAX-ACCESS		read-only
		STATUS			current
		DESCRIPTION
				"TYPE: - Display
				 PAGE: - Setup- Logging Status
					AES3=  cmdID= 2996  format=   "
		::= { iqmux10CmdEntry 2996 }


	iqmux10SetupLoggingStatusAES4 OBJECT-TYPE
		SYNTAX		RollCallString
		MAX-ACCESS		read-only
		STATUS			current
		DESCRIPTION
				"TYPE: - Display
				 PAGE: - Setup- Logging Status
					AES4=  cmdID= 2997  format=   "
		::= { iqmux10CmdEntry 2997 }


	iqmux10SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqmux10CmdEntry 2998 }


	iqmux10SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqmux10CmdEntry 2999 }


	iqmux10SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqmux10CmdEntry 3000 }


	iqmux10SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqmux10CmdEntry 3001 }


	iqmux10SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqmux10CmdEntry 3002 }


	iqmux10SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqmux10CmdEntry 3003 }


	iqmux10SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqmux10CmdEntry 3004 }


	iqmux10SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqmux10CmdEntry 3005 }


	iqmux10SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqmux10CmdEntry 2990 }


	iqmux10SetupInformationWindow OBJECT-TYPE
		SYNTAX		INTEGER {
							val_Input_Status(0),
							val_EDH_ANC_Status(1),
							val_Audio_Input_Status(2)
							}
		MAX-ACCESS		read-write
		STATUS			current
		DESCRIPTION
				"TYPE: - Button
				 PAGE: - Setup- Information Window
					Input Status  cmdID= 1915  value= 0  
					EDH & ANC Status  cmdID= 1915  value= 1  
					Audio Input Status  cmdID= 1915  value= 2  "
		::= { iqmux10CmdEntry 1915 }


	iqmux10SetupInformationWindowResetErrors OBJECT-TYPE
		SYNTAX		INTEGER { noAction(0),val_Reset_Errors(1) }
		MAX-ACCESS		read-write
		STATUS			current
		DESCRIPTION
				"TYPE: - Button
				 PAGE: - Setup- Information Window
					Reset Errors  cmdID= 2978  value= 1  "
		::= { iqmux10CmdEntry 2978 }


	iqmux10SetupDefaultOutput OBJECT-TYPE
		SYNTAX		INTEGER {
							val_Video(1),
							val_Freeze(2),
							val_Pattern(3)
							}
		MAX-ACCESS		read-write
		STATUS			current
		DESCRIPTION
				"TYPE: - Button
				 PAGE: - Setup- Default Output
					Video  cmdID= 1202  value= 1  
					Freeze  cmdID= 1202  value= 2  
					Pattern  cmdID= 1202  value= 3  "
		::= { iqmux10CmdEntry 1202 }


	iqmux10SetupDefaultOutputPattern OBJECT-TYPE
		SYNTAX		INTEGER {
							val_Black(0),
							val_EBU_Colour_Bars(1),
							val_100_Colour_Bars(2),
							val_Ramp(3),
							val_Multiburst(4),
							val_Pulse_Bar(5)
							}
		MAX-ACCESS		read-write
		STATUS			current
		DESCRIPTION
				"TYPE: - Button
				 PAGE: - Setup- Default Output
					Black  cmdID= 1038  value= 0  
					EBU Colour Bars  cmdID= 1038  value= 1  
					100% Colour Bars  cmdID= 1038  value= 2  
					Ramp  cmdID= 1038  value= 3  
					Multiburst  cmdID= 1038  value= 4  
					Pulse & Bar  cmdID= 1038  value= 5  "
		::= { iqmux10CmdEntry 1038 }


	iqmux10SetupUnitSoftwareVersion OBJECT-TYPE
		SYNTAX		RollCallString
		MAX-ACCESS		read-only
		STATUS			current
		DESCRIPTION
				"TYPE: - Display
				 PAGE: - Setup- Unit
					Software Version  cmdID= 2  format=   "
		::= { iqmux10CmdEntry 2 }


	iqmux10SetupUnitSerialNo OBJECT-TYPE
		SYNTAX		RollCallString
		MAX-ACCESS		read-only
		STATUS			current
		DESCRIPTION
				"TYPE: - Display
				 PAGE: - Setup- Unit
					Serial No  cmdID= 1  format=   "
		::= { iqmux10CmdEntry 1 }


	iqmux10SetupUnitPresetUnit OBJECT-TYPE
		SYNTAX		INTEGER { noAction(0),val_Preset_Unit(1) }
		MAX-ACCESS		read-write
		STATUS			current
		DESCRIPTION
				"TYPE: - Button
				 PAGE: - Setup- Unit
					Preset Unit  cmdID= 3  value= 1  "
		::= { iqmux10CmdEntry 3 }


	iqmux10SetupUnitRestart OBJECT-TYPE
		SYNTAX		INTEGER { noAction(0),val_Restart(1) }
		MAX-ACCESS		read-write
		STATUS			current
		DESCRIPTION
				"TYPE: - Button
				 PAGE: - Setup- Unit
					Restart  cmdID= 4  value= 1  "
		::= { iqmux10CmdEntry 4 }


	iqmux10SetupUnitBuildNo OBJECT-TYPE
		SYNTAX		RollCallString
		MAX-ACCESS		read-only
		STATUS			current
		DESCRIPTION
				"TYPE: - Display
				 PAGE: - Setup- Unit
					Build No  cmdID= 5  format=   "
		::= { iqmux10CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: xxxxxxxxxxxxxxxxxxx
--				: 
-- Comments		: Serial Number   Runtime string  
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE              The unit is not locked to the input signal
--				: FAIL              EDH errors have been found on the input signal
--              : OK                No EDH errors found on the input signal
--              : RESET             EDH statistics have been reset
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: STDERR            Input signal standard not recognized or no signal
--				: UNKNOWN           Not a selected input standard
--              : 525               Input standard 525
--              : 625               Input standard 625
-- Comments		: 
--
---------------------------------------------------------------------------------------------------
-- Header		: STD1
--
-- MIB ref		: swCardEventLogSlotXX       .4.83.84.68.49
-- absolute OID	: 1.3.6.1.4.1.7995.2.6.1.1.XX.4.83.84.68.49
-- Vary			: YES
--
-- Value(s)		: ERR               Not a selected input standard Input 1
--				: 525               Input 1 standard 525
--              : 625               Input 1 standard 625
-- Comments		: 
--
---------------------------------------------------------------------------------------------------
-- Header		: STD2
--
-- MIB ref		: swCardEventLogSlotXX       .4.83.84.68.50
-- absolute OID	: 1.3.6.1.4.1.7995.2.6.1.1.XX.4.83.84.68.50
-- Vary			: YES
--
-- Value(s)		: ERR               Not a selected input standard Input 2
--				: 525               Input 2 standard 525
--              : 625               Input 2 standard 625
-- Comments		: 
--
---------------------------------------------------------------------------------------------------
-- Header		: AES_1
--
-- MIB ref		: swCardEventLogSlotXX       .5.65.69.83.95.49
-- absolute OID	: 1.3.6.1.4.1.7995.2.6.1.1.XX.5.65.69.83.95.49
-- Vary			: YES
--
-- Value(s)		: NONPCM            Non-PCM signal present on AES input 1
--				: OK                Valid signal present on AES input 1
--              : LOST              Signal not present at AES input 1
-- Comments		: 
--
---------------------------------------------------------------------------------------------------
-- Header		: AES_2
--
-- MIB ref		: swCardEventLogSlotXX       .5.65.69.83.95.50
-- absolute OID	: 1.3.6.1.4.1.7995.2.6.1.1.XX.5.65.69.83.95.50
-- Vary			: YES
--
-- Value(s)		: NONPCM            Non-PCM signal present on AES input 2
--				: OK                Valid signal present on AES input 2
--              : LOST              Signal not present at AES input 2
-- Comments		: 
--
---------------------------------------------------------------------------------------------------
-- Header		: AES_3
--
-- MIB ref		: swCardEventLogSlotXX       .5.65.69.83.95.51
-- absolute OID	: 1.3.6.1.4.1.7995.2.6.1.1.XX.5.65.69.83.95.51
-- Vary			: YES
--
-- Value(s)		: NONPCM            Non-PCM signal present on AES input 3
--				: OK                Valid signal present on AES input 3
--              : LOST              Signal not present at AES input 3
-- Comments		: 
--
---------------------------------------------------------------------------------------------------
-- Header		: AES_4
--
-- MIB ref		: swCardEventLogSlotXX       .5.65.69.83.95.52
-- absolute OID	: 1.3.6.1.4.1.7995.2.6.1.1.XX.5.65.69.83.95.52
-- Vary			: YES
--
-- Value(s)		: NONPCM            Non-PCM signal present on AES input 4
--				: OK                Valid signal present on AES input 4
--              : LOST              Signal not present at AES input 4
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE              No Internal errors detected
--				: FAIL              Internal error detected
--              : FAIL.FPGA_LOAD    Fpga load failure detected
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: OK                Valid input signal
--				: ERR               Invalid input signal
--              : LOST              Input signal lost
-- Comments		: 
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: OK                Router BUS A Left channel has valid signal selected            
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: OK                Router BUS A Right channel has valid signal selected
--              : WARNING           Router BUS A Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: OK                Router BUS B Left channel has valid signal selected            
--              : WARNING           Router BUS B Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: OK                Router BUS B Right channel has valid signal selected
--              : WARNING           Router BUS B Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: OK                Router BUS C Left channel has valid signal selected            
--              : WARNING           Router BUS C Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: OK                Router BUS C Right channel has valid signal selected
--              : WARNING           Router BUS C Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: OK                Router BUS D Left channel has valid signal selected            
--              : WARNING           Router BUS D Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: OK                Router BUS D Right channel has valid signal selected
--              : WARNING           Router BUS D Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
--
-- Value(s)		: 0s                Number or Errored Seconds
--				: 
-- Comments		: Runtime string
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: NONE              No reference signal present                
--				: 525               Valid 525 reference signal                 
--              : ERROR             Reference/Output standard mismatch         
--              : WARNING           Reference signal available but not selected
--              : 625               Valid 625 reference signal                 
-- Comments		: 
--
---------------------------------------------------------------------------------------------------
-- Header		: INPUT1
--
-- MIB ref		: swCardEventLogSlotXX       .6.73.78.80.85.84.49
-- absolute OID	: 1.3.6.1.4.1.7995.2.6.1.1.XX.6.73.78.80.85.84.49
-- Vary			: YES
--
-- Value(s)		: OK                Valid input 1 signal  
--				: ERR               Invalid input 1 signal
--              : LOST              Input 1 signal lost   
-- Comments		: 
--
---------------------------------------------------------------------------------------------------
-- Header		: INPUT2
--
-- MIB ref		: swCardEventLogSlotXX       .6.73.78.80.85.84.50
-- absolute OID	: 1.3.6.1.4.1.7995.2.6.1.1.XX.6.73.78.80.85.84.50
-- Vary			: YES
--
-- Value(s)		: OK                Valid input 2 signal  
--				: ERR               Invalid input 2 signal
--              : LOST              Input 2 signal lost   
-- Comments		: 
--
---------------------------------------------------------------------------------------------------
-- Header		: NPCM_1
--
-- MIB ref		: swCardEventLogSlotXX       .6.78.80.67.77.95.49
-- absolute OID	: 1.3.6.1.4.1.7995.2.6.1.1.XX.6.78.80.67.77.95.49
-- Vary			: YES
--
-- Value(s)		: NONE              Non-PCM not present on pair 1 of selected SDI input
--				: OK                Non-PCM present on pair 1 of selected SDI input
-- Comments		: 
--
---------------------------------------------------------------------------------------------------
-- Header		: NPCM_2
--
-- MIB ref		: swCardEventLogSlotXX       .6.78.80.67.77.95.50
-- absolute OID	: 1.3.6.1.4.1.7995.2.6.1.1.XX.6.78.80.67.77.95.50
-- Vary			: YES
--
-- Value(s)		: NONE              Non-PCM not present on pair 2 of selected SDI input
--				: OK                Non-PCM present on pair 2 of selected SDI input
-- Comments		: 
--
---------------------------------------------------------------------------------------------------
-- Header		: NPCM_3
--
-- MIB ref		: swCardEventLogSlotXX       .6.78.80.67.77.95.51
-- absolute OID	: 1.3.6.1.4.1.7995.2.6.1.1.XX.6.78.80.67.77.95.51
-- Vary			: YES
--
-- Value(s)		: NONE              Non-PCM not present on pair 3 of selected SDI input
--				: OK                Non-PCM present on pair 3 of selected SDI input
-- Comments		: 
--
---------------------------------------------------------------------------------------------------
-- Header		: NPCM_4
--
-- MIB ref		: swCardEventLogSlotXX       .6.78.80.67.77.95.52
-- absolute OID	: 1.3.6.1.4.1.7995.2.6.1.1.XX.6.78.80.67.77.95.52
-- Vary			: YES
--
-- Value(s)		: NONE              Non-PCM not present on pair 4 of selected SDI input
--				: OK                Non-PCM present on pair 4 of selected SDI input
-- Comments		: 
--
---------------------------------------------------------------------------------------------------
-- Header		: NPCM_5
--
-- MIB ref		: swCardEventLogSlotXX       .6.78.80.67.77.95.53
-- absolute OID	: 1.3.6.1.4.1.7995.2.6.1.1.XX.6.78.80.67.77.95.53
-- Vary			: YES
--
-- Value(s)		: NONE              Non-PCM not present on pair 5 of selected SDI input
--				: OK                Non-PCM present on pair 5 of selected SDI input
-- Comments		: 
--
---------------------------------------------------------------------------------------------------
-- Header		: NPCM_6
--
-- MIB ref		: swCardEventLogSlotXX       .6.78.80.67.77.95.54
-- absolute OID	: 1.3.6.1.4.1.7995.2.6.1.1.XX.6.78.80.67.77.95.54
-- Vary			: YES
--
-- Value(s)		: NONE              Non-PCM not present on pair 6 of selected SDI input
--				: OK                Non-PCM present on pair 6 of selected SDI input
-- Comments		: 
--
---------------------------------------------------------------------------------------------------
-- Header		: NPCM_7
--
-- MIB ref		: swCardEventLogSlotXX       .6.78.80.67.77.95.55
-- absolute OID	: 1.3.6.1.4.1.7995.2.6.1.1.XX.6.78.80.67.77.95.55
-- Vary			: YES
--
-- Value(s)		: NONE              Non-PCM not present on pair 7 of selected SDI input
--				: OK                Non-PCM present on pair 7 of selected SDI input
-- Comments		: 
--
---------------------------------------------------------------------------------------------------
-- Header		: NPCM_8
--
-- MIB ref		: swCardEventLogSlotXX       .6.78.80.67.77.95.56
-- absolute OID	: 1.3.6.1.4.1.7995.2.6.1.1.XX.6.78.80.67.77.95.56
-- Vary			: YES
--
-- Value(s)		: NONE              Non-PCM not present on pair 8 of selected SDI input
--				: OK                Non-PCM present on pair 8 of selected SDI input
-- Comments		: 
--
---------------------------------------------------------------------------------------------------
-- Header		: DEEMBED_1
--
-- MIB ref		: swCardEventLogSlotXX       .9.68.69.69.77.66.69.68.95.49
-- absolute OID	: 1.3.6.1.4.1.7995.2.6.1.1.XX.9.68.69.69.77.66.69.68.95.49
-- Vary			: YES
--
-- Value(s)		: NONE              Nothing present on pair 1
--				: OK                Embedded pair 1 present on selected SDI input
-- Comments		: 
--
---------------------------------------------------------------------------------------------------
-- Header		: DEEMBED_2
--
-- MIB ref		: swCardEventLogSlotXX       .9.68.69.69.77.66.69.68.95.50
-- absolute OID	: 1.3.6.1.4.1.7995.2.6.1.1.XX.9.68.69.69.77.66.69.68.95.50
-- Vary			: YES
--
-- Value(s)		: NONE              Nothing present on pair 2
--				: OK                Embedded pair 2 present on selected SDI input
-- Comments		: 
--
---------------------------------------------------------------------------------------------------
-- Header		: DEEMBED_3
--
-- MIB ref		: swCardEventLogSlotXX       .9.68.69.69.77.66.69.68.95.51
-- absolute OID	: 1.3.6.1.4.1.7995.2.6.1.1.XX.9.68.69.69.77.66.69.68.95.51
-- Vary			: YES
--
-- Value(s)		: NONE              Nothing present on pair 3
--				: OK                Embedded pair 3 present on selected SDI input
-- Comments		: 
--
---------------------------------------------------------------------------------------------------
-- Header		: DEEMBED_4
--
-- MIB ref		: swCardEventLogSlotXX       .9.68.69.69.77.66.69.68.95.52
-- absolute OID	: 1.3.6.1.4.1.7995.2.6.1.1.XX.9.68.69.69.77.66.69.68.95.52
-- Vary			: YES
--
-- Value(s)		: NONE              Nothing present on pair 4
--				: OK                Embedded pair 4 present on selected SDI input
-- Comments		: 
--
---------------------------------------------------------------------------------------------------
-- Header		: DEEMBED_5
--
-- MIB ref		: swCardEventLogSlotXX       .9.68.69.69.77.66.69.68.95.53
-- absolute OID	: 1.3.6.1.4.1.7995.2.6.1.1.XX.9.68.69.69.77.66.69.68.95.53
-- Vary			: YES
--
-- Value(s)		: NONE              Nothing present on pair 5
--				: OK                Embedded pair 5 present on selected SDI input
-- Comments		: 
--
---------------------------------------------------------------------------------------------------
-- Header		: DEEMBED_6
--
-- MIB ref		: swCardEventLogSlotXX       .9.68.69.69.77.66.69.68.95.54
-- absolute OID	: 1.3.6.1.4.1.7995.2.6.1.1.XX.9.68.69.69.77.66.69.68.95.54
-- Vary			: YES
--
-- Value(s)		: NONE              Nothing present on pair 6
--				: OK                Embedded pair 6 present on selected SDI input
-- Comments		: 
--
---------------------------------------------------------------------------------------------------
-- Header		: DEEMBED_7
--
-- MIB ref		: swCardEventLogSlotXX       .9.68.69.69.77.66.69.68.95.55
-- absolute OID	: 1.3.6.1.4.1.7995.2.6.1.1.XX.9.68.69.69.77.66.69.68.95.55
-- Vary			: YES
--
-- Value(s)		: NONE              Nothing present on pair 7
--				: OK                Embedded pair 7 present on selected SDI input
-- Comments		: 
--
---------------------------------------------------------------------------------------------------
-- Header		: DEEMBED_8
--
-- MIB ref		: swCardEventLogSlotXX       .9.68.69.69.77.66.69.68.95.56
-- absolute OID	: 1.3.6.1.4.1.7995.2.6.1.1.XX.9.68.69.69.77.66.69.68.95.56
-- Vary			: YES
--
-- Value(s)		: NONE              Nothing present on pair 8
--				: OK                Embedded pair 8 present on selected SDI input
-- Comments		: 
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK                RollTrack message sent and received OK
--				: FAIL              RollTrack message not acknowledged    
-- Comments		: 
--
---------------------------------------------------------------------------------------------------
