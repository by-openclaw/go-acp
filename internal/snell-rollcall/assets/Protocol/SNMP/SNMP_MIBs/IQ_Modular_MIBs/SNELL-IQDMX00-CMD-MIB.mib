-- ************************************************************************************
-- Snell&Wilcox Card:IQDMX00
--        Module Id#:362
--       Command Set:5
--          Filename:SNELL-IQDMX00-CMD-MIB.mib
--            Author:Jonathan Riches
--              Date:08/06/2005
--              Time:10:45
--
-- Copyright (c) 2005 Snell & Wilcox Ltd
-- All rights reserved.
--
-- ************************************************************************************

SNELL-IQDMX00-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMX00,
    moduleIQDMX00MIB
        FROM SNELL-WILCOX-PRODUCT-REG;

 moduleIQDMX00CmdMi MODULE-IDENTITY
    LAST-UPDATED "0506081045Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMX00MIB 1 }




--********************************************************************************
--*
--*  Snell Wilcox Card:
--*  command set:
--*  list commands/menus:
--*
--******************************************************************************
	iqdmx00CmdTable OBJECT-TYPE
		SYNTAX			SEQUENCE OF Iqdmx00CmdEntry
		MAX-ACCESS		not-accessible
		STATUS			current
		DESCRIPTION
				"Note the instance of this table is relected in the command set Version"
		::= { moduleIQDMX00 1 }

	iqdmx00CmdEntry OBJECT-TYPE
		SYNTAX		Iqdmx00CmdEntry
		MAX-ACCESS		not-accessible
		STATUS			current
		DESCRIPTION
				"Entry in command table."
		INDEX	{ iqdmx00SlotIndex }
		::= { iqdmx00CmdTable 1 }

	Iqdmx00CmdEntry ::=
		SEQUENCE {
			iqdmx00SlotIndex
				Unsigned32,
			iqdmx00VideoInput
				INTEGER,
			iqdmx00VideoInput525
				INTEGER,
			iqdmx00VideoInput625
				INTEGER,
			iqdmx00VideoProcAmp1In1ProcAmpEnable
				INTEGER,
			iqdmx00VideoProcAmp1LumaGain
				INTEGER,
			iqdmx00VideoProcAmp1ChromaGain
				INTEGER,
			iqdmx00VideoProcAmp1BlackLevel
				INTEGER,
			iqdmx00VideoProcAmp1PicturePosition
				INTEGER,
			iqdmx00VideoProcAmp1YCTiming
				INTEGER,
			iqdmx00VideoProcAmp2In2ProcAmpEnable
				INTEGER,
			iqdmx00VideoProcAmp2LumaGain
				INTEGER,
			iqdmx00VideoProcAmp2ChromaGain
				INTEGER,
			iqdmx00VideoProcAmp2BlackLevel
				INTEGER,
			iqdmx00VideoProcAmp2PicturePosition
				INTEGER,
			iqdmx00VideoProcAmp2YCTiming
				INTEGER,
			iqdmx00AudioDeembed
				INTEGER,
			iqdmx00AudioAESOutputAES1Source
				INTEGER,
			iqdmx00AudioAESOutputAES2Source
				INTEGER,
			iqdmx00AudioProcAmpStereo1
				INTEGER,
			iqdmx00ProcAmpDeembed1LGainDeembed1L
				INTEGER,
			iqdmx00ProcAmpDeembed1LInvert
				INTEGER,
			iqdmx00ProcAmpDeembed1LMute
				INTEGER,
			iqdmx00ProcAmpDeembed1RGainDeembed1R
				INTEGER,
			iqdmx00ProcAmpDeembed1RInvert
				INTEGER,
			iqdmx00ProcAmpDeembed1RMute
				INTEGER,
			iqdmx00AudioProcAmpStereo2
				INTEGER,
			iqdmx00ProcAmpDeembed2LGainDeembed2L
				INTEGER,
			iqdmx00ProcAmpDeembed2LInvert
				INTEGER,
			iqdmx00ProcAmpDeembed2LMute
				INTEGER,
			iqdmx00ProcAmpDeembed2RGainDeembed2R
				INTEGER,
			iqdmx00ProcAmpDeembed2RInvert
				INTEGER,
			iqdmx00ProcAmpDeembed2RMute
				INTEGER,
			iqdmx00AudioProcAmpStereo3
				INTEGER,
			iqdmx00ProcAmpDeembed3LGainDeembed3L
				INTEGER,
			iqdmx00ProcAmpDeembed3LInvert
				INTEGER,
			iqdmx00ProcAmpDeembed3LMute
				INTEGER,
			iqdmx00ProcAmpDeembed3RGainDeembed3R
				INTEGER,
			iqdmx00ProcAmpDeembed3RInvert
				INTEGER,
			iqdmx00ProcAmpDeembed3RMute
				INTEGER,
			iqdmx00AudioProcAmpStereo4
				INTEGER,
			iqdmx00ProcAmpDeembed4LGainDeembed4L
				INTEGER,
			iqdmx00ProcAmpDeembed4LInvert
				INTEGER,
			iqdmx00ProcAmpDeembed4LMute
				INTEGER,
			iqdmx00ProcAmpDeembed4RGainDeembed4R
				INTEGER,
			iqdmx00ProcAmpDeembed4RInvert
				INTEGER,
			iqdmx00ProcAmpDeembed4RMute
				INTEGER,
			iqdmx00AudioProcAmpStereo5
				INTEGER,
			iqdmx00ProcAmpDeembed5LGainDeembed5L
				INTEGER,
			iqdmx00ProcAmpDeembed5LInvert
				INTEGER,
			iqdmx00ProcAmpDeembed5LMute
				INTEGER,
			iqdmx00ProcAmpDeembed5RGainDeembed5R
				INTEGER,
			iqdmx00ProcAmpDeembed5RInvert
				INTEGER,
			iqdmx00ProcAmpDeembed5RMute
				INTEGER,
			iqdmx00AudioProcAmpStereo6
				INTEGER,
			iqdmx00ProcAmpDeembed6LGainDeembed6L
				INTEGER,
			iqdmx00ProcAmpDeembed6LInvert
				INTEGER,
			iqdmx00ProcAmpDeembed6LMute
				INTEGER,
			iqdmx00ProcAmpDeembed6RGainDeembed6R
				INTEGER,
			iqdmx00ProcAmpDeembed6RInvert
				INTEGER,
			iqdmx00ProcAmpDeembed6RMute
				INTEGER,
			iqdmx00AudioProcAmpStereo7
				INTEGER,
			iqdmx00ProcAmpDeembed7LGainDeembed7L
				INTEGER,
			iqdmx00ProcAmpDeembed7LInvert
				INTEGER,
			iqdmx00ProcAmpDeembed7LMute
				INTEGER,
			iqdmx00ProcAmpDeembed7RGainDeembed7R
				INTEGER,
			iqdmx00ProcAmpDeembed7RInvert
				INTEGER,
			iqdmx00ProcAmpDeembed7RMute
				INTEGER,
			iqdmx00AudioProcAmpStereo8
				INTEGER,
			iqdmx00ProcAmpDeembed8LGainDeembed8L
				INTEGER,
			iqdmx00ProcAmpDeembed8LInvert
				INTEGER,
			iqdmx00ProcAmpDeembed8LMute
				INTEGER,
			iqdmx00ProcAmpDeembed8RGainDeembed8R
				INTEGER,
			iqdmx00ProcAmpDeembed8RInvert
				INTEGER,
			iqdmx00ProcAmpDeembed8RMute
				INTEGER,
			iqdmx00EmbedEmbedder1Embed1Source
				INTEGER,
			iqdmx00EmbedEmbedder1PairSelection
				INTEGER,
			iqdmx00EmbedEmbedder1Disable
				INTEGER,
			iqdmx00EmbedEmbedder2Embed2Source
				INTEGER,
			iqdmx00EmbedEmbedder2PairSelection
				INTEGER,
			iqdmx00EmbedEmbedder2Disable
				INTEGER,
			iqdmx00EmbedEmbedder3Embed3Source
				INTEGER,
			iqdmx00EmbedEmbedder3PairSelection
				INTEGER,
			iqdmx00EmbedEmbedder3Disable
				INTEGER,
			iqdmx00EmbedEmbedder4Embed4Source
				INTEGER,
			iqdmx00EmbedEmbedder4PairSelection
				INTEGER,
			iqdmx00EmbedEmbedder4Disable
				INTEGER,
			iqdmx00Mixer1Mix1Source1
				INTEGER,
			iqdmx00MixMixer1Gain1
				INTEGER,
			iqdmx00Mixer1Mix1Source2
				INTEGER,
			iqdmx00MixMixer1Gain2
				INTEGER,
			iqdmx00Mixer1Mix1Source3
				INTEGER,
			iqdmx00MixMixer1Gain3
				INTEGER,
			iqdmx00Mixer1Mix1Source4
				INTEGER,
			iqdmx00MixMixer1Gain4
				INTEGER,
			iqdmx00Mixer2Mix2Source1
				INTEGER,
			iqdmx00MixMixer2Gain1
				INTEGER,
			iqdmx00Mixer2Mix2Source2
				INTEGER,
			iqdmx00MixMixer2Gain2
				INTEGER,
			iqdmx00Mixer2Mix2Source3
				INTEGER,
			iqdmx00MixMixer2Gain3
				INTEGER,
			iqdmx00Mixer2Mix2Source4
				INTEGER,
			iqdmx00MixMixer2Gain4
				INTEGER,
			iqdmx00Mixer3Mix3Source1
				INTEGER,
			iqdmx00MixMixer3Gain1
				INTEGER,
			iqdmx00Mixer3Mix3Source2
				INTEGER,
			iqdmx00MixMixer3Gain2
				INTEGER,
			iqdmx00Mixer3Mix3Source3
				INTEGER,
			iqdmx00MixMixer3Gain3
				INTEGER,
			iqdmx00Mixer3Mix3Source4
				INTEGER,
			iqdmx00MixMixer3Gain4
				INTEGER,
			iqdmx00Mixer4Mix4Source1
				INTEGER,
			iqdmx00MixMixer4Gain1
				INTEGER,
			iqdmx00Mixer4Mix4Source2
				INTEGER,
			iqdmx00MixMixer4Gain2
				INTEGER,
			iqdmx00Mixer4Mix4Source3
				INTEGER,
			iqdmx00MixMixer4Gain3
				INTEGER,
			iqdmx00Mixer4Mix4Source4
				INTEGER,
			iqdmx00MixMixer4Gain4
				INTEGER,
			iqdmx00BusSourceBusALSource
				INTEGER,
			iqdmx00BusSourceBusARSource
				INTEGER,
			iqdmx00BusSourceBusBLSource
				INTEGER,
			iqdmx00BusSourceBusBRSource
				INTEGER,
			iqdmx00BusSourceBusCLSource
				INTEGER,
			iqdmx00BusSourceBusCRSource
				INTEGER,
			iqdmx00BusSourceBusDLSource
				INTEGER,
			iqdmx00BusSourceBusDRSource
				INTEGER,
			iqdmx00BusesBusProcAmpStereoA
				INTEGER,
			iqdmx00BusProcAmpBusALGainBusAL
				INTEGER,
			iqdmx00BusProcAmpBusALInvert
				INTEGER,
			iqdmx00BusProcAmpBusALMute
				INTEGER,
			iqdmx00BusProcAmpBusARGainBusAR
				INTEGER,
			iqdmx00BusProcAmpBusARInvert
				INTEGER,
			iqdmx00BusProcAmpBusARMute
				INTEGER,
			iqdmx00BusesBusProcAmpStereoB
				INTEGER,
			iqdmx00BusProcAmpBusBLGainBusBL
				INTEGER,
			iqdmx00BusProcAmpBusBLInvert
				INTEGER,
			iqdmx00BusProcAmpBusBLMute
				INTEGER,
			iqdmx00BusProcAmpBusBRGainBusBR
				INTEGER,
			iqdmx00BusProcAmpBusBRInvert
				INTEGER,
			iqdmx00BusProcAmpBusBRMute
				INTEGER,
			iqdmx00BusesBusProcAmpStereoC
				INTEGER,
			iqdmx00BusProcAmpBusCLGainBusCL
				INTEGER,
			iqdmx00BusProcAmpBusCLInvert
				INTEGER,
			iqdmx00BusProcAmpBusCLMute
				INTEGER,
			iqdmx00BusProcAmpBusCRGainBusCR
				INTEGER,
			iqdmx00BusProcAmpBusCRInvert
				INTEGER,
			iqdmx00BusProcAmpBusCRMute
				INTEGER,
			iqdmx00BusesBusProcAmpStereoD
				INTEGER,
			iqdmx00BusProcAmpBusDLGainBusDL
				INTEGER,
			iqdmx00BusProcAmpBusDLInvert
				INTEGER,
			iqdmx00BusProcAmpBusDLMute
				INTEGER,
			iqdmx00BusProcAmpBusDRGainBusDR
				INTEGER,
			iqdmx00BusProcAmpBusDRInvert
				INTEGER,
			iqdmx00BusProcAmpBusDRMute
				INTEGER,
			iqdmx00DelayDelaySelectInternal
				INTEGER,
			iqdmx00DelayDelaySelectManual
				INTEGER,
			iqdmx00DelayDelaySelectRolltrack14
				INTEGER,
			iqdmx00DelayDelaySelectRolltrack15
				INTEGER,
			iqdmx00DelayDelaySelectRolltrack16
				INTEGER,
			iqdmx00DelayDelaySelectRolltrack17
				INTEGER,
			iqdmx00DelayDelaySelectGPIDelaySelect
				INTEGER,
			iqdmx00DelayDelayStatusManual
				INTEGER,
			iqdmx00DelayDelayStatusInternal
				RollCallString,
			iqdmx00DelayDelayStatusRolltrack14
				RollCallString,
			iqdmx00DelayDelayStatusRolltrack15
				RollCallString,
			iqdmx00DelayDelayStatusRolltrack16
				RollCallString,
			iqdmx00DelayDelayStatusRolltrack17
				RollCallString,
			iqdmx00DelayDelayStatusGPIDelayDisplay
				RollCallString,
			iqdmx00DelayDelayStatusTotalDelayDisplay
				RollCallString,
			iqdmx00AudioMonitorSilenceLevel
				INTEGER,
			iqdmx00AudioMonitorLowLevel
				INTEGER,
			iqdmx00AudioMonitorHighLevel
				INTEGER,
			iqdmx00AudioMonitorOverloadLevel
				INTEGER,
			iqdmx00AudioMonitorWarningTimer
				INTEGER,
			iqdmx00Freeze
				INTEGER,
			iqdmx00Genlock
				INTEGER,
			iqdmx00GenlockGenlockPhase625HPhase
				INTEGER,
			iqdmx00GenlockGenlockPhase625VPhase
				INTEGER,
			iqdmx00GenlockGenlockPhase525HPhase
				INTEGER,
			iqdmx00GenlockGenlockPhase525VPhase
				INTEGER,
			iqdmx00GenlockFreerunFreq
				INTEGER,
			iqdmx00GenlockFrameDelay
				INTEGER,
			iqdmx00GenlockDelayPhase625HPhase
				INTEGER,
			iqdmx00GenlockDelayPhase625VPhase
				INTEGER,
			iqdmx00GenlockDelayPhase525HPhase
				INTEGER,
			iqdmx00GenlockDelayPhase525VPhase
				INTEGER,
			iqdmx00UserMemMemory1Save1
				INTEGER,
			iqdmx00UserMemMemory1Recall1
				INTEGER,
			iqdmx00UserMemMemory1Clear1
				INTEGER,
			iqdmx00UserMemMemory1Name1
				RollCallString,
			iqdmx00UserMemMemory2Save2
				INTEGER,
			iqdmx00UserMemMemory2Recall2
				INTEGER,
			iqdmx00UserMemMemory2Clear2
				INTEGER,
			iqdmx00UserMemMemory2Name2
				RollCallString,
			iqdmx00UserMemMemory3Save3
				INTEGER,
			iqdmx00UserMemMemory3Recall3
				INTEGER,
			iqdmx00UserMemMemory3Clear3
				INTEGER,
			iqdmx00UserMemMemory3Name3
				RollCallString,
			iqdmx00UserMemMemory4Save4
				INTEGER,
			iqdmx00UserMemMemory4Recall4
				INTEGER,
			iqdmx00UserMemMemory4Clear4
				INTEGER,
			iqdmx00UserMemMemory4Name4
				RollCallString,
			iqdmx00UserMemMemory5Save5
				INTEGER,
			iqdmx00UserMemMemory5Recall5
				INTEGER,
			iqdmx00UserMemMemory5Clear5
				INTEGER,
			iqdmx00UserMemMemory5Name5
				RollCallString,
			iqdmx00UserMemMemory6Save6
				INTEGER,
			iqdmx00UserMemMemory6Recall6
				INTEGER,
			iqdmx00UserMemMemory6Clear6
				INTEGER,
			iqdmx00UserMemMemory6Name6
				RollCallString,
			iqdmx00UserMemMemory7Save7
				INTEGER,
			iqdmx00UserMemMemory7Recall7
				INTEGER,
			iqdmx00UserMemMemory7Clear7
				INTEGER,
			iqdmx00UserMemMemory7Name7
				RollCallString,
			iqdmx00UserMemMemory8Save8
				INTEGER,
			iqdmx00UserMemMemory8Recall8
				INTEGER,
			iqdmx00UserMemMemory8Clear8
				INTEGER,
			iqdmx00UserMemMemory8Name8
				RollCallString,
			iqdmx00SetupPatternAnimatedPattern
				INTEGER,
			iqdmx00SetupPatternEnablePattern
				INTEGER,
			iqdmx00SetupPattern
				INTEGER,
			iqdmx00SetupCaptionEditCaption
				RollCallString,
			iqdmx00SetupCaption
				INTEGER,
			iqdmx00BlankingVIPass525BlankAll
				INTEGER,
			iqdmx00BlankingVIPass525PassAll
				INTEGER,
			iqdmx00BlankingVIPass525Line11
				INTEGER,
			iqdmx00BlankingVIPass525Line274
				INTEGER,
			iqdmx00BlankingVIPass525Line12
				INTEGER,
			iqdmx00BlankingVIPass525Line275
				INTEGER,
			iqdmx00BlankingVIPass525Line13
				INTEGER,
			iqdmx00BlankingVIPass525Line276
				INTEGER,
			iqdmx00BlankingVIPass525Line14
				INTEGER,
			iqdmx00BlankingVIPass525Line277
				INTEGER,
			iqdmx00BlankingVIPass525Line15
				INTEGER,
			iqdmx00BlankingVIPass525Line278
				INTEGER,
			iqdmx00BlankingVIPass525Line16
				INTEGER,
			iqdmx00BlankingVIPass525Line279
				INTEGER,
			iqdmx00BlankingVIPass525Line17
				INTEGER,
			iqdmx00BlankingVIPass525Line280
				INTEGER,
			iqdmx00BlankingVIPass525Line18
				INTEGER,
			iqdmx00BlankingVIPass525Line281
				INTEGER,
			iqdmx00BlankingVIPass525Line19
				INTEGER,
			iqdmx00BlankingVIPass525Line282
				INTEGER,
			iqdmx00BlankingVIPass525Line20
				INTEGER,
			iqdmx00BlankingVIPass525Line283
				INTEGER,
			iqdmx00BlankingVIPass525Line21
				INTEGER,
			iqdmx00BlankingVIPass625BlankAll
				INTEGER,
			iqdmx00BlankingVIPass625PassAll
				INTEGER,
			iqdmx00BlankingVIPass625Line7
				INTEGER,
			iqdmx00BlankingVIPass625Line320
				INTEGER,
			iqdmx00BlankingVIPass625Line8
				INTEGER,
			iqdmx00BlankingVIPass625Line321
				INTEGER,
			iqdmx00BlankingVIPass625Line9
				INTEGER,
			iqdmx00BlankingVIPass625Line322
				INTEGER,
			iqdmx00BlankingVIPass625Line10
				INTEGER,
			iqdmx00BlankingVIPass625Line323
				INTEGER,
			iqdmx00BlankingVIPass625Line11
				INTEGER,
			iqdmx00BlankingVIPass625Line324
				INTEGER,
			iqdmx00BlankingVIPass625Line12
				INTEGER,
			iqdmx00BlankingVIPass625Line325
				INTEGER,
			iqdmx00BlankingVIPass625Line13
				INTEGER,
			iqdmx00BlankingVIPass625Line326
				INTEGER,
			iqdmx00BlankingVIPass625Line14
				INTEGER,
			iqdmx00BlankingVIPass625Line327
				INTEGER,
			iqdmx00BlankingVIPass625Line15
				INTEGER,
			iqdmx00BlankingVIPass625Line328
				INTEGER,
			iqdmx00BlankingVIPass625Line16
				INTEGER,
			iqdmx00BlankingVIPass625Line329
				INTEGER,
			iqdmx00BlankingVIPass625Line17
				INTEGER,
			iqdmx00BlankingVIPass625Line330
				INTEGER,
			iqdmx00BlankingVIPass625Line18
				INTEGER,
			iqdmx00BlankingVIPass625Line331
				INTEGER,
			iqdmx00BlankingVIPass625Line19
				INTEGER,
			iqdmx00BlankingVIPass625Line332
				INTEGER,
			iqdmx00BlankingVIPass625Line20
				INTEGER,
			iqdmx00BlankingVIPass625Line333
				INTEGER,
			iqdmx00BlankingVIPass625Line21
				INTEGER,
			iqdmx00BlankingVIPass625Line334
				INTEGER,
			iqdmx00BlankingVIPass625Line22
				INTEGER,
			iqdmx00BlankingVIPass625Line335
				INTEGER,
			iqdmx00BlankingVIPass625Line23
				INTEGER,
			iqdmx00SetupBlankingHancBlank
				INTEGER,
			iqdmx00SetupAudioToneIdentEnable
				INTEGER,
			iqdmx00SetupAudioToneFrequency
				INTEGER,
			iqdmx00SetupAudioToneFrequencyR
				INTEGER,
			iqdmx00SetupAudioToneHeadRoom
				INTEGER,
			iqdmx00SetupSlewRate
				INTEGER,
			iqdmx00SetupChannelStatus
				RollCallString,
			iqdmx00GPIIOGPIInputDisableInputs
				INTEGER,
			iqdmx00GPIIOGPIInputInputTimerEnable
				INTEGER,
			iqdmx00GPIIOGPIInputTimerActiveHigh
				INTEGER,
			iqdmx00GPIIOGPIInputInputSelection
				INTEGER,
			iqdmx00GPIIOGPIInputGPIInStatus
				RollCallString,
			iqdmx00GPIIOGPIOutputOutActiveHigh
				INTEGER,
			iqdmx00GPIIOGPIOutputOutputSelection
				INTEGER,
			iqdmx00GPIIOGPIOutputGPIOutStatus
				RollCallString,
			iqdmx00GPIIOGPIInputOutputGPIO1
				INTEGER,
			iqdmx00SetupGPIIOInputSelection
				INTEGER,
			iqdmx00SetupGPIIOOutputSelection
				INTEGER,
			iqdmx00SetupRollTrackRollTrackIndex
				INTEGER,
			iqdmx00SetupRollTrackRollTrackSource
				INTEGER,
			iqdmx00SetupRollTrackRollTrackDisable
				INTEGER,
			iqdmx00SetupRollTrackRollTrackAddress
				RollCallString,
			iqdmx00SetupRollTrackRollTrackCommand
				RollCallString,
			iqdmx00SetupRollTrackRollTrackSending
				RollCallString,
			iqdmx00SetupRollTrackRollTrackStatus
				RollCallString,
			iqdmx00SetupRollTrackRollTrack_Index
				INTEGER,
			iqdmx00SetupRollTrackRollTrack_Source
				INTEGER,
			iqdmx00SetupRollTrackRollTrack_Address
				RollCallString,
			iqdmx00SetupRollTrackRollTrack_Command
				RollCallString,
			iqdmx00SetupLoggingInput
				INTEGER,
			iqdmx00SetupLoggingStd
				INTEGER,
			iqdmx00SetupLoggingInput1
				INTEGER,
			iqdmx00SetupLoggingStd1
				INTEGER,
			iqdmx00SetupLoggingInput2
				INTEGER,
			iqdmx00SetupLoggingStd2
				INTEGER,
			iqdmx00SetupLoggingReference
				INTEGER,
			iqdmx00SetupLoggingEDH
				INTEGER,
			iqdmx00SetupLoggingEDHErrors
				INTEGER,
			iqdmx00SetupLoggingRollTrack
				INTEGER,
			iqdmx00SetupLoggingDeembed1
				INTEGER,
			iqdmx00SetupLoggingDeembed2
				INTEGER,
			iqdmx00SetupLoggingDeembed3
				INTEGER,
			iqdmx00SetupLoggingDeembed4
				INTEGER,
			iqdmx00SetupLoggingDeembed5
				INTEGER,
			iqdmx00SetupLoggingDeembed6
				INTEGER,
			iqdmx00SetupLoggingDeembed7
				INTEGER,
			iqdmx00SetupLoggingDeembed8
				INTEGER,
			iqdmx00SetupLoggingnPCM1
				INTEGER,
			iqdmx00SetupLoggingnPCM2
				INTEGER,
			iqdmx00SetupLoggingnPCM3
				INTEGER,
			iqdmx00SetupLoggingnPCM4
				INTEGER,
			iqdmx00SetupLoggingnPCM5
				INTEGER,
			iqdmx00SetupLoggingnPCM6
				INTEGER,
			iqdmx00SetupLoggingnPCM7
				INTEGER,
			iqdmx00SetupLoggingnPCM8
				INTEGER,
			iqdmx00SetupLoggingBusAL
				INTEGER,
			iqdmx00SetupLoggingBusAR
				INTEGER,
			iqdmx00SetupLoggingBusBL
				INTEGER,
			iqdmx00SetupLoggingBusBR
				INTEGER,
			iqdmx00SetupLoggingBusCL
				INTEGER,
			iqdmx00SetupLoggingBusCR
				INTEGER,
			iqdmx00SetupLoggingBusDL
				INTEGER,
			iqdmx00SetupLoggingBusDR
				INTEGER,
			iqdmx00SetupLoggingFault
				INTEGER,
			iqdmx00SetupLoggingStatusINPUT
				RollCallString,
			iqdmx00SetupLoggingStatusSTD
				RollCallString,
			iqdmx00SetupLoggingStatusINPUT1
				RollCallString,
			iqdmx00SetupLoggingStatusSTD1
				RollCallString,
			iqdmx00SetupLoggingStatusINPUT2
				RollCallString,
			iqdmx00SetupLoggingStatusSTD2
				RollCallString,
			iqdmx00SetupLoggingStatusEXTREF
				RollCallString,
			iqdmx00SetupLoggingStatusEDH
				RollCallString,
			iqdmx00SetupLoggingStatusERRSEC
				RollCallString,
			iqdmx00SetupLoggingStatusROLLTRACK
				RollCallString,
			iqdmx00SetupLoggingStatusDEEMBED1
				RollCallString,
			iqdmx00SetupLoggingStatusDEEMBED2
				RollCallString,
			iqdmx00SetupLoggingStatusDEEMBED3
				RollCallString,
			iqdmx00SetupLoggingStatusDEEMBED4
				RollCallString,
			iqdmx00SetupLoggingStatusDEEMBED5
				RollCallString,
			iqdmx00SetupLoggingStatusDEEMBED6
				RollCallString,
			iqdmx00SetupLoggingStatusDEEMBED7
				RollCallString,
			iqdmx00SetupLoggingStatusDEEMBED8
				RollCallString,
			iqdmx00SetupLoggingStatusNPCM1
				RollCallString,
			iqdmx00SetupLoggingStatusNPCM2
				RollCallString,
			iqdmx00SetupLoggingStatusNPCM3
				RollCallString,
			iqdmx00SetupLoggingStatusNPCM4
				RollCallString,
			iqdmx00SetupLoggingStatusNPCM5
				RollCallString,
			iqdmx00SetupLoggingStatusNPCM6
				RollCallString,
			iqdmx00SetupLoggingStatusNPCM7
				RollCallString,
			iqdmx00SetupLoggingStatusNPCM8
				RollCallString,
			iqdmx00SetupLoggingStatusBUSAL
				RollCallString,
			iqdmx00SetupLoggingStatusBUSAR
				RollCallString,
			iqdmx00SetupLoggingStatusBUSBL
				RollCallString,
			iqdmx00SetupLoggingStatusBUSBR
				RollCallString,
			iqdmx00SetupLoggingStatusBUSCL
				RollCallString,
			iqdmx00SetupLoggingStatusBUSCR
				RollCallString,
			iqdmx00SetupLoggingStatusBUSDL
				RollCallString,
			iqdmx00SetupLoggingStatusBUSDR
				RollCallString,
			iqdmx00SetupLoggingStatusFAULT
				RollCallString,
			iqdmx00SetupInformationWindow
				INTEGER,
			iqdmx00SetupInformationWindowResetErrors
				INTEGER,
			iqdmx00SetupDefaultOutput
				INTEGER,
			iqdmx00SetupDefaultPattern
				INTEGER,
			iqdmx00SetupUnitSoftwareVersion
				RollCallString,
			iqdmx00SetupUnitSerialNo
				RollCallString,
			iqdmx00SetupUnitPresetUnit
				INTEGER,
			iqdmx00SetupUnitRestart
				INTEGER,
			iqdmx00SetupUnitBuildNo
				RollCallString
		}

	iqdmx00SlotIndex OBJECT-TYPE
		SYNTAX		Unsigned32
		MAX-ACCESS		not-accessible
		STATUS			current
		DESCRIPTION
				"The unique Index value for each slot.  Its value
					ranges between 1 and the value of slotNumber."
		::= { iqdmx00CmdEntry 0 }


	iqdmx00VideoInput OBJECT-TYPE
		SYNTAX		INTEGER {
							val_Input_1_SDI(0),
							val_Input_2_SDI(1)
							}
		MAX-ACCESS		read-write
		STATUS			current
		DESCRIPTION
				"TYPE: - Button
				 PAGE: - Video- Input
					Input 1 SDI  cmdID= 2251  value= 0  
					Input 2 SDI  cmdID= 2251  value= 1  "
		::= { iqdmx00CmdEntry 2251 }


	iqdmx00VideoInput525 OBJECT-TYPE
		SYNTAX		INTEGER { disable(0), enable(1) }
		MAX-ACCESS		read-write
		STATUS			current
		DESCRIPTION
				"TYPE: - Checkbox
				 PAGE: - Video- Input
					525  cmdID= 1405 "
		::= { iqdmx00CmdEntry 1405 }


	iqdmx00VideoInput625 OBJECT-TYPE
		SYNTAX		INTEGER { disable(0), enable(1) }
		MAX-ACCESS		read-write
		STATUS			current
		DESCRIPTION
				"TYPE: - Checkbox
				 PAGE: - Video- Input
					625  cmdID= 1406 "
		::= { iqdmx00CmdEntry 1406 }


	iqdmx00VideoProcAmp1In1ProcAmpEnable OBJECT-TYPE
		SYNTAX		INTEGER { disable(0), enable(1) }
		MAX-ACCESS		read-write
		STATUS			current
		DESCRIPTION
				"TYPE: - Checkbox
				 PAGE: - Video- ProcAmp 1
					In1 ProcAmp Enable  cmdID= 2864 "
		::= { iqdmx00CmdEntry 2864 }


	iqdmx00VideoProcAmp1LumaGain OBJECT-TYPE
		SYNTAX		INTEGER
		MAX-ACCESS		read-write
		STATUS			current
		DESCRIPTION
				"TYPE: - Number
				 PAGE: - Video- ProcAmp 1
					Luma Gain  cmdID= 2707  min= -60  max= 60  step= 1  format= %1.1f dB  div_scale= 10 
					Min = -6.0 dB  Max = 6.0 dB  Step = 0.1 dB "
		::= { iqdmx00CmdEntry 2707 }


	iqdmx00VideoProcAmp1ChromaGain OBJECT-TYPE
		SYNTAX		INTEGER
		MAX-ACCESS		read-write
		STATUS			current
		DESCRIPTION
				"TYPE: - Number
				 PAGE: - Video- ProcAmp 1
					Chroma Gain  cmdID= 2706  min= -60  max= 60  step= 1  format= %1.1f dB  div_scale= 10 
					Min = -6.0 dB  Max = 6.0 dB  Step = 0.1 dB "
		::= { iqdmx00CmdEntry 2706 }


	iqdmx00VideoProcAmp1BlackLevel OBJECT-TYPE
		SYNTAX		INTEGER
		MAX-ACCESS		read-write
		STATUS			current
		DESCRIPTION
				"TYPE: - Number
				 PAGE: - Video- ProcAmp 1
					Black Level  cmdID= 2708  min= -1000  max= 1000  step= 8  format= %1.1f mV  div_scale= 10 
					Min = -100.0 mV  Max = 100.0 mV  Step = 0.8 mV "
		::= { iqdmx00CmdEntry 2708 }


	iqdmx00VideoProcAmp1PicturePosition OBJECT-TYPE
		SYNTAX		INTEGER
		MAX-ACCESS		read-write
		STATUS			current
		DESCRIPTION
				"TYPE: - Number
				 PAGE: - Video- ProcAmp 1
					Picture Position  cmdID= 2709  min= -592  max= 592  step= 148  format= %3.0f ns  div_scale= 1 
					Min = -592 ns  Max = 592 ns  Step = 148 ns "
		::= { iqdmx00CmdEntry 2709 }


	iqdmx00VideoProcAmp1YCTiming OBJECT-TYPE
		SYNTAX		INTEGER
		MAX-ACCESS		read-write
		STATUS			current
		DESCRIPTION
				"TYPE: - Number
				 PAGE: - Video- ProcAmp 1
					Y/C Timing  cmdID= 2924  min= -592  max= 592  step= 148  format= %3.0fns  div_scale= 1 
					Min = -592ns  Max = 592ns  Step = 148ns "
		::= { iqdmx00CmdEntry 2924 }


	iqdmx00VideoProcAmp2In2ProcAmpEnable OBJECT-TYPE
		SYNTAX		INTEGER { disable(0), enable(1) }
		MAX-ACCESS		read-write
		STATUS			current
		DESCRIPTION
				"TYPE: - Checkbox
				 PAGE: - Video- ProcAmp 2
					In2 ProcAmp Enable  cmdID= 2865 "
		::= { iqdmx00CmdEntry 2865 }


	iqdmx00VideoProcAmp2LumaGain OBJECT-TYPE
		SYNTAX		INTEGER
		MAX-ACCESS		read-write
		STATUS			current
		DESCRIPTION
				"TYPE: - Number
				 PAGE: - Video- ProcAmp 2
					Luma Gain  cmdID= 2711  min= -60  max= 60  step= 1  format= %1.1f dB  div_scale= 10 
					Min = -6.0 dB  Max = 6.0 dB  Step = 0.1 dB "
		::= { iqdmx00CmdEntry 2711 }


	iqdmx00VideoProcAmp2ChromaGain OBJECT-TYPE
		SYNTAX		INTEGER
		MAX-ACCESS		read-write
		STATUS			current
		DESCRIPTION
				"TYPE: - Number
				 PAGE: - Video- ProcAmp 2
					Chroma Gain  cmdID= 2710  min= -60  max= 60  step= 1  format= %1.1f dB  div_scale= 10 
					Min = -6.0 dB  Max = 6.0 dB  Step = 0.1 dB "
		::= { iqdmx00CmdEntry 2710 }


	iqdmx00VideoProcAmp2BlackLevel OBJECT-TYPE
		SYNTAX		INTEGER
		MAX-ACCESS		read-write
		STATUS			current
		DESCRIPTION
				"TYPE: - Number
				 PAGE: - Video- ProcAmp 2
					Black Level  cmdID= 2712  min= -1000  max= 1000  step= 8  format= %1.1f mV  div_scale= 10 
					Min = -100.0 mV  Max = 100.0 mV  Step = 0.8 mV "
		::= { iqdmx00CmdEntry 2712 }


	iqdmx00VideoProcAmp2PicturePosition OBJECT-TYPE
		SYNTAX		INTEGER
		MAX-ACCESS		read-write
		STATUS			current
		DESCRIPTION
				"TYPE: - Number
				 PAGE: - Video- ProcAmp 2
					Picture Position  cmdID= 2713  min= -592  max= 592  step= 148  format= %3.0f ns  div_scale= 1 
					Min = -592 ns  Max = 592 ns  Step = 148 ns "
		::= { iqdmx00CmdEntry 2713 }


	iqdmx00VideoProcAmp2YCTiming OBJECT-TYPE
		SYNTAX		INTEGER
		MAX-ACCESS		read-write
		STATUS			current
		DESCRIPTION
				"TYPE: - Number
				 PAGE: - Video- ProcAmp 2
					Y/C Timing  cmdID= 2925  min= -592  max= 592  step= 148  format= %3.0fns  div_scale= 1 
					Min = -592ns  Max = 592ns  Step = 148ns "
		::= { iqdmx00CmdEntry 2925 }


	iqdmx00AudioDeembed OBJECT-TYPE
		SYNTAX		INTEGER {
							val_Input_1_SDI(0),
							val_Input_2_SDI(1),
							val_Follow_Video(2)
							}
		MAX-ACCESS		read-write
		STATUS			current
		DESCRIPTION
				"TYPE: - Button
				 PAGE: - Audio- De-embed
					Input 1 SDI  cmdID= 2923  value= 0  
					Input 2 SDI  cmdID= 2923  value= 1  
					Follow Video  cmdID= 2923  value= 2  "
		::= { iqdmx00CmdEntry 2923 }


	iqdmx00AudioAESOutputAES1Source OBJECT-TYPE
		SYNTAX		INTEGER {
							val_BUS_A(0),
							val_BUS_B(1),
							val_BUS_C(2),
							val_BUS_D(3),
							val_DeEmbed_1(4),
							val_DeEmbed_2(5),
							val_DeEmbed_3(6),
							val_DeEmbed_4(7),
							val_DeEmbed_5(8),
							val_DeEmbed_6(9),
							val_DeEmbed_7(10),
							val_DeEmbed_8(11),
							val_Test_tone(12),
							val_Silence(13)
							}
		MAX-ACCESS		read-write
		STATUS			current
		DESCRIPTION
				"TYPE: - RadiobuttonList
				 PAGE: - Audio- AES Output
					AES 1 Source  cmdID= 2951 
					BUS A  value= 0  
					BUS B  value= 1  
					BUS C  value= 2  
					BUS D  value= 3  
					DeEmbed 1  value= 4  
					DeEmbed 2  value= 5  
					DeEmbed 3  value= 6  
					DeEmbed 4  value= 7  
					DeEmbed 5  value= 8  
					DeEmbed 6  value= 9  
					DeEmbed 7  value= 10  
					DeEmbed 8  value= 11  
					Test tone  value= 12  
					Silence  value= 13  "
		::= { iqdmx00CmdEntry 2951 }


	iqdmx00AudioAESOutputAES2Source OBJECT-TYPE
		SYNTAX		INTEGER {
							val_BUS_A(0),
							val_BUS_B(1),
							val_BUS_C(2),
							val_BUS_D(3),
							val_DeEmbed_1(4),
							val_DeEmbed_2(5),
							val_DeEmbed_3(6),
							val_DeEmbed_4(7),
							val_DeEmbed_5(8),
							val_DeEmbed_6(9),
							val_DeEmbed_7(10),
							val_DeEmbed_8(11),
							val_Test_tone(12),
							val_Silence(13)
							}
		MAX-ACCESS		read-write
		STATUS			current
		DESCRIPTION
				"TYPE: - RadiobuttonList
				 PAGE: - Audio- AES Output
					AES 2 Source  cmdID= 2952 
					BUS A  value= 0  
					BUS B  value= 1  
					BUS C  value= 2  
					BUS D  value= 3  
					DeEmbed 1  value= 4  
					DeEmbed 2  value= 5  
					DeEmbed 3  value= 6  
					DeEmbed 4  value= 7  
					DeEmbed 5  value= 8  
					DeEmbed 6  value= 9  
					DeEmbed 7  value= 10  
					DeEmbed 8  value= 11  
					Test tone  value= 12  
					Silence  value= 13  "
		::= { iqdmx00CmdEntry 2952 }


	iqdmx00AudioProcAmpStereo1 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqdmx00CmdEntry 3324 }


	iqdmx00ProcAmpDeembed1LGainDeembed1L OBJECT-TYPE
		SYNTAX		INTEGER
		MAX-ACCESS		read-write
		STATUS			current
		DESCRIPTION
				"TYPE: - Number
				 PAGE: - Audio- ProcAmp
					Gain De-embed 1L  cmdID= 3088  min= -180  max= 180  step= 1  format= %0.1fdB  div_scale= 10 
					Min = -18.0dB  Max = 18.0dB  Step = 0.1dB "
		::= { iqdmx00CmdEntry 3088 }


	iqdmx00ProcAmpDeembed1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqdmx00CmdEntry 3168 }


	iqdmx00ProcAmpDeembed1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqdmx00CmdEntry 3248 }


	iqdmx00ProcAmpDeembed1RGainDeembed1R OBJECT-TYPE
		SYNTAX		INTEGER
		MAX-ACCESS		read-write
		STATUS			current
		DESCRIPTION
				"TYPE: - Number
				 PAGE: - Audio- ProcAmp
					Gain De-embed 1R  cmdID= 3089  min= -180  max= 180  step= 1  format= %0.1fdB  div_scale= 10 
					Min = -18.0dB  Max = 18.0dB  Step = 0.1dB "
		::= { iqdmx00CmdEntry 3089 }


	iqdmx00ProcAmpDeembed1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqdmx00CmdEntry 3169 }


	iqdmx00ProcAmpDeembed1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqdmx00CmdEntry 3249 }


	iqdmx00AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqdmx00CmdEntry 3325 }


	iqdmx00ProcAmpDeembed2LGainDeembed2L OBJECT-TYPE
		SYNTAX		INTEGER
		MAX-ACCESS		read-write
		STATUS			current
		DESCRIPTION
				"TYPE: - Number
				 PAGE: - Audio- ProcAmp
					Gain De-embed 2L  cmdID= 3090  min= -180  max= 180  step= 1  format= %0.1fdB  div_scale= 10 
					Min = -18.0dB  Max = 18.0dB  Step = 0.1dB "
		::= { iqdmx00CmdEntry 3090 }


	iqdmx00ProcAmpDeembed2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqdmx00CmdEntry 3170 }


	iqdmx00ProcAmpDeembed2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqdmx00CmdEntry 3250 }


	iqdmx00ProcAmpDeembed2RGainDeembed2R OBJECT-TYPE
		SYNTAX		INTEGER
		MAX-ACCESS		read-write
		STATUS			current
		DESCRIPTION
				"TYPE: - Number
				 PAGE: - Audio- ProcAmp
					Gain De-embed 2R  cmdID= 3091  min= -180  max= 180  step= 1  format= %0.1fdB  div_scale= 10 
					Min = -18.0dB  Max = 18.0dB  Step = 0.1dB "
		::= { iqdmx00CmdEntry 3091 }


	iqdmx00ProcAmpDeembed2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqdmx00CmdEntry 3171 }


	iqdmx00ProcAmpDeembed2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqdmx00CmdEntry 3251 }


	iqdmx00AudioProcAmpStereo3 OBJECT-TYPE
		SYNTAX		INTEGER { disable(0), enable(1) }
		MAX-ACCESS		read-write
		STATUS			current
		DESCRIPTION
				"TYPE: - Checkbox
				 PAGE: - Audio- ProcAmp
					Stereo 3  cmdID= 3326 "
		::= { iqdmx00CmdEntry 3326 }


	iqdmx00ProcAmpDeembed3LGainDeembed3L OBJECT-TYPE
		SYNTAX		INTEGER
		MAX-ACCESS		read-write
		STATUS			current
		DESCRIPTION
				"TYPE: - Number
				 PAGE: - Audio- ProcAmp
					Gain De-embed 3L  cmdID= 3092  min= -180  max= 180  step= 1  format= %0.1fdB  div_scale= 10 
					Min = -18.0dB  Max = 18.0dB  Step = 0.1dB "
		::= { iqdmx00CmdEntry 3092 }


	iqdmx00ProcAmpDeembed3LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqdmx00CmdEntry 3172 }


	iqdmx00ProcAmpDeembed3LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqdmx00CmdEntry 3252 }


	iqdmx00ProcAmpDeembed3RGainDeembed3R OBJECT-TYPE
		SYNTAX		INTEGER
		MAX-ACCESS		read-write
		STATUS			current
		DESCRIPTION
				"TYPE: - Number
				 PAGE: - Audio- ProcAmp
					Gain De-embed 3R  cmdID= 3093  min= -180  max= 180  step= 1  format= %0.1fdB  div_scale= 10 
					Min = -18.0dB  Max = 18.0dB  Step = 0.1dB "
		::= { iqdmx00CmdEntry 3093 }


	iqdmx00ProcAmpDeembed3RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqdmx00CmdEntry 3173 }


	iqdmx00ProcAmpDeembed3RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqdmx00CmdEntry 3253 }


	iqdmx00AudioProcAmpStereo4 OBJECT-TYPE
		SYNTAX		INTEGER { disable(0), enable(1) }
		MAX-ACCESS		read-write
		STATUS			current
		DESCRIPTION
				"TYPE: - Checkbox
				 PAGE: - Audio- ProcAmp
					Stereo 4  cmdID= 3327 "
		::= { iqdmx00CmdEntry 3327 }


	iqdmx00ProcAmpDeembed4LGainDeembed4L OBJECT-TYPE
		SYNTAX		INTEGER
		MAX-ACCESS		read-write
		STATUS			current
		DESCRIPTION
				"TYPE: - Number
				 PAGE: - Audio- ProcAmp
					Gain De-embed 4L  cmdID= 3094  min= -180  max= 180  step= 1  format= %0.1fdB  div_scale= 10 
					Min = -18.0dB  Max = 18.0dB  Step = 0.1dB "
		::= { iqdmx00CmdEntry 3094 }


	iqdmx00ProcAmpDeembed4LInvert OBJECT-TYPE
		SYNTAX		INTEGER { disable(0), enable(1) }
		MAX-ACCESS		read-write
		STATUS			current
		DESCRIPTION
				"TYPE: - Checkbox
				 PAGE: - Audio- ProcAmp
					Invert  cmdID= 3174 "
		::= { iqdmx00CmdEntry 3174 }


	iqdmx00ProcAmpDeembed4LMute OBJECT-TYPE
		SYNTAX		INTEGER { disable(0), enable(1) }
		MAX-ACCESS		read-write
		STATUS			current
		DESCRIPTION
				"TYPE: - Checkbox
				 PAGE: - Audio- ProcAmp
					Mute  cmdID= 3254 "
		::= { iqdmx00CmdEntry 3254 }


	iqdmx00ProcAmpDeembed4RGainDeembed4R OBJECT-TYPE
		SYNTAX		INTEGER
		MAX-ACCESS		read-write
		STATUS			current
		DESCRIPTION
				"TYPE: - Number
				 PAGE: - Audio- ProcAmp
					Gain De-embed 4R  cmdID= 3095  min= -180  max= 180  step= 1  format= %0.1fdB  div_scale= 10 
					Min = -18.0dB  Max = 18.0dB  Step = 0.1dB "
		::= { iqdmx00CmdEntry 3095 }


	iqdmx00ProcAmpDeembed4RInvert OBJECT-TYPE
		SYNTAX		INTEGER { disable(0), enable(1) }
		MAX-ACCESS		read-write
		STATUS			current
		DESCRIPTION
				"TYPE: - Checkbox
				 PAGE: - Audio- ProcAmp
					Invert  cmdID= 3175 "
		::= { iqdmx00CmdEntry 3175 }


	iqdmx00ProcAmpDeembed4RMute OBJECT-TYPE
		SYNTAX		INTEGER { disable(0), enable(1) }
		MAX-ACCESS		read-write
		STATUS			current
		DESCRIPTION
				"TYPE: - Checkbox
				 PAGE: - Audio- ProcAmp
					Mute  cmdID= 3255 "
		::= { iqdmx00CmdEntry 3255 }


	iqdmx00AudioProcAmpStereo5 OBJECT-TYPE
		SYNTAX		INTEGER { disable(0), enable(1) }
		MAX-ACCESS		read-write
		STATUS			current
		DESCRIPTION
				"TYPE: - Checkbox
				 PAGE: - Audio- ProcAmp
					Stereo 5  cmdID= 3328 "
		::= { iqdmx00CmdEntry 3328 }


	iqdmx00ProcAmpDeembed5LGainDeembed5L OBJECT-TYPE
		SYNTAX		INTEGER
		MAX-ACCESS		read-write
		STATUS			current
		DESCRIPTION
				"TYPE: - Number
				 PAGE: - Audio- ProcAmp
					Gain De-embed 5L  cmdID= 3096  min= -180  max= 180  step= 1  format= %0.1fdB  div_scale= 10 
					Min = -18.0dB  Max = 18.0dB  Step = 0.1dB "
		::= { iqdmx00CmdEntry 3096 }


	iqdmx00ProcAmpDeembed5LInvert OBJECT-TYPE
		SYNTAX		INTEGER { disable(0), enable(1) }
		MAX-ACCESS		read-write
		STATUS			current
		DESCRIPTION
				"TYPE: - Checkbox
				 PAGE: - Audio- ProcAmp
					Invert  cmdID= 3176 "
		::= { iqdmx00CmdEntry 3176 }


	iqdmx00ProcAmpDeembed5LMute OBJECT-TYPE
		SYNTAX		INTEGER { disable(0), enable(1) }
		MAX-ACCESS		read-write
		STATUS			current
		DESCRIPTION
				"TYPE: - Checkbox
				 PAGE: - Audio- ProcAmp
					Mute  cmdID= 3256 "
		::= { iqdmx00CmdEntry 3256 }


	iqdmx00ProcAmpDeembed5RGainDeembed5R OBJECT-TYPE
		SYNTAX		INTEGER
		MAX-ACCESS		read-write
		STATUS			current
		DESCRIPTION
				"TYPE: - Number
				 PAGE: - Audio- ProcAmp
					Gain De-embed 5R  cmdID= 3097  min= -180  max= 180  step= 1  format= %0.1fdB  div_scale= 10 
					Min = -18.0dB  Max = 18.0dB  Step = 0.1dB "
		::= { iqdmx00CmdEntry 3097 }


	iqdmx00ProcAmpDeembed5RInvert OBJECT-TYPE
		SYNTAX		INTEGER { disable(0), enable(1) }
		MAX-ACCESS		read-write
		STATUS			current
		DESCRIPTION
				"TYPE: - Checkbox
				 PAGE: - Audio- ProcAmp
					Invert  cmdID= 3177 "
		::= { iqdmx00CmdEntry 3177 }


	iqdmx00ProcAmpDeembed5RMute OBJECT-TYPE
		SYNTAX		INTEGER { disable(0), enable(1) }
		MAX-ACCESS		read-write
		STATUS			current
		DESCRIPTION
				"TYPE: - Checkbox
				 PAGE: - Audio- ProcAmp
					Mute  cmdID= 3257 "
		::= { iqdmx00CmdEntry 3257 }


	iqdmx00AudioProcAmpStereo6 OBJECT-TYPE
		SYNTAX		INTEGER { disable(0), enable(1) }
		MAX-ACCESS		read-write
		STATUS			current
		DESCRIPTION
				"TYPE: - Checkbox
				 PAGE: - Audio- ProcAmp
					Stereo 6  cmdID= 3329 "
		::= { iqdmx00CmdEntry 3329 }


	iqdmx00ProcAmpDeembed6LGainDeembed6L OBJECT-TYPE
		SYNTAX		INTEGER
		MAX-ACCESS		read-write
		STATUS			current
		DESCRIPTION
				"TYPE: - Number
				 PAGE: - Audio- ProcAmp
					Gain De-embed 6L  cmdID= 3098  min= -180  max= 180  step= 1  format= %0.1fdB  div_scale= 10 
					Min = -18.0dB  Max = 18.0dB  Step = 0.1dB "
		::= { iqdmx00CmdEntry 3098 }


	iqdmx00ProcAmpDeembed6LInvert OBJECT-TYPE
		SYNTAX		INTEGER { disable(0), enable(1) }
		MAX-ACCESS		read-write
		STATUS			current
		DESCRIPTION
				"TYPE: - Checkbox
				 PAGE: - Audio- ProcAmp
					Invert  cmdID= 3178 "
		::= { iqdmx00CmdEntry 3178 }


	iqdmx00ProcAmpDeembed6LMute OBJECT-TYPE
		SYNTAX		INTEGER { disable(0), enable(1) }
		MAX-ACCESS		read-write
		STATUS			current
		DESCRIPTION
				"TYPE: - Checkbox
				 PAGE: - Audio- ProcAmp
					Mute  cmdID= 3258 "
		::= { iqdmx00CmdEntry 3258 }


	iqdmx00ProcAmpDeembed6RGainDeembed6R OBJECT-TYPE
		SYNTAX		INTEGER
		MAX-ACCESS		read-write
		STATUS			current
		DESCRIPTION
				"TYPE: - Number
				 PAGE: - Audio- ProcAmp
					Gain De-embed 6R  cmdID= 3099  min= -180  max= 180  step= 1  format= %0.1fdB  div_scale= 10 
					Min = -18.0dB  Max = 18.0dB  Step = 0.1dB "
		::= { iqdmx00CmdEntry 3099 }


	iqdmx00ProcAmpDeembed6RInvert OBJECT-TYPE
		SYNTAX		INTEGER { disable(0), enable(1) }
		MAX-ACCESS		read-write
		STATUS			current
		DESCRIPTION
				"TYPE: - Checkbox
				 PAGE: - Audio- ProcAmp
					Invert  cmdID= 3179 "
		::= { iqdmx00CmdEntry 3179 }


	iqdmx00ProcAmpDeembed6RMute OBJECT-TYPE
		SYNTAX		INTEGER { disable(0), enable(1) }
		MAX-ACCESS		read-write
		STATUS			current
		DESCRIPTION
				"TYPE: - Checkbox
				 PAGE: - Audio- ProcAmp
					Mute  cmdID= 3259 "
		::= { iqdmx00CmdEntry 3259 }


	iqdmx00AudioProcAmpStereo7 OBJECT-TYPE
		SYNTAX		INTEGER { disable(0), enable(1) }
		MAX-ACCESS		read-write
		STATUS			current
		DESCRIPTION
				"TYPE: - Checkbox
				 PAGE: - Audio- ProcAmp
					Stereo 7  cmdID= 3330 "
		::= { iqdmx00CmdEntry 3330 }


	iqdmx00ProcAmpDeembed7LGainDeembed7L OBJECT-TYPE
		SYNTAX		INTEGER
		MAX-ACCESS		read-write
		STATUS			current
		DESCRIPTION
				"TYPE: - Number
				 PAGE: - Audio- ProcAmp
					Gain De-embed 7L  cmdID= 3100  min= -180  max= 180  step= 1  format= %0.1fdB  div_scale= 10 
					Min = -18.0dB  Max = 18.0dB  Step = 0.1dB "
		::= { iqdmx00CmdEntry 3100 }


	iqdmx00ProcAmpDeembed7LInvert OBJECT-TYPE
		SYNTAX		INTEGER { disable(0), enable(1) }
		MAX-ACCESS		read-write
		STATUS			current
		DESCRIPTION
				"TYPE: - Checkbox
				 PAGE: - Audio- ProcAmp
					Invert  cmdID= 3180 "
		::= { iqdmx00CmdEntry 3180 }


	iqdmx00ProcAmpDeembed7LMute OBJECT-TYPE
		SYNTAX		INTEGER { disable(0), enable(1) }
		MAX-ACCESS		read-write
		STATUS			current
		DESCRIPTION
				"TYPE: - Checkbox
				 PAGE: - Audio- ProcAmp
					Mute  cmdID= 3260 "
		::= { iqdmx00CmdEntry 3260 }


	iqdmx00ProcAmpDeembed7RGainDeembed7R OBJECT-TYPE
		SYNTAX		INTEGER
		MAX-ACCESS		read-write
		STATUS			current
		DESCRIPTION
				"TYPE: - Number
				 PAGE: - Audio- ProcAmp
					Gain De-embed 7R  cmdID= 3101  min= -180  max= 180  step= 1  format= %0.1fdB  div_scale= 10 
					Min = -18.0dB  Max = 18.0dB  Step = 0.1dB "
		::= { iqdmx00CmdEntry 3101 }


	iqdmx00ProcAmpDeembed7RInvert OBJECT-TYPE
		SYNTAX		INTEGER { disable(0), enable(1) }
		MAX-ACCESS		read-write
		STATUS			current
		DESCRIPTION
				"TYPE: - Checkbox
				 PAGE: - Audio- ProcAmp
					Invert  cmdID= 3181 "
		::= { iqdmx00CmdEntry 3181 }


	iqdmx00ProcAmpDeembed7RMute OBJECT-TYPE
		SYNTAX		INTEGER { disable(0), enable(1) }
		MAX-ACCESS		read-write
		STATUS			current
		DESCRIPTION
				"TYPE: - Checkbox
				 PAGE: - Audio- ProcAmp
					Mute  cmdID= 3261 "
		::= { iqdmx00CmdEntry 3261 }


	iqdmx00AudioProcAmpStereo8 OBJECT-TYPE
		SYNTAX		INTEGER { disable(0), enable(1) }
		MAX-ACCESS		read-write
		STATUS			current
		DESCRIPTION
				"TYPE: - Checkbox
				 PAGE: - Audio- ProcAmp
					Stereo 8  cmdID= 3331 "
		::= { iqdmx00CmdEntry 3331 }


	iqdmx00ProcAmpDeembed8LGainDeembed8L OBJECT-TYPE
		SYNTAX		INTEGER
		MAX-ACCESS		read-write
		STATUS			current
		DESCRIPTION
				"TYPE: - Number
				 PAGE: - Audio- ProcAmp
					Gain De-embed 8L  cmdID= 3102  min= -180  max= 180  step= 1  format= %0.1fdB  div_scale= 10 
					Min = -18.0dB  Max = 18.0dB  Step = 0.1dB "
		::= { iqdmx00CmdEntry 3102 }


	iqdmx00ProcAmpDeembed8LInvert OBJECT-TYPE
		SYNTAX		INTEGER { disable(0), enable(1) }
		MAX-ACCESS		read-write
		STATUS			current
		DESCRIPTION
				"TYPE: - Checkbox
				 PAGE: - Audio- ProcAmp
					Invert  cmdID= 3182 "
		::= { iqdmx00CmdEntry 3182 }


	iqdmx00ProcAmpDeembed8LMute OBJECT-TYPE
		SYNTAX		INTEGER { disable(0), enable(1) }
		MAX-ACCESS		read-write
		STATUS			current
		DESCRIPTION
				"TYPE: - Checkbox
				 PAGE: - Audio- ProcAmp
					Mute  cmdID= 3262 "
		::= { iqdmx00CmdEntry 3262 }


	iqdmx00ProcAmpDeembed8RGainDeembed8R OBJECT-TYPE
		SYNTAX		INTEGER
		MAX-ACCESS		read-write
		STATUS			current
		DESCRIPTION
				"TYPE: - Number
				 PAGE: - Audio- ProcAmp
					Gain De-embed 8R  cmdID= 3103  min= -180  max= 180  step= 1  format= %0.1fdB  div_scale= 10 
					Min = -18.0dB  Max = 18.0dB  Step = 0.1dB "
		::= { iqdmx00CmdEntry 3103 }


	iqdmx00ProcAmpDeembed8RInvert OBJECT-TYPE
		SYNTAX		INTEGER { disable(0), enable(1) }
		MAX-ACCESS		read-write
		STATUS			current
		DESCRIPTION
				"TYPE: - Checkbox
				 PAGE: - Audio- ProcAmp
					Invert  cmdID= 3183 "
		::= { iqdmx00CmdEntry 3183 }


	iqdmx00ProcAmpDeembed8RMute OBJECT-TYPE
		SYNTAX		INTEGER { disable(0), enable(1) }
		MAX-ACCESS		read-write
		STATUS			current
		DESCRIPTION
				"TYPE: - Checkbox
				 PAGE: - Audio- ProcAmp
					Mute  cmdID= 3263 "
		::= { iqdmx00CmdEntry 3263 }


	iqdmx00EmbedEmbedder1Embed1Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 1
					Embed 1 Source  cmdID= 2941 
					BUS A  value= 0  
					BUS B  value= 1  
					BUS C  value= 2  
					BUS D  value= 3  
					Test tone  value= 4  
					Silence  value= 5  "
		::= { iqdmx00CmdEntry 2941 }


	iqdmx00EmbedEmbedder1PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 1
					Pair Selection  cmdID= 2531 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqdmx00CmdEntry 2531 }


	iqdmx00EmbedEmbedder1Disable OBJECT-TYPE
		SYNTAX		INTEGER { disable(0), enable(1) }
		MAX-ACCESS		read-write
		STATUS			current
		DESCRIPTION
				"TYPE: - Checkbox
				 PAGE: - Audio- Embed- Embedder 1
					Disable  cmdID= 2541 "
		::= { iqdmx00CmdEntry 2541 }


	iqdmx00EmbedEmbedder2Embed2Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 2
					Embed 2 Source  cmdID= 2942 
					BUS A  value= 0  
					BUS B  value= 1  
					BUS C  value= 2  
					BUS D  value= 3  
					Test tone  value= 4  
					Silence  value= 5  "
		::= { iqdmx00CmdEntry 2942 }


	iqdmx00EmbedEmbedder2PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 2
					Pair Selection  cmdID= 2532 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqdmx00CmdEntry 2532 }


	iqdmx00EmbedEmbedder2Disable OBJECT-TYPE
		SYNTAX		INTEGER { disable(0), enable(1) }
		MAX-ACCESS		read-write
		STATUS			current
		DESCRIPTION
				"TYPE: - Checkbox
				 PAGE: - Audio- Embed- Embedder 2
					Disable  cmdID= 2542 "
		::= { iqdmx00CmdEntry 2542 }


	iqdmx00EmbedEmbedder3Embed3Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 3
					Embed 3 Source  cmdID= 2943 
					BUS A  value= 0  
					BUS B  value= 1  
					BUS C  value= 2  
					BUS D  value= 3  
					Test tone  value= 4  
					Silence  value= 5  "
		::= { iqdmx00CmdEntry 2943 }


	iqdmx00EmbedEmbedder3PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 3
					Pair Selection  cmdID= 2533 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqdmx00CmdEntry 2533 }


	iqdmx00EmbedEmbedder3Disable OBJECT-TYPE
		SYNTAX		INTEGER { disable(0), enable(1) }
		MAX-ACCESS		read-write
		STATUS			current
		DESCRIPTION
				"TYPE: - Checkbox
				 PAGE: - Audio- Embed- Embedder 3
					Disable  cmdID= 2543 "
		::= { iqdmx00CmdEntry 2543 }


	iqdmx00EmbedEmbedder4Embed4Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 4
					Embed 4 Source  cmdID= 2944 
					BUS A  value= 0  
					BUS B  value= 1  
					BUS C  value= 2  
					BUS D  value= 3  
					Test tone  value= 4  
					Silence  value= 5  "
		::= { iqdmx00CmdEntry 2944 }


	iqdmx00EmbedEmbedder4PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 4
					Pair Selection  cmdID= 2534 
					Select Pair 1  value= 0  
					Select Pair 2  value= 1  
					Select Pair 3  value= 2  
					Select Pair 4  value= 3  
					Select Pair 5  value= 4  
					Select Pair 6  value= 5  
					Select Pair 7  value= 6  
					Select Pair 8  value= 7  "
		::= { iqdmx00CmdEntry 2534 }


	iqdmx00EmbedEmbedder4Disable OBJECT-TYPE
		SYNTAX		INTEGER { disable(0), enable(1) }
		MAX-ACCESS		read-write
		STATUS			current
		DESCRIPTION
				"TYPE: - Checkbox
				 PAGE: - Audio- Embed- Embedder 4
					Disable  cmdID= 2544 "
		::= { iqdmx00CmdEntry 2544 }


	iqdmx00Mixer1Mix1Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source1
					Mix1 Source1  cmdID= 3440 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3440 }


	iqdmx00MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1 
					Min = -71dB  Max = 0dB  Step = 1dB "
		::= { iqdmx00CmdEntry 3360 }


	iqdmx00Mixer1Mix1Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source2
					Mix1 Source2  cmdID= 3441 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3441 }


	iqdmx00MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1 
					Min = -71dB  Max = 0dB  Step = 1dB "
		::= { iqdmx00CmdEntry 3361 }


	iqdmx00Mixer1Mix1Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source3
					Mix1 Source3  cmdID= 3442 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3442 }


	iqdmx00MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1 
					Min = -71dB  Max = 0dB  Step = 1dB "
		::= { iqdmx00CmdEntry 3362 }


	iqdmx00Mixer1Mix1Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source4
					Mix1 Source4  cmdID= 3443 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3443 }


	iqdmx00MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1 
					Min = -71dB  Max = 0dB  Step = 1dB "
		::= { iqdmx00CmdEntry 3363 }


	iqdmx00Mixer2Mix2Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source1
					Mix2 Source1  cmdID= 3444 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3444 }


	iqdmx00MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1 
					Min = -71dB  Max = 0dB  Step = 1dB "
		::= { iqdmx00CmdEntry 3364 }


	iqdmx00Mixer2Mix2Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source2
					Mix2 Source2  cmdID= 3445 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3445 }


	iqdmx00MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1 
					Min = -71dB  Max = 0dB  Step = 1dB "
		::= { iqdmx00CmdEntry 3365 }


	iqdmx00Mixer2Mix2Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source3
					Mix2 Source3  cmdID= 3446 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3446 }


	iqdmx00MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1 
					Min = -71dB  Max = 0dB  Step = 1dB "
		::= { iqdmx00CmdEntry 3366 }


	iqdmx00Mixer2Mix2Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source4
					Mix2 Source4  cmdID= 3447 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3447 }


	iqdmx00MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1 
					Min = -71dB  Max = 0dB  Step = 1dB "
		::= { iqdmx00CmdEntry 3367 }


	iqdmx00Mixer3Mix3Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source1
					Mix3 Source1  cmdID= 3448 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3448 }


	iqdmx00MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1 
					Min = -71dB  Max = 0dB  Step = 1dB "
		::= { iqdmx00CmdEntry 3368 }


	iqdmx00Mixer3Mix3Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source2
					Mix3 Source2  cmdID= 3449 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3449 }


	iqdmx00MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1 
					Min = -71dB  Max = 0dB  Step = 1dB "
		::= { iqdmx00CmdEntry 3369 }


	iqdmx00Mixer3Mix3Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source3
					Mix3 Source3  cmdID= 3450 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3450 }


	iqdmx00MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1 
					Min = -71dB  Max = 0dB  Step = 1dB "
		::= { iqdmx00CmdEntry 3370 }


	iqdmx00Mixer3Mix3Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source4
					Mix3 Source4  cmdID= 3451 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3451 }


	iqdmx00MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1 
					Min = -71dB  Max = 0dB  Step = 1dB "
		::= { iqdmx00CmdEntry 3371 }


	iqdmx00Mixer4Mix4Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source1
					Mix4 Source1  cmdID= 3452 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3452 }


	iqdmx00MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1 
					Min = -71dB  Max = 0dB  Step = 1dB "
		::= { iqdmx00CmdEntry 3372 }


	iqdmx00Mixer4Mix4Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source2
					Mix4 Source2  cmdID= 3453 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3453 }


	iqdmx00MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1 
					Min = -71dB  Max = 0dB  Step = 1dB "
		::= { iqdmx00CmdEntry 3373 }


	iqdmx00Mixer4Mix4Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source3
					Mix4 Source3  cmdID= 3454 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3454 }


	iqdmx00MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1 
					Min = -71dB  Max = 0dB  Step = 1dB "
		::= { iqdmx00CmdEntry 3374 }


	iqdmx00Mixer4Mix4Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source4
					Mix4 Source4  cmdID= 3455 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  "
		::= { iqdmx00CmdEntry 3455 }


	iqdmx00MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1 
					Min = -71dB  Max = 0dB  Step = 1dB "
		::= { iqdmx00CmdEntry 3375 }


	iqdmx00BusSourceBusALSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusAL Source
					BusAL Source  cmdID= 3520 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3520 }


	iqdmx00BusSourceBusARSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusAR Source
					BusAR Source  cmdID= 3521 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3521 }


	iqdmx00BusSourceBusBLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusBL Source
					BusBL Source  cmdID= 3522 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3522 }


	iqdmx00BusSourceBusBRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusBR Source
					BusBR Source  cmdID= 3523 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3523 }


	iqdmx00BusSourceBusCLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusCL Source
					BusCL Source  cmdID= 3524 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3524 }


	iqdmx00BusSourceBusCRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusCR Source
					BusCR Source  cmdID= 3525 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3525 }


	iqdmx00BusSourceBusDLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusDL Source
					BusDL Source  cmdID= 3526 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3526 }


	iqdmx00BusSourceBusDRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusDR Source
					BusDR Source  cmdID= 3527 
					DeEmbed 1L  value= 0  
					DeEmbed 1R  value= 1  
					DeEmbed 2L  value= 2  
					DeEmbed 2R  value= 3  
					DeEmbed 3L  value= 4  
					DeEmbed 3R  value= 5  
					DeEmbed 4L  value= 6  
					DeEmbed 4R  value= 7  
					DeEmbed 5L  value= 8  
					DeEmbed 5R  value= 9  
					DeEmbed 6L  value= 10  
					DeEmbed 6R  value= 11  
					DeEmbed 7L  value= 12  
					DeEmbed 7R  value= 13  
					DeEmbed 8L  value= 14  
					DeEmbed 8R  value= 15  
					MIX 1  value= 16  
					MIX 2  value= 17  
					MIX 3  value= 18  
					MIX 4  value= 19  "
		::= { iqdmx00CmdEntry 3527 }


	iqdmx00BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqdmx00CmdEntry 3320 }


	iqdmx00BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10 
					Min = -18.0dB  Max = 18.0dB  Step = 0.1dB "
		::= { iqdmx00CmdEntry 3080 }


	iqdmx00BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqdmx00CmdEntry 3160 }


	iqdmx00BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqdmx00CmdEntry 3240 }


	iqdmx00BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10 
					Min = -18.0dB  Max = 18.0dB  Step = 0.1dB "
		::= { iqdmx00CmdEntry 3081 }


	iqdmx00BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqdmx00CmdEntry 3161 }


	iqdmx00BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqdmx00CmdEntry 3241 }


	iqdmx00BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqdmx00CmdEntry 3321 }


	iqdmx00BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10 
					Min = -18.0dB  Max = 18.0dB  Step = 0.1dB "
		::= { iqdmx00CmdEntry 3082 }


	iqdmx00BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqdmx00CmdEntry 3162 }


	iqdmx00BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqdmx00CmdEntry 3242 }


	iqdmx00BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10 
					Min = -18.0dB  Max = 18.0dB  Step = 0.1dB "
		::= { iqdmx00CmdEntry 3083 }


	iqdmx00BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqdmx00CmdEntry 3163 }


	iqdmx00BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqdmx00CmdEntry 3243 }


	iqdmx00BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqdmx00CmdEntry 3322 }


	iqdmx00BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10 
					Min = -18.0dB  Max = 18.0dB  Step = 0.1dB "
		::= { iqdmx00CmdEntry 3084 }


	iqdmx00BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqdmx00CmdEntry 3164 }


	iqdmx00BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqdmx00CmdEntry 3244 }


	iqdmx00BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10 
					Min = -18.0dB  Max = 18.0dB  Step = 0.1dB "
		::= { iqdmx00CmdEntry 3085 }


	iqdmx00BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqdmx00CmdEntry 3165 }


	iqdmx00BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqdmx00CmdEntry 3245 }


	iqdmx00BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqdmx00CmdEntry 3323 }


	iqdmx00BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10 
					Min = -18.0dB  Max = 18.0dB  Step = 0.1dB "
		::= { iqdmx00CmdEntry 3086 }


	iqdmx00BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqdmx00CmdEntry 3166 }


	iqdmx00BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqdmx00CmdEntry 3246 }


	iqdmx00BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10 
					Min = -18.0dB  Max = 18.0dB  Step = 0.1dB "
		::= { iqdmx00CmdEntry 3087 }


	iqdmx00BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqdmx00CmdEntry 3167 }


	iqdmx00BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqdmx00CmdEntry 3247 }


	iqdmx00DelayDelaySelectInternal OBJECT-TYPE
		SYNTAX		INTEGER { disable(0), enable(1) }
		MAX-ACCESS		read-write
		STATUS			current
		DESCRIPTION
				"TYPE: - Checkbox
				 PAGE: - Audio- Delay
					Internal  cmdID= 2567 "
		::= { iqdmx00CmdEntry 2567 }


	iqdmx00DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqdmx00CmdEntry 2568 }


	iqdmx00DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqdmx00CmdEntry 2569 }


	iqdmx00DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqdmx00CmdEntry 2570 }


	iqdmx00DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqdmx00CmdEntry 2571 }


	iqdmx00DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqdmx00CmdEntry 2572 }


	iqdmx00DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqdmx00CmdEntry 3051 }


	iqdmx00DelayDelayStatusManual OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1 
					Manual  cmdID= 2573  format=   
					Min = -40 ms  Max = 1500 ms  Step =   1 ms "
		::= { iqdmx00CmdEntry 2573 }


	iqdmx00DelayDelayStatusInternal OBJECT-TYPE
		SYNTAX		RollCallString
		MAX-ACCESS		read-only
		STATUS			current
		DESCRIPTION
				"TYPE: - Display
				 PAGE: - Audio- Delay
					Internal  cmdID= 2574  format=   "
		::= { iqdmx00CmdEntry 2574 }


	iqdmx00DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqdmx00CmdEntry 14 }


	iqdmx00DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqdmx00CmdEntry 15 }


	iqdmx00DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqdmx00CmdEntry 16 }


	iqdmx00DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqdmx00CmdEntry 17 }


	iqdmx00DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqdmx00CmdEntry 3052 }


	iqdmx00DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqdmx00CmdEntry 2979 }


	iqdmx00AudioMonitorSilenceLevel OBJECT-TYPE
		SYNTAX		INTEGER
		MAX-ACCESS		read-write
		STATUS			current
		DESCRIPTION
				"TYPE: - Number
				 PAGE: - Audio- Monitor
					Silence Level  cmdID= 3056  min= -96  max= 0  step= 1  format= %1.1f dB  div_scale= 1 
					Min = -96.0 dB  Max = 0.0 dB  Step = 1.0 dB "
		::= { iqdmx00CmdEntry 3056 }


	iqdmx00AudioMonitorLowLevel OBJECT-TYPE
		SYNTAX		INTEGER
		MAX-ACCESS		read-write
		STATUS			current
		DESCRIPTION
				"TYPE: - Number
				 PAGE: - Audio- Monitor
					Low Level  cmdID= 2517  min= -96  max= 0  step= 1  format= %1.1f dB  div_scale= 1 
					Min = -96.0 dB  Max = 0.0 dB  Step = 1.0 dB "
		::= { iqdmx00CmdEntry 2517 }


	iqdmx00AudioMonitorHighLevel OBJECT-TYPE
		SYNTAX		INTEGER
		MAX-ACCESS		read-write
		STATUS			current
		DESCRIPTION
				"TYPE: - Number
				 PAGE: - Audio- Monitor
					High Level  cmdID= 3057  min= -96  max= 0  step= 1  format= %1.1f dB  div_scale= 1 
					Min = -96.0 dB  Max = 0.0 dB  Step = 1.0 dB "
		::= { iqdmx00CmdEntry 3057 }


	iqdmx00AudioMonitorOverloadLevel OBJECT-TYPE
		SYNTAX		INTEGER
		MAX-ACCESS		read-write
		STATUS			current
		DESCRIPTION
				"TYPE: - Number
				 PAGE: - Audio- Monitor
					Overload Level  cmdID= 3058  min= -96  max= 0  step= 1  format= %1.1f dB  div_scale= 1 
					Min = -96.0 dB  Max = 0.0 dB  Step = 1.0 dB "
		::= { iqdmx00CmdEntry 3058 }


	iqdmx00AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1 
					Min = 1 sec  Max = 20 sec  Step = 1 sec "
		::= { iqdmx00CmdEntry 2518 }


	iqdmx00Freeze OBJECT-TYPE
		SYNTAX		INTEGER { disable(0), enable(1) }
		MAX-ACCESS		read-write
		STATUS			current
		DESCRIPTION
				"TYPE: - Checkbox
					Freeze  cmdID= 1208 "
		::= { iqdmx00CmdEntry 1208 }


	iqdmx00Genlock OBJECT-TYPE
		SYNTAX		INTEGER {
							val_Lock_to_Reference(0),
							val_Lock_to_Input(1),
							val_Free_Run(2)
							}
		MAX-ACCESS		read-write
		STATUS			current
		DESCRIPTION
				"TYPE: - Button
				 PAGE: - Genlock
					Lock to Reference  cmdID= 1049  value= 0  
					Lock to Input  cmdID= 1049  value= 1  
					Free Run  cmdID= 1049  value= 2  "
		::= { iqdmx00CmdEntry 1049 }


	iqdmx00GenlockGenlockPhase625HPhase OBJECT-TYPE
		SYNTAX		INTEGER
		MAX-ACCESS		read-write
		STATUS			current
		DESCRIPTION
				"TYPE: - Number
				 PAGE: - Genlock
					625 H Phase  cmdID= 1050  min= -31999968  max= 31962931  step= -28499  format=    %.0fns  div_scale= 1000 
					Min =    -32000ns  Max =    31963ns  Step =    -28ns "
		::= { iqdmx00CmdEntry 1050 }


	iqdmx00GenlockGenlockPhase625VPhase OBJECT-TYPE
		SYNTAX		INTEGER
		MAX-ACCESS		read-write
		STATUS			current
		DESCRIPTION
				"TYPE: - Number
				 PAGE: - Genlock
					625 V Phase  cmdID= 1051  min= -312  max= 312  step= 1  format=    %.0flines  div_scale= 1 
					Min =    -312lines  Max =    312lines  Step =    1lines "
		::= { iqdmx00CmdEntry 1051 }


	iqdmx00GenlockGenlockPhase525HPhase OBJECT-TYPE
		SYNTAX		INTEGER
		MAX-ACCESS		read-write
		STATUS			current
		DESCRIPTION
				"TYPE: - Number
				 PAGE: - Genlock
					525 H Phase  cmdID= 1052  min= -31777746  max= 31740709  step= -28499  format=    %.0fns  div_scale= 1000 
					Min =    -31778ns  Max =    31741ns  Step =    -28ns "
		::= { iqdmx00CmdEntry 1052 }


	iqdmx00GenlockGenlockPhase525VPhase OBJECT-TYPE
		SYNTAX		INTEGER
		MAX-ACCESS		read-write
		STATUS			current
		DESCRIPTION
				"TYPE: - Number
				 PAGE: - Genlock
					525 V Phase  cmdID= 1053  min= -262  max= 262  step= 1  format=    %.0flines  div_scale= 1 
					Min =    -262lines  Max =    262lines  Step =    1lines "
		::= { iqdmx00CmdEntry 1053 }


	iqdmx00GenlockFreerunFreq OBJECT-TYPE
		SYNTAX		INTEGER
		MAX-ACCESS		read-write
		STATUS			current
		DESCRIPTION
				"TYPE: - Number
				 PAGE: - Genlock
					Freerun Freq  cmdID= 2449  min= -60  max= 60  step= 1  format=   %.0f  div_scale= 1 
					Min =   -60  Max =   60  Step =   1 "
		::= { iqdmx00CmdEntry 2449 }


	iqdmx00GenlockFrameDelay OBJECT-TYPE
		SYNTAX		INTEGER {
							val_0_Frame_Delay(0),
							val_1_Frame_Delay(1),
							val_2_Frame_Delay(2)
							}
		MAX-ACCESS		read-write
		STATUS			current
		DESCRIPTION
				"TYPE: - Button
				 PAGE: - Genlock
					0 Frame Delay  cmdID= 2973  value= 0  
					1 Frame Delay  cmdID= 2973  value= 1  
					2 Frame Delay  cmdID= 2973  value= 2  "
		::= { iqdmx00CmdEntry 2973 }


	iqdmx00GenlockDelayPhase625HPhase OBJECT-TYPE
		SYNTAX		INTEGER
		MAX-ACCESS		read-write
		STATUS			current
		DESCRIPTION
				"TYPE: - Number
				 PAGE: - Genlock
					625 H Phase  cmdID= 2974  min= 0  max= 63962899  step= -28499  format=  %.0fns  div_scale= 1000 
					Min =  0ns  Max =  63963ns  Step =  -28ns "
		::= { iqdmx00CmdEntry 2974 }


	iqdmx00GenlockDelayPhase625VPhase OBJECT-TYPE
		SYNTAX		INTEGER
		MAX-ACCESS		read-write
		STATUS			current
		DESCRIPTION
				"TYPE: - Number
				 PAGE: - Genlock
					625 V Phase  cmdID= 2975  min= 0  max= 624  step= 1  format=  %.0flines  div_scale= 1 
					Min =  0lines  Max =  624lines  Step =  1lines "
		::= { iqdmx00CmdEntry 2975 }


	iqdmx00GenlockDelayPhase525HPhase OBJECT-TYPE
		SYNTAX		INTEGER
		MAX-ACCESS		read-write
		STATUS			current
		DESCRIPTION
				"TYPE: - Number
				 PAGE: - Genlock
					525 H Phase  cmdID= 2976  min= 0  max= 63518455  step= -28499  format=  %.0fns  div_scale= 1000 
					Min =  0ns  Max =  63518ns  Step =  -28ns "
		::= { iqdmx00CmdEntry 2976 }


	iqdmx00GenlockDelayPhase525VPhase OBJECT-TYPE
		SYNTAX		INTEGER
		MAX-ACCESS		read-write
		STATUS			current
		DESCRIPTION
				"TYPE: - Number
				 PAGE: - Genlock
					525 V Phase  cmdID= 2977  min= 0  max= 524  step= 1  format=  %.0flines  div_scale= 1 
					Min =  0lines  Max =  524lines  Step =  1lines "
		::= { iqdmx00CmdEntry 2977 }


	iqdmx00UserMemMemory1Save1 OBJECT-TYPE
		SYNTAX		INTEGER { noAction(0),val_Save_1(1) }
		MAX-ACCESS		read-write
		STATUS			current
		DESCRIPTION
				"TYPE: - Button
				 PAGE: - User Mem
					Save 1  cmdID= 1600  value= 1  "
		::= { iqdmx00CmdEntry 1600 }


	iqdmx00UserMemMemory1Recall1 OBJECT-TYPE
		SYNTAX		INTEGER { noAction(0),val_Recall_1(1) }
		MAX-ACCESS		read-write
		STATUS			current
		DESCRIPTION
				"TYPE: - Button
				 PAGE: - User Mem
					Recall 1  cmdID= 1601  value= 1  "
		::= { iqdmx00CmdEntry 1601 }


	iqdmx00UserMemMemory1Clear1 OBJECT-TYPE
		SYNTAX		INTEGER { noAction(0),val_Clear_1(1) }
		MAX-ACCESS		read-write
		STATUS			current
		DESCRIPTION
				"TYPE: - Button
				 PAGE: - User Mem
					Clear 1  cmdID= 1602  value= 1  "
		::= { iqdmx00CmdEntry 1602 }


	iqdmx00UserMemMemory1Name1 OBJECT-TYPE
		SYNTAX		RollCallString
		MAX-ACCESS		read-write
		STATUS			current
		DESCRIPTION
				"TYPE: - Editstring
				 PAGE: - User Mem
					Name 1  cmdID= 1603  "
		::= { iqdmx00CmdEntry 1603 }


	iqdmx00UserMemMemory2Save2 OBJECT-TYPE
		SYNTAX		INTEGER { noAction(0),val_Save_2(1) }
		MAX-ACCESS		read-write
		STATUS			current
		DESCRIPTION
				"TYPE: - Button
				 PAGE: - User Mem
					Save 2  cmdID= 1604  value= 1  "
		::= { iqdmx00CmdEntry 1604 }


	iqdmx00UserMemMemory2Recall2 OBJECT-TYPE
		SYNTAX		INTEGER { noAction(0),val_Recall_2(1) }
		MAX-ACCESS		read-write
		STATUS			current
		DESCRIPTION
				"TYPE: - Button
				 PAGE: - User Mem
					Recall 2  cmdID= 1605  value= 1  "
		::= { iqdmx00CmdEntry 1605 }


	iqdmx00UserMemMemory2Clear2 OBJECT-TYPE
		SYNTAX		INTEGER { noAction(0),val_Clear_2(1) }
		MAX-ACCESS		read-write
		STATUS			current
		DESCRIPTION
				"TYPE: - Button
				 PAGE: - User Mem
					Clear 2  cmdID= 1606  value= 1  "
		::= { iqdmx00CmdEntry 1606 }


	iqdmx00UserMemMemory2Name2 OBJECT-TYPE
		SYNTAX		RollCallString
		MAX-ACCESS		read-write
		STATUS			current
		DESCRIPTION
				"TYPE: - Editstring
				 PAGE: - User Mem
					Name 2  cmdID= 1607  "
		::= { iqdmx00CmdEntry 1607 }


	iqdmx00UserMemMemory3Save3 OBJECT-TYPE
		SYNTAX		INTEGER { noAction(0),val_Save_3(1) }
		MAX-ACCESS		read-write
		STATUS			current
		DESCRIPTION
				"TYPE: - Button
				 PAGE: - User Mem
					Save 3  cmdID= 1608  value= 1  "
		::= { iqdmx00CmdEntry 1608 }


	iqdmx00UserMemMemory3Recall3 OBJECT-TYPE
		SYNTAX		INTEGER { noAction(0),val_Recall_3(1) }
		MAX-ACCESS		read-write
		STATUS			current
		DESCRIPTION
				"TYPE: - Button
				 PAGE: - User Mem
					Recall 3  cmdID= 1609  value= 1  "
		::= { iqdmx00CmdEntry 1609 }


	iqdmx00UserMemMemory3Clear3 OBJECT-TYPE
		SYNTAX		INTEGER { noAction(0),val_Clear_3(1) }
		MAX-ACCESS		read-write
		STATUS			current
		DESCRIPTION
				"TYPE: - Button
				 PAGE: - User Mem
					Clear 3  cmdID= 1610  value= 1  "
		::= { iqdmx00CmdEntry 1610 }


	iqdmx00UserMemMemory3Name3 OBJECT-TYPE
		SYNTAX		RollCallString
		MAX-ACCESS		read-write
		STATUS			current
		DESCRIPTION
				"TYPE: - Editstring
				 PAGE: - User Mem
					Name 3  cmdID= 1611  "
		::= { iqdmx00CmdEntry 1611 }


	iqdmx00UserMemMemory4Save4 OBJECT-TYPE
		SYNTAX		INTEGER { noAction(0),val_Save_4(1) }
		MAX-ACCESS		read-write
		STATUS			current
		DESCRIPTION
				"TYPE: - Button
				 PAGE: - User Mem
					Save 4  cmdID= 1612  value= 1  "
		::= { iqdmx00CmdEntry 1612 }


	iqdmx00UserMemMemory4Recall4 OBJECT-TYPE
		SYNTAX		INTEGER { noAction(0),val_Recall_4(1) }
		MAX-ACCESS		read-write
		STATUS			current
		DESCRIPTION
				"TYPE: - Button
				 PAGE: - User Mem
					Recall 4  cmdID= 1613  value= 1  "
		::= { iqdmx00CmdEntry 1613 }


	iqdmx00UserMemMemory4Clear4 OBJECT-TYPE
		SYNTAX		INTEGER { noAction(0),val_Clear_4(1) }
		MAX-ACCESS		read-write
		STATUS			current
		DESCRIPTION
				"TYPE: - Button
				 PAGE: - User Mem
					Clear 4  cmdID= 1614  value= 1  "
		::= { iqdmx00CmdEntry 1614 }


	iqdmx00UserMemMemory4Name4 OBJECT-TYPE
		SYNTAX		RollCallString
		MAX-ACCESS		read-write
		STATUS			current
		DESCRIPTION
				"TYPE: - Editstring
				 PAGE: - User Mem
					Name 4  cmdID= 1615  "
		::= { iqdmx00CmdEntry 1615 }


	iqdmx00UserMemMemory5Save5 OBJECT-TYPE
		SYNTAX		INTEGER { noAction(0),val_Save_5(1) }
		MAX-ACCESS		read-write
		STATUS			current
		DESCRIPTION
				"TYPE: - Button
				 PAGE: - User Mem
					Save 5  cmdID= 1616  value= 1  "
		::= { iqdmx00CmdEntry 1616 }


	iqdmx00UserMemMemory5Recall5 OBJECT-TYPE
		SYNTAX		INTEGER { noAction(0),val_Recall_5(1) }
		MAX-ACCESS		read-write
		STATUS			current
		DESCRIPTION
				"TYPE: - Button
				 PAGE: - User Mem
					Recall 5  cmdID= 1617  value= 1  "
		::= { iqdmx00CmdEntry 1617 }


	iqdmx00UserMemMemory5Clear5 OBJECT-TYPE
		SYNTAX		INTEGER { noAction(0),val_Clear_5(1) }
		MAX-ACCESS		read-write
		STATUS			current
		DESCRIPTION
				"TYPE: - Button
				 PAGE: - User Mem
					Clear 5  cmdID= 1618  value= 1  "
		::= { iqdmx00CmdEntry 1618 }


	iqdmx00UserMemMemory5Name5 OBJECT-TYPE
		SYNTAX		RollCallString
		MAX-ACCESS		read-write
		STATUS			current
		DESCRIPTION
				"TYPE: - Editstring
				 PAGE: - User Mem
					Name 5  cmdID= 1619  "
		::= { iqdmx00CmdEntry 1619 }


	iqdmx00UserMemMemory6Save6 OBJECT-TYPE
		SYNTAX		INTEGER { noAction(0),val_Save_6(1) }
		MAX-ACCESS		read-write
		STATUS			current
		DESCRIPTION
				"TYPE: - Button
				 PAGE: - User Mem
					Save 6  cmdID= 1620  value= 1  "
		::= { iqdmx00CmdEntry 1620 }


	iqdmx00UserMemMemory6Recall6 OBJECT-TYPE
		SYNTAX		INTEGER { noAction(0),val_Recall_6(1) }
		MAX-ACCESS		read-write
		STATUS			current
		DESCRIPTION
				"TYPE: - Button
				 PAGE: - User Mem
					Recall 6  cmdID= 1621  value= 1  "
		::= { iqdmx00CmdEntry 1621 }


	iqdmx00UserMemMemory6Clear6 OBJECT-TYPE
		SYNTAX		INTEGER { noAction(0),val_Clear_6(1) }
		MAX-ACCESS		read-write
		STATUS			current
		DESCRIPTION
				"TYPE: - Button
				 PAGE: - User Mem
					Clear 6  cmdID= 1622  value= 1  "
		::= { iqdmx00CmdEntry 1622 }


	iqdmx00UserMemMemory6Name6 OBJECT-TYPE
		SYNTAX		RollCallString
		MAX-ACCESS		read-write
		STATUS			current
		DESCRIPTION
				"TYPE: - Editstring
				 PAGE: - User Mem
					Name 6  cmdID= 1623  "
		::= { iqdmx00CmdEntry 1623 }


	iqdmx00UserMemMemory7Save7 OBJECT-TYPE
		SYNTAX		INTEGER { noAction(0),val_Save_7(1) }
		MAX-ACCESS		read-write
		STATUS			current
		DESCRIPTION
				"TYPE: - Button
				 PAGE: - User Mem
					Save 7  cmdID= 1624  value= 1  "
		::= { iqdmx00CmdEntry 1624 }


	iqdmx00UserMemMemory7Recall7 OBJECT-TYPE
		SYNTAX		INTEGER { noAction(0),val_Recall_7(1) }
		MAX-ACCESS		read-write
		STATUS			current
		DESCRIPTION
				"TYPE: - Button
				 PAGE: - User Mem
					Recall 7  cmdID= 1625  value= 1  "
		::= { iqdmx00CmdEntry 1625 }


	iqdmx00UserMemMemory7Clear7 OBJECT-TYPE
		SYNTAX		INTEGER { noAction(0),val_Clear_7(1) }
		MAX-ACCESS		read-write
		STATUS			current
		DESCRIPTION
				"TYPE: - Button
				 PAGE: - User Mem
					Clear 7  cmdID= 1626  value= 1  "
		::= { iqdmx00CmdEntry 1626 }


	iqdmx00UserMemMemory7Name7 OBJECT-TYPE
		SYNTAX		RollCallString
		MAX-ACCESS		read-write
		STATUS			current
		DESCRIPTION
				"TYPE: - Editstring
				 PAGE: - User Mem
					Name 7  cmdID= 1627  "
		::= { iqdmx00CmdEntry 1627 }


	iqdmx00UserMemMemory8Save8 OBJECT-TYPE
		SYNTAX		INTEGER { noAction(0),val_Save_8(1) }
		MAX-ACCESS		read-write
		STATUS			current
		DESCRIPTION
				"TYPE: - Button
				 PAGE: - User Mem
					Save 8  cmdID= 1628  value= 1  "
		::= { iqdmx00CmdEntry 1628 }


	iqdmx00UserMemMemory8Recall8 OBJECT-TYPE
		SYNTAX		INTEGER { noAction(0),val_Recall_8(1) }
		MAX-ACCESS		read-write
		STATUS			current
		DESCRIPTION
				"TYPE: - Button
				 PAGE: - User Mem
					Recall 8  cmdID= 1629  value= 1  "
		::= { iqdmx00CmdEntry 1629 }


	iqdmx00UserMemMemory8Clear8 OBJECT-TYPE
		SYNTAX		INTEGER { noAction(0),val_Clear_8(1) }
		MAX-ACCESS		read-write
		STATUS			current
		DESCRIPTION
				"TYPE: - Button
				 PAGE: - User Mem
					Clear 8  cmdID= 1630  value= 1  "
		::= { iqdmx00CmdEntry 1630 }


	iqdmx00UserMemMemory8Name8 OBJECT-TYPE
		SYNTAX		RollCallString
		MAX-ACCESS		read-write
		STATUS			current
		DESCRIPTION
				"TYPE: - Editstring
				 PAGE: - User Mem
					Name 8  cmdID= 1631  "
		::= { iqdmx00CmdEntry 1631 }


	iqdmx00SetupPatternAnimatedPattern OBJECT-TYPE
		SYNTAX		INTEGER { disable(0), enable(1) }
		MAX-ACCESS		read-write
		STATUS			current
		DESCRIPTION
				"TYPE: - Checkbox
				 PAGE: - Setup- Pattern
					Animated Pattern  cmdID= 2940 "
		::= { iqdmx00CmdEntry 2940 }


	iqdmx00SetupPatternEnablePattern OBJECT-TYPE
		SYNTAX		INTEGER { disable(0), enable(1) }
		MAX-ACCESS		read-write
		STATUS			current
		DESCRIPTION
				"TYPE: - Checkbox
				 PAGE: - Setup- Pattern
					Enable Pattern  cmdID= 1035 "
		::= { iqdmx00CmdEntry 1035 }


	iqdmx00SetupPattern OBJECT-TYPE
		SYNTAX		INTEGER {
							val_Black(0),
							val_EBU_Colour_Bars(1),
							val_100_Colour_Bars(2),
							val_Ramp(3),
							val_Multiburst(4),
							val_Pulse_Bar(5)
							}
		MAX-ACCESS		read-write
		STATUS			current
		DESCRIPTION
				"TYPE: - Button
				 PAGE: - Setup- Pattern
					Black  cmdID= 1036  value= 0  
					EBU Colour Bars  cmdID= 1036  value= 1  
					100% Colour Bars  cmdID= 1036  value= 2  
					Ramp  cmdID= 1036  value= 3  
					Multiburst  cmdID= 1036  value= 4  
					Pulse & Bar  cmdID= 1036  value= 5  "
		::= { iqdmx00CmdEntry 1036 }


	iqdmx00SetupCaptionEditCaption OBJECT-TYPE
		SYNTAX		RollCallString
		MAX-ACCESS		read-write
		STATUS			current
		DESCRIPTION
				"TYPE: - Editstring
				 PAGE: - Setup- Caption
					Edit Caption  cmdID= 1041  "
		::= { iqdmx00CmdEntry 1041 }


	iqdmx00SetupCaption OBJECT-TYPE
		SYNTAX		INTEGER {
							val_Caption_Off(0),
							val_Caption_On(1)
							}
		MAX-ACCESS		read-write
		STATUS			current
		DESCRIPTION
				"TYPE: - Button
				 PAGE: - Setup- Caption
					Caption Off  cmdID= 1037  value= 0  
					Caption On  cmdID= 1037  value= 1  "
		::= { iqdmx00CmdEntry 1037 }


	iqdmx00BlankingVIPass525BlankAll OBJECT-TYPE
		SYNTAX		INTEGER { noAction(0),val_Blank_All(1) }
		MAX-ACCESS		read-write
		STATUS			current
		DESCRIPTION
				"TYPE: - Button
				 PAGE: - Setup- Blanking
					Blank All  cmdID= 1298  value= 1  "
		::= { iqdmx00CmdEntry 1298 }


	iqdmx00BlankingVIPass525PassAll OBJECT-TYPE
		SYNTAX		INTEGER { noAction(0),val_Pass_All(1) }
		MAX-ACCESS		read-write
		STATUS			current
		DESCRIPTION
				"TYPE: - Button
				 PAGE: - Setup- Blanking
					Pass All  cmdID= 1297  value= 1  "
		::= { iqdmx00CmdEntry 1297 }


	iqdmx00BlankingVIPass525Line11 OBJECT-TYPE
		SYNTAX		INTEGER { disable(0), enable(1) }
		MAX-ACCESS		read-write
		STATUS			current
		DESCRIPTION
				"TYPE: - Checkbox
				 PAGE: - Setup- Blanking
					Line 11  cmdID= 1211 "
		::= { iqdmx00CmdEntry 1211 }


	iqdmx00BlankingVIPass525Line274 OBJECT-TYPE
		SYNTAX		INTEGER { disable(0), enable(1) }
		MAX-ACCESS		read-write
		STATUS			current
		DESCRIPTION
				"TYPE: - Checkbox
				 PAGE: - Setup- Blanking
					Line 274  cmdID= 1231 "
		::= { iqdmx00CmdEntry 1231 }


	iqdmx00BlankingVIPass525Line12 OBJECT-TYPE
		SYNTAX		INTEGER { disable(0), enable(1) }
		MAX-ACCESS		read-write
		STATUS			current
		DESCRIPTION
				"TYPE: - Checkbox
				 PAGE: - Setup- Blanking
					Line 12  cmdID= 1212 "
		::= { iqdmx00CmdEntry 1212 }


	iqdmx00BlankingVIPass525Line275 OBJECT-TYPE
		SYNTAX		INTEGER { disable(0), enable(1) }
		MAX-ACCESS		read-write
		STATUS			current
		DESCRIPTION
				"TYPE: - Checkbox
				 PAGE: - Setup- Blanking
					Line 275  cmdID= 1232 "
		::= { iqdmx00CmdEntry 1232 }


	iqdmx00BlankingVIPass525Line13 OBJECT-TYPE
		SYNTAX		INTEGER { disable(0), enable(1) }
		MAX-ACCESS		read-write
		STATUS			current
		DESCRIPTION
				"TYPE: - Checkbox
				 PAGE: - Setup- Blanking
					Line 13  cmdID= 1213 "
		::= { iqdmx00CmdEntry 1213 }


	iqdmx00BlankingVIPass525Line276 OBJECT-TYPE
		SYNTAX		INTEGER { disable(0), enable(1) }
		MAX-ACCESS		read-write
		STATUS			current
		DESCRIPTION
				"TYPE: - Checkbox
				 PAGE: - Setup- Blanking
					Line 276  cmdID= 1233 "
		::= { iqdmx00CmdEntry 1233 }


	iqdmx00BlankingVIPass525Line14 OBJECT-TYPE
		SYNTAX		INTEGER { disable(0), enable(1) }
		MAX-ACCESS		read-write
		STATUS			current
		DESCRIPTION
				"TYPE: - Checkbox
				 PAGE: - Setup- Blanking
					Line 14  cmdID= 1214 "
		::= { iqdmx00CmdEntry 1214 }


	iqdmx00BlankingVIPass525Line277 OBJECT-TYPE
		SYNTAX		INTEGER { disable(0), enable(1) }
		MAX-ACCESS		read-write
		STATUS			current
		DESCRIPTION
				"TYPE: - Checkbox
				 PAGE: - Setup- Blanking
					Line 277  cmdID= 1234 "
		::= { iqdmx00CmdEntry 1234 }


	iqdmx00BlankingVIPass525Line15 OBJECT-TYPE
		SYNTAX		INTEGER { disable(0), enable(1) }
		MAX-ACCESS		read-write
		STATUS			current
		DESCRIPTION
				"TYPE: - Checkbox
				 PAGE: - Setup- Blanking
					Line 15  cmdID= 1215 "
		::= { iqdmx00CmdEntry 1215 }


	iqdmx00BlankingVIPass525Line278 OBJECT-TYPE
		SYNTAX		INTEGER { disable(0), enable(1) }
		MAX-ACCESS		read-write
		STATUS			current
		DESCRIPTION
				"TYPE: - Checkbox
				 PAGE: - Setup- Blanking
					Line 278  cmdID= 1235 "
		::= { iqdmx00CmdEntry 1235 }


	iqdmx00BlankingVIPass525Line16 OBJECT-TYPE
		SYNTAX		INTEGER { disable(0), enable(1) }
		MAX-ACCESS		read-write
		STATUS			current
		DESCRIPTION
				"TYPE: - Checkbox
				 PAGE: - Setup- Blanking
					Line 16  cmdID= 1216 "
		::= { iqdmx00CmdEntry 1216 }


	iqdmx00BlankingVIPass525Line279 OBJECT-TYPE
		SYNTAX		INTEGER { disable(0), enable(1) }
		MAX-ACCESS		read-write
		STATUS			current
		DESCRIPTION
				"TYPE: - Checkbox
				 PAGE: - Setup- Blanking
					Line 279  cmdID= 1236 "
		::= { iqdmx00CmdEntry 1236 }


	iqdmx00BlankingVIPass525Line17 OBJECT-TYPE
		SYNTAX		INTEGER { disable(0), enable(1) }
		MAX-ACCESS		read-write
		STATUS			current
		DESCRIPTION
				"TYPE: - Checkbox
				 PAGE: - Setup- Blanking
					Line 17  cmdID= 1217 "
		::= { iqdmx00CmdEntry 1217 }


	iqdmx00BlankingVIPass525Line280 OBJECT-TYPE
		SYNTAX		INTEGER { disable(0), enable(1) }
		MAX-ACCESS		read-write
		STATUS			current
		DESCRIPTION
				"TYPE: - Checkbox
				 PAGE: - Setup- Blanking
					Line 280  cmdID= 1237 "
		::= { iqdmx00CmdEntry 1237 }


	iqdmx00BlankingVIPass525Line18 OBJECT-TYPE
		SYNTAX		INTEGER { disable(0), enable(1) }
		MAX-ACCESS		read-write
		STATUS			current
		DESCRIPTION
				"TYPE: - Checkbox
				 PAGE: - Setup- Blanking
					Line 18  cmdID= 1218 "
		::= { iqdmx00CmdEntry 1218 }


	iqdmx00BlankingVIPass525Line281 OBJECT-TYPE
		SYNTAX		INTEGER { disable(0), enable(1) }
		MAX-ACCESS		read-write
		STATUS			current
		DESCRIPTION
				"TYPE: - Checkbox
				 PAGE: - Setup- Blanking
					Line 281  cmdID= 1238 "
		::= { iqdmx00CmdEntry 1238 }


	iqdmx00BlankingVIPass525Line19 OBJECT-TYPE
		SYNTAX		INTEGER { disable(0), enable(1) }
		MAX-ACCESS		read-write
		STATUS			current
		DESCRIPTION
				"TYPE: - Checkbox
				 PAGE: - Setup- Blanking
					Line 19  cmdID= 1219 "
		::= { iqdmx00CmdEntry 1219 }


	iqdmx00BlankingVIPass525Line282 OBJECT-TYPE
		SYNTAX		INTEGER { disable(0), enable(1) }
		MAX-ACCESS		read-write
		STATUS			current
		DESCRIPTION
				"TYPE: - Checkbox
				 PAGE: - Setup- Blanking
					Line 282  cmdID= 1239 "
		::= { iqdmx00CmdEntry 1239 }


	iqdmx00BlankingVIPass525Line20 OBJECT-TYPE
		SYNTAX		INTEGER { disable(0), enable(1) }
		MAX-ACCESS		read-write
		STATUS			current
		DESCRIPTION
				"TYPE: - Checkbox
				 PAGE: - Setup- Blanking
					Line 20  cmdID= 1220 "
		::= { iqdmx00CmdEntry 1220 }


	iqdmx00BlankingVIPass525Line283 OBJECT-TYPE
		SYNTAX		INTEGER { disable(0), enable(1) }
		MAX-ACCESS		read-write
		STATUS			current
		DESCRIPTION
				"TYPE: - Checkbox
				 PAGE: - Setup- Blanking
					Line 283  cmdID= 1240 "
		::= { iqdmx00CmdEntry 1240 }


	iqdmx00BlankingVIPass525Line21 OBJECT-TYPE
		SYNTAX		INTEGER { disable(0), enable(1) }
		MAX-ACCESS		read-write
		STATUS			current
		DESCRIPTION
				"TYPE: - Checkbox
				 PAGE: - Setup- Blanking
					Line 21  cmdID= 1221 "
		::= { iqdmx00CmdEntry 1221 }


	iqdmx00BlankingVIPass625BlankAll OBJECT-TYPE
		SYNTAX		INTEGER { noAction(0),val_Blank_All(1) }
		MAX-ACCESS		read-write
		STATUS			current
		DESCRIPTION
				"TYPE: - Button
				 PAGE: - Setup- Blanking
					Blank All  cmdID= 1296  value= 1  "
		::= { iqdmx00CmdEntry 1296 }


	iqdmx00BlankingVIPass625PassAll OBJECT-TYPE
		SYNTAX		INTEGER { noAction(0),val_Pass_All(1) }
		MAX-ACCESS		read-write
		STATUS			current
		DESCRIPTION
				"TYPE: - Button
				 PAGE: - Setup- Blanking
					Pass All  cmdID= 1295  value= 1  "
		::= { iqdmx00CmdEntry 1295 }


	iqdmx00BlankingVIPass625Line7 OBJECT-TYPE
		SYNTAX		INTEGER { disable(0), enable(1) }
		MAX-ACCESS		read-write
		STATUS			current
		DESCRIPTION
				"TYPE: - Checkbox
				 PAGE: - Setup- Blanking
					Line 7  cmdID= 1251 "
		::= { iqdmx00CmdEntry 1251 }


	iqdmx00BlankingVIPass625Line320 OBJECT-TYPE
		SYNTAX		INTEGER { disable(0), enable(1) }
		MAX-ACCESS		read-write
		STATUS			current
		DESCRIPTION
				"TYPE: - Checkbox
				 PAGE: - Setup- Blanking
					Line 320  cmdID= 1272 "
		::= { iqdmx00CmdEntry 1272 }


	iqdmx00BlankingVIPass625Line8 OBJECT-TYPE
		SYNTAX		INTEGER { disable(0), enable(1) }
		MAX-ACCESS		read-write
		STATUS			current
		DESCRIPTION
				"TYPE: - Checkbox
				 PAGE: - Setup- Blanking
					Line 8  cmdID= 1252 "
		::= { iqdmx00CmdEntry 1252 }


	iqdmx00BlankingVIPass625Line321 OBJECT-TYPE
		SYNTAX		INTEGER { disable(0), enable(1) }
		MAX-ACCESS		read-write
		STATUS			current
		DESCRIPTION
				"TYPE: - Checkbox
				 PAGE: - Setup- Blanking
					Line 321  cmdID= 1273 "
		::= { iqdmx00CmdEntry 1273 }


	iqdmx00BlankingVIPass625Line9 OBJECT-TYPE
		SYNTAX		INTEGER { disable(0), enable(1) }
		MAX-ACCESS		read-write
		STATUS			current
		DESCRIPTION
				"TYPE: - Checkbox
				 PAGE: - Setup- Blanking
					Line 9  cmdID= 1253 "
		::= { iqdmx00CmdEntry 1253 }


	iqdmx00BlankingVIPass625Line322 OBJECT-TYPE
		SYNTAX		INTEGER { disable(0), enable(1) }
		MAX-ACCESS		read-write
		STATUS			current
		DESCRIPTION
				"TYPE: - Checkbox
				 PAGE: - Setup- Blanking
					Line 322  cmdID= 1274 "
		::= { iqdmx00CmdEntry 1274 }


	iqdmx00BlankingVIPass625Line10 OBJECT-TYPE
		SYNTAX		INTEGER { disable(0), enable(1) }
		MAX-ACCESS		read-write
		STATUS			current
		DESCRIPTION
				"TYPE: - Checkbox
				 PAGE: - Setup- Blanking
					Line 10  cmdID= 1254 "
		::= { iqdmx00CmdEntry 1254 }


	iqdmx00BlankingVIPass625Line323 OBJECT-TYPE
		SYNTAX		INTEGER { disable(0), enable(1) }
		MAX-ACCESS		read-write
		STATUS			current
		DESCRIPTION
				"TYPE: - Checkbox
				 PAGE: - Setup- Blanking
					Line 323  cmdID= 1275 "
		::= { iqdmx00CmdEntry 1275 }


	iqdmx00BlankingVIPass625Line11 OBJECT-TYPE
		SYNTAX		INTEGER { disable(0), enable(1) }
		MAX-ACCESS		read-write
		STATUS			current
		DESCRIPTION
				"TYPE: - Checkbox
				 PAGE: - Setup- Blanking
					Line 11  cmdID= 1255 "
		::= { iqdmx00CmdEntry 1255 }


	iqdmx00BlankingVIPass625Line324 OBJECT-TYPE
		SYNTAX		INTEGER { disable(0), enable(1) }
		MAX-ACCESS		read-write
		STATUS			current
		DESCRIPTION
				"TYPE: - Checkbox
				 PAGE: - Setup- Blanking
					Line 324  cmdID= 1276 "
		::= { iqdmx00CmdEntry 1276 }


	iqdmx00BlankingVIPass625Line12 OBJECT-TYPE
		SYNTAX		INTEGER { disable(0), enable(1) }
		MAX-ACCESS		read-write
		STATUS			current
		DESCRIPTION
				"TYPE: - Checkbox
				 PAGE: - Setup- Blanking
					Line 12  cmdID= 1256 "
		::= { iqdmx00CmdEntry 1256 }


	iqdmx00BlankingVIPass625Line325 OBJECT-TYPE
		SYNTAX		INTEGER { disable(0), enable(1) }
		MAX-ACCESS		read-write
		STATUS			current
		DESCRIPTION
				"TYPE: - Checkbox
				 PAGE: - Setup- Blanking
					Line 325  cmdID= 1277 "
		::= { iqdmx00CmdEntry 1277 }


	iqdmx00BlankingVIPass625Line13 OBJECT-TYPE
		SYNTAX		INTEGER { disable(0), enable(1) }
		MAX-ACCESS		read-write
		STATUS			current
		DESCRIPTION
				"TYPE: - Checkbox
				 PAGE: - Setup- Blanking
					Line 13  cmdID= 1257 "
		::= { iqdmx00CmdEntry 1257 }


	iqdmx00BlankingVIPass625Line326 OBJECT-TYPE
		SYNTAX		INTEGER { disable(0), enable(1) }
		MAX-ACCESS		read-write
		STATUS			current
		DESCRIPTION
				"TYPE: - Checkbox
				 PAGE: - Setup- Blanking
					Line 326  cmdID= 1278 "
		::= { iqdmx00CmdEntry 1278 }


	iqdmx00BlankingVIPass625Line14 OBJECT-TYPE
		SYNTAX		INTEGER { disable(0), enable(1) }
		MAX-ACCESS		read-write
		STATUS			current
		DESCRIPTION
				"TYPE: - Checkbox
				 PAGE: - Setup- Blanking
					Line 14  cmdID= 1258 "
		::= { iqdmx00CmdEntry 1258 }


	iqdmx00BlankingVIPass625Line327 OBJECT-TYPE
		SYNTAX		INTEGER { disable(0), enable(1) }
		MAX-ACCESS		read-write
		STATUS			current
		DESCRIPTION
				"TYPE: - Checkbox
				 PAGE: - Setup- Blanking
					Line 327  cmdID= 1279 "
		::= { iqdmx00CmdEntry 1279 }


	iqdmx00BlankingVIPass625Line15 OBJECT-TYPE
		SYNTAX		INTEGER { disable(0), enable(1) }
		MAX-ACCESS		read-write
		STATUS			current
		DESCRIPTION
				"TYPE: - Checkbox
				 PAGE: - Setup- Blanking
					Line 15  cmdID= 1259 "
		::= { iqdmx00CmdEntry 1259 }


	iqdmx00BlankingVIPass625Line328 OBJECT-TYPE
		SYNTAX		INTEGER { disable(0), enable(1) }
		MAX-ACCESS		read-write
		STATUS			current
		DESCRIPTION
				"TYPE: - Checkbox
				 PAGE: - Setup- Blanking
					Line 328  cmdID= 1280 "
		::= { iqdmx00CmdEntry 1280 }


	iqdmx00BlankingVIPass625Line16 OBJECT-TYPE
		SYNTAX		INTEGER { disable(0), enable(1) }
		MAX-ACCESS		read-write
		STATUS			current
		DESCRIPTION
				"TYPE: - Checkbox
				 PAGE: - Setup- Blanking
					Line 16  cmdID= 1260 "
		::= { iqdmx00CmdEntry 1260 }


	iqdmx00BlankingVIPass625Line329 OBJECT-TYPE
		SYNTAX		INTEGER { disable(0), enable(1) }
		MAX-ACCESS		read-write
		STATUS			current
		DESCRIPTION
				"TYPE: - Checkbox
				 PAGE: - Setup- Blanking
					Line 329  cmdID= 1281 "
		::= { iqdmx00CmdEntry 1281 }


	iqdmx00BlankingVIPass625Line17 OBJECT-TYPE
		SYNTAX		INTEGER { disable(0), enable(1) }
		MAX-ACCESS		read-write
		STATUS			current
		DESCRIPTION
				"TYPE: - Checkbox
				 PAGE: - Setup- Blanking
					Line 17  cmdID= 1261 "
		::= { iqdmx00CmdEntry 1261 }


	iqdmx00BlankingVIPass625Line330 OBJECT-TYPE
		SYNTAX		INTEGER { disable(0), enable(1) }
		MAX-ACCESS		read-write
		STATUS			current
		DESCRIPTION
				"TYPE: - Checkbox
				 PAGE: - Setup- Blanking
					Line 330  cmdID= 1282 "
		::= { iqdmx00CmdEntry 1282 }


	iqdmx00BlankingVIPass625Line18 OBJECT-TYPE
		SYNTAX		INTEGER { disable(0), enable(1) }
		MAX-ACCESS		read-write
		STATUS			current
		DESCRIPTION
				"TYPE: - Checkbox
				 PAGE: - Setup- Blanking
					Line 18  cmdID= 1262 "
		::= { iqdmx00CmdEntry 1262 }


	iqdmx00BlankingVIPass625Line331 OBJECT-TYPE
		SYNTAX		INTEGER { disable(0), enable(1) }
		MAX-ACCESS		read-write
		STATUS			current
		DESCRIPTION
				"TYPE: - Checkbox
				 PAGE: - Setup- Blanking
					Line 331  cmdID= 1283 "
		::= { iqdmx00CmdEntry 1283 }


	iqdmx00BlankingVIPass625Line19 OBJECT-TYPE
		SYNTAX		INTEGER { disable(0), enable(1) }
		MAX-ACCESS		read-write
		STATUS			current
		DESCRIPTION
				"TYPE: - Checkbox
				 PAGE: - Setup- Blanking
					Line 19  cmdID= 1263 "
		::= { iqdmx00CmdEntry 1263 }


	iqdmx00BlankingVIPass625Line332 OBJECT-TYPE
		SYNTAX		INTEGER { disable(0), enable(1) }
		MAX-ACCESS		read-write
		STATUS			current
		DESCRIPTION
				"TYPE: - Checkbox
				 PAGE: - Setup- Blanking
					Line 332  cmdID= 1284 "
		::= { iqdmx00CmdEntry 1284 }


	iqdmx00BlankingVIPass625Line20 OBJECT-TYPE
		SYNTAX		INTEGER { disable(0), enable(1) }
		MAX-ACCESS		read-write
		STATUS			current
		DESCRIPTION
				"TYPE: - Checkbox
				 PAGE: - Setup- Blanking
					Line 20  cmdID= 1264 "
		::= { iqdmx00CmdEntry 1264 }


	iqdmx00BlankingVIPass625Line333 OBJECT-TYPE
		SYNTAX		INTEGER { disable(0), enable(1) }
		MAX-ACCESS		read-write
		STATUS			current
		DESCRIPTION
				"TYPE: - Checkbox
				 PAGE: - Setup- Blanking
					Line 333  cmdID= 1285 "
		::= { iqdmx00CmdEntry 1285 }


	iqdmx00BlankingVIPass625Line21 OBJECT-TYPE
		SYNTAX		INTEGER { disable(0), enable(1) }
		MAX-ACCESS		read-write
		STATUS			current
		DESCRIPTION
				"TYPE: - Checkbox
				 PAGE: - Setup- Blanking
					Line 21  cmdID= 1265 "
		::= { iqdmx00CmdEntry 1265 }


	iqdmx00BlankingVIPass625Line334 OBJECT-TYPE
		SYNTAX		INTEGER { disable(0), enable(1) }
		MAX-ACCESS		read-write
		STATUS			current
		DESCRIPTION
				"TYPE: - Checkbox
				 PAGE: - Setup- Blanking
					Line 334  cmdID= 1286 "
		::= { iqdmx00CmdEntry 1286 }


	iqdmx00BlankingVIPass625Line22 OBJECT-TYPE
		SYNTAX		INTEGER { disable(0), enable(1) }
		MAX-ACCESS		read-write
		STATUS			current
		DESCRIPTION
				"TYPE: - Checkbox
				 PAGE: - Setup- Blanking
					Line 22  cmdID= 1266 "
		::= { iqdmx00CmdEntry 1266 }


	iqdmx00BlankingVIPass625Line335 OBJECT-TYPE
		SYNTAX		INTEGER { disable(0), enable(1) }
		MAX-ACCESS		read-write
		STATUS			current
		DESCRIPTION
				"TYPE: - Checkbox
				 PAGE: - Setup- Blanking
					Line 335  cmdID= 1287 "
		::= { iqdmx00CmdEntry 1287 }


	iqdmx00BlankingVIPass625Line23 OBJECT-TYPE
		SYNTAX		INTEGER { disable(0), enable(1) }
		MAX-ACCESS		read-write
		STATUS			current
		DESCRIPTION
				"TYPE: - Checkbox
				 PAGE: - Setup- Blanking
					Line 23  cmdID= 1267 "
		::= { iqdmx00CmdEntry 1267 }


	iqdmx00SetupBlankingHancBlank OBJECT-TYPE
		SYNTAX		INTEGER { disable(0), enable(1) }
		MAX-ACCESS		read-write
		STATUS			current
		DESCRIPTION
				"TYPE: - Checkbox
				 PAGE: - Setup- Blanking
					Hanc Blank  cmdID= 2971 "
		::= { iqdmx00CmdEntry 2971 }


	iqdmx00SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqdmx00CmdEntry 2489 }


	iqdmx00SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1 
					Min = 100.0 Hz  Max = 15000.0 Hz  Step = 100.0 Hz "
		::= { iqdmx00CmdEntry 2487 }


	iqdmx00SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1 
					Min = 100.0 Hz  Max = 15000.0 Hz  Step = 100.0 Hz "
		::= { iqdmx00CmdEntry 2488 }


	iqdmx00SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1 
					Min = 4.0 dB  Max = 24.0 dB  Step = 1.0 dB "
		::= { iqdmx00CmdEntry 3055 }


	iqdmx00SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972 
					Instant  value= 0  
					Fast  value= 1  
					Medium  value= 2  
					Slow  value= 3  
					Slowest  value= 4  "
		::= { iqdmx00CmdEntry 2972 }


	iqdmx00SetupChannelStatus OBJECT-TYPE
		SYNTAX		RollCallString
		MAX-ACCESS		read-write
		STATUS			current
		DESCRIPTION
				"TYPE: - Editstring
				 PAGE: - Setup
					Channel Status  cmdID= 3060  "
		::= { iqdmx00CmdEntry 3060 }


	iqdmx00GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqdmx00CmdEntry 2605 }


	iqdmx00GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqdmx00CmdEntry 3053 }


	iqdmx00GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqdmx00CmdEntry 3054 }


	iqdmx00GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 12  step= 1  format= %.0f  div_scale= 1 
					Min = -1  Max = 12  Step = 1 "
		::= { iqdmx00CmdEntry 2011 }


	iqdmx00GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqdmx00CmdEntry 2048 }


	iqdmx00GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqdmx00CmdEntry 3540 }


	iqdmx00GPIIOGPIOutputOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2013 
					Input Present  value= 0  
					Standard 625  value= 1  
					Video Delay  value= 2  
					Unused  value= 3  "
		::= { iqdmx00CmdEntry 2013 }


	iqdmx00GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqdmx00CmdEntry 2049 }


	iqdmx00GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqdmx00CmdEntry 2014 }


	iqdmx00SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 12  step= 1  format= %.0f  div_scale= 1 
					Min = -1  Max = 12  Step = 1 "
		::= { iqdmx00CmdEntry 2875 }


	iqdmx00SetupGPIIOOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2877 
					Input Present  value= 0  
					Standard 625  value= 1  
					Video Delay  value= 2  
					Unused  value= 3  "
		::= { iqdmx00CmdEntry 2877 }


	iqdmx00SetupRollTrackRollTrackIndex OBJECT-TYPE
		SYNTAX		INTEGER
		MAX-ACCESS		read-write
		STATUS			current
		DESCRIPTION
				"TYPE: - Number
				 PAGE: - Setup- RollTrack
					RollTrack Index  cmdID= 1495  min= 0  max= 49  step= 1  format= %.0f  div_scale= 1 
					Min = 0  Max = 49  Step = 1 "
		::= { iqdmx00CmdEntry 1495 }


	iqdmx00SetupRollTrackRollTrackSource OBJECT-TYPE
		SYNTAX		INTEGER
		MAX-ACCESS		read-write
		STATUS			current
		DESCRIPTION
				"TYPE: - Number
				 PAGE: - Setup- RollTrack
					RollTrack Source  cmdID= 1496  min= -1  max= 35  step= 1  format= %.0f  div_scale= 1 
					Min = -1  Max = 35  Step = 1 "
		::= { iqdmx00CmdEntry 1496 }


	iqdmx00SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqdmx00CmdEntry 1513 }


	iqdmx00SetupRollTrackRollTrackAddress OBJECT-TYPE
		SYNTAX		RollCallString
		MAX-ACCESS		read-write
		STATUS			current
		DESCRIPTION
				"TYPE: - Editstring
				 PAGE: - Setup- RollTrack
					RollTrack Address  cmdID= 1497  "
		::= { iqdmx00CmdEntry 1497 }


	iqdmx00SetupRollTrackRollTrackCommand OBJECT-TYPE
		SYNTAX		RollCallString
		MAX-ACCESS		read-write
		STATUS			current
		DESCRIPTION
				"TYPE: - Editstring
				 PAGE: - Setup- RollTrack
					RollTrack Command  cmdID= 1498  "
		::= { iqdmx00CmdEntry 1498 }


	iqdmx00SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqdmx00CmdEntry 1514 }


	iqdmx00SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqdmx00CmdEntry 1511 }


	iqdmx00SetupRollTrackRollTrack_Index OBJECT-TYPE
		SYNTAX		INTEGER
		MAX-ACCESS		read-write
		STATUS			current
		DESCRIPTION
				"TYPE: - Number
				 PAGE: - Setup- RollTrack
					RollTrack Index  cmdID= 2870  min= 0  max= 49  step= 1  format= %.0f  div_scale= 1 
					Min = 0  Max = 49  Step = 1 "
		::= { iqdmx00CmdEntry 2870 }


	iqdmx00SetupRollTrackRollTrack_Source OBJECT-TYPE
		SYNTAX		INTEGER
		MAX-ACCESS		read-write
		STATUS			current
		DESCRIPTION
				"TYPE: - Number
				 PAGE: - Setup- RollTrack
					RollTrack Source  cmdID= 2871  min= -1  max= 35  step= 1  format= %.0f  div_scale= 1 
					Min = -1  Max = 35  Step = 1 "
		::= { iqdmx00CmdEntry 2871 }


	iqdmx00SetupRollTrackRollTrack_Address OBJECT-TYPE
		SYNTAX		RollCallString
		MAX-ACCESS		read-write
		STATUS			current
		DESCRIPTION
				"TYPE: - Editstring
				 PAGE: - Setup- RollTrack
					RollTrack Address  cmdID= 2872  "
		::= { iqdmx00CmdEntry 2872 }


	iqdmx00SetupRollTrackRollTrack_Command OBJECT-TYPE
		SYNTAX		RollCallString
		MAX-ACCESS		read-write
		STATUS			current
		DESCRIPTION
				"TYPE: - Editstring
				 PAGE: - Setup- RollTrack
					RollTrack Command  cmdID= 2873  "
		::= { iqdmx00CmdEntry 2873 }


	iqdmx00SetupLoggingInput OBJECT-TYPE
		SYNTAX		INTEGER { disable(0), enable(1) }
		MAX-ACCESS		read-write
		STATUS			current
		DESCRIPTION
				"TYPE: - Checkbox
				 PAGE: - Setup- Logging
					Input  cmdID= 1060 "
		::= { iqdmx00CmdEntry 1060 }


	iqdmx00SetupLoggingStd OBJECT-TYPE
		SYNTAX		INTEGER { disable(0), enable(1) }
		MAX-ACCESS		read-write
		STATUS			current
		DESCRIPTION
				"TYPE: - Checkbox
				 PAGE: - Setup- Logging
					Std  cmdID= 1061 "
		::= { iqdmx00CmdEntry 1061 }


	iqdmx00SetupLoggingInput1 OBJECT-TYPE
		SYNTAX		INTEGER { disable(0), enable(1) }
		MAX-ACCESS		read-write
		STATUS			current
		DESCRIPTION
				"TYPE: - Checkbox
				 PAGE: - Setup- Logging
					Input1  cmdID= 1094 "
		::= { iqdmx00CmdEntry 1094 }


	iqdmx00SetupLoggingStd1 OBJECT-TYPE
		SYNTAX		INTEGER { disable(0), enable(1) }
		MAX-ACCESS		read-write
		STATUS			current
		DESCRIPTION
				"TYPE: - Checkbox
				 PAGE: - Setup- Logging
					Std1  cmdID= 1097 "
		::= { iqdmx00CmdEntry 1097 }


	iqdmx00SetupLoggingInput2 OBJECT-TYPE
		SYNTAX		INTEGER { disable(0), enable(1) }
		MAX-ACCESS		read-write
		STATUS			current
		DESCRIPTION
				"TYPE: - Checkbox
				 PAGE: - Setup- Logging
					Input2  cmdID= 1095 "
		::= { iqdmx00CmdEntry 1095 }


	iqdmx00SetupLoggingStd2 OBJECT-TYPE
		SYNTAX		INTEGER { disable(0), enable(1) }
		MAX-ACCESS		read-write
		STATUS			current
		DESCRIPTION
				"TYPE: - Checkbox
				 PAGE: - Setup- Logging
					Std2  cmdID= 1098 "
		::= { iqdmx00CmdEntry 1098 }


	iqdmx00SetupLoggingReference OBJECT-TYPE
		SYNTAX		INTEGER { disable(0), enable(1) }
		MAX-ACCESS		read-write
		STATUS			current
		DESCRIPTION
				"TYPE: - Checkbox
				 PAGE: - Setup- Logging
					Reference  cmdID= 1062 "
		::= { iqdmx00CmdEntry 1062 }


	iqdmx00SetupLoggingEDH OBJECT-TYPE
		SYNTAX		INTEGER { disable(0), enable(1) }
		MAX-ACCESS		read-write
		STATUS			current
		DESCRIPTION
				"TYPE: - Checkbox
				 PAGE: - Setup- Logging
					EDH  cmdID= 1064 "
		::= { iqdmx00CmdEntry 1064 }


	iqdmx00SetupLoggingEDHErrors OBJECT-TYPE
		SYNTAX		INTEGER { disable(0), enable(1) }
		MAX-ACCESS		read-write
		STATUS			current
		DESCRIPTION
				"TYPE: - Checkbox
				 PAGE: - Setup- Logging
					EDH Errors  cmdID= 1070 "
		::= { iqdmx00CmdEntry 1070 }


	iqdmx00SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqdmx00CmdEntry 1106 }


	iqdmx00SetupLoggingDeembed1 OBJECT-TYPE
		SYNTAX		INTEGER { disable(0), enable(1) }
		MAX-ACCESS		read-write
		STATUS			current
		DESCRIPTION
				"TYPE: - Checkbox
				 PAGE: - Setup- Logging
					De-embed 1  cmdID= 1120 "
		::= { iqdmx00CmdEntry 1120 }


	iqdmx00SetupLoggingDeembed2 OBJECT-TYPE
		SYNTAX		INTEGER { disable(0), enable(1) }
		MAX-ACCESS		read-write
		STATUS			current
		DESCRIPTION
				"TYPE: - Checkbox
				 PAGE: - Setup- Logging
					De-embed 2  cmdID= 1121 "
		::= { iqdmx00CmdEntry 1121 }


	iqdmx00SetupLoggingDeembed3 OBJECT-TYPE
		SYNTAX		INTEGER { disable(0), enable(1) }
		MAX-ACCESS		read-write
		STATUS			current
		DESCRIPTION
				"TYPE: - Checkbox
				 PAGE: - Setup- Logging
					De-embed 3  cmdID= 1122 "
		::= { iqdmx00CmdEntry 1122 }


	iqdmx00SetupLoggingDeembed4 OBJECT-TYPE
		SYNTAX		INTEGER { disable(0), enable(1) }
		MAX-ACCESS		read-write
		STATUS			current
		DESCRIPTION
				"TYPE: - Checkbox
				 PAGE: - Setup- Logging
					De-embed 4  cmdID= 1123 "
		::= { iqdmx00CmdEntry 1123 }


	iqdmx00SetupLoggingDeembed5 OBJECT-TYPE
		SYNTAX		INTEGER { disable(0), enable(1) }
		MAX-ACCESS		read-write
		STATUS			current
		DESCRIPTION
				"TYPE: - Checkbox
				 PAGE: - Setup- Logging
					De-embed 5  cmdID= 1124 "
		::= { iqdmx00CmdEntry 1124 }


	iqdmx00SetupLoggingDeembed6 OBJECT-TYPE
		SYNTAX		INTEGER { disable(0), enable(1) }
		MAX-ACCESS		read-write
		STATUS			current
		DESCRIPTION
				"TYPE: - Checkbox
				 PAGE: - Setup- Logging
					De-embed 6  cmdID= 1125 "
		::= { iqdmx00CmdEntry 1125 }


	iqdmx00SetupLoggingDeembed7 OBJECT-TYPE
		SYNTAX		INTEGER { disable(0), enable(1) }
		MAX-ACCESS		read-write
		STATUS			current
		DESCRIPTION
				"TYPE: - Checkbox
				 PAGE: - Setup- Logging
					De-embed 7  cmdID= 1126 "
		::= { iqdmx00CmdEntry 1126 }


	iqdmx00SetupLoggingDeembed8 OBJECT-TYPE
		SYNTAX		INTEGER { disable(0), enable(1) }
		MAX-ACCESS		read-write
		STATUS			current
		DESCRIPTION
				"TYPE: - Checkbox
				 PAGE: - Setup- Logging
					De-embed 8  cmdID= 1127 "
		::= { iqdmx00CmdEntry 1127 }


	iqdmx00SetupLoggingnPCM1 OBJECT-TYPE
		SYNTAX		INTEGER { disable(0), enable(1) }
		MAX-ACCESS		read-write
		STATUS			current
		DESCRIPTION
				"TYPE: - Checkbox
				 PAGE: - Setup- Logging
					nPCM 1  cmdID= 1128 "
		::= { iqdmx00CmdEntry 1128 }


	iqdmx00SetupLoggingnPCM2 OBJECT-TYPE
		SYNTAX		INTEGER { disable(0), enable(1) }
		MAX-ACCESS		read-write
		STATUS			current
		DESCRIPTION
				"TYPE: - Checkbox
				 PAGE: - Setup- Logging
					nPCM 2  cmdID= 1129 "
		::= { iqdmx00CmdEntry 1129 }


	iqdmx00SetupLoggingnPCM3 OBJECT-TYPE
		SYNTAX		INTEGER { disable(0), enable(1) }
		MAX-ACCESS		read-write
		STATUS			current
		DESCRIPTION
				"TYPE: - Checkbox
				 PAGE: - Setup- Logging
					nPCM 3  cmdID= 1130 "
		::= { iqdmx00CmdEntry 1130 }


	iqdmx00SetupLoggingnPCM4 OBJECT-TYPE
		SYNTAX		INTEGER { disable(0), enable(1) }
		MAX-ACCESS		read-write
		STATUS			current
		DESCRIPTION
				"TYPE: - Checkbox
				 PAGE: - Setup- Logging
					nPCM 4  cmdID= 1131 "
		::= { iqdmx00CmdEntry 1131 }


	iqdmx00SetupLoggingnPCM5 OBJECT-TYPE
		SYNTAX		INTEGER { disable(0), enable(1) }
		MAX-ACCESS		read-write
		STATUS			current
		DESCRIPTION
				"TYPE: - Checkbox
				 PAGE: - Setup- Logging
					nPCM 5  cmdID= 1132 "
		::= { iqdmx00CmdEntry 1132 }


	iqdmx00SetupLoggingnPCM6 OBJECT-TYPE
		SYNTAX		INTEGER { disable(0), enable(1) }
		MAX-ACCESS		read-write
		STATUS			current
		DESCRIPTION
				"TYPE: - Checkbox
				 PAGE: - Setup- Logging
					nPCM 6  cmdID= 1133 "
		::= { iqdmx00CmdEntry 1133 }


	iqdmx00SetupLoggingnPCM7 OBJECT-TYPE
		SYNTAX		INTEGER { disable(0), enable(1) }
		MAX-ACCESS		read-write
		STATUS			current
		DESCRIPTION
				"TYPE: - Checkbox
				 PAGE: - Setup- Logging
					nPCM 7  cmdID= 1134 "
		::= { iqdmx00CmdEntry 1134 }


	iqdmx00SetupLoggingnPCM8 OBJECT-TYPE
		SYNTAX		INTEGER { disable(0), enable(1) }
		MAX-ACCESS		read-write
		STATUS			current
		DESCRIPTION
				"TYPE: - Checkbox
				 PAGE: - Setup- Logging
					nPCM 8  cmdID= 1135 "
		::= { iqdmx00CmdEntry 1135 }


	iqdmx00SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqdmx00CmdEntry 1112 }


	iqdmx00SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqdmx00CmdEntry 1113 }


	iqdmx00SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqdmx00CmdEntry 1114 }


	iqdmx00SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqdmx00CmdEntry 1115 }


	iqdmx00SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqdmx00CmdEntry 1116 }


	iqdmx00SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqdmx00CmdEntry 1117 }


	iqdmx00SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqdmx00CmdEntry 1118 }


	iqdmx00SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqdmx00CmdEntry 1119 }


	iqdmx00SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqdmx00CmdEntry 1069 }


	iqdmx00SetupLoggingStatusINPUT OBJECT-TYPE
		SYNTAX		RollCallString
		MAX-ACCESS		read-only
		STATUS			current
		DESCRIPTION
				"TYPE: - Display
				 PAGE: - Setup- Logging Status
					INPUT=  cmdID= 2980  format=   "
		::= { iqdmx00CmdEntry 2980 }


	iqdmx00SetupLoggingStatusSTD OBJECT-TYPE
		SYNTAX		RollCallString
		MAX-ACCESS		read-only
		STATUS			current
		DESCRIPTION
				"TYPE: - Display
				 PAGE: - Setup- Logging Status
					STD=  cmdID= 2981  format=   "
		::= { iqdmx00CmdEntry 2981 }


	iqdmx00SetupLoggingStatusINPUT1 OBJECT-TYPE
		SYNTAX		RollCallString
		MAX-ACCESS		read-only
		STATUS			current
		DESCRIPTION
				"TYPE: - Display
				 PAGE: - Setup- Logging Status
					INPUT1=  cmdID= 2982  format=   "
		::= { iqdmx00CmdEntry 2982 }


	iqdmx00SetupLoggingStatusSTD1 OBJECT-TYPE
		SYNTAX		RollCallString
		MAX-ACCESS		read-only
		STATUS			current
		DESCRIPTION
				"TYPE: - Display
				 PAGE: - Setup- Logging Status
					STD1=  cmdID= 2983  format=   "
		::= { iqdmx00CmdEntry 2983 }


	iqdmx00SetupLoggingStatusINPUT2 OBJECT-TYPE
		SYNTAX		RollCallString
		MAX-ACCESS		read-only
		STATUS			current
		DESCRIPTION
				"TYPE: - Display
				 PAGE: - Setup- Logging Status
					INPUT2=  cmdID= 2984  format=   "
		::= { iqdmx00CmdEntry 2984 }


	iqdmx00SetupLoggingStatusSTD2 OBJECT-TYPE
		SYNTAX		RollCallString
		MAX-ACCESS		read-only
		STATUS			current
		DESCRIPTION
				"TYPE: - Display
				 PAGE: - Setup- Logging Status
					STD2=  cmdID= 2985  format=   "
		::= { iqdmx00CmdEntry 2985 }


	iqdmx00SetupLoggingStatusEXTREF OBJECT-TYPE
		SYNTAX		RollCallString
		MAX-ACCESS		read-only
		STATUS			current
		DESCRIPTION
				"TYPE: - Display
				 PAGE: - Setup- Logging Status
					EXTREF=  cmdID= 2986  format=   "
		::= { iqdmx00CmdEntry 2986 }


	iqdmx00SetupLoggingStatusEDH OBJECT-TYPE
		SYNTAX		RollCallString
		MAX-ACCESS		read-only
		STATUS			current
		DESCRIPTION
				"TYPE: - Display
				 PAGE: - Setup- Logging Status
					EDH=  cmdID= 2987  format=   "
		::= { iqdmx00CmdEntry 2987 }


	iqdmx00SetupLoggingStatusERRSEC OBJECT-TYPE
		SYNTAX		RollCallString
		MAX-ACCESS		read-only
		STATUS			current
		DESCRIPTION
				"TYPE: - Display
				 PAGE: - Setup- Logging Status
					ERRSEC=  cmdID= 2988  format=   "
		::= { iqdmx00CmdEntry 2988 }


	iqdmx00SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqdmx00CmdEntry 2989 }


	iqdmx00SetupLoggingStatusDEEMBED1 OBJECT-TYPE
		SYNTAX		RollCallString
		MAX-ACCESS		read-only
		STATUS			current
		DESCRIPTION
				"TYPE: - Display
				 PAGE: - Setup- Logging Status
					DEEMBED1=  cmdID= 3014  format=   "
		::= { iqdmx00CmdEntry 3014 }


	iqdmx00SetupLoggingStatusDEEMBED2 OBJECT-TYPE
		SYNTAX		RollCallString
		MAX-ACCESS		read-only
		STATUS			current
		DESCRIPTION
				"TYPE: - Display
				 PAGE: - Setup- Logging Status
					DEEMBED2=  cmdID= 3015  format=   "
		::= { iqdmx00CmdEntry 3015 }


	iqdmx00SetupLoggingStatusDEEMBED3 OBJECT-TYPE
		SYNTAX		RollCallString
		MAX-ACCESS		read-only
		STATUS			current
		DESCRIPTION
				"TYPE: - Display
				 PAGE: - Setup- Logging Status
					DEEMBED3=  cmdID= 3016  format=   "
		::= { iqdmx00CmdEntry 3016 }


	iqdmx00SetupLoggingStatusDEEMBED4 OBJECT-TYPE
		SYNTAX		RollCallString
		MAX-ACCESS		read-only
		STATUS			current
		DESCRIPTION
				"TYPE: - Display
				 PAGE: - Setup- Logging Status
					DEEMBED4=  cmdID= 3017  format=   "
		::= { iqdmx00CmdEntry 3017 }


	iqdmx00SetupLoggingStatusDEEMBED5 OBJECT-TYPE
		SYNTAX		RollCallString
		MAX-ACCESS		read-only
		STATUS			current
		DESCRIPTION
				"TYPE: - Display
				 PAGE: - Setup- Logging Status
					DEEMBED5=  cmdID= 3018  format=   "
		::= { iqdmx00CmdEntry 3018 }


	iqdmx00SetupLoggingStatusDEEMBED6 OBJECT-TYPE
		SYNTAX		RollCallString
		MAX-ACCESS		read-only
		STATUS			current
		DESCRIPTION
				"TYPE: - Display
				 PAGE: - Setup- Logging Status
					DEEMBED6=  cmdID= 3019  format=   "
		::= { iqdmx00CmdEntry 3019 }


	iqdmx00SetupLoggingStatusDEEMBED7 OBJECT-TYPE
		SYNTAX		RollCallString
		MAX-ACCESS		read-only
		STATUS			current
		DESCRIPTION
				"TYPE: - Display
				 PAGE: - Setup- Logging Status
					DEEMBED7=  cmdID= 3020  format=   "
		::= { iqdmx00CmdEntry 3020 }


	iqdmx00SetupLoggingStatusDEEMBED8 OBJECT-TYPE
		SYNTAX		RollCallString
		MAX-ACCESS		read-only
		STATUS			current
		DESCRIPTION
				"TYPE: - Display
				 PAGE: - Setup- Logging Status
					DEEMBED8=  cmdID= 3021  format=   "
		::= { iqdmx00CmdEntry 3021 }


	iqdmx00SetupLoggingStatusNPCM1 OBJECT-TYPE
		SYNTAX		RollCallString
		MAX-ACCESS		read-only
		STATUS			current
		DESCRIPTION
				"TYPE: - Display
				 PAGE: - Setup- Logging Status
					NPCM1=  cmdID= 3022  format=   "
		::= { iqdmx00CmdEntry 3022 }


	iqdmx00SetupLoggingStatusNPCM2 OBJECT-TYPE
		SYNTAX		RollCallString
		MAX-ACCESS		read-only
		STATUS			current
		DESCRIPTION
				"TYPE: - Display
				 PAGE: - Setup- Logging Status
					NPCM2=  cmdID= 3023  format=   "
		::= { iqdmx00CmdEntry 3023 }


	iqdmx00SetupLoggingStatusNPCM3 OBJECT-TYPE
		SYNTAX		RollCallString
		MAX-ACCESS		read-only
		STATUS			current
		DESCRIPTION
				"TYPE: - Display
				 PAGE: - Setup- Logging Status
					NPCM3=  cmdID= 3024  format=   "
		::= { iqdmx00CmdEntry 3024 }


	iqdmx00SetupLoggingStatusNPCM4 OBJECT-TYPE
		SYNTAX		RollCallString
		MAX-ACCESS		read-only
		STATUS			current
		DESCRIPTION
				"TYPE: - Display
				 PAGE: - Setup- Logging Status
					NPCM4=  cmdID= 3025  format=   "
		::= { iqdmx00CmdEntry 3025 }


	iqdmx00SetupLoggingStatusNPCM5 OBJECT-TYPE
		SYNTAX		RollCallString
		MAX-ACCESS		read-only
		STATUS			current
		DESCRIPTION
				"TYPE: - Display
				 PAGE: - Setup- Logging Status
					NPCM5=  cmdID= 3026  format=   "
		::= { iqdmx00CmdEntry 3026 }


	iqdmx00SetupLoggingStatusNPCM6 OBJECT-TYPE
		SYNTAX		RollCallString
		MAX-ACCESS		read-only
		STATUS			current
		DESCRIPTION
				"TYPE: - Display
				 PAGE: - Setup- Logging Status
					NPCM6=  cmdID= 3027  format=   "
		::= { iqdmx00CmdEntry 3027 }


	iqdmx00SetupLoggingStatusNPCM7 OBJECT-TYPE
		SYNTAX		RollCallString
		MAX-ACCESS		read-only
		STATUS			current
		DESCRIPTION
				"TYPE: - Display
				 PAGE: - Setup- Logging Status
					NPCM7=  cmdID= 3028  format=   "
		::= { iqdmx00CmdEntry 3028 }


	iqdmx00SetupLoggingStatusNPCM8 OBJECT-TYPE
		SYNTAX		RollCallString
		MAX-ACCESS		read-only
		STATUS			current
		DESCRIPTION
				"TYPE: - Display
				 PAGE: - Setup- Logging Status
					NPCM8=  cmdID= 3029  format=   "
		::= { iqdmx00CmdEntry 3029 }


	iqdmx00SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqdmx00CmdEntry 2998 }


	iqdmx00SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqdmx00CmdEntry 2999 }


	iqdmx00SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqdmx00CmdEntry 3000 }


	iqdmx00SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqdmx00CmdEntry 3001 }


	iqdmx00SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqdmx00CmdEntry 3002 }


	iqdmx00SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqdmx00CmdEntry 3003 }


	iqdmx00SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqdmx00CmdEntry 3004 }


	iqdmx00SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqdmx00CmdEntry 3005 }


	iqdmx00SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqdmx00CmdEntry 2990 }


	iqdmx00SetupInformationWindow OBJECT-TYPE
		SYNTAX		INTEGER {
							val_Input_Status(0),
							val_EDH_ANC_Status(1),
							val_Audio_Input_Status(2)
							}
		MAX-ACCESS		read-write
		STATUS			current
		DESCRIPTION
				"TYPE: - Button
				 PAGE: - Setup- Information Window
					Input Status  cmdID= 1915  value= 0  
					EDH & ANC Status  cmdID= 1915  value= 1  
					Audio Input Status  cmdID= 1915  value= 2  "
		::= { iqdmx00CmdEntry 1915 }


	iqdmx00SetupInformationWindowResetErrors OBJECT-TYPE
		SYNTAX		INTEGER { noAction(0),val_Reset_Errors(1) }
		MAX-ACCESS		read-write
		STATUS			current
		DESCRIPTION
				"TYPE: - Button
				 PAGE: - Setup- Information Window
					Reset Errors  cmdID= 2978  value= 1  "
		::= { iqdmx00CmdEntry 2978 }


	iqdmx00SetupDefaultOutput OBJECT-TYPE
		SYNTAX		INTEGER {
							val_Video(1),
							val_Freeze(2),
							val_Pattern(3)
							}
		MAX-ACCESS		read-write
		STATUS			current
		DESCRIPTION
				"TYPE: - Button
				 PAGE: - Setup- Default Output
					Video  cmdID= 1202  value= 1  
					Freeze  cmdID= 1202  value= 2  
					Pattern  cmdID= 1202  value= 3  "
		::= { iqdmx00CmdEntry 1202 }


	iqdmx00SetupDefaultPattern OBJECT-TYPE
		SYNTAX		INTEGER {
							val_Black(0),
							val_EBU_Colour_Bars(1),
							val_100_Colour_Bars(2),
							val_Ramp(3),
							val_Multiburst(4),
							val_Pulse_Bar(5)
							}
		MAX-ACCESS		read-write
		STATUS			current
		DESCRIPTION
				"TYPE: - Button
				 PAGE: - Setup- Default Output
					Black  cmdID= 1038  value= 0  
					EBU Colour Bars  cmdID= 1038  value= 1  
					100% Colour Bars  cmdID= 1038  value= 2  
					Ramp  cmdID= 1038  value= 3  
					Multiburst  cmdID= 1038  value= 4  
					Pulse & Bar  cmdID= 1038  value= 5  "
		::= { iqdmx00CmdEntry 1038 }


	iqdmx00SetupUnitSoftwareVersion OBJECT-TYPE
		SYNTAX		RollCallString
		MAX-ACCESS		read-only
		STATUS			current
		DESCRIPTION
				"TYPE: - Display
				 PAGE: - Setup- Unit
					Software Version  cmdID= 2  format=   "
		::= { iqdmx00CmdEntry 2 }


	iqdmx00SetupUnitSerialNo OBJECT-TYPE
		SYNTAX		RollCallString
		MAX-ACCESS		read-only
		STATUS			current
		DESCRIPTION
				"TYPE: - Display
				 PAGE: - Setup- Unit
					Serial No  cmdID= 1  format=   "
		::= { iqdmx00CmdEntry 1 }


	iqdmx00SetupUnitPresetUnit OBJECT-TYPE
		SYNTAX		INTEGER { noAction(0),val_Preset_Unit(1) }
		MAX-ACCESS		read-write
		STATUS			current
		DESCRIPTION
				"TYPE: - Button
				 PAGE: - Setup- Unit
					Preset Unit  cmdID= 3  value= 1  "
		::= { iqdmx00CmdEntry 3 }


	iqdmx00SetupUnitRestart OBJECT-TYPE
		SYNTAX		INTEGER { noAction(0),val_Restart(1) }
		MAX-ACCESS		read-write
		STATUS			current
		DESCRIPTION
				"TYPE: - Button
				 PAGE: - Setup- Unit
					Restart  cmdID= 4  value= 1  "
		::= { iqdmx00CmdEntry 4 }


	iqdmx00SetupUnitBuildNo OBJECT-TYPE
		SYNTAX		RollCallString
		MAX-ACCESS		read-only
		STATUS			current
		DESCRIPTION
				"TYPE: - Display
				 PAGE: - Setup- Unit
					Build No  cmdID= 5  format=   "
		::= { iqdmx00CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: xxxxxxxxxxxxxxxxxxx
--				: 
-- Comments		: Serial Number   Runtime string  
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE              The unit is not locked to the input signal
--				: FAIL              EDH errors have been found on the input signal
--              : OK                No EDH errors found on the input signal
--              : RESET             EDH statistics have been reset
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: STDERR            Input signal standard not recognized or no signal
--				: UNKNOWN           Not a selected input standard
--              : 525               Input standard 525
--              : 625               Input standard 625
-- Comments		: 
--
---------------------------------------------------------------------------------------------------
-- Header		: STD1
--
-- MIB ref		: swCardEventLogSlotXX       .4.83.84.68.49
-- absolute OID	: 1.3.6.1.4.1.7995.2.6.1.1.XX.4.83.84.68.49
-- Vary			: YES
--
-- Value(s)		: ERR               Not a selected input standard Input 1
--				: 525               Input 1 standard 525
--              : 625               Input 1 standard 625
-- Comments		: 
--
---------------------------------------------------------------------------------------------------
-- Header		: STD2
--
-- MIB ref		: swCardEventLogSlotXX       .4.83.84.68.50
-- absolute OID	: 1.3.6.1.4.1.7995.2.6.1.1.XX.4.83.84.68.50
-- Vary			: YES
--
-- Value(s)		: ERR               Not a selected input standard Input 2
--				: 525               Input 2 standard 525
--              : 625               Input 2 standard 625
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE              No Internal errors detected
--				: FAIL              Internal error detected
--              : FAIL.FPGA_LOAD    Fpga load failure detected
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: OK                Valid input signal
--				: ERR               Invalid input signal
--              : LOST              Input signal lost
-- Comments		: 
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: OK                Router BUS A Left channel has valid signal selected            
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: OK                Router BUS A Right channel has valid signal selected
--              : WARNING           Router BUS A Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: OK                Router BUS B Left channel has valid signal selected            
--              : WARNING           Router BUS B Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: OK                Router BUS B Right channel has valid signal selected
--              : WARNING           Router BUS B Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: OK                Router BUS C Left channel has valid signal selected            
--              : WARNING           Router BUS C Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: OK                Router BUS C Right channel has valid signal selected
--              : WARNING           Router BUS C Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: OK                Router BUS D Left channel has valid signal selected            
--              : WARNING           Router BUS D Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: OK                Router BUS D Right channel has valid signal selected
--              : WARNING           Router BUS D Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
--
-- Value(s)		: 0s                Number or Errored Seconds
--				: 
-- Comments		: Runtime string
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: NONE              No reference signal present                
--				: 525               Valid 525 reference signal                 
--              : ERROR             Reference/Output standard mismatch         
--              : WARNING           Reference signal available but not selected
--              : 625               Valid 625 reference signal                 
-- Comments		: 
--
---------------------------------------------------------------------------------------------------
-- Header		: INPUT1
--
-- MIB ref		: swCardEventLogSlotXX       .6.73.78.80.85.84.49
-- absolute OID	: 1.3.6.1.4.1.7995.2.6.1.1.XX.6.73.78.80.85.84.49
-- Vary			: YES
--
-- Value(s)		: OK                Valid input 1 signal  
--				: ERR               Invalid input 1 signal
--              : LOST              Input 1 signal lost   
-- Comments		: 
--
---------------------------------------------------------------------------------------------------
-- Header		: INPUT2
--
-- MIB ref		: swCardEventLogSlotXX       .6.73.78.80.85.84.50
-- absolute OID	: 1.3.6.1.4.1.7995.2.6.1.1.XX.6.73.78.80.85.84.50
-- Vary			: YES
--
-- Value(s)		: OK                Valid input 2 signal  
--				: ERR               Invalid input 2 signal
--              : LOST              Input 2 signal lost   
-- Comments		: 
--
---------------------------------------------------------------------------------------------------
-- Header		: NPCM_1
--
-- MIB ref		: swCardEventLogSlotXX       .6.78.80.67.77.95.49
-- absolute OID	: 1.3.6.1.4.1.7995.2.6.1.1.XX.6.78.80.67.77.95.49
-- Vary			: YES
--
-- Value(s)		: NONE              Non-PCM not present on pair 1 of selected SDI input
--				: OK                Non-PCM present on pair 1 of selected SDI input
-- Comments		: 
--
---------------------------------------------------------------------------------------------------
-- Header		: NPCM_2
--
-- MIB ref		: swCardEventLogSlotXX       .6.78.80.67.77.95.50
-- absolute OID	: 1.3.6.1.4.1.7995.2.6.1.1.XX.6.78.80.67.77.95.50
-- Vary			: YES
--
-- Value(s)		: NONE              Non-PCM not present on pair 2 of selected SDI input
--				: OK                Non-PCM present on pair 2 of selected SDI input
-- Comments		: 
--
---------------------------------------------------------------------------------------------------
-- Header		: NPCM_3
--
-- MIB ref		: swCardEventLogSlotXX       .6.78.80.67.77.95.51
-- absolute OID	: 1.3.6.1.4.1.7995.2.6.1.1.XX.6.78.80.67.77.95.51
-- Vary			: YES
--
-- Value(s)		: NONE              Non-PCM not present on pair 3 of selected SDI input
--				: OK                Non-PCM present on pair 3 of selected SDI input
-- Comments		: 
--
---------------------------------------------------------------------------------------------------
-- Header		: NPCM_4
--
-- MIB ref		: swCardEventLogSlotXX       .6.78.80.67.77.95.52
-- absolute OID	: 1.3.6.1.4.1.7995.2.6.1.1.XX.6.78.80.67.77.95.52
-- Vary			: YES
--
-- Value(s)		: NONE              Non-PCM not present on pair 4 of selected SDI input
--				: OK                Non-PCM present on pair 4 of selected SDI input
-- Comments		: 
--
---------------------------------------------------------------------------------------------------
-- Header		: NPCM_5
--
-- MIB ref		: swCardEventLogSlotXX       .6.78.80.67.77.95.53
-- absolute OID	: 1.3.6.1.4.1.7995.2.6.1.1.XX.6.78.80.67.77.95.53
-- Vary			: YES
--
-- Value(s)		: NONE              Non-PCM not present on pair 5 of selected SDI input
--				: OK                Non-PCM present on pair 5 of selected SDI input
-- Comments		: 
--
---------------------------------------------------------------------------------------------------
-- Header		: NPCM_6
--
-- MIB ref		: swCardEventLogSlotXX       .6.78.80.67.77.95.54
-- absolute OID	: 1.3.6.1.4.1.7995.2.6.1.1.XX.6.78.80.67.77.95.54
-- Vary			: YES
--
-- Value(s)		: NONE              Non-PCM not present on pair 6 of selected SDI input
--				: OK                Non-PCM present on pair 6 of selected SDI input
-- Comments		: 
--
---------------------------------------------------------------------------------------------------
-- Header		: NPCM_7
--
-- MIB ref		: swCardEventLogSlotXX       .6.78.80.67.77.95.55
-- absolute OID	: 1.3.6.1.4.1.7995.2.6.1.1.XX.6.78.80.67.77.95.55
-- Vary			: YES
--
-- Value(s)		: NONE              Non-PCM not present on pair 7 of selected SDI input
--				: OK                Non-PCM present on pair 7 of selected SDI input
-- Comments		: 
--
---------------------------------------------------------------------------------------------------
-- Header		: NPCM_8
--
-- MIB ref		: swCardEventLogSlotXX       .6.78.80.67.77.95.56
-- absolute OID	: 1.3.6.1.4.1.7995.2.6.1.1.XX.6.78.80.67.77.95.56
-- Vary			: YES
--
-- Value(s)		: NONE              Non-PCM not present on pair 8 of selected SDI input
--				: OK                Non-PCM present on pair 8 of selected SDI input
-- Comments		: 
--
---------------------------------------------------------------------------------------------------
-- Header		: DEEMBED_1
--
-- MIB ref		: swCardEventLogSlotXX       .9.68.69.69.77.66.69.68.95.49
-- absolute OID	: 1.3.6.1.4.1.7995.2.6.1.1.XX.9.68.69.69.77.66.69.68.95.49
-- Vary			: YES
--
-- Value(s)		: NONE              Nothing present on pair 1
--				: OK                Embedded pair 1 present on selected SDI input
-- Comments		: 
--
---------------------------------------------------------------------------------------------------
-- Header		: DEEMBED_2
--
-- MIB ref		: swCardEventLogSlotXX       .9.68.69.69.77.66.69.68.95.50
-- absolute OID	: 1.3.6.1.4.1.7995.2.6.1.1.XX.9.68.69.69.77.66.69.68.95.50
-- Vary			: YES
--
-- Value(s)		: NONE              Nothing present on pair 2
--				: OK                Embedded pair 2 present on selected SDI input
-- Comments		: 
--
---------------------------------------------------------------------------------------------------
-- Header		: DEEMBED_3
--
-- MIB ref		: swCardEventLogSlotXX       .9.68.69.69.77.66.69.68.95.51
-- absolute OID	: 1.3.6.1.4.1.7995.2.6.1.1.XX.9.68.69.69.77.66.69.68.95.51
-- Vary			: YES
--
-- Value(s)		: NONE              Nothing present on pair 3
--				: OK                Embedded pair 3 present on selected SDI input
-- Comments		: 
--
---------------------------------------------------------------------------------------------------
-- Header		: DEEMBED_4
--
-- MIB ref		: swCardEventLogSlotXX       .9.68.69.69.77.66.69.68.95.52
-- absolute OID	: 1.3.6.1.4.1.7995.2.6.1.1.XX.9.68.69.69.77.66.69.68.95.52
-- Vary			: YES
--
-- Value(s)		: NONE              Nothing present on pair 4
--				: OK                Embedded pair 4 present on selected SDI input
-- Comments		: 
--
---------------------------------------------------------------------------------------------------
-- Header		: DEEMBED_5
--
-- MIB ref		: swCardEventLogSlotXX       .9.68.69.69.77.66.69.68.95.53
-- absolute OID	: 1.3.6.1.4.1.7995.2.6.1.1.XX.9.68.69.69.77.66.69.68.95.53
-- Vary			: YES
--
-- Value(s)		: NONE              Nothing present on pair 5
--				: OK                Embedded pair 5 present on selected SDI input
-- Comments		: 
--
---------------------------------------------------------------------------------------------------
-- Header		: DEEMBED_6
--
-- MIB ref		: swCardEventLogSlotXX       .9.68.69.69.77.66.69.68.95.54
-- absolute OID	: 1.3.6.1.4.1.7995.2.6.1.1.XX.9.68.69.69.77.66.69.68.95.54
-- Vary			: YES
--
-- Value(s)		: NONE              Nothing present on pair 6
--				: OK                Embedded pair 6 present on selected SDI input
-- Comments		: 
--
---------------------------------------------------------------------------------------------------
-- Header		: DEEMBED_7
--
-- MIB ref		: swCardEventLogSlotXX       .9.68.69.69.77.66.69.68.95.55
-- absolute OID	: 1.3.6.1.4.1.7995.2.6.1.1.XX.9.68.69.69.77.66.69.68.95.55
-- Vary			: YES
--
-- Value(s)		: NONE              Nothing present on pair 7
--				: OK                Embedded pair 7 present on selected SDI input
-- Comments		: 
--
---------------------------------------------------------------------------------------------------
-- Header		: DEEMBED_8
--
-- MIB ref		: swCardEventLogSlotXX       .9.68.69.69.77.66.69.68.95.56
-- absolute OID	: 1.3.6.1.4.1.7995.2.6.1.1.XX.9.68.69.69.77.66.69.68.95.56
-- Vary			: YES
--
-- Value(s)		: NONE              Nothing present on pair 8
--				: OK                Embedded pair 8 present on selected SDI input
-- Comments		: 
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK                RollTrack message sent and received OK
--				: FAIL              RollTrack message not acknowledged    
-- Comments		: 
--
---------------------------------------------------------------------------------------------------
