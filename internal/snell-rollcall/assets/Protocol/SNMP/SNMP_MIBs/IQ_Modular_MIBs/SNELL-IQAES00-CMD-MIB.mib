-- ************************************************************************************
-- Snell&Wilcox Card:IQAES00
--        Module Id#:439
--       Command Set:6
--          Filename:SNELL-IQAES00-CMD-MIB.mib
--            Author:Jonathan Riches
--              Date:17/07/2007
--              Time:14:23
--
-- Copyright (c) 2007 Snell & Wilcox Ltd
-- All rights reserved.
--
-- ************************************************************************************

SNELL-IQAES00-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQAES00,
    moduleIQAES00MIB
        FROM SNELL-WILCOX-PRODUCT-REG;

 moduleIQAES00CmdMi MODULE-IDENTITY
    LAST-UPDATED "0707171423Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQAES00MIB 1 }




--********************************************************************************
--*
--*  Snell Wilcox Card:
--*  command set:
--*  list commands/menus:
--*
--******************************************************************************
	iqaes00CmdTable OBJECT-TYPE
		SYNTAX			SEQUENCE OF Iqaes00CmdEntry
		MAX-ACCESS		not-accessible
		STATUS			current
		DESCRIPTION
				"Note the instance of this table is relected in the command set Version"
		::= { moduleIQAES00 1 }

	iqaes00CmdEntry OBJECT-TYPE
		SYNTAX		Iqaes00CmdEntry
		MAX-ACCESS		not-accessible
		STATUS			current
		DESCRIPTION
				"Entry in command table."
		INDEX	{ iqaes00SlotIndex }
		::= { iqaes00CmdTable 1 }

	Iqaes00CmdEntry ::=
		SEQUENCE {
			iqaes00SlotIndex
				Unsigned32,
			iqaes00StatusInput1Locked
				RollCallString,
			iqaes00StatusInput1SampleRate
				RollCallString,
			iqaes00StatusInput1PCM
				RollCallString,
			iqaes00StatusInput1ProSumer
				RollCallString,
			iqaes00StatusInput1CRCError
				RollCallString,
			iqaes00StatusInput1CSMode
				RollCallString,
			iqaes00StatusInput1CSModeValue
				RollCallString,
			iqaes00StatusInput2Locked
				RollCallString,
			iqaes00StatusInput2SampleRate
				RollCallString,
			iqaes00StatusInput2PCM
				RollCallString,
			iqaes00StatusInput2ProSumer
				RollCallString,
			iqaes00StatusInput2CRCError
				RollCallString,
			iqaes00StatusInput2CSMode
				RollCallString,
			iqaes00StatusInput2CSModeValue
				RollCallString,
			iqaes00LoggingControlInput1State
				INTEGER,
			iqaes00LoggingControlInput1Samplerate
				INTEGER,
			iqaes00LoggingControlInput1AudioType
				INTEGER,
			iqaes00LoggingControlInput1CSMode
				INTEGER,
			iqaes00LoggingControlInput1RearLabel
				INTEGER,
			iqaes00LoggingControlInput1Type
				INTEGER,
			iqaes00LoggingControlInput2State
				INTEGER,
			iqaes00LoggingControlInput2Samplerate
				INTEGER,
			iqaes00LoggingControlInput2AudioType
				INTEGER,
			iqaes00LoggingControlInput2CSMode
				INTEGER,
			iqaes00LoggingControlInput2RearLabel
				INTEGER,
			iqaes00LoggingControlInput2Type
				INTEGER,
			iqaes00LoggingStatusINPUT2TYPE
				RollCallString,
			iqaes00LoggingStatusINPUT2IDENT
				RollCallString,
			iqaes00LoggingStatusINPUT2AUDIOCSMO
				RollCallString,
			iqaes00LoggingStatusINPUT2AUDIOTYPE
				RollCallString,
			iqaes00LoggingStatusINPUT2AUDIORATE
				RollCallString,
			iqaes00LoggingStatusINPUT2STATE
				RollCallString,
			iqaes00LoggingStatusINPUT1TYPE
				RollCallString,
			iqaes00LoggingStatusINPUT1IDENT
				RollCallString,
			iqaes00LoggingStatusINPUT1AUDIOCSMO
				RollCallString,
			iqaes00LoggingStatusINPUT1AUDIOTYPE
				RollCallString,
			iqaes00LoggingStatusINPUT1AUDIORATE
				RollCallString,
			iqaes00LoggingStatusINPUT1STATE
				RollCallString,
			iqaes00RollTrackIndex
				INTEGER,
			iqaes00RollTrackSource
				INTEGER,
			iqaes00RollTrackDisable
				INTEGER,
			iqaes00RollTrackAddress
				RollCallString,
			iqaes00RollTrackCommand
				RollCallString,
			iqaes00RollTrackSending
				RollCallString,
			iqaes00RollTrackStatus
				RollCallString,
			iqaes00RollTrackIndexB
				INTEGER,
			iqaes00RollTrackSourceB
				INTEGER,
			iqaes00RollTrackAddressB
				RollCallString,
			iqaes00RollTrackCommandB
				RollCallString,
			iqaes00SetupMode
				INTEGER,
			iqaes00SetupNonPCMDetectTestnAUDIO
				INTEGER,
			iqaes00SetupNonPCMDetectTestVbit
				INTEGER,
			iqaes00SetupSoftwareVersion
				RollCallString,
			iqaes00SetupSerialNo
				RollCallString,
			iqaes00SetupPresetUnit
				INTEGER,
			iqaes00SetupRestart
				INTEGER,
			iqaes00SetupBuildNo
				RollCallString
		}

	iqaes00SlotIndex OBJECT-TYPE
		SYNTAX		Unsigned32
		MAX-ACCESS		not-accessible
		STATUS			current
		DESCRIPTION
				"The unique Index value for each slot.  Its value
					ranges between 1 and the value of slotNumber."
		::= { iqaes00CmdEntry 0 }


	iqaes00StatusInput1Locked OBJECT-TYPE
		SYNTAX		RollCallString
		MAX-ACCESS		read-only
		STATUS			current
		DESCRIPTION
				"TYPE: - Display
					Locked  cmdID= 5001  format=   "
		::= { iqaes00CmdEntry 5001 }


	iqaes00StatusInput1SampleRate OBJECT-TYPE
		SYNTAX		RollCallString
		MAX-ACCESS		read-only
		STATUS			current
		DESCRIPTION
				"TYPE: - Display
					Sample Rate  cmdID= 5002  format=   "
		::= { iqaes00CmdEntry 5002 }


	iqaes00StatusInput1PCM OBJECT-TYPE
		SYNTAX		RollCallString
		MAX-ACCESS		read-only
		STATUS			current
		DESCRIPTION
				"TYPE: - Display
					PCM  cmdID= 5003  format=   "
		::= { iqaes00CmdEntry 5003 }


	iqaes00StatusInput1ProSumer OBJECT-TYPE
		SYNTAX		RollCallString
		MAX-ACCESS		read-only
		STATUS			current
		DESCRIPTION
				"TYPE: - Display
					ProSumer  cmdID= 5004  format=   "
		::= { iqaes00CmdEntry 5004 }


	iqaes00StatusInput1CRCError OBJECT-TYPE
		SYNTAX		RollCallString
		MAX-ACCESS		read-only
		STATUS			current
		DESCRIPTION
				"TYPE: - Display
					CRC Error  cmdID= 5005  format=   "
		::= { iqaes00CmdEntry 5005 }


	iqaes00StatusInput1CSMode OBJECT-TYPE
		SYNTAX		RollCallString
		MAX-ACCESS		read-only
		STATUS			current
		DESCRIPTION
				"TYPE: - Display
					CS Mode  cmdID= 5006  format=   "
		::= { iqaes00CmdEntry 5006 }


	iqaes00StatusInput1CSModeValue OBJECT-TYPE
		SYNTAX		RollCallString
		MAX-ACCESS		read-only
		STATUS			current
		DESCRIPTION
				"TYPE: - Display
					CS Mode Value  cmdID= 5007  format=   "
		::= { iqaes00CmdEntry 5007 }


	iqaes00StatusInput2Locked OBJECT-TYPE
		SYNTAX		RollCallString
		MAX-ACCESS		read-only
		STATUS			current
		DESCRIPTION
				"TYPE: - Display
					Locked  cmdID= 5011  format=   "
		::= { iqaes00CmdEntry 5011 }


	iqaes00StatusInput2SampleRate OBJECT-TYPE
		SYNTAX		RollCallString
		MAX-ACCESS		read-only
		STATUS			current
		DESCRIPTION
				"TYPE: - Display
					Sample Rate  cmdID= 5012  format=   "
		::= { iqaes00CmdEntry 5012 }


	iqaes00StatusInput2PCM OBJECT-TYPE
		SYNTAX		RollCallString
		MAX-ACCESS		read-only
		STATUS			current
		DESCRIPTION
				"TYPE: - Display
					PCM  cmdID= 5013  format=   "
		::= { iqaes00CmdEntry 5013 }


	iqaes00StatusInput2ProSumer OBJECT-TYPE
		SYNTAX		RollCallString
		MAX-ACCESS		read-only
		STATUS			current
		DESCRIPTION
				"TYPE: - Display
					ProSumer  cmdID= 5014  format=   "
		::= { iqaes00CmdEntry 5014 }


	iqaes00StatusInput2CRCError OBJECT-TYPE
		SYNTAX		RollCallString
		MAX-ACCESS		read-only
		STATUS			current
		DESCRIPTION
				"TYPE: - Display
					CRC Error  cmdID= 5015  format=   "
		::= { iqaes00CmdEntry 5015 }


	iqaes00StatusInput2CSMode OBJECT-TYPE
		SYNTAX		RollCallString
		MAX-ACCESS		read-only
		STATUS			current
		DESCRIPTION
				"TYPE: - Display
					CS Mode  cmdID= 5016  format=   "
		::= { iqaes00CmdEntry 5016 }


	iqaes00StatusInput2CSModeValue OBJECT-TYPE
		SYNTAX		RollCallString
		MAX-ACCESS		read-only
		STATUS			current
		DESCRIPTION
				"TYPE: - Display
					CS Mode Value  cmdID= 5017  format=   "
		::= { iqaes00CmdEntry 5017 }


	iqaes00LoggingControlInput1State OBJECT-TYPE
		SYNTAX		INTEGER { disable(0), enable(1) }
		MAX-ACCESS		read-write
		STATUS			current
		DESCRIPTION
				"TYPE: - Checkbox
				 PAGE: - Logging- Control
					Input1 State  cmdID= 1094 "
		::= { iqaes00CmdEntry 1094 }


	iqaes00LoggingControlInput1Samplerate OBJECT-TYPE
		SYNTAX		INTEGER { disable(0), enable(1) }
		MAX-ACCESS		read-write
		STATUS			current
		DESCRIPTION
				"TYPE: - Checkbox
				 PAGE: - Logging- Control
					Input1 Samplerate  cmdID= 1136 "
		::= { iqaes00CmdEntry 1136 }


	iqaes00LoggingControlInput1AudioType OBJECT-TYPE
		SYNTAX		INTEGER { disable(0), enable(1) }
		MAX-ACCESS		read-write
		STATUS			current
		DESCRIPTION
				"TYPE: - Checkbox
				 PAGE: - Logging- Control
					Input1 Audio Type  cmdID= 1128 "
		::= { iqaes00CmdEntry 1128 }


	iqaes00LoggingControlInput1CSMode OBJECT-TYPE
		SYNTAX		INTEGER { disable(0), enable(1) }
		MAX-ACCESS		read-write
		STATUS			current
		DESCRIPTION
				"TYPE: - Checkbox
				 PAGE: - Logging- Control
					Input1 CS Mode  cmdID= 1144 "
		::= { iqaes00CmdEntry 1144 }


	iqaes00LoggingControlInput1RearLabel OBJECT-TYPE
		SYNTAX		INTEGER { disable(0), enable(1) }
		MAX-ACCESS		read-write
		STATUS			current
		DESCRIPTION
				"TYPE: - Checkbox
				 PAGE: - Logging- Control
					Input1 Rear Label  cmdID= 3590 "
		::= { iqaes00CmdEntry 3590 }


	iqaes00LoggingControlInput1Type OBJECT-TYPE
		SYNTAX		INTEGER { disable(0), enable(1) }
		MAX-ACCESS		read-write
		STATUS			current
		DESCRIPTION
				"TYPE: - Checkbox
				 PAGE: - Logging- Control
					Input1 Type  cmdID= 3600 "
		::= { iqaes00CmdEntry 3600 }


	iqaes00LoggingControlInput2State OBJECT-TYPE
		SYNTAX		INTEGER { disable(0), enable(1) }
		MAX-ACCESS		read-write
		STATUS			current
		DESCRIPTION
				"TYPE: - Checkbox
				 PAGE: - Logging- Control
					Input2 State  cmdID= 1095 "
		::= { iqaes00CmdEntry 1095 }


	iqaes00LoggingControlInput2Samplerate OBJECT-TYPE
		SYNTAX		INTEGER { disable(0), enable(1) }
		MAX-ACCESS		read-write
		STATUS			current
		DESCRIPTION
				"TYPE: - Checkbox
				 PAGE: - Logging- Control
					Input2 Samplerate  cmdID= 1137 "
		::= { iqaes00CmdEntry 1137 }


	iqaes00LoggingControlInput2AudioType OBJECT-TYPE
		SYNTAX		INTEGER { disable(0), enable(1) }
		MAX-ACCESS		read-write
		STATUS			current
		DESCRIPTION
				"TYPE: - Checkbox
				 PAGE: - Logging- Control
					Input2 Audio Type  cmdID= 1129 "
		::= { iqaes00CmdEntry 1129 }


	iqaes00LoggingControlInput2CSMode OBJECT-TYPE
		SYNTAX		INTEGER { disable(0), enable(1) }
		MAX-ACCESS		read-write
		STATUS			current
		DESCRIPTION
				"TYPE: - Checkbox
				 PAGE: - Logging- Control
					Input2 CS Mode  cmdID= 1145 "
		::= { iqaes00CmdEntry 1145 }


	iqaes00LoggingControlInput2RearLabel OBJECT-TYPE
		SYNTAX		INTEGER { disable(0), enable(1) }
		MAX-ACCESS		read-write
		STATUS			current
		DESCRIPTION
				"TYPE: - Checkbox
				 PAGE: - Logging- Control
					Input2 Rear Label  cmdID= 3591 "
		::= { iqaes00CmdEntry 3591 }


	iqaes00LoggingControlInput2Type OBJECT-TYPE
		SYNTAX		INTEGER { disable(0), enable(1) }
		MAX-ACCESS		read-write
		STATUS			current
		DESCRIPTION
				"TYPE: - Checkbox
				 PAGE: - Logging- Control
					Input2 Type  cmdID= 3601 "
		::= { iqaes00CmdEntry 3601 }


	iqaes00LoggingStatusINPUT2TYPE OBJECT-TYPE
		SYNTAX		RollCallString
		MAX-ACCESS		read-only
		STATUS			current
		DESCRIPTION
				"TYPE: - Display
				 PAGE: - Logging- Status
					INPUT_2_TYPE=  cmdID= 3621  format=   "
		::= { iqaes00CmdEntry 3621 }


	iqaes00LoggingStatusINPUT2IDENT OBJECT-TYPE
		SYNTAX		RollCallString
		MAX-ACCESS		read-only
		STATUS			current
		DESCRIPTION
				"TYPE: - Display
				 PAGE: - Logging- Status
					INPUT_2_IDENT=  cmdID= 3611  format=   "
		::= { iqaes00CmdEntry 3611 }


	iqaes00LoggingStatusINPUT2AUDIOCSMO OBJECT-TYPE
		SYNTAX		RollCallString
		MAX-ACCESS		read-only
		STATUS			current
		DESCRIPTION
				"TYPE: - Display
				 PAGE: - Logging- Status
					INPUT_2_AUDIO_CS_MO  cmdID= 3039  format=   "
		::= { iqaes00CmdEntry 3039 }


	iqaes00LoggingStatusINPUT2AUDIOTYPE OBJECT-TYPE
		SYNTAX		RollCallString
		MAX-ACCESS		read-only
		STATUS			current
		DESCRIPTION
				"TYPE: - Display
				 PAGE: - Logging- Status
					INPUT_2_AUDIO_TYPE=  cmdID= 3023  format=   "
		::= { iqaes00CmdEntry 3023 }


	iqaes00LoggingStatusINPUT2AUDIORATE OBJECT-TYPE
		SYNTAX		RollCallString
		MAX-ACCESS		read-only
		STATUS			current
		DESCRIPTION
				"TYPE: - Display
				 PAGE: - Logging- Status
					INPUT_2_AUDIO_RATE=  cmdID= 3031  format=   "
		::= { iqaes00CmdEntry 3031 }


	iqaes00LoggingStatusINPUT2STATE OBJECT-TYPE
		SYNTAX		RollCallString
		MAX-ACCESS		read-only
		STATUS			current
		DESCRIPTION
				"TYPE: - Display
				 PAGE: - Logging- Status
					INPUT_2_STATE=  cmdID= 2984  format=   "
		::= { iqaes00CmdEntry 2984 }


	iqaes00LoggingStatusINPUT1TYPE OBJECT-TYPE
		SYNTAX		RollCallString
		MAX-ACCESS		read-only
		STATUS			current
		DESCRIPTION
				"TYPE: - Display
				 PAGE: - Logging- Status
					INPUT_1_TYPE=  cmdID= 3620  format=   "
		::= { iqaes00CmdEntry 3620 }


	iqaes00LoggingStatusINPUT1IDENT OBJECT-TYPE
		SYNTAX		RollCallString
		MAX-ACCESS		read-only
		STATUS			current
		DESCRIPTION
				"TYPE: - Display
				 PAGE: - Logging- Status
					INPUT_1_IDENT=  cmdID= 3610  format=   "
		::= { iqaes00CmdEntry 3610 }


	iqaes00LoggingStatusINPUT1AUDIOCSMO OBJECT-TYPE
		SYNTAX		RollCallString
		MAX-ACCESS		read-only
		STATUS			current
		DESCRIPTION
				"TYPE: - Display
				 PAGE: - Logging- Status
					INPUT_1_AUDIO_CS_MO  cmdID= 3038  format=   "
		::= { iqaes00CmdEntry 3038 }


	iqaes00LoggingStatusINPUT1AUDIOTYPE OBJECT-TYPE
		SYNTAX		RollCallString
		MAX-ACCESS		read-only
		STATUS			current
		DESCRIPTION
				"TYPE: - Display
				 PAGE: - Logging- Status
					INPUT_1_AUDIO_TYPE=  cmdID= 3022  format=   "
		::= { iqaes00CmdEntry 3022 }


	iqaes00LoggingStatusINPUT1AUDIORATE OBJECT-TYPE
		SYNTAX		RollCallString
		MAX-ACCESS		read-only
		STATUS			current
		DESCRIPTION
				"TYPE: - Display
				 PAGE: - Logging- Status
					INPUT_1_AUDIO_RATE=  cmdID= 3030  format=   "
		::= { iqaes00CmdEntry 3030 }


	iqaes00LoggingStatusINPUT1STATE OBJECT-TYPE
		SYNTAX		RollCallString
		MAX-ACCESS		read-only
		STATUS			current
		DESCRIPTION
				"TYPE: - Display
				 PAGE: - Logging- Status
					INPUT_1_STATE=  cmdID= 2982  format=   "
		::= { iqaes00CmdEntry 2982 }


	iqaes00RollTrackIndex OBJECT-TYPE
		SYNTAX		INTEGER
		MAX-ACCESS		read-write
		STATUS			current
		DESCRIPTION
				"TYPE: - Number
					RollTrack Index  cmdID= 1495  min= 0  max= 15  step= 1  format= %.0f  div_scale= 1
					Min = 0  Max = 15  Step = 1 "
		::= { iqaes00CmdEntry 1495 }


	iqaes00RollTrackSource OBJECT-TYPE
		SYNTAX		INTEGER
		MAX-ACCESS		read-write
		STATUS			current
		DESCRIPTION
				"TYPE: - Number
					RollTrack Source  cmdID= 1496  min= -1  max= 19  step= 1  format= %.0f  div_scale= 1
					Min = -1  Max = 19  Step = 1 "
		::= { iqaes00CmdEntry 1496 }


	iqaes00RollTrackDisable OBJECT-TYPE
		SYNTAX		INTEGER { disable(0), enable(1) }
		MAX-ACCESS		read-write
		STATUS			current
		DESCRIPTION
				"TYPE: - Checkbox
					RollTrack Disable  cmdID= 1513 "
		::= { iqaes00CmdEntry 1513 }


	iqaes00RollTrackAddress OBJECT-TYPE
		SYNTAX		RollCallString
		MAX-ACCESS		read-write
		STATUS			current
		DESCRIPTION
				"TYPE: - Editstring
					RollTrack Address  cmdID= 1497  "
		::= { iqaes00CmdEntry 1497 }


	iqaes00RollTrackCommand OBJECT-TYPE
		SYNTAX		RollCallString
		MAX-ACCESS		read-write
		STATUS			current
		DESCRIPTION
				"TYPE: - Editstring
					RollTrack Command  cmdID= 1498  "
		::= { iqaes00CmdEntry 1498 }


	iqaes00RollTrackSending OBJECT-TYPE
		SYNTAX		RollCallString
		MAX-ACCESS		read-only
		STATUS			current
		DESCRIPTION
				"TYPE: - Display
					RollTrack Sending  cmdID= 1514  format=   "
		::= { iqaes00CmdEntry 1514 }


	iqaes00RollTrackStatus OBJECT-TYPE
		SYNTAX		RollCallString
		MAX-ACCESS		read-only
		STATUS			current
		DESCRIPTION
				"TYPE: - Display
					RollTrack Status  cmdID= 1511  format=   "
		::= { iqaes00CmdEntry 1511 }


	iqaes00RollTrackIndexB OBJECT-TYPE
		SYNTAX		INTEGER
		MAX-ACCESS		read-write
		STATUS			current
		DESCRIPTION
				"TYPE: - Number
					RollTrack Index  cmdID= 2870  min= 0  max= 15  step= 1  format= %.0f  div_scale= 1
					Min = 0  Max = 15  Step = 1 "
		::= { iqaes00CmdEntry 2870 }


	iqaes00RollTrackSourceB OBJECT-TYPE
		SYNTAX		INTEGER
		MAX-ACCESS		read-write
		STATUS			current
		DESCRIPTION
				"TYPE: - Number
					RollTrack Source  cmdID= 2871  min= -1  max= 19  step= 1  format= %.0f  div_scale= 1
					Min = -1  Max = 19  Step = 1 "
		::= { iqaes00CmdEntry 2871 }


	iqaes00RollTrackAddressB OBJECT-TYPE
		SYNTAX		RollCallString
		MAX-ACCESS		read-write
		STATUS			current
		DESCRIPTION
				"TYPE: - Editstring
					RollTrack Address  cmdID= 2872  "
		::= { iqaes00CmdEntry 2872 }


	iqaes00RollTrackCommandB OBJECT-TYPE
		SYNTAX		RollCallString
		MAX-ACCESS		read-write
		STATUS			current
		DESCRIPTION
				"TYPE: - Editstring
					RollTrack Command  cmdID= 2873  "
		::= { iqaes00CmdEntry 2873 }


	iqaes00SetupMode OBJECT-TYPE
		SYNTAX		INTEGER {
							val_1_Input(0),
							val_2_Inputs(1)
							}
		MAX-ACCESS		read-write
		STATUS			current
		DESCRIPTION
				"TYPE: - RadiobuttonList
					Mode  cmdID= 5021
					1 Input  value= 0
					2 Inputs  value= 1  "
		::= { iqaes00CmdEntry 5021 }


	iqaes00SetupNonPCMDetectTestnAUDIO OBJECT-TYPE
		SYNTAX		INTEGER { disable(0), enable(1) }
		MAX-ACCESS		read-write
		STATUS			current
		DESCRIPTION
				"TYPE: - Checkbox
					Test nAUDIO  cmdID= 5022 "
		::= { iqaes00CmdEntry 5022 }


	iqaes00SetupNonPCMDetectTestVbit OBJECT-TYPE
		SYNTAX		INTEGER { disable(0), enable(1) }
		MAX-ACCESS		read-write
		STATUS			current
		DESCRIPTION
				"TYPE: - Checkbox
					Test V bit  cmdID= 5023 "
		::= { iqaes00CmdEntry 5023 }


	iqaes00SetupSoftwareVersion OBJECT-TYPE
		SYNTAX		RollCallString
		MAX-ACCESS		read-only
		STATUS			current
		DESCRIPTION
				"TYPE: - Display
					Software Version  cmdID= 2  format=   "
		::= { iqaes00CmdEntry 2 }


	iqaes00SetupSerialNo OBJECT-TYPE
		SYNTAX		RollCallString
		MAX-ACCESS		read-only
		STATUS			current
		DESCRIPTION
				"TYPE: - Display
					Serial No  cmdID= 1  format=   "
		::= { iqaes00CmdEntry 1 }


	iqaes00SetupPresetUnit OBJECT-TYPE
		SYNTAX		INTEGER { noAction(0),val_Preset_Unit(1) }
		MAX-ACCESS		read-write
		STATUS			current
		DESCRIPTION
				"TYPE: - Button
					Preset Unit  cmdID= 3  value= 1  "
		::= { iqaes00CmdEntry 3 }


	iqaes00SetupRestart OBJECT-TYPE
		SYNTAX		INTEGER { noAction(0),val_Restart(1) }
		MAX-ACCESS		read-write
		STATUS			current
		DESCRIPTION
				"TYPE: - Button
					Restart  cmdID= 4  value= 1  "
		::= { iqaes00CmdEntry 4 }


	iqaes00SetupBuildNo OBJECT-TYPE
		SYNTAX		RollCallString
		MAX-ACCESS		read-only
		STATUS			current
		DESCRIPTION
				"TYPE: - Display
					Build No  cmdID= 5  format=   "
		::= { iqaes00CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S36094328
--				:
-- Comments		: Serial Number, Alpha-numberic string
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 1
--				: n
-- Comments		: n >= 0    Number of connected rollcall session
--
---------------------------------------------------------------------------------------------------
-- Header		: INFORMATION1
--
-- MIB ref		: swCardEventLogSlotXX       .12.73.78.70.79.82.77.65.84.73.79.78.49
-- absolute OID	: 1.3.6.1.4.1.7995.2.6.1.1.XX.12.73.78.70.79.82.77.65.84.73.79.78.49
-- Vary			: YES
--
-- Value(s)		: Info 1 field
--				: Any 19 char string
-- Comments		: User defined field 1.  If edit field is empty this is not logged
--
---------------------------------------------------------------------------------------------------
-- Header		: INFORMATION2
--
-- MIB ref		: swCardEventLogSlotXX       .12.73.78.70.79.82.77.65.84.73.79.78.50
-- absolute OID	: 1.3.6.1.4.1.7995.2.6.1.1.XX.12.73.78.70.79.82.77.65.84.73.79.78.50
-- Vary			: YES
--
-- Value(s)		: Info 2 field
--				: Any 19 char string
-- Comments		: User defined field 2.  If edit field is empty this is not logged
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: AES
--				:
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: AES
--				:
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2007-07-17T14:09:55Z
--				: -
-- Comments		: UTC time and date of box restart  ISO standardised
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: AES_In_1
--				:
-- Comments		:
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
-- Comments		:
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: AES_In_2
--				:
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: OK
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2007-07-17T14:10:48Z
--				: -
-- Comments		: Date and time of last modification of Gateway controls,  Note this appears every
--              : 5 seconds during continual control change, and/or 5 seconds after most recent update.
--              : Format local time on Gateway dd/mm/yy hh:mm:ss
--              : -  no control changes made since last start
--
---------------------------------------------------------------------------------------------------
-- Header		: INPUT_1_AUDIO_RATE
--
-- MIB ref		: swCardEventLogSlotXX       .18.73.78.80.85.84.95.49.95.65.85.68.73.79.95.82.65.84.69
-- absolute OID	: 1.3.6.1.4.1.7995.2.6.1.1.XX.18.73.78.80.85.84.95.49.95.65.85.68.73.79.95.82.65.84.69
-- Vary			: YES
--
-- Value(s)		: WARN:NoInput
--				: WARN:Unknown
--              : 32k
--              : 44.1k
--              : 48k
--              : 96k
-- Comments		:
--
---------------------------------------------------------------------------------------------------
-- Header		: INPUT_1_AUDIO_TYPE
--
-- MIB ref		: swCardEventLogSlotXX       .18.73.78.80.85.84.95.49.95.65.85.68.73.79.95.84.89.80.69
-- absolute OID	: 1.3.6.1.4.1.7995.2.6.1.1.XX.18.73.78.80.85.84.95.49.95.65.85.68.73.79.95.84.89.80.69
-- Vary			: YES
--
-- Value(s)		: WARN:NoInput
--				: PCM
--              : Non-PCM
-- Comments		:
--
---------------------------------------------------------------------------------------------------
-- Header		: INPUT_2_AUDIO_RATE
--
-- MIB ref		: swCardEventLogSlotXX       .18.73.78.80.85.84.95.50.95.65.85.68.73.79.95.82.65.84.69
-- absolute OID	: 1.3.6.1.4.1.7995.2.6.1.1.XX.18.73.78.80.85.84.95.50.95.65.85.68.73.79.95.82.65.84.69
-- Vary			: YES
--
-- Value(s)		: WARN:NoInput
--				: WARN:Unknown
--              : 32k
--              : 44.1k
--              : 48k
--              : 96k
-- Comments		:
--
---------------------------------------------------------------------------------------------------
-- Header		: INPUT_2_AUDIO_TYPE
--
-- MIB ref		: swCardEventLogSlotXX       .18.73.78.80.85.84.95.50.95.65.85.68.73.79.95.84.89.80.69
-- absolute OID	: 1.3.6.1.4.1.7995.2.6.1.1.XX.18.73.78.80.85.84.95.50.95.65.85.68.73.79.95.84.89.80.69
-- Vary			: YES
--
-- Value(s)		: WARN:NoInput
--				: PCM
--              : Non-PCM
-- Comments		:
--
---------------------------------------------------------------------------------------------------
-- Header		: INPUT_1_AUDIO_CS_MODE
--
-- MIB ref		: swCardEventLogSlotXX       .21.73.78.80.85.84.95.49.95.65.85.68.73.79.95.67.83.95.77.79.68.69
-- absolute OID	: 1.3.6.1.4.1.7995.2.6.1.1.XX.21.73.78.80.85.84.95.49.95.65.85.68.73.79.95.67.83.95.77.79.68.69
-- Vary			: YES
--
-- Value(s)		: WARN:NoInput
--				: n   where  0 <= n <= 15
-- Comments		:
--
---------------------------------------------------------------------------------------------------
-- Header		: INPUT_2_AUDIO_CS_MODE
--
-- MIB ref		: swCardEventLogSlotXX       .21.73.78.80.85.84.95.50.95.65.85.68.73.79.95.67.83.95.77.79.68.69
-- absolute OID	: 1.3.6.1.4.1.7995.2.6.1.1.XX.21.73.78.80.85.84.95.50.95.65.85.68.73.79.95.67.83.95.77.79.68.69
-- Vary			: YES
--
-- Value(s)		: WARN:NoInput
--				: n   where  0 <= n <= 15
-- Comments		:
--
---------------------------------------------------------------------------------------------------
