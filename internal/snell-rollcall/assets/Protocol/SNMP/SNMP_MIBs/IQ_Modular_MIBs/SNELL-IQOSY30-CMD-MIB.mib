-- ************************************************************************************
--        Snell Card:IQOSY30
--        Module Id#:571
--       Command Set:14
--          Filename:SNELL-IQOSY30-CMD-MIB.mib
--            Author:N Hewer
--              Date:13/11/2014
--              Time:14:23
--
-- Copyright (c) 2010 Snell Ltd
-- All rights reserved.
--
-- ************************************************************************************

SNELL-IQOSY30-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQOSY30,
    moduleIQOSY30MIB
        FROM SNELL-WILCOX-PRODUCT-REG;

 moduleIQOSY30CmdMi MODULE-IDENTITY
    LAST-UPDATED "1411131423Z"
    ORGANIZATION "Snell Ltd"
    CONTACT-INFO
        "Primary Author:N Hewer

         postal:    Southleigh Park House
                    Eastleigh Road
                    Havant, Hants
                    PO9 2PE
         phone:     +44 (0)23 92489000
         email:     snmp.support@snellgroup.com"
    DESCRIPTION
        "This file defines the Snell card, command set  translations."
    ::= { moduleIQOSY30MIB 1 }




--********************************************************************************
--*
--*  Snell Card:
--*  command set:
--*  list commands/menus:
--*
--******************************************************************************
	iqosy30CmdTable OBJECT-TYPE
		SYNTAX			SEQUENCE OF Iqosy30CmdEntry
		MAX-ACCESS		not-accessible
		STATUS			current
		DESCRIPTION
				"Note the instance of this table is relected in the command set Version"
		::= { moduleIQOSY30 1 }

	iqosy30CmdEntry OBJECT-TYPE
		SYNTAX		Iqosy30CmdEntry
		MAX-ACCESS		not-accessible
		STATUS			current
		DESCRIPTION
				"Entry in command table."
		INDEX	{ iqosy30SlotIndex }
		::= { iqosy30CmdTable 1 }

	Iqosy30CmdEntry ::=
		SEQUENCE {
			iqosy30SlotIndex
				Unsigned32,
			iqosy30VideoVideoInputSelect
				INTEGER,
			iqosy30VideoValidInputFormats62525i
				INTEGER,
			iqosy30VideoValidInputFormats52529i
				INTEGER,
			iqosy30VideoValidInputFormats72050p
				INTEGER,
			iqosy30VideoValidInputFormats72059p
				INTEGER,
			iqosy30VideoValidInputFormats108025i
				INTEGER,
			iqosy30VideoValidInputFormats108029i
				INTEGER,
			iqosy30VideoValidInputFormats108050pA
				INTEGER,
			iqosy30VideoValidInputFormats108059pA
				INTEGER,
			iqosy30VideoValidInputFormats108050pB
				INTEGER,
			iqosy30VideoValidInputFormats108059pB
				INTEGER,
			iqosy30VideoDefaultFormat
				INTEGER,
			iqosy30VideoDefaultOutput
				INTEGER,
			iqosy30VideoVideoProcampProcAmpEnable
				INTEGER,
			iqosy30VideoVideoProcampBlackLevel
				INTEGER,
			iqosy30VideoVideoProcampHueAdjust
				INTEGER,
			iqosy30VideoVideoProcampMasterVideoGain
				INTEGER,
			iqosy30VideoVideoProcampYGain
				INTEGER,
			iqosy30VideoVideoProcampCbCrGain
				INTEGER,
			iqosy30VideoVideoProcampYCTiming
				INTEGER,
			iqosy30VideoVideoProcampPictureposition
				INTEGER,
			iqosy30VideoVideoProcampModalIndex
				INTEGER,
			iqosy30VideoVideoProcampYCTimingnm
				INTEGER,
			iqosy30VideoVideoProcampPicturepositionnm
				INTEGER,
			iqosy30VideoBlankingBlankVANC
				INTEGER,
			iqosy30Blanking625BlankLinesLine23
				INTEGER,
			iqosy30Blanking625BlankLinesLine336
				INTEGER,
			iqosy30Blanking525BlankLinesLine21
				INTEGER,
			iqosy30Blanking525BlankLinesLine22
				INTEGER,
			iqosy30Blanking525BlankLinesLine283
				INTEGER,
			iqosy30Blanking525BlankLinesLine284
				INTEGER,
			iqosy30VideoBlankingBlankHANC
				INTEGER,
			iqosy30VideoOpticalLaserOff5305
				INTEGER,
			iqosy30VideoOpticalLaserOffonloss5306
				INTEGER,
			iqosy30VideoOpticalTxWavelength5300
				RollCallString,
			iqosy30VideoOpticalLaserBias5301
				RollCallString,
			iqosy30VideoOpticalLaserBiasState5302
				RollCallString,
			iqosy30VideoOpticalTxPower5303
				RollCallString,
			iqosy30VideoOpticalTxPowerState5304
				RollCallString,
			iqosy30VideoOpticalLaserOff5314
				INTEGER,
			iqosy30VideoOpticalLaserOffonloss5315
				INTEGER,
			iqosy30VideoOpticalTxWavelength5309
				RollCallString,
			iqosy30VideoOpticalLaserBias5310
				RollCallString,
			iqosy30VideoOpticalLaserBiasState5311
				RollCallString,
			iqosy30VideoOpticalTxPower5312
				RollCallString,
			iqosy30VideoOpticalTxPowerState5313
				RollCallString,
			iqosy30VideoOpticalRxPower5307
				RollCallString,
			iqosy30VideoOpticalRxPowerState5308
				RollCallString,
			iqosy30VideoOpticalRxPower5316
				RollCallString,
			iqosy30VideoOpticalRxPowerState5317
				RollCallString,
			iqosy30VideoCaption
				INTEGER,
			iqosy30VideoCaptionEditCaption
				RollCallString,
			iqosy30VideoPattern
				INTEGER,
			iqosy30VideoFreeze
				INTEGER,
			iqosy30VideoFreezeManualFreeze
				INTEGER,
			iqosy30AudioAudioInputSelect
				INTEGER,
			iqosy30EmbeddersEmbedder1Enable
				INTEGER,
			iqosy30EmbeddersEmbedder1SourceLNonPCM5034
				INTEGER,
			iqosy30EmbeddersEmbedder1SourceR5035
				INTEGER,
			iqosy30EmbeddersEmbedder1Mute3240
				INTEGER,
			iqosy30EmbeddersEmbedder1MuteonVbit3272
				INTEGER,
			iqosy30EmbeddersEmbedder1InvertL3160
				INTEGER,
			iqosy30EmbeddersEmbedder1InvertR3161
				INTEGER,
			iqosy30EmbeddersEmbedder1GainL3080
				INTEGER,
			iqosy30EmbeddersEmbedder1GainR3081
				INTEGER,
			iqosy30EmbeddersEmbedder1PairMode3930
				INTEGER,
			iqosy30EmbeddersEmbedder1SourceLNonPCM5036
				INTEGER,
			iqosy30EmbeddersEmbedder1SourceR5037
				INTEGER,
			iqosy30EmbeddersEmbedder1Mute3241
				INTEGER,
			iqosy30EmbeddersEmbedder1MuteonVbit3273
				INTEGER,
			iqosy30EmbeddersEmbedder1InvertL3162
				INTEGER,
			iqosy30EmbeddersEmbedder1InvertR3163
				INTEGER,
			iqosy30EmbeddersEmbedder1GainL3082
				INTEGER,
			iqosy30EmbeddersEmbedder1GainR3083
				INTEGER,
			iqosy30EmbeddersEmbedder1PairMode3931
				INTEGER,
			iqosy30EmbeddersEmbedder1NonModalIndex
				INTEGER,
			iqosy30EmbeddersEmbedder1NonModalGain
				INTEGER,
			iqosy30EmbeddersEmbedder2Enable
				INTEGER,
			iqosy30EmbeddersEmbedder2SourceLNonPCM5038
				INTEGER,
			iqosy30EmbeddersEmbedder2SourceR5039
				INTEGER,
			iqosy30EmbeddersEmbedder2Mute3242
				INTEGER,
			iqosy30EmbeddersEmbedder2MuteonVbit3274
				INTEGER,
			iqosy30EmbeddersEmbedder2InvertL3164
				INTEGER,
			iqosy30EmbeddersEmbedder2InvertR3165
				INTEGER,
			iqosy30EmbeddersEmbedder2GainL3084
				INTEGER,
			iqosy30EmbeddersEmbedder2GainR3085
				INTEGER,
			iqosy30EmbeddersEmbedder2PairMode3932
				INTEGER,
			iqosy30EmbeddersEmbedder2SourceLNonPCM5040
				INTEGER,
			iqosy30EmbeddersEmbedder2SourceR5041
				INTEGER,
			iqosy30EmbeddersEmbedder2Mute3243
				INTEGER,
			iqosy30EmbeddersEmbedder2MuteonVbit3275
				INTEGER,
			iqosy30EmbeddersEmbedder2InvertL3166
				INTEGER,
			iqosy30EmbeddersEmbedder2InvertR3167
				INTEGER,
			iqosy30EmbeddersEmbedder2GainL3086
				INTEGER,
			iqosy30EmbeddersEmbedder2GainR3087
				INTEGER,
			iqosy30EmbeddersEmbedder2PairMode3933
				INTEGER,
			iqosy30EmbeddersEmbedder3Enable
				INTEGER,
			iqosy30EmbeddersEmbedder3SourceLNonPCM5042
				INTEGER,
			iqosy30EmbeddersEmbedder3SourceR5043
				INTEGER,
			iqosy30EmbeddersEmbedder3Mute3244
				INTEGER,
			iqosy30EmbeddersEmbedder3MuteonVbit3276
				INTEGER,
			iqosy30EmbeddersEmbedder3InvertL3168
				INTEGER,
			iqosy30EmbeddersEmbedder3InvertR3169
				INTEGER,
			iqosy30EmbeddersEmbedder3GainL3088
				INTEGER,
			iqosy30EmbeddersEmbedder3GainR3089
				INTEGER,
			iqosy30EmbeddersEmbedder3PairMode3934
				INTEGER,
			iqosy30EmbeddersEmbedder3SourceLNonPCM5044
				INTEGER,
			iqosy30EmbeddersEmbedder3SourceR5045
				INTEGER,
			iqosy30EmbeddersEmbedder3Mute3245
				INTEGER,
			iqosy30EmbeddersEmbedder3MuteonVbit3277
				INTEGER,
			iqosy30EmbeddersEmbedder3InvertL3170
				INTEGER,
			iqosy30EmbeddersEmbedder3InvertR3171
				INTEGER,
			iqosy30EmbeddersEmbedder3GainL3090
				INTEGER,
			iqosy30EmbeddersEmbedder3GainR3091
				INTEGER,
			iqosy30EmbeddersEmbedder3PairMode3935
				INTEGER,
			iqosy30EmbeddersEmbedder4Enable
				INTEGER,
			iqosy30EmbeddersEmbedder4SourceLNonPCM5046
				INTEGER,
			iqosy30EmbeddersEmbedder4SourceR5047
				INTEGER,
			iqosy30EmbeddersEmbedder4Mute3246
				INTEGER,
			iqosy30EmbeddersEmbedder4MuteonVbit3278
				INTEGER,
			iqosy30EmbeddersEmbedder4InvertL3172
				INTEGER,
			iqosy30EmbeddersEmbedder4InvertR3173
				INTEGER,
			iqosy30EmbeddersEmbedder4GainL3092
				INTEGER,
			iqosy30EmbeddersEmbedder4GainR3093
				INTEGER,
			iqosy30EmbeddersEmbedder4PairMode3936
				INTEGER,
			iqosy30EmbeddersEmbedder4SourceLNonPCM5048
				INTEGER,
			iqosy30EmbeddersEmbedder4SourceR5049
				INTEGER,
			iqosy30EmbeddersEmbedder4Mute3247
				INTEGER,
			iqosy30EmbeddersEmbedder4MuteonVbit3279
				INTEGER,
			iqosy30EmbeddersEmbedder4InvertL3174
				INTEGER,
			iqosy30EmbeddersEmbedder4InvertR3175
				INTEGER,
			iqosy30EmbeddersEmbedder4GainL3094
				INTEGER,
			iqosy30EmbeddersEmbedder4GainR3095
				INTEGER,
			iqosy30EmbeddersEmbedder4PairMode3937
				INTEGER,
			iqosy30AudioDelayDelaysVideoDelay
				INTEGER,
			iqosy30AudioDelayDelaysManualDelay
				INTEGER,
			iqosy30AudioDelayDelaysTrack14Delay
				INTEGER,
			iqosy30AudioDelayDelaysTrack15Delay
				INTEGER,
			iqosy30AudioDelayDelaysTrack16Delay
				INTEGER,
			iqosy30AudioDelayDelaysTrack17Delay
				INTEGER,
			iqosy30AudioDelayDelaysCoarseDelay
				INTEGER,
			iqosy30AudioDelayDelaysFineDelay
				INTEGER,
			iqosy30AudioDelayDelayStatusTotalDelay
				RollCallString,
			iqosy30AudioDelayDelayStatusVideoDelay
				RollCallString,
			iqosy30AudioDelayDelayStatusManualDelay
				RollCallString,
			iqosy30AudioDelayDelayStatusTrack14Delay
				RollCallString,
			iqosy30AudioDelayDelayStatusTrack15Delay
				RollCallString,
			iqosy30AudioDelayDelayStatusTrack16Delay
				RollCallString,
			iqosy30AudioDelayDelayStatusTrack17Delay
				RollCallString,
			iqosy30AudioDolbyEDolbyEAutoAlign
				INTEGER,
			iqosy30AudioDolbyEUserDolbyELine
				INTEGER,
			iqosy30AudioDolbyEDolbyEAutoLineNo
				INTEGER,
			iqosy30AudioDolbyELineStandard
				INTEGER,
			iqosy30AudioToneFrequency
				INTEGER,
			iqosy30AudioToneChannelident
				INTEGER,
			iqosy30AudioAudioMonitorSilenceLevel
				INTEGER,
			iqosy30AudioAudioMonitorOverloadLevel
				INTEGER,
			iqosy30AudioAudioMonitorWarningTimer
				INTEGER,
			iqosy30Genlock
				INTEGER,
			iqosy30GenlockFreerunFrequency
				INTEGER,
			iqosy30GenlockGenlockHPhase3790
				INTEGER,
			iqosy30GenlockGenlockVPhase3791
				INTEGER,
			iqosy30GenlockVideoHdelay3794
				INTEGER,
			iqosy30GenlockVideoVdelay3795
				INTEGER,
			iqosy30GenlockVideoFdelay
				INTEGER,
			iqosy30GenlockGenlocksaveindex
				INTEGER,
			iqosy30GenlockGenlockHPhase3992
				INTEGER,
			iqosy30GenlockGenlockVPhase3993
				INTEGER,
			iqosy30GenlockVideoHdelay3994
				INTEGER,
			iqosy30GenlockVideoVdelay3995
				INTEGER,
			iqosy30ReferenceSelect
				INTEGER,
			iqosy30StatusStatusDisplay
				INTEGER,
			iqosy30StatusProduct
				RollCallString,
			iqosy30StatusSoftwareVersion
				RollCallString,
			iqosy30StatusSerialNo
				RollCallString,
			iqosy30StatusFactoryDefaults
				INTEGER,
			iqosy30StatusDefaultSetting
				INTEGER,
			iqosy30StatusRestart
				INTEGER,
			iqosy30StatusBuild
				RollCallString,
			iqosy30StatusPCB
				RollCallString,
			iqosy30StatusKOSVersion
				RollCallString,
			iqosy30StatusFirmwareVersion
				RollCallString,
			iqosy30StatusUpTime
				RollCallString,
			iqosy30MemoriesSelMemory
				INTEGER,
			iqosy30MemoriesSetMemName
				RollCallString,
			iqosy30MemoriesRecallMemory
				INTEGER,
			iqosy30MemoriesSaveMemory
				INTEGER,
			iqosy30MemoriesLastUserMemory
				RollCallString,
			iqosy30MemoriesClearMemory
				INTEGER,
			iqosy30MemoriesMemoryNamesMemory1Name
				RollCallString,
			iqosy30MemoriesMemoryNamesMemory2Name
				RollCallString,
			iqosy30MemoriesMemoryNamesMemory3Name
				RollCallString,
			iqosy30MemoriesMemoryNamesMemory4Name
				RollCallString,
			iqosy30MemoriesMemoryNamesMemory5Name
				RollCallString,
			iqosy30MemoriesMemoryNamesMemory6Name
				RollCallString,
			iqosy30MemoriesMemoryNamesMemory7Name
				RollCallString,
			iqosy30MemoriesMemoryNamesMemory8Name
				RollCallString,
			iqosy30MemoriesMemoryNamesMemory9Name
				RollCallString,
			iqosy30MemoriesMemoryNamesMemory10Name
				RollCallString,
			iqosy30MemoriesMemoryNamesMemory11Name
				RollCallString,
			iqosy30MemoriesMemoryNamesMemory12Name
				RollCallString,
			iqosy30MemoriesMemoryNamesMemory13Name
				RollCallString,
			iqosy30MemoriesMemoryNamesMemory14Name
				RollCallString,
			iqosy30MemoriesMemoryNamesMemory15Name
				RollCallString,
			iqosy30MemoriesMemoryNamesMemory16Name
				RollCallString,
			iqosy30LoggingLogMiscSlotStarten
				INTEGER,
			iqosy30LoggingLogMiscSlotStart
				RollCallString,
			iqosy30LoggingLogMiscSlotWidthen
				INTEGER,
			iqosy30LoggingLogMiscSlotWidth
				RollCallString,
			iqosy30LoggingLogMiscRearStatusen
				INTEGER,
			iqosy30LoggingLogMiscRearStatus
				RollCallString,
			iqosy30LoggingLogMiscRearIDen
				INTEGER,
			iqosy30LoggingLogMiscRearID
				RollCallString,
			iqosy30LoggingLogMiscFirmwareVersionen
				INTEGER,
			iqosy30LoggingLogMiscFirmwareVersion
				RollCallString,
			iqosy30LoggingLogMiscLicensedOptionsen
				INTEGER,
			iqosy30LoggingLogMiscLicensedOptions
				RollCallString,
			iqosy30LoggingLogMiscBuildNumberen
				INTEGER,
			iqosy30LoggingLogMiscBuildNumber
				RollCallString,
			iqosy30LoggingLogMiscOSVersionen
				INTEGER,
			iqosy30LoggingLogMiscOSVersion
				RollCallString,
			iqosy30LoggingLogMiscHardwareVersionen
				INTEGER,
			iqosy30LoggingLogMiscHardwareVersion
				RollCallString,
			iqosy30LoggingLogMiscUptimeen
				INTEGER,
			iqosy30LoggingLogMiscUptime
				RollCallString,
			iqosy30LoggingLogMiscSerialNumberen
				INTEGER,
			iqosy30LoggingLogMiscSerialNumber
				RollCallString,
			iqosy30LoggingLogVideoInput1Input1en
				INTEGER,
			iqosy30LoggingLogVideoInput1Input1
				RollCallString,
			iqosy30LoggingLogVideoInput1Input1Standarden
				INTEGER,
			iqosy30LoggingLogVideoInput1Input1Standard
				RollCallString,
			iqosy30LoggingLogVideoInput1In1SDIERRSen
				INTEGER,
			iqosy30LoggingLogVideoInput1In1SDIERRS
				RollCallString,
			iqosy30LoggingLogVideoInput1In1SDIANCERRSen
				INTEGER,
			iqosy30LoggingLogVideoInput1In1SDIANCERRS
				RollCallString,
			iqosy30LoggingLogVideoInput1Input1Typeen
				INTEGER,
			iqosy30LoggingLogVideoInput1Input1Type
				RollCallString,
			iqosy30LoggingLogVideoInput1Input1Identen
				INTEGER,
			iqosy30LoggingLogVideoInput1Input1Ident
				RollCallString,
			iqosy30LoggingLogVideoInput1Input3en
				INTEGER,
			iqosy30LoggingLogVideoInput1Input3
				RollCallString,
			iqosy30LoggingLogVideoInput1Input3Standarden
				INTEGER,
			iqosy30LoggingLogVideoInput1Input3Standard
				RollCallString,
			iqosy30LoggingLogVideoInput1In3SDIERRSen
				INTEGER,
			iqosy30LoggingLogVideoInput1In3SDIERRS
				RollCallString,
			iqosy30LoggingLogVideoInput1In3SDIANCERRSen
				INTEGER,
			iqosy30LoggingLogVideoInput1In3SDIANCERRS
				RollCallString,
			iqosy30LoggingLogVideoInput1Input3Typeen
				INTEGER,
			iqosy30LoggingLogVideoInput1Input3Type
				RollCallString,
			iqosy30LoggingLogVideoInput1Input3Identen
				INTEGER,
			iqosy30LoggingLogVideoInput1Input3Ident
				RollCallString,
			iqosy30LoggingLogVideoInput2Input2en
				INTEGER,
			iqosy30LoggingLogVideoInput2Input2
				RollCallString,
			iqosy30LoggingLogVideoInput2Input2Standarden
				INTEGER,
			iqosy30LoggingLogVideoInput2Input2Standard
				RollCallString,
			iqosy30LoggingLogVideoInput2In2SDIERRSen
				INTEGER,
			iqosy30LoggingLogVideoInput2In2SDIERRS
				RollCallString,
			iqosy30LoggingLogVideoInput2In2SDIANCERRSen
				INTEGER,
			iqosy30LoggingLogVideoInput2In2SDIANCERRS
				RollCallString,
			iqosy30LoggingLogVideoInput2Input2Typeen
				INTEGER,
			iqosy30LoggingLogVideoInput2Input2Type
				RollCallString,
			iqosy30LoggingLogVideoInput2Input2Identen
				INTEGER,
			iqosy30LoggingLogVideoInput2Input2Ident
				RollCallString,
			iqosy30LoggingLogVideoInput2Input4en
				INTEGER,
			iqosy30LoggingLogVideoInput2Input4
				RollCallString,
			iqosy30LoggingLogVideoInput2Input4Standarden
				INTEGER,
			iqosy30LoggingLogVideoInput2Input4Standard
				RollCallString,
			iqosy30LoggingLogVideoInput2In4SDIERRSen
				INTEGER,
			iqosy30LoggingLogVideoInput2In4SDIERRS
				RollCallString,
			iqosy30LoggingLogVideoInput2In4SDIANCERRSen
				INTEGER,
			iqosy30LoggingLogVideoInput2In4SDIANCERRS
				RollCallString,
			iqosy30LoggingLogVideoInput2Input4Typeen
				INTEGER,
			iqosy30LoggingLogVideoInput2Input4Type
				RollCallString,
			iqosy30LoggingLogVideoInput2Input4Identen
				INTEGER,
			iqosy30LoggingLogVideoInput2Input4Ident
				RollCallString,
			iqosy30LoggingLogReferenceRef1Stateen
				INTEGER,
			iqosy30LoggingLogReferenceRef1State
				RollCallString,
			iqosy30LoggingLogReferenceRef1Standarden
				INTEGER,
			iqosy30LoggingLogReferenceRef1Standard
				RollCallString,
			iqosy30LoggingLogReferenceRef1Typeen
				INTEGER,
			iqosy30LoggingLogReferenceRef1Type
				RollCallString,
			iqosy30LoggingLogReferenceGenlock1Stateen
				INTEGER,
			iqosy30LoggingLogReferenceGenlock1State
				RollCallString,
			iqosy30LoggingLogAudioInput1Input1Audio1en
				INTEGER,
			iqosy30LoggingLogAudioInput1Input1Audio1
				RollCallString,
			iqosy30LoggingLogAudioInput1Input1Audio2en
				INTEGER,
			iqosy30LoggingLogAudioInput1Input1Audio2
				RollCallString,
			iqosy30LoggingLogAudioInput1Input1Audio3en
				INTEGER,
			iqosy30LoggingLogAudioInput1Input1Audio3
				RollCallString,
			iqosy30LoggingLogAudioInput1Input1Audio4en
				INTEGER,
			iqosy30LoggingLogAudioInput1Input1Audio4
				RollCallString,
			iqosy30LoggingLogAudioInput1Input1Audio5en
				INTEGER,
			iqosy30LoggingLogAudioInput1Input1Audio5
				RollCallString,
			iqosy30LoggingLogAudioInput1Input1Audio6en
				INTEGER,
			iqosy30LoggingLogAudioInput1Input1Audio6
				RollCallString,
			iqosy30LoggingLogAudioInput1Input1Audio7en
				INTEGER,
			iqosy30LoggingLogAudioInput1Input1Audio7
				RollCallString,
			iqosy30LoggingLogAudioInput1Input1Audio8en
				INTEGER,
			iqosy30LoggingLogAudioInput1Input1Audio8
				RollCallString,
			iqosy30LoggingLogAudioInput2Input2Audio1en
				INTEGER,
			iqosy30LoggingLogAudioInput2Input2Audio1
				RollCallString,
			iqosy30LoggingLogAudioInput2Input2Audio2en
				INTEGER,
			iqosy30LoggingLogAudioInput2Input2Audio2
				RollCallString,
			iqosy30LoggingLogAudioInput2Input2Audio3en
				INTEGER,
			iqosy30LoggingLogAudioInput2Input2Audio3
				RollCallString,
			iqosy30LoggingLogAudioInput2Input2Audio4en
				INTEGER,
			iqosy30LoggingLogAudioInput2Input2Audio4
				RollCallString,
			iqosy30LoggingLogAudioInput2Input2Audio5en
				INTEGER,
			iqosy30LoggingLogAudioInput2Input2Audio5
				RollCallString,
			iqosy30LoggingLogAudioInput2Input2Audio6en
				INTEGER,
			iqosy30LoggingLogAudioInput2Input2Audio6
				RollCallString,
			iqosy30LoggingLogAudioInput2Input2Audio7en
				INTEGER,
			iqosy30LoggingLogAudioInput2Input2Audio7
				RollCallString,
			iqosy30LoggingLogAudioInput2Input2Audio8en
				INTEGER,
			iqosy30LoggingLogAudioInput2Input2Audio8
				RollCallString,
			iqosy30LoggingLogAudioInput3Input3Audio1en
				INTEGER,
			iqosy30LoggingLogAudioInput3Input3Audio1
				RollCallString,
			iqosy30LoggingLogAudioInput3Input3Audio2en
				INTEGER,
			iqosy30LoggingLogAudioInput3Input3Audio2
				RollCallString,
			iqosy30LoggingLogAudioInput3Input3Audio3en
				INTEGER,
			iqosy30LoggingLogAudioInput3Input3Audio3
				RollCallString,
			iqosy30LoggingLogAudioInput3Input3Audio4en
				INTEGER,
			iqosy30LoggingLogAudioInput3Input3Audio4
				RollCallString,
			iqosy30LoggingLogAudioInput3Input3Audio5en
				INTEGER,
			iqosy30LoggingLogAudioInput3Input3Audio5
				RollCallString,
			iqosy30LoggingLogAudioInput3Input3Audio6en
				INTEGER,
			iqosy30LoggingLogAudioInput3Input3Audio6
				RollCallString,
			iqosy30LoggingLogAudioInput3Input3Audio7en
				INTEGER,
			iqosy30LoggingLogAudioInput3Input3Audio7
				RollCallString,
			iqosy30LoggingLogAudioInput3Input3Audio8en
				INTEGER,
			iqosy30LoggingLogAudioInput3Input3Audio8
				RollCallString,
			iqosy30LoggingLogAudioInput4Input4Audio1en
				INTEGER,
			iqosy30LoggingLogAudioInput4Input4Audio1
				RollCallString,
			iqosy30LoggingLogAudioInput4Input4Audio2en
				INTEGER,
			iqosy30LoggingLogAudioInput4Input4Audio2
				RollCallString,
			iqosy30LoggingLogAudioInput4Input4Audio3en
				INTEGER,
			iqosy30LoggingLogAudioInput4Input4Audio3
				RollCallString,
			iqosy30LoggingLogAudioInput4Input4Audio4en
				INTEGER,
			iqosy30LoggingLogAudioInput4Input4Audio4
				RollCallString,
			iqosy30LoggingLogAudioInput4Input4Audio5en
				INTEGER,
			iqosy30LoggingLogAudioInput4Input4Audio5
				RollCallString,
			iqosy30LoggingLogAudioInput4Input4Audio6en
				INTEGER,
			iqosy30LoggingLogAudioInput4Input4Audio6
				RollCallString,
			iqosy30LoggingLogAudioInput4Input4Audio7en
				INTEGER,
			iqosy30LoggingLogAudioInput4Input4Audio7
				RollCallString,
			iqosy30LoggingLogAudioInput4Input4Audio8en
				INTEGER,
			iqosy30LoggingLogAudioInput4Input4Audio8
				RollCallString,
			iqosy30LoggingLogVideoOutputOutput1Typeen
				INTEGER,
			iqosy30LoggingLogVideoOutputOutput1Type
				RollCallString,
			iqosy30LoggingLogVideoOutputOutput1Stateen
				INTEGER,
			iqosy30LoggingLogVideoOutputOutput1State
				RollCallString,
			iqosy30LoggingLogVideoOutputOutput1Stden
				INTEGER,
			iqosy30LoggingLogVideoOutputOutput1Std
				RollCallString,
			iqosy30LoggingLogVideoOutputOutput1Captionen
				INTEGER,
			iqosy30LoggingLogVideoOutputOutput1Caption
				RollCallString,
			iqosy30LoggingLogVideoOutputOutput1en
				INTEGER,
			iqosy30LoggingLogVideoOutputOutput1
				RollCallString,
			iqosy30LoggingLogAudioOutputOutput1Embed11en
				INTEGER,
			iqosy30LoggingLogAudioOutputOutput1Embed11
				RollCallString,
			iqosy30LoggingLogAudioOutputOutput1Embed12en
				INTEGER,
			iqosy30LoggingLogAudioOutputOutput1Embed12
				RollCallString,
			iqosy30LoggingLogAudioOutputOutput1Embed21en
				INTEGER,
			iqosy30LoggingLogAudioOutputOutput1Embed21
				RollCallString,
			iqosy30LoggingLogAudioOutputOutput1Embed22en
				INTEGER,
			iqosy30LoggingLogAudioOutputOutput1Embed22
				RollCallString,
			iqosy30LoggingLogAudioOutputOutput1Embed31en
				INTEGER,
			iqosy30LoggingLogAudioOutputOutput1Embed31
				RollCallString,
			iqosy30LoggingLogAudioOutputOutput1Embed32en
				INTEGER,
			iqosy30LoggingLogAudioOutputOutput1Embed32
				RollCallString,
			iqosy30LoggingLogAudioOutputOutput1Embed41en
				INTEGER,
			iqosy30LoggingLogAudioOutputOutput1Embed41
				RollCallString,
			iqosy30LoggingLogAudioOutputOutput1Embed42en
				INTEGER,
			iqosy30LoggingLogAudioOutputOutput1Embed42
				RollCallString,
			iqosy30LoggingLogAudioOutputOutput1Embed51en
				INTEGER,
			iqosy30LoggingLogAudioOutputOutput1Embed51
				RollCallString,
			iqosy30LoggingLogAudioOutputOutput1Embed52en
				INTEGER,
			iqosy30LoggingLogAudioOutputOutput1Embed52
				RollCallString,
			iqosy30LoggingLogAudioOutputOutput1Embed61en
				INTEGER,
			iqosy30LoggingLogAudioOutputOutput1Embed61
				RollCallString,
			iqosy30LoggingLogAudioOutputOutput1Embed62en
				INTEGER,
			iqosy30LoggingLogAudioOutputOutput1Embed62
				RollCallString,
			iqosy30LoggingLogAudioOutputOutput1Embed71en
				INTEGER,
			iqosy30LoggingLogAudioOutputOutput1Embed71
				RollCallString,
			iqosy30LoggingLogAudioOutputOutput1Embed72en
				INTEGER,
			iqosy30LoggingLogAudioOutputOutput1Embed72
				RollCallString,
			iqosy30LoggingLogAudioOutputOutput1Embed81en
				INTEGER,
			iqosy30LoggingLogAudioOutputOutput1Embed81
				RollCallString,
			iqosy30LoggingLogAudioOutputOutput1Embed82en
				INTEGER,
			iqosy30LoggingLogAudioOutputOutput1Embed82
				RollCallString,
			iqosy30LoggingLogAudioOutputOutputEmbeden
				INTEGER,
			iqosy30LoggingLogAudioOutputOutputEmbed
				RollCallString,
			iqosy30LoggingLogFiberTx1BiasStateen
				INTEGER,
			iqosy30LoggingLogFiberTx1BiasState
				RollCallString,
			iqosy30LoggingLogFiberTx2BiasStateen
				INTEGER,
			iqosy30LoggingLogFiberTx2BiasState
				RollCallString,
			iqosy30LoggingLogFiberTx1Biasen
				INTEGER,
			iqosy30LoggingLogFiberTx1Bias
				RollCallString,
			iqosy30LoggingLogFiberTx2Biasen
				INTEGER,
			iqosy30LoggingLogFiberTx2Bias
				RollCallString,
			iqosy30LoggingLogFiberTx1PwrStateen
				INTEGER,
			iqosy30LoggingLogFiberTx1PwrState
				RollCallString,
			iqosy30LoggingLogFiberTx2PwrStateen
				INTEGER,
			iqosy30LoggingLogFiberTx2PwrState
				RollCallString,
			iqosy30LoggingLogFiberTx1Poweren
				INTEGER,
			iqosy30LoggingLogFiberTx1Power
				RollCallString,
			iqosy30LoggingLogFiberTx2Poweren
				INTEGER,
			iqosy30LoggingLogFiberTx2Power
				RollCallString,
			iqosy30LoggingLogFiberRx1Stateen
				INTEGER,
			iqosy30LoggingLogFiberRx1State
				RollCallString,
			iqosy30LoggingLogFiberRx2Stateen
				INTEGER,
			iqosy30LoggingLogFiberRx2State
				RollCallString,
			iqosy30LoggingLogFiberRx1Poweren
				INTEGER,
			iqosy30LoggingLogFiberRx1Power
				RollCallString,
			iqosy30LoggingLogFiberRx2Poweren
				INTEGER,
			iqosy30LoggingLogFiberRx2Power
				RollCallString,
			iqosy30SetupRollTracksRollTrackIndex1495
				INTEGER,
			iqosy30SetupRollTracksRollTrackSource1496
				INTEGER,
			iqosy30SetupRollTracksRollTrackDisable
				INTEGER,
			iqosy30SetupRollTracksRollTrackAddress1497
				RollCallString,
			iqosy30SetupRollTracksRollTrackCommand1498
				RollCallString,
			iqosy30SetupRollTracksRollTrackSending
				RollCallString,
			iqosy30SetupRollTracksRollTrackStatus
				RollCallString,
			iqosy30SetupRollTracksRollTrackIndex2870
				INTEGER,
			iqosy30SetupRollTracksRollTrackSource2871
				INTEGER,
			iqosy30SetupRollTracksRollTrackAddress2872
				RollCallString,
			iqosy30SetupRollTracksRollTrackCommand2873
				RollCallString
		}

	iqosy30SlotIndex OBJECT-TYPE
		SYNTAX		Unsigned32
		MAX-ACCESS		not-accessible
		STATUS			current
		DESCRIPTION
				"The unique Index value for each slot.  Its value
					ranges between 1 and the value of slotNumber."
		::= { iqosy30CmdEntry 0 }


	iqosy30VideoVideoInputSelect OBJECT-TYPE
		SYNTAX		INTEGER {
							val-Input-1(0),
							val-Input-2(1),
							val-Option-1(2),
							val-Option-2(3)
							}
		MAX-ACCESS		read-write
		STATUS			current
		DESCRIPTION
				"TYPE: - RadiobuttonList
				 PAGE: - Video
					Video Input Select  cmdID= 2251 
					Input 1  value= 0  
					Input 2  value= 1  
					Option 1  value= 2  
					Option 2  value= 3  "
		::= { iqosy30CmdEntry 2251 }


	iqosy30VideoValidInputFormats62525i OBJECT-TYPE
		SYNTAX		INTEGER { disable(0), enable(1) }
		MAX-ACCESS		read-write
		STATUS			current
		DESCRIPTION
				"TYPE: - Checkbox
				 PAGE: - Video
					625/25i  cmdID= 3802 "
		::= { iqosy30CmdEntry 3802 }


	iqosy30VideoValidInputFormats52529i OBJECT-TYPE
		SYNTAX		INTEGER { disable(0), enable(1) }
		MAX-ACCESS		read-write
		STATUS			current
		DESCRIPTION
				"TYPE: - Checkbox
				 PAGE: - Video
					525/29i  cmdID= 3803 "
		::= { iqosy30CmdEntry 3803 }


	iqosy30VideoValidInputFormats72050p OBJECT-TYPE
		SYNTAX		INTEGER { disable(0), enable(1) }
		MAX-ACCESS		read-write
		STATUS			current
		DESCRIPTION
				"TYPE: - Checkbox
				 PAGE: - Video
					720/50p  cmdID= 3809 "
		::= { iqosy30CmdEntry 3809 }


	iqosy30VideoValidInputFormats72059p OBJECT-TYPE
		SYNTAX		INTEGER { disable(0), enable(1) }
		MAX-ACCESS		read-write
		STATUS			current
		DESCRIPTION
				"TYPE: - Checkbox
				 PAGE: - Video
					720/59p  cmdID= 3810 "
		::= { iqosy30CmdEntry 3810 }


	iqosy30VideoValidInputFormats108025i OBJECT-TYPE
		SYNTAX		INTEGER { disable(0), enable(1) }
		MAX-ACCESS		read-write
		STATUS			current
		DESCRIPTION
				"TYPE: - Checkbox
				 PAGE: - Video
					1080/25i  cmdID= 3817 "
		::= { iqosy30CmdEntry 3817 }


	iqosy30VideoValidInputFormats108029i OBJECT-TYPE
		SYNTAX		INTEGER { disable(0), enable(1) }
		MAX-ACCESS		read-write
		STATUS			current
		DESCRIPTION
				"TYPE: - Checkbox
				 PAGE: - Video
					1080/29i  cmdID= 3818 "
		::= { iqosy30CmdEntry 3818 }


	iqosy30VideoValidInputFormats108050pA OBJECT-TYPE
		SYNTAX		INTEGER { disable(0), enable(1) }
		MAX-ACCESS		read-write
		STATUS			current
		DESCRIPTION
				"TYPE: - Checkbox
				 PAGE: - Video
					1080/50p-A  cmdID= 3822 "
		::= { iqosy30CmdEntry 3822 }


	iqosy30VideoValidInputFormats108059pA OBJECT-TYPE
		SYNTAX		INTEGER { disable(0), enable(1) }
		MAX-ACCESS		read-write
		STATUS			current
		DESCRIPTION
				"TYPE: - Checkbox
				 PAGE: - Video
					1080/59p-A  cmdID= 3823 "
		::= { iqosy30CmdEntry 3823 }


	iqosy30VideoValidInputFormats108050pB OBJECT-TYPE
		SYNTAX		INTEGER { disable(0), enable(1) }
		MAX-ACCESS		read-write
		STATUS			current
		DESCRIPTION
				"TYPE: - Checkbox
				 PAGE: - Video
					1080/50p-B  cmdID= 3825 "
		::= { iqosy30CmdEntry 3825 }


	iqosy30VideoValidInputFormats108059pB OBJECT-TYPE
		SYNTAX		INTEGER { disable(0), enable(1) }
		MAX-ACCESS		read-write
		STATUS			current
		DESCRIPTION
				"TYPE: - Checkbox
				 PAGE: - Video
					1080/59p-B  cmdID= 3826 "
		::= { iqosy30CmdEntry 3826 }


	iqosy30VideoDefaultFormat OBJECT-TYPE
		SYNTAX		INTEGER {
							val-Last-Known-Good(1),
							val-625-25i(2),
							val-525-29i(3),
							val-720-50p(9),
							val-720-59p(10),
							val-1080-25i(17),
							val-1080-29i(18),
							val-1080-50p-A(22),
							val-1080-59p-A(23),
							val-1080-50p-B(25),
							val-1080-59p-B(26)
							}
		MAX-ACCESS		read-write
		STATUS			current
		DESCRIPTION
				"TYPE: - RadiobuttonList
				 PAGE: - Video
					Default Format  cmdID= 3793 
					Last Known Good  value= 1  
					625/25i  value= 2  
					525/29i  value= 3  
					720/50p  value= 9  
					720/59p  value= 10  
					1080/25i  value= 17  
					1080/29i  value= 18  
					1080/50p-A  value= 22  
					1080/59p-A  value= 23  
					1080/50p-B  value= 25  
					1080/59p-B  value= 26  "
		::= { iqosy30CmdEntry 3793 }


	iqosy30VideoDefaultOutput OBJECT-TYPE
		SYNTAX		INTEGER {
							val-Black(0),
							val-Freeze(1),
							val-Pattern(2)
							}
		MAX-ACCESS		read-write
		STATUS			current
		DESCRIPTION
				"TYPE: - RadiobuttonList
				 PAGE: - Video
					Default Output  cmdID= 2623 
					Black  value= 0  
					Freeze  value= 1  
					Pattern  value= 2  "
		::= { iqosy30CmdEntry 2623 }


	iqosy30VideoVideoProcampProcAmpEnable OBJECT-TYPE
		SYNTAX		INTEGER { disable(0), enable(1) }
		MAX-ACCESS		read-write
		STATUS			current
		DESCRIPTION
				"TYPE: - Checkbox
				 PAGE: - Video
					ProcAmp Enable  cmdID= 2864 "
		::= { iqosy30CmdEntry 2864 }


	iqosy30VideoVideoProcampBlackLevel OBJECT-TYPE
		SYNTAX		INTEGER
		MAX-ACCESS		read-write
		STATUS			current
		DESCRIPTION
				"TYPE: - Number
				 PAGE: - Video
					Black Level  cmdID= 2708  min= -1000  max= 1000  step= 8  format= %3.1fmV  div_scale= 10 
					Min = -100.0mV  Max = 100.0mV  Step = 0.8mV "
		::= { iqosy30CmdEntry 2708 }


	iqosy30VideoVideoProcampHueAdjust OBJECT-TYPE
		SYNTAX		INTEGER
		MAX-ACCESS		read-write
		STATUS			current
		DESCRIPTION
				"TYPE: - Number
				 PAGE: - Video
					Hue Adjust  cmdID= 3622  min= -180  max= 180  step= 1  format= %1.0fdeg  div_scale= 1 
					Min = -180deg  Max = 180deg  Step = 1deg "
		::= { iqosy30CmdEntry 3622 }


	iqosy30VideoVideoProcampMasterVideoGain OBJECT-TYPE
		SYNTAX		INTEGER
		MAX-ACCESS		read-write
		STATUS			current
		DESCRIPTION
				"TYPE: - Number
				 PAGE: - Video
					Master Video Gain  cmdID= 3780  min= -60  max= 60  step= 1  format= %0.1fdB  div_scale= 10 
					Min = -6.0dB  Max = 6.0dB  Step = 0.1dB "
		::= { iqosy30CmdEntry 3780 }


	iqosy30VideoVideoProcampYGain OBJECT-TYPE
		SYNTAX		INTEGER
		MAX-ACCESS		read-write
		STATUS			current
		DESCRIPTION
				"TYPE: - Number
				 PAGE: - Video
					Y Gain  cmdID= 2707  min= -60  max= 60  step= 1  format= %0.1fdB  div_scale= 10 
					Min = -6.0dB  Max = 6.0dB  Step = 0.1dB "
		::= { iqosy30CmdEntry 2707 }


	iqosy30VideoVideoProcampCbCrGain OBJECT-TYPE
		SYNTAX		INTEGER
		MAX-ACCESS		read-write
		STATUS			current
		DESCRIPTION
				"TYPE: - Number
				 PAGE: - Video
					Cb/Cr Gain  cmdID= 2706  min= -60  max= 60  step= 1  format= %0.1fdB  div_scale= 10 
					Min = -6.0dB  Max = 6.0dB  Step = 0.1dB "
		::= { iqosy30CmdEntry 2706 }


	iqosy30VideoVideoProcampYCTiming OBJECT-TYPE
		SYNTAX		INTEGER
		MAX-ACCESS		read-write
		STATUS			current
		DESCRIPTION
				"TYPE: - Number
				 PAGE: - Video
					Y/C Timing  cmdID= 2924  min= -8  max= 8  step= 2  format= %1.0f pixels  div_scale= 1 
					Min = -8 pixels  Max = 8 pixels  Step = 2 pixels "
		::= { iqosy30CmdEntry 2924 }


	iqosy30VideoVideoProcampPictureposition OBJECT-TYPE
		SYNTAX		INTEGER
		MAX-ACCESS		read-write
		STATUS			current
		DESCRIPTION
				"TYPE: - Number
				 PAGE: - Video
					Picture position  cmdID= 2709  min= -8  max= 8  step= 2  format= %1.0f pixels  div_scale= 1 
					Min = -8 pixels  Max = 8 pixels  Step = 2 pixels "
		::= { iqosy30CmdEntry 2709 }


	iqosy30VideoVideoProcampModalIndex OBJECT-TYPE
		SYNTAX		INTEGER
		MAX-ACCESS		read-write
		STATUS			current
		DESCRIPTION
				"TYPE: - Number
				 PAGE: - Video
					Modal Index  cmdID= 5006  min= 0  max= 1  step= 1  format= %1.0f  div_scale= 1 
					Min = 0  Max = 1  Step = 1 "
		::= { iqosy30CmdEntry 5006 }


	iqosy30VideoVideoProcampYCTimingnm OBJECT-TYPE
		SYNTAX		INTEGER
		MAX-ACCESS		read-write
		STATUS			current
		DESCRIPTION
				"TYPE: - Number
				 PAGE: - Video
					Y/C Timing nm  cmdID= 5008  min= -16  max= 16  step= 2  format= %1.0f pixels  div_scale= 1 
					Min = -16 pixels  Max = 16 pixels  Step = 2 pixels "
		::= { iqosy30CmdEntry 5008 }


	iqosy30VideoVideoProcampPicturepositionnm OBJECT-TYPE
		SYNTAX		INTEGER
		MAX-ACCESS		read-write
		STATUS			current
		DESCRIPTION
				"TYPE: - Number
				 PAGE: - Video
					Picture position nm  cmdID= 5007  min= -16  max= 16  step= 2  format= %1.0f pixels  div_scale= 1 
					Min = -16 pixels  Max = 16 pixels  Step = 2 pixels "
		::= { iqosy30CmdEntry 5007 }


	iqosy30VideoBlankingBlankVANC OBJECT-TYPE
		SYNTAX		INTEGER { disable(0), enable(1) }
		MAX-ACCESS		read-write
		STATUS			current
		DESCRIPTION
				"TYPE: - Checkbox
				 PAGE: - Video
					Blank VANC  cmdID= 3949 "
		::= { iqosy30CmdEntry 3949 }


	iqosy30Blanking625BlankLinesLine23 OBJECT-TYPE
		SYNTAX		INTEGER { disable(0), enable(1) }
		MAX-ACCESS		read-write
		STATUS			current
		DESCRIPTION
				"TYPE: - Checkbox
				 PAGE: - Video
					Line 23  cmdID= 3951 "
		::= { iqosy30CmdEntry 3951 }


	iqosy30Blanking625BlankLinesLine336 OBJECT-TYPE
		SYNTAX		INTEGER { disable(0), enable(1) }
		MAX-ACCESS		read-write
		STATUS			current
		DESCRIPTION
				"TYPE: - Checkbox
				 PAGE: - Video
					Line 336  cmdID= 3952 "
		::= { iqosy30CmdEntry 3952 }


	iqosy30Blanking525BlankLinesLine21 OBJECT-TYPE
		SYNTAX		INTEGER { disable(0), enable(1) }
		MAX-ACCESS		read-write
		STATUS			current
		DESCRIPTION
				"TYPE: - Checkbox
				 PAGE: - Video
					Line 21  cmdID= 3953 "
		::= { iqosy30CmdEntry 3953 }


	iqosy30Blanking525BlankLinesLine22 OBJECT-TYPE
		SYNTAX		INTEGER { disable(0), enable(1) }
		MAX-ACCESS		read-write
		STATUS			current
		DESCRIPTION
				"TYPE: - Checkbox
				 PAGE: - Video
					Line 22  cmdID= 3955 "
		::= { iqosy30CmdEntry 3955 }


	iqosy30Blanking525BlankLinesLine283 OBJECT-TYPE
		SYNTAX		INTEGER { disable(0), enable(1) }
		MAX-ACCESS		read-write
		STATUS			current
		DESCRIPTION
				"TYPE: - Checkbox
				 PAGE: - Video
					Line 283  cmdID= 3954 "
		::= { iqosy30CmdEntry 3954 }


	iqosy30Blanking525BlankLinesLine284 OBJECT-TYPE
		SYNTAX		INTEGER { disable(0), enable(1) }
		MAX-ACCESS		read-write
		STATUS			current
		DESCRIPTION
				"TYPE: - Checkbox
				 PAGE: - Video
					Line 284  cmdID= 3956 "
		::= { iqosy30CmdEntry 3956 }


	iqosy30VideoBlankingBlankHANC OBJECT-TYPE
		SYNTAX		INTEGER { disable(0), enable(1) }
		MAX-ACCESS		read-write
		STATUS			current
		DESCRIPTION
				"TYPE: - Checkbox
				 PAGE: - Video
					Blank HANC  cmdID= 3947 "
		::= { iqosy30CmdEntry 3947 }


	iqosy30VideoOpticalLaserOff5305 OBJECT-TYPE
		SYNTAX		INTEGER { disable(0), enable(1) }
		MAX-ACCESS		read-write
		STATUS			current
		DESCRIPTION
				"TYPE: - Checkbox
				 PAGE: - Video
					Laser Off  cmdID= 5305 "
		::= { iqosy30CmdEntry 5305 }


	iqosy30VideoOpticalLaserOffonloss5306 OBJECT-TYPE
		SYNTAX		INTEGER { disable(0), enable(1) }
		MAX-ACCESS		read-write
		STATUS			current
		DESCRIPTION
				"TYPE: - Checkbox
				 PAGE: - Video
					Laser Off on loss  cmdID= 5306 "
		::= { iqosy30CmdEntry 5306 }


	iqosy30VideoOpticalTxWavelength5300 OBJECT-TYPE
		SYNTAX		RollCallString
		MAX-ACCESS		read-only
		STATUS			current
		DESCRIPTION
				"TYPE: - Display
				 PAGE: - Video
					Tx Wavelength  cmdID= 5300  format=   "
		::= { iqosy30CmdEntry 5300 }


	iqosy30VideoOpticalLaserBias5301 OBJECT-TYPE
		SYNTAX		RollCallString
		MAX-ACCESS		read-only
		STATUS			current
		DESCRIPTION
				"TYPE: - Display
				 PAGE: - Video
					Laser Bias  cmdID= 5301  format=   "
		::= { iqosy30CmdEntry 5301 }


	iqosy30VideoOpticalLaserBiasState5302 OBJECT-TYPE
		SYNTAX		RollCallString
		MAX-ACCESS		read-only
		STATUS			current
		DESCRIPTION
				"TYPE: - Display
				 PAGE: - Video
					Laser Bias State  cmdID= 5302  format=   "
		::= { iqosy30CmdEntry 5302 }


	iqosy30VideoOpticalTxPower5303 OBJECT-TYPE
		SYNTAX		RollCallString
		MAX-ACCESS		read-only
		STATUS			current
		DESCRIPTION
				"TYPE: - Display
				 PAGE: - Video
					Tx Power  cmdID= 5303  format=   "
		::= { iqosy30CmdEntry 5303 }


	iqosy30VideoOpticalTxPowerState5304 OBJECT-TYPE
		SYNTAX		RollCallString
		MAX-ACCESS		read-only
		STATUS			current
		DESCRIPTION
				"TYPE: - Display
				 PAGE: - Video
					Tx Power State  cmdID= 5304  format=   "
		::= { iqosy30CmdEntry 5304 }


	iqosy30VideoOpticalLaserOff5314 OBJECT-TYPE
		SYNTAX		INTEGER { disable(0), enable(1) }
		MAX-ACCESS		read-write
		STATUS			current
		DESCRIPTION
				"TYPE: - Checkbox
				 PAGE: - Video
					Laser Off  cmdID= 5314 "
		::= { iqosy30CmdEntry 5314 }


	iqosy30VideoOpticalLaserOffonloss5315 OBJECT-TYPE
		SYNTAX		INTEGER { disable(0), enable(1) }
		MAX-ACCESS		read-write
		STATUS			current
		DESCRIPTION
				"TYPE: - Checkbox
				 PAGE: - Video
					Laser Off on loss  cmdID= 5315 "
		::= { iqosy30CmdEntry 5315 }


	iqosy30VideoOpticalTxWavelength5309 OBJECT-TYPE
		SYNTAX		RollCallString
		MAX-ACCESS		read-only
		STATUS			current
		DESCRIPTION
				"TYPE: - Display
				 PAGE: - Video
					Tx Wavelength  cmdID= 5309  format=   "
		::= { iqosy30CmdEntry 5309 }


	iqosy30VideoOpticalLaserBias5310 OBJECT-TYPE
		SYNTAX		RollCallString
		MAX-ACCESS		read-only
		STATUS			current
		DESCRIPTION
				"TYPE: - Display
				 PAGE: - Video
					Laser Bias  cmdID= 5310  format=   "
		::= { iqosy30CmdEntry 5310 }


	iqosy30VideoOpticalLaserBiasState5311 OBJECT-TYPE
		SYNTAX		RollCallString
		MAX-ACCESS		read-only
		STATUS			current
		DESCRIPTION
				"TYPE: - Display
				 PAGE: - Video
					Laser Bias State  cmdID= 5311  format=   "
		::= { iqosy30CmdEntry 5311 }


	iqosy30VideoOpticalTxPower5312 OBJECT-TYPE
		SYNTAX		RollCallString
		MAX-ACCESS		read-only
		STATUS			current
		DESCRIPTION
				"TYPE: - Display
				 PAGE: - Video
					Tx Power  cmdID= 5312  format=   "
		::= { iqosy30CmdEntry 5312 }


	iqosy30VideoOpticalTxPowerState5313 OBJECT-TYPE
		SYNTAX		RollCallString
		MAX-ACCESS		read-only
		STATUS			current
		DESCRIPTION
				"TYPE: - Display
				 PAGE: - Video
					Tx Power State  cmdID= 5313  format=   "
		::= { iqosy30CmdEntry 5313 }


	iqosy30VideoOpticalRxPower5307 OBJECT-TYPE
		SYNTAX		RollCallString
		MAX-ACCESS		read-only
		STATUS			current
		DESCRIPTION
				"TYPE: - Display
				 PAGE: - Video
					Rx Power  cmdID= 5307  format=   "
		::= { iqosy30CmdEntry 5307 }


	iqosy30VideoOpticalRxPowerState5308 OBJECT-TYPE
		SYNTAX		RollCallString
		MAX-ACCESS		read-only
		STATUS			current
		DESCRIPTION
				"TYPE: - Display
				 PAGE: - Video
					Rx Power State  cmdID= 5308  format=   "
		::= { iqosy30CmdEntry 5308 }


	iqosy30VideoOpticalRxPower5316 OBJECT-TYPE
		SYNTAX		RollCallString
		MAX-ACCESS		read-only
		STATUS			current
		DESCRIPTION
				"TYPE: - Display
				 PAGE: - Video
					Rx Power  cmdID= 5316  format=   "
		::= { iqosy30CmdEntry 5316 }


	iqosy30VideoOpticalRxPowerState5317 OBJECT-TYPE
		SYNTAX		RollCallString
		MAX-ACCESS		read-only
		STATUS			current
		DESCRIPTION
				"TYPE: - Display
				 PAGE: - Video
					Rx Power State  cmdID= 5317  format=   "
		::= { iqosy30CmdEntry 5317 }


	iqosy30VideoCaption OBJECT-TYPE
		SYNTAX		INTEGER {
							val-Off(0),
							val-On(1),
							val-Animated-Slow(2),
							val-Animated-Medium(3),
							val-Animated-Fast(4)
							}
		MAX-ACCESS		read-write
		STATUS			current
		DESCRIPTION
				"TYPE: - Button
				 PAGE: - Video
					Off  cmdID= 1037  value= 0  
					On  cmdID= 1037  value= 1  
					Animated Slow  cmdID= 1037  value= 2  
					Animated Medium  cmdID= 1037  value= 3  
					Animated Fast  cmdID= 1037  value= 4  "
		::= { iqosy30CmdEntry 1037 }


	iqosy30VideoCaptionEditCaption OBJECT-TYPE
		SYNTAX		RollCallString
		MAX-ACCESS		read-write
		STATUS			current
		DESCRIPTION
				"TYPE: - Editstring
				 PAGE: - Video
					Edit Caption  cmdID= 1041  "
		::= { iqosy30CmdEntry 1041 }


	iqosy30VideoPattern OBJECT-TYPE
		SYNTAX		INTEGER {
							val-Off(0),
							val-Black(1),
							val-Bars(2)
							}
		MAX-ACCESS		read-write
		STATUS			current
		DESCRIPTION
				"TYPE: - RadiobuttonList
				 PAGE: - Video
					Pattern  cmdID= 2624 
					Off  value= 0  
					Black  value= 1  
					Bars  value= 2  "
		::= { iqosy30CmdEntry 2624 }


	iqosy30VideoFreeze OBJECT-TYPE
		SYNTAX		INTEGER {
							val-Field(0),
							val-Frame(1)
							}
		MAX-ACCESS		read-write
		STATUS			current
		DESCRIPTION
				"TYPE: - Button
				 PAGE: - Video
					Field  cmdID= 5023  value= 0  
					Frame  cmdID= 5023  value= 1  "
		::= { iqosy30CmdEntry 5023 }


	iqosy30VideoFreezeManualFreeze OBJECT-TYPE
		SYNTAX		INTEGER { disable(0), enable(1) }
		MAX-ACCESS		read-write
		STATUS			current
		DESCRIPTION
				"TYPE: - Checkbox
				 PAGE: - Video
					Manual Freeze  cmdID= 5022 "
		::= { iqosy30CmdEntry 5022 }


	iqosy30AudioAudioInputSelect OBJECT-TYPE
		SYNTAX		INTEGER {
							val-Input-1(0),
							val-Input-2(1),
							val-Option-1(2),
							val-Option-2(3),
							val-Follow-Video(4)
							}
		MAX-ACCESS		read-write
		STATUS			current
		DESCRIPTION
				"TYPE: - RadiobuttonList
				 PAGE: - Audio
					Audio Input Select  cmdID= 2252 
					Input 1  value= 0  
					Input 2  value= 1  
					Option 1  value= 2  
					Option 2  value= 3  
					Follow Video  value= 4  "
		::= { iqosy30CmdEntry 2252 }


	iqosy30EmbeddersEmbedder1Enable OBJECT-TYPE
		SYNTAX		INTEGER { disable(0), enable(1) }
		MAX-ACCESS		read-write
		STATUS			current
		DESCRIPTION
				"TYPE: - Checkbox
				 PAGE: - Audio- Embedders- Embedder 1
					Enable  cmdID= 5066 "
		::= { iqosy30CmdEntry 5066 }


	iqosy30EmbeddersEmbedder1SourceLNonPCM5034 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 1
					Source L / Non-PCM  cmdID= 5034 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5034 }


	iqosy30EmbeddersEmbedder1SourceR5035 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 1
					Source R  cmdID= 5035 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5035 }


	iqosy30EmbeddersEmbedder1Mute3240 OBJECT-TYPE
		SYNTAX		INTEGER { disable(0), enable(1) }
		MAX-ACCESS		read-write
		STATUS			current
		DESCRIPTION
				"TYPE: - Checkbox
				 PAGE: - Audio- Embedders- Embedder 1
					Mute  cmdID= 3240 "
		::= { iqosy30CmdEntry 3240 }


	iqosy30EmbeddersEmbedder1MuteonVbit3272 OBJECT-TYPE
		SYNTAX		INTEGER { disable(0), enable(1) }
		MAX-ACCESS		read-write
		STATUS			current
		DESCRIPTION
				"TYPE: - Checkbox
				 PAGE: - Audio- Embedders- Embedder 1
					Mute on V bit  cmdID= 3272 "
		::= { iqosy30CmdEntry 3272 }


	iqosy30EmbeddersEmbedder1InvertL3160 OBJECT-TYPE
		SYNTAX		INTEGER { disable(0), enable(1) }
		MAX-ACCESS		read-write
		STATUS			current
		DESCRIPTION
				"TYPE: - Checkbox
				 PAGE: - Audio- Embedders- Embedder 1
					Invert L  cmdID= 3160 "
		::= { iqosy30CmdEntry 3160 }


	iqosy30EmbeddersEmbedder1InvertR3161 OBJECT-TYPE
		SYNTAX		INTEGER { disable(0), enable(1) }
		MAX-ACCESS		read-write
		STATUS			current
		DESCRIPTION
				"TYPE: - Checkbox
				 PAGE: - Audio- Embedders- Embedder 1
					Invert R  cmdID= 3161 "
		::= { iqosy30CmdEntry 3161 }


	iqosy30EmbeddersEmbedder1GainL3080 OBJECT-TYPE
		SYNTAX		INTEGER
		MAX-ACCESS		read-write
		STATUS			current
		DESCRIPTION
				"TYPE: - Number
				 PAGE: - Audio- Embedders- Embedder 1
					Gain L  cmdID= 3080  min= -720  max= 120  step= 1  format= %0.1fdB  div_scale= 10 
					Min = -72.0dB  Max = 12.0dB  Step = 0.1dB "
		::= { iqosy30CmdEntry 3080 }


	iqosy30EmbeddersEmbedder1GainR3081 OBJECT-TYPE
		SYNTAX		INTEGER
		MAX-ACCESS		read-write
		STATUS			current
		DESCRIPTION
				"TYPE: - Number
				 PAGE: - Audio- Embedders- Embedder 1
					Gain R  cmdID= 3081  min= -720  max= 120  step= 1  format= %0.1fdB  div_scale= 10 
					Min = -72.0dB  Max = 12.0dB  Step = 0.1dB "
		::= { iqosy30CmdEntry 3081 }


	iqosy30EmbeddersEmbedder1PairMode3930 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 1
					Pair Mode  cmdID= 3930 
					2 Channel PCM  value= 0  
					Stereo PCM  value= 1  
					Non-PCM  value= 2  "
		::= { iqosy30CmdEntry 3930 }


	iqosy30EmbeddersEmbedder1SourceLNonPCM5036 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 1
					Source L / Non-PCM  cmdID= 5036 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5036 }


	iqosy30EmbeddersEmbedder1SourceR5037 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 1
					Source R  cmdID= 5037 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5037 }


	iqosy30EmbeddersEmbedder1Mute3241 OBJECT-TYPE
		SYNTAX		INTEGER { disable(0), enable(1) }
		MAX-ACCESS		read-write
		STATUS			current
		DESCRIPTION
				"TYPE: - Checkbox
				 PAGE: - Audio- Embedders- Embedder 1
					Mute  cmdID= 3241 "
		::= { iqosy30CmdEntry 3241 }


	iqosy30EmbeddersEmbedder1MuteonVbit3273 OBJECT-TYPE
		SYNTAX		INTEGER { disable(0), enable(1) }
		MAX-ACCESS		read-write
		STATUS			current
		DESCRIPTION
				"TYPE: - Checkbox
				 PAGE: - Audio- Embedders- Embedder 1
					Mute on V bit  cmdID= 3273 "
		::= { iqosy30CmdEntry 3273 }


	iqosy30EmbeddersEmbedder1InvertL3162 OBJECT-TYPE
		SYNTAX		INTEGER { disable(0), enable(1) }
		MAX-ACCESS		read-write
		STATUS			current
		DESCRIPTION
				"TYPE: - Checkbox
				 PAGE: - Audio- Embedders- Embedder 1
					Invert L  cmdID= 3162 "
		::= { iqosy30CmdEntry 3162 }


	iqosy30EmbeddersEmbedder1InvertR3163 OBJECT-TYPE
		SYNTAX		INTEGER { disable(0), enable(1) }
		MAX-ACCESS		read-write
		STATUS			current
		DESCRIPTION
				"TYPE: - Checkbox
				 PAGE: - Audio- Embedders- Embedder 1
					Invert R  cmdID= 3163 "
		::= { iqosy30CmdEntry 3163 }


	iqosy30EmbeddersEmbedder1GainL3082 OBJECT-TYPE
		SYNTAX		INTEGER
		MAX-ACCESS		read-write
		STATUS			current
		DESCRIPTION
				"TYPE: - Number
				 PAGE: - Audio- Embedders- Embedder 1
					Gain L  cmdID= 3082  min= -720  max= 120  step= 1  format= %0.1fdB  div_scale= 10 
					Min = -72.0dB  Max = 12.0dB  Step = 0.1dB "
		::= { iqosy30CmdEntry 3082 }


	iqosy30EmbeddersEmbedder1GainR3083 OBJECT-TYPE
		SYNTAX		INTEGER
		MAX-ACCESS		read-write
		STATUS			current
		DESCRIPTION
				"TYPE: - Number
				 PAGE: - Audio- Embedders- Embedder 1
					Gain R  cmdID= 3083  min= -720  max= 120  step= 1  format= %0.1fdB  div_scale= 10 
					Min = -72.0dB  Max = 12.0dB  Step = 0.1dB "
		::= { iqosy30CmdEntry 3083 }


	iqosy30EmbeddersEmbedder1PairMode3931 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 1
					Pair Mode  cmdID= 3931 
					2 Channel PCM  value= 0  
					Stereo PCM  value= 1  
					Non-PCM  value= 2  "
		::= { iqosy30CmdEntry 3931 }


	iqosy30EmbeddersEmbedder1NonModalIndex OBJECT-TYPE
		SYNTAX		INTEGER
		MAX-ACCESS		read-write
		STATUS			current
		DESCRIPTION
				"TYPE: - Number
				 PAGE: - Audio- Embedders- Embedder 1
					NonModal Index  cmdID= 5338  min= 0  max= 31  step= 1  format=   div_scale= 1 
					Min =   Max =   Step =  "
		::= { iqosy30CmdEntry 5338 }


	iqosy30EmbeddersEmbedder1NonModalGain OBJECT-TYPE
		SYNTAX		INTEGER
		MAX-ACCESS		read-write
		STATUS			current
		DESCRIPTION
				"TYPE: - Number
				 PAGE: - Audio- Embedders- Embedder 1
					NonModal Gain  cmdID= 5339  min= -720  max= 120  step= 1  format=   div_scale= 10 
					Min =   Max =   Step =  "
		::= { iqosy30CmdEntry 5339 }


	iqosy30EmbeddersEmbedder2Enable OBJECT-TYPE
		SYNTAX		INTEGER { disable(0), enable(1) }
		MAX-ACCESS		read-write
		STATUS			current
		DESCRIPTION
				"TYPE: - Checkbox
				 PAGE: - Audio- Embedders- Embedder 2
					Enable  cmdID= 5067 "
		::= { iqosy30CmdEntry 5067 }


	iqosy30EmbeddersEmbedder2SourceLNonPCM5038 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 2
					Source L / Non-PCM  cmdID= 5038 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5038 }


	iqosy30EmbeddersEmbedder2SourceR5039 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 2
					Source R  cmdID= 5039 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5039 }


	iqosy30EmbeddersEmbedder2Mute3242 OBJECT-TYPE
		SYNTAX		INTEGER { disable(0), enable(1) }
		MAX-ACCESS		read-write
		STATUS			current
		DESCRIPTION
				"TYPE: - Checkbox
				 PAGE: - Audio- Embedders- Embedder 2
					Mute  cmdID= 3242 "
		::= { iqosy30CmdEntry 3242 }


	iqosy30EmbeddersEmbedder2MuteonVbit3274 OBJECT-TYPE
		SYNTAX		INTEGER { disable(0), enable(1) }
		MAX-ACCESS		read-write
		STATUS			current
		DESCRIPTION
				"TYPE: - Checkbox
				 PAGE: - Audio- Embedders- Embedder 2
					Mute on V bit  cmdID= 3274 "
		::= { iqosy30CmdEntry 3274 }


	iqosy30EmbeddersEmbedder2InvertL3164 OBJECT-TYPE
		SYNTAX		INTEGER { disable(0), enable(1) }
		MAX-ACCESS		read-write
		STATUS			current
		DESCRIPTION
				"TYPE: - Checkbox
				 PAGE: - Audio- Embedders- Embedder 2
					Invert L  cmdID= 3164 "
		::= { iqosy30CmdEntry 3164 }


	iqosy30EmbeddersEmbedder2InvertR3165 OBJECT-TYPE
		SYNTAX		INTEGER { disable(0), enable(1) }
		MAX-ACCESS		read-write
		STATUS			current
		DESCRIPTION
				"TYPE: - Checkbox
				 PAGE: - Audio- Embedders- Embedder 2
					Invert R  cmdID= 3165 "
		::= { iqosy30CmdEntry 3165 }


	iqosy30EmbeddersEmbedder2GainL3084 OBJECT-TYPE
		SYNTAX		INTEGER
		MAX-ACCESS		read-write
		STATUS			current
		DESCRIPTION
				"TYPE: - Number
				 PAGE: - Audio- Embedders- Embedder 2
					Gain L  cmdID= 3084  min= -720  max= 120  step= 1  format= %0.1fdB  div_scale= 10 
					Min = -72.0dB  Max = 12.0dB  Step = 0.1dB "
		::= { iqosy30CmdEntry 3084 }


	iqosy30EmbeddersEmbedder2GainR3085 OBJECT-TYPE
		SYNTAX		INTEGER
		MAX-ACCESS		read-write
		STATUS			current
		DESCRIPTION
				"TYPE: - Number
				 PAGE: - Audio- Embedders- Embedder 2
					Gain R  cmdID= 3085  min= -720  max= 120  step= 1  format= %0.1fdB  div_scale= 10 
					Min = -72.0dB  Max = 12.0dB  Step = 0.1dB "
		::= { iqosy30CmdEntry 3085 }


	iqosy30EmbeddersEmbedder2PairMode3932 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 2
					Pair Mode  cmdID= 3932 
					2 Channel PCM  value= 0  
					Stereo PCM  value= 1  
					Non-PCM  value= 2  "
		::= { iqosy30CmdEntry 3932 }


	iqosy30EmbeddersEmbedder2SourceLNonPCM5040 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 2
					Source L / Non-PCM  cmdID= 5040 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5040 }


	iqosy30EmbeddersEmbedder2SourceR5041 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 2
					Source R  cmdID= 5041 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5041 }


	iqosy30EmbeddersEmbedder2Mute3243 OBJECT-TYPE
		SYNTAX		INTEGER { disable(0), enable(1) }
		MAX-ACCESS		read-write
		STATUS			current
		DESCRIPTION
				"TYPE: - Checkbox
				 PAGE: - Audio- Embedders- Embedder 2
					Mute  cmdID= 3243 "
		::= { iqosy30CmdEntry 3243 }


	iqosy30EmbeddersEmbedder2MuteonVbit3275 OBJECT-TYPE
		SYNTAX		INTEGER { disable(0), enable(1) }
		MAX-ACCESS		read-write
		STATUS			current
		DESCRIPTION
				"TYPE: - Checkbox
				 PAGE: - Audio- Embedders- Embedder 2
					Mute on V bit  cmdID= 3275 "
		::= { iqosy30CmdEntry 3275 }


	iqosy30EmbeddersEmbedder2InvertL3166 OBJECT-TYPE
		SYNTAX		INTEGER { disable(0), enable(1) }
		MAX-ACCESS		read-write
		STATUS			current
		DESCRIPTION
				"TYPE: - Checkbox
				 PAGE: - Audio- Embedders- Embedder 2
					Invert L  cmdID= 3166 "
		::= { iqosy30CmdEntry 3166 }


	iqosy30EmbeddersEmbedder2InvertR3167 OBJECT-TYPE
		SYNTAX		INTEGER { disable(0), enable(1) }
		MAX-ACCESS		read-write
		STATUS			current
		DESCRIPTION
				"TYPE: - Checkbox
				 PAGE: - Audio- Embedders- Embedder 2
					Invert R  cmdID= 3167 "
		::= { iqosy30CmdEntry 3167 }


	iqosy30EmbeddersEmbedder2GainL3086 OBJECT-TYPE
		SYNTAX		INTEGER
		MAX-ACCESS		read-write
		STATUS			current
		DESCRIPTION
				"TYPE: - Number
				 PAGE: - Audio- Embedders- Embedder 2
					Gain L  cmdID= 3086  min= -720  max= 120  step= 1  format= %0.1fdB  div_scale= 10 
					Min = -72.0dB  Max = 12.0dB  Step = 0.1dB "
		::= { iqosy30CmdEntry 3086 }


	iqosy30EmbeddersEmbedder2GainR3087 OBJECT-TYPE
		SYNTAX		INTEGER
		MAX-ACCESS		read-write
		STATUS			current
		DESCRIPTION
				"TYPE: - Number
				 PAGE: - Audio- Embedders- Embedder 2
					Gain R  cmdID= 3087  min= -720  max= 120  step= 1  format= %0.1fdB  div_scale= 10 
					Min = -72.0dB  Max = 12.0dB  Step = 0.1dB "
		::= { iqosy30CmdEntry 3087 }


	iqosy30EmbeddersEmbedder2PairMode3933 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 2
					Pair Mode  cmdID= 3933 
					2 Channel PCM  value= 0  
					Stereo PCM  value= 1  
					Non-PCM  value= 2  "
		::= { iqosy30CmdEntry 3933 }


	iqosy30EmbeddersEmbedder3Enable OBJECT-TYPE
		SYNTAX		INTEGER { disable(0), enable(1) }
		MAX-ACCESS		read-write
		STATUS			current
		DESCRIPTION
				"TYPE: - Checkbox
				 PAGE: - Audio- Embedders- Embedder 3
					Enable  cmdID= 5068 "
		::= { iqosy30CmdEntry 5068 }


	iqosy30EmbeddersEmbedder3SourceLNonPCM5042 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 3
					Source L / Non-PCM  cmdID= 5042 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5042 }


	iqosy30EmbeddersEmbedder3SourceR5043 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 3
					Source R  cmdID= 5043 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5043 }


	iqosy30EmbeddersEmbedder3Mute3244 OBJECT-TYPE
		SYNTAX		INTEGER { disable(0), enable(1) }
		MAX-ACCESS		read-write
		STATUS			current
		DESCRIPTION
				"TYPE: - Checkbox
				 PAGE: - Audio- Embedders- Embedder 3
					Mute  cmdID= 3244 "
		::= { iqosy30CmdEntry 3244 }


	iqosy30EmbeddersEmbedder3MuteonVbit3276 OBJECT-TYPE
		SYNTAX		INTEGER { disable(0), enable(1) }
		MAX-ACCESS		read-write
		STATUS			current
		DESCRIPTION
				"TYPE: - Checkbox
				 PAGE: - Audio- Embedders- Embedder 3
					Mute on V bit  cmdID= 3276 "
		::= { iqosy30CmdEntry 3276 }


	iqosy30EmbeddersEmbedder3InvertL3168 OBJECT-TYPE
		SYNTAX		INTEGER { disable(0), enable(1) }
		MAX-ACCESS		read-write
		STATUS			current
		DESCRIPTION
				"TYPE: - Checkbox
				 PAGE: - Audio- Embedders- Embedder 3
					Invert L  cmdID= 3168 "
		::= { iqosy30CmdEntry 3168 }


	iqosy30EmbeddersEmbedder3InvertR3169 OBJECT-TYPE
		SYNTAX		INTEGER { disable(0), enable(1) }
		MAX-ACCESS		read-write
		STATUS			current
		DESCRIPTION
				"TYPE: - Checkbox
				 PAGE: - Audio- Embedders- Embedder 3
					Invert R  cmdID= 3169 "
		::= { iqosy30CmdEntry 3169 }


	iqosy30EmbeddersEmbedder3GainL3088 OBJECT-TYPE
		SYNTAX		INTEGER
		MAX-ACCESS		read-write
		STATUS			current
		DESCRIPTION
				"TYPE: - Number
				 PAGE: - Audio- Embedders- Embedder 3
					Gain L  cmdID= 3088  min= -720  max= 120  step= 1  format= %0.1fdB  div_scale= 10 
					Min = -72.0dB  Max = 12.0dB  Step = 0.1dB "
		::= { iqosy30CmdEntry 3088 }


	iqosy30EmbeddersEmbedder3GainR3089 OBJECT-TYPE
		SYNTAX		INTEGER
		MAX-ACCESS		read-write
		STATUS			current
		DESCRIPTION
				"TYPE: - Number
				 PAGE: - Audio- Embedders- Embedder 3
					Gain R  cmdID= 3089  min= -720  max= 120  step= 1  format= %0.1fdB  div_scale= 10 
					Min = -72.0dB  Max = 12.0dB  Step = 0.1dB "
		::= { iqosy30CmdEntry 3089 }


	iqosy30EmbeddersEmbedder3PairMode3934 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 3
					Pair Mode  cmdID= 3934 
					2 Channel PCM  value= 0  
					Stereo PCM  value= 1  
					Non-PCM  value= 2  "
		::= { iqosy30CmdEntry 3934 }


	iqosy30EmbeddersEmbedder3SourceLNonPCM5044 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 3
					Source L / Non-PCM  cmdID= 5044 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5044 }


	iqosy30EmbeddersEmbedder3SourceR5045 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 3
					Source R  cmdID= 5045 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5045 }


	iqosy30EmbeddersEmbedder3Mute3245 OBJECT-TYPE
		SYNTAX		INTEGER { disable(0), enable(1) }
		MAX-ACCESS		read-write
		STATUS			current
		DESCRIPTION
				"TYPE: - Checkbox
				 PAGE: - Audio- Embedders- Embedder 3
					Mute  cmdID= 3245 "
		::= { iqosy30CmdEntry 3245 }


	iqosy30EmbeddersEmbedder3MuteonVbit3277 OBJECT-TYPE
		SYNTAX		INTEGER { disable(0), enable(1) }
		MAX-ACCESS		read-write
		STATUS			current
		DESCRIPTION
				"TYPE: - Checkbox
				 PAGE: - Audio- Embedders- Embedder 3
					Mute on V bit  cmdID= 3277 "
		::= { iqosy30CmdEntry 3277 }


	iqosy30EmbeddersEmbedder3InvertL3170 OBJECT-TYPE
		SYNTAX		INTEGER { disable(0), enable(1) }
		MAX-ACCESS		read-write
		STATUS			current
		DESCRIPTION
				"TYPE: - Checkbox
				 PAGE: - Audio- Embedders- Embedder 3
					Invert L  cmdID= 3170 "
		::= { iqosy30CmdEntry 3170 }


	iqosy30EmbeddersEmbedder3InvertR3171 OBJECT-TYPE
		SYNTAX		INTEGER { disable(0), enable(1) }
		MAX-ACCESS		read-write
		STATUS			current
		DESCRIPTION
				"TYPE: - Checkbox
				 PAGE: - Audio- Embedders- Embedder 3
					Invert R  cmdID= 3171 "
		::= { iqosy30CmdEntry 3171 }


	iqosy30EmbeddersEmbedder3GainL3090 OBJECT-TYPE
		SYNTAX		INTEGER
		MAX-ACCESS		read-write
		STATUS			current
		DESCRIPTION
				"TYPE: - Number
				 PAGE: - Audio- Embedders- Embedder 3
					Gain L  cmdID= 3090  min= -720  max= 120  step= 1  format= %0.1fdB  div_scale= 10 
					Min = -72.0dB  Max = 12.0dB  Step = 0.1dB "
		::= { iqosy30CmdEntry 3090 }


	iqosy30EmbeddersEmbedder3GainR3091 OBJECT-TYPE
		SYNTAX		INTEGER
		MAX-ACCESS		read-write
		STATUS			current
		DESCRIPTION
				"TYPE: - Number
				 PAGE: - Audio- Embedders- Embedder 3
					Gain R  cmdID= 3091  min= -720  max= 120  step= 1  format= %0.1fdB  div_scale= 10 
					Min = -72.0dB  Max = 12.0dB  Step = 0.1dB "
		::= { iqosy30CmdEntry 3091 }


	iqosy30EmbeddersEmbedder3PairMode3935 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 3
					Pair Mode  cmdID= 3935 
					2 Channel PCM  value= 0  
					Stereo PCM  value= 1  
					Non-PCM  value= 2  "
		::= { iqosy30CmdEntry 3935 }


	iqosy30EmbeddersEmbedder4Enable OBJECT-TYPE
		SYNTAX		INTEGER { disable(0), enable(1) }
		MAX-ACCESS		read-write
		STATUS			current
		DESCRIPTION
				"TYPE: - Checkbox
				 PAGE: - Audio- Embedders- Embedder 4
					Enable  cmdID= 5069 "
		::= { iqosy30CmdEntry 5069 }


	iqosy30EmbeddersEmbedder4SourceLNonPCM5046 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 4
					Source L / Non-PCM  cmdID= 5046 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5046 }


	iqosy30EmbeddersEmbedder4SourceR5047 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 4
					Source R  cmdID= 5047 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5047 }


	iqosy30EmbeddersEmbedder4Mute3246 OBJECT-TYPE
		SYNTAX		INTEGER { disable(0), enable(1) }
		MAX-ACCESS		read-write
		STATUS			current
		DESCRIPTION
				"TYPE: - Checkbox
				 PAGE: - Audio- Embedders- Embedder 4
					Mute  cmdID= 3246 "
		::= { iqosy30CmdEntry 3246 }


	iqosy30EmbeddersEmbedder4MuteonVbit3278 OBJECT-TYPE
		SYNTAX		INTEGER { disable(0), enable(1) }
		MAX-ACCESS		read-write
		STATUS			current
		DESCRIPTION
				"TYPE: - Checkbox
				 PAGE: - Audio- Embedders- Embedder 4
					Mute on V bit  cmdID= 3278 "
		::= { iqosy30CmdEntry 3278 }


	iqosy30EmbeddersEmbedder4InvertL3172 OBJECT-TYPE
		SYNTAX		INTEGER { disable(0), enable(1) }
		MAX-ACCESS		read-write
		STATUS			current
		DESCRIPTION
				"TYPE: - Checkbox
				 PAGE: - Audio- Embedders- Embedder 4
					Invert L  cmdID= 3172 "
		::= { iqosy30CmdEntry 3172 }


	iqosy30EmbeddersEmbedder4InvertR3173 OBJECT-TYPE
		SYNTAX		INTEGER { disable(0), enable(1) }
		MAX-ACCESS		read-write
		STATUS			current
		DESCRIPTION
				"TYPE: - Checkbox
				 PAGE: - Audio- Embedders- Embedder 4
					Invert R  cmdID= 3173 "
		::= { iqosy30CmdEntry 3173 }


	iqosy30EmbeddersEmbedder4GainL3092 OBJECT-TYPE
		SYNTAX		INTEGER
		MAX-ACCESS		read-write
		STATUS			current
		DESCRIPTION
				"TYPE: - Number
				 PAGE: - Audio- Embedders- Embedder 4
					Gain L  cmdID= 3092  min= -720  max= 120  step= 1  format= %0.1fdB  div_scale= 10 
					Min = -72.0dB  Max = 12.0dB  Step = 0.1dB "
		::= { iqosy30CmdEntry 3092 }


	iqosy30EmbeddersEmbedder4GainR3093 OBJECT-TYPE
		SYNTAX		INTEGER
		MAX-ACCESS		read-write
		STATUS			current
		DESCRIPTION
				"TYPE: - Number
				 PAGE: - Audio- Embedders- Embedder 4
					Gain R  cmdID= 3093  min= -720  max= 120  step= 1  format= %0.1fdB  div_scale= 10 
					Min = -72.0dB  Max = 12.0dB  Step = 0.1dB "
		::= { iqosy30CmdEntry 3093 }


	iqosy30EmbeddersEmbedder4PairMode3936 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 4
					Pair Mode  cmdID= 3936 
					2 Channel PCM  value= 0  
					Stereo PCM  value= 1  
					Non-PCM  value= 2  "
		::= { iqosy30CmdEntry 3936 }


	iqosy30EmbeddersEmbedder4SourceLNonPCM5048 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(32),
							val-Silence(34)
							}
		MAX-ACCESS		read-write
		STATUS			current
		DESCRIPTION
				"TYPE: - RadiobuttonList
				 PAGE: - Audio- Embedders- Embedder 4
					Source L / Non-PCM  cmdID= 5048 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 32  
					Silence  value= 34  "
		::= { iqosy30CmdEntry 5048 }


	iqosy30EmbeddersEmbedder4SourceR5049 OBJECT-TYPE
		SYNTAX		INTEGER {
							val-Dis-embed-1-1(0),
							val-Dis-embed-1-2(1),
							val-Dis-embed-2-1(2),
							val-Dis-embed-2-2(3),
							val-Dis-embed-3-1(4),
							val-Dis-embed-3-2(5),
							val-Dis-embed-4-1(6),
							val-Dis-embed-4-2(7),
							val-Dis-embed-5-1(8),
							val-Dis-embed-5-2(9),
							val-Dis-embed-6-1(10),
							val-Dis-embed-6-2(11),
							val-Dis-embed-7-1(12),
							val-Dis-embed-7-2(13),
							val-Dis-embed-8-1(14),
							val-Dis-embed-8-2(15),
							val-Tone(33),
							val-Silence(34)
							}
		MAX-ACCESS		read-write
		STATUS			current
		DESCRIPTION
				"TYPE: - RadiobuttonList
				 PAGE: - Audio- Embedders- Embedder 4
					Source R  cmdID= 5049 
					Dis-embed 1_1  value= 0  
					Dis-embed 1_2  value= 1  
					Dis-embed 2_1  value= 2  
					Dis-embed 2_2  value= 3  
					Dis-embed 3_1  value= 4  
					Dis-embed 3_2  value= 5  
					Dis-embed 4_1  value= 6  
					Dis-embed 4_2  value= 7  
					Dis-embed 5_1  value= 8  
					Dis-embed 5_2  value= 9  
					Dis-embed 6_1  value= 10  
					Dis-embed 6_2  value= 11  
					Dis-embed 7_1  value= 12  
					Dis-embed 7_2  value= 13  
					Dis-embed 8_1  value= 14  
					Dis-embed 8_2  value= 15  
					Tone  value= 33  
					Silence  value= 34  "
		::= { iqosy30CmdEntry 5049 }


	iqosy30EmbeddersEmbedder4Mute3247 OBJECT-TYPE
		SYNTAX		INTEGER { disable(0), enable(1) }
		MAX-ACCESS		read-write
		STATUS			current
		DESCRIPTION
				"TYPE: - Checkbox
				 PAGE: - Audio- Embedders- Embedder 4
					Mute  cmdID= 3247 "
		::= { iqosy30CmdEntry 3247 }


	iqosy30EmbeddersEmbedder4MuteonVbit3279 OBJECT-TYPE
		SYNTAX		INTEGER { disable(0), enable(1) }
		MAX-ACCESS		read-write
		STATUS			current
		DESCRIPTION
				"TYPE: - Checkbox
				 PAGE: - Audio- Embedders- Embedder 4
					Mute on V bit  cmdID= 3279 "
		::= { iqosy30CmdEntry 3279 }


	iqosy30EmbeddersEmbedder4InvertL3174 OBJECT-TYPE
		SYNTAX		INTEGER { disable(0), enable(1) }
		MAX-ACCESS		read-write
		STATUS			current
		DESCRIPTION
				"TYPE: - Checkbox
				 PAGE: - Audio- Embedders- Embedder 4
					Invert L  cmdID= 3174 "
		::= { iqosy30CmdEntry 3174 }


	iqosy30EmbeddersEmbedder4InvertR3175 OBJECT-TYPE
		SYNTAX		INTEGER { disable(0), enable(1) }
		MAX-ACCESS		read-write
		STATUS			current
		DESCRIPTION
				"TYPE: - Checkbox
				 PAGE: - Audio- Embedders- Embedder 4
					Invert R  cmdID= 3175 "
		::= { iqosy30CmdEntry 3175 }


	iqosy30EmbeddersEmbedder4GainL3094 OBJECT-TYPE
		SYNTAX		INTEGER
		MAX-ACCESS		read-write
		STATUS			current
		DESCRIPTION
				"TYPE: - Number
				 PAGE: - Audio- Embedders- Embedder 4
					Gain L  cmdID= 3094  min= -720  max= 120  step= 1  format= %0.1fdB  div_scale= 10 
					Min = -72.0dB  Max = 12.0dB  Step = 0.1dB "
		::= { iqosy30CmdEntry 3094 }


	iqosy30EmbeddersEmbedder4GainR3095 OBJECT-TYPE
		SYNTAX		INTEGER
		MAX-ACCESS		read-write
		STATUS			current
		DESCRIPTION
				"TYPE: - Number
				 PAGE: - Audio- Embedders- Embedder 4
					Gain R  cmdID= 3095  min= -720  max= 120  step= 1  format= %0.1fdB  div_scale= 10 
					Min = -72.0dB  Max = 12.0dB  Step = 0.1dB "
		::= { iqosy30CmdEntry 3095 }


	iqosy30EmbeddersEmbedder4PairMode3937 OBJECT-TYPE
		SYNTAX		INTEGER {
							val-2-Channel-PCM(0),
							val-Stereo-PCM(1),
							val-Non-PCM(2)
							}
		MAX-ACCESS		read-write
		STATUS			current
		DESCRIPTION
				"TYPE: - RadiobuttonList
				 PAGE: - Audio- Embedders- Embedder 4
					Pair Mode  cmdID= 3937 
					2 Channel PCM  value= 0  
					Stereo PCM  value= 1  
					Non-PCM  value= 2  "
		::= { iqosy30CmdEntry 3937 }


	iqosy30AudioDelayDelaysVideoDelay OBJECT-TYPE
		SYNTAX		INTEGER { disable(0), enable(1) }
		MAX-ACCESS		read-write
		STATUS			current
		DESCRIPTION
				"TYPE: - Checkbox
				 PAGE: - Audio
					Video Delay  cmdID= 5078 "
		::= { iqosy30CmdEntry 5078 }


	iqosy30AudioDelayDelaysManualDelay OBJECT-TYPE
		SYNTAX		INTEGER { disable(0), enable(1) }
		MAX-ACCESS		read-write
		STATUS			current
		DESCRIPTION
				"TYPE: - Checkbox
				 PAGE: - Audio
					Manual Delay  cmdID= 5079 "
		::= { iqosy30CmdEntry 5079 }


	iqosy30AudioDelayDelaysTrack14Delay OBJECT-TYPE
		SYNTAX		INTEGER { disable(0), enable(1) }
		MAX-ACCESS		read-write
		STATUS			current
		DESCRIPTION
				"TYPE: - Checkbox
				 PAGE: - Audio
					Track 14 Delay  cmdID= 5080 "
		::= { iqosy30CmdEntry 5080 }


	iqosy30AudioDelayDelaysTrack15Delay OBJECT-TYPE
		SYNTAX		INTEGER { disable(0), enable(1) }
		MAX-ACCESS		read-write
		STATUS			current
		DESCRIPTION
				"TYPE: - Checkbox
				 PAGE: - Audio
					Track 15 Delay  cmdID= 5081 "
		::= { iqosy30CmdEntry 5081 }


	iqosy30AudioDelayDelaysTrack16Delay OBJECT-TYPE
		SYNTAX		INTEGER { disable(0), enable(1) }
		MAX-ACCESS		read-write
		STATUS			current
		DESCRIPTION
				"TYPE: - Checkbox
				 PAGE: - Audio
					Track 16 Delay  cmdID= 5082 "
		::= { iqosy30CmdEntry 5082 }


	iqosy30AudioDelayDelaysTrack17Delay OBJECT-TYPE
		SYNTAX		INTEGER { disable(0), enable(1) }
		MAX-ACCESS		read-write
		STATUS			current
		DESCRIPTION
				"TYPE: - Checkbox
				 PAGE: - Audio
					Track 17 Delay  cmdID= 5083 "
		::= { iqosy30CmdEntry 5083 }


	iqosy30AudioDelayDelaysCoarseDelay OBJECT-TYPE
		SYNTAX		INTEGER
		MAX-ACCESS		read-write
		STATUS			current
		DESCRIPTION
				"TYPE: - Number
				 PAGE: - Audio
					Coarse Delay  cmdID= 5075  min= 0  max= 1750  step= 5  format= %5.3fs  div_scale= 1000 
					Min = 0.000s  Max = 1.750s  Step = 0.005s "
		::= { iqosy30CmdEntry 5075 }


	iqosy30AudioDelayDelaysFineDelay OBJECT-TYPE
		SYNTAX		INTEGER
		MAX-ACCESS		read-write
		STATUS			current
		DESCRIPTION
				"TYPE: - Number
				 PAGE: - Audio
					Fine Delay  cmdID= 5077  min= -2500  max= 2500  step= 5  format= %0.1fms  div_scale= 10 
					Min = -250.0ms  Max = 250.0ms  Step = 0.5ms "
		::= { iqosy30CmdEntry 5077 }


	iqosy30AudioDelayDelayStatusTotalDelay OBJECT-TYPE
		SYNTAX		RollCallString
		MAX-ACCESS		read-only
		STATUS			current
		DESCRIPTION
				"TYPE: - Display
				 PAGE: - Audio
					Total Delay  cmdID= 5084  format=   "
		::= { iqosy30CmdEntry 5084 }


	iqosy30AudioDelayDelayStatusVideoDelay OBJECT-TYPE
		SYNTAX		RollCallString
		MAX-ACCESS		read-only
		STATUS			current
		DESCRIPTION
				"TYPE: - Display
				 PAGE: - Audio
					Video Delay  cmdID= 5074  format=   "
		::= { iqosy30CmdEntry 5074 }


	iqosy30AudioDelayDelayStatusManualDelay OBJECT-TYPE
		SYNTAX		RollCallString
		MAX-ACCESS		read-only
		STATUS			current
		DESCRIPTION
				"TYPE: - Display
				 PAGE: - Audio
					Manual Delay  cmdID= 5076  format=   "
		::= { iqosy30CmdEntry 5076 }


	iqosy30AudioDelayDelayStatusTrack14Delay OBJECT-TYPE
		SYNTAX		RollCallString
		MAX-ACCESS		read-only
		STATUS			current
		DESCRIPTION
				"TYPE: - Display
				 PAGE: - Audio
					Track 14 Delay  cmdID= 3924  format=   "
		::= { iqosy30CmdEntry 3924 }


	iqosy30AudioDelayDelayStatusTrack15Delay OBJECT-TYPE
		SYNTAX		RollCallString
		MAX-ACCESS		read-only
		STATUS			current
		DESCRIPTION
				"TYPE: - Display
				 PAGE: - Audio
					Track 15 Delay  cmdID= 3925  format=   "
		::= { iqosy30CmdEntry 3925 }


	iqosy30AudioDelayDelayStatusTrack16Delay OBJECT-TYPE
		SYNTAX		RollCallString
		MAX-ACCESS		read-only
		STATUS			current
		DESCRIPTION
				"TYPE: - Display
				 PAGE: - Audio
					Track 16 Delay  cmdID= 3926  format=   "
		::= { iqosy30CmdEntry 3926 }


	iqosy30AudioDelayDelayStatusTrack17Delay OBJECT-TYPE
		SYNTAX		RollCallString
		MAX-ACCESS		read-only
		STATUS			current
		DESCRIPTION
				"TYPE: - Display
				 PAGE: - Audio
					Track 17 Delay  cmdID= 3927  format=   "
		::= { iqosy30CmdEntry 3927 }


	iqosy30AudioDolbyEDolbyEAutoAlign OBJECT-TYPE
		SYNTAX		INTEGER { disable(0), enable(1) }
		MAX-ACCESS		read-write
		STATUS			current
		DESCRIPTION
				"TYPE: - Checkbox
				 PAGE: - Audio
					DolbyE Auto Align  cmdID= 5032 "
		::= { iqosy30CmdEntry 5032 }


	iqosy30AudioDolbyEUserDolbyELine OBJECT-TYPE
		SYNTAX		INTEGER { disable(0), enable(1) }
		MAX-ACCESS		read-write
		STATUS			current
		DESCRIPTION
				"TYPE: - Checkbox
				 PAGE: - Audio
					User DolbyE Line  cmdID= 6701 "
		::= { iqosy30CmdEntry 6701 }


	iqosy30AudioDolbyEDolbyEAutoLineNo OBJECT-TYPE
		SYNTAX		INTEGER
		MAX-ACCESS		read-write
		STATUS			current
		DESCRIPTION
				"TYPE: - Number
				 PAGE: - Audio
					DolbyE Auto Line No  cmdID= 6703  min= 8  max= 22  step= 1  format= %0.0f  div_scale= 1 
					Min = 8  Max = 22  Step = 1 "
		::= { iqosy30CmdEntry 6703 }


	iqosy30AudioDolbyELineStandard OBJECT-TYPE
		SYNTAX		INTEGER
		MAX-ACCESS		read-write
		STATUS			current
		DESCRIPTION
				"TYPE: - Number
				 PAGE: - Audio
					Line Standard  cmdID= 6700  min= 0  max= 10  step= 1  format= %0.0f  div_scale= 1 
					Min = 0  Max = 10  Step = 1 "
		::= { iqosy30CmdEntry 6700 }


	iqosy30AudioToneFrequency OBJECT-TYPE
		SYNTAX		INTEGER
		MAX-ACCESS		read-write
		STATUS			current
		DESCRIPTION
				"TYPE: - Number
				 PAGE: - Audio
					Frequency  cmdID= 2487  min= 100  max= 10000  step= 100  format= %5.0fHz  div_scale= 1 
					Min =   100Hz  Max = 10000Hz  Step =   100Hz "
		::= { iqosy30CmdEntry 2487 }


	iqosy30AudioToneChannelident OBJECT-TYPE
		SYNTAX		INTEGER { disable(0), enable(1) }
		MAX-ACCESS		read-write
		STATUS			current
		DESCRIPTION
				"TYPE: - Checkbox
				 PAGE: - Audio
					Channel ident  cmdID= 5030 "
		::= { iqosy30CmdEntry 5030 }


	iqosy30AudioAudioMonitorSilenceLevel OBJECT-TYPE
		SYNTAX		INTEGER
		MAX-ACCESS		read-write
		STATUS			current
		DESCRIPTION
				"TYPE: - Number
				 PAGE: - Audio
					Silence Level  cmdID= 3061  min= -80  max= 0  step= 1  format= %1.0f dB  div_scale= 1 
					Min = -80 dB  Max = 0 dB  Step = 1 dB "
		::= { iqosy30CmdEntry 3061 }


	iqosy30AudioAudioMonitorOverloadLevel OBJECT-TYPE
		SYNTAX		INTEGER
		MAX-ACCESS		read-write
		STATUS			current
		DESCRIPTION
				"TYPE: - Number
				 PAGE: - Audio
					Overload Level  cmdID= 3064  min= -80  max= 0  step= 1  format= %1.0f dB  div_scale= 1 
					Min = -80 dB  Max = 0 dB  Step = 1 dB "
		::= { iqosy30CmdEntry 3064 }


	iqosy30AudioAudioMonitorWarningTimer OBJECT-TYPE
		SYNTAX		INTEGER
		MAX-ACCESS		read-write
		STATUS			current
		DESCRIPTION
				"TYPE: - Number
				 PAGE: - Audio
					Warning Timer  cmdID= 3065  min= 1  max= 20  step= 1  format= %1.0f sec  div_scale= 1 
					Min = 1 sec  Max = 20 sec  Step = 1 sec "
		::= { iqosy30CmdEntry 3065 }


	iqosy30Genlock OBJECT-TYPE
		SYNTAX		INTEGER {
							val-Freerun(2),
							val-Lock-to-Reference(0),
							val-Lock-to-Input(1)
							}
		MAX-ACCESS		read-write
		STATUS			current
		DESCRIPTION
				"TYPE: - Button
					Freerun  cmdID= 3674  value= 2  
					Lock to Reference  cmdID= 3674  value= 0  
					Lock to Input  cmdID= 3674  value= 1  "
		::= { iqosy30CmdEntry 3674 }


	iqosy30GenlockFreerunFrequency OBJECT-TYPE
		SYNTAX		INTEGER
		MAX-ACCESS		read-write
		STATUS			current
		DESCRIPTION
				"TYPE: - Number
					Freerun Frequency  cmdID= 2449  min= -200  max= 200  step= 1  format= %.0f  div_scale= 1 
					Min = -200  Max = 200  Step = 1 "
		::= { iqosy30CmdEntry 2449 }


	iqosy30GenlockGenlockHPhase3790 OBJECT-TYPE
		SYNTAX		INTEGER
		MAX-ACCESS		read-write
		STATUS			current
		DESCRIPTION
				"TYPE: - Number
					Genlock H Phase  cmdID= 3790  min= -1320  max= 1320  step= 1  format= %.0f pixels  div_scale= 1 
					Min = -1320 pixels  Max = 1320 pixels  Step = 1 pixels "
		::= { iqosy30CmdEntry 3790 }


	iqosy30GenlockGenlockVPhase3791 OBJECT-TYPE
		SYNTAX		INTEGER
		MAX-ACCESS		read-write
		STATUS			current
		DESCRIPTION
				"TYPE: - Number
					Genlock V Phase  cmdID= 3791  min= -562  max= 562  step= 1  format= %.0f lines  div_scale= 1 
					Min = -562 lines  Max = 562 lines  Step = 1 lines "
		::= { iqosy30CmdEntry 3791 }


	iqosy30GenlockVideoHdelay3794 OBJECT-TYPE
		SYNTAX		INTEGER
		MAX-ACCESS		read-write
		STATUS			current
		DESCRIPTION
				"TYPE: - Number
					Video H delay  cmdID= 3794  min= 0  max= 2640  step= 1  format= %.0f pixels  div_scale= 1 
					Min = 0 pixels  Max = 2640 pixels  Step = 1 pixels "
		::= { iqosy30CmdEntry 3794 }


	iqosy30GenlockVideoVdelay3795 OBJECT-TYPE
		SYNTAX		INTEGER
		MAX-ACCESS		read-write
		STATUS			current
		DESCRIPTION
				"TYPE: - Number
					Video V delay  cmdID= 3795  min= 0  max= 1125  step= 1  format= %.0f lines  div_scale= 1 
					Min = 0 lines  Max = 1125 lines  Step = 1 lines "
		::= { iqosy30CmdEntry 3795 }


	iqosy30GenlockVideoFdelay OBJECT-TYPE
		SYNTAX		INTEGER
		MAX-ACCESS		read-write
		STATUS			current
		DESCRIPTION
				"TYPE: - Number
					Video F delay  cmdID= 3796  min= 0  max= 9  step= 1  format= %.0f frames  div_scale= 1 
					Min = 0 frames  Max = 9 frames  Step = 1 frames "
		::= { iqosy30CmdEntry 3796 }


	iqosy30GenlockGenlocksaveindex OBJECT-TYPE
		SYNTAX		INTEGER
		MAX-ACCESS		read-write
		STATUS			current
		DESCRIPTION
				"TYPE: - Number
					Genlock save index  cmdID= 3991  min= 0  max= 10  step= 1  format= %.0f  div_scale= 1 
					Min = 0  Max = 10  Step = 1 "
		::= { iqosy30CmdEntry 3991 }


	iqosy30GenlockGenlockHPhase3992 OBJECT-TYPE
		SYNTAX		INTEGER
		MAX-ACCESS		read-write
		STATUS			current
		DESCRIPTION
				"TYPE: - Number
					Genlock H Phase  cmdID= 3992  min= -1320  max= 1320  step= 1  format= %.0f pixels  div_scale= 1 
					Min = -1320 pixels  Max = 1320 pixels  Step = 1 pixels "
		::= { iqosy30CmdEntry 3992 }


	iqosy30GenlockGenlockVPhase3993 OBJECT-TYPE
		SYNTAX		INTEGER
		MAX-ACCESS		read-write
		STATUS			current
		DESCRIPTION
				"TYPE: - Number
					Genlock V Phase  cmdID= 3993  min= -562  max= 562  step= 1  format= %.0f lines  div_scale= 1 
					Min = -562 lines  Max = 562 lines  Step = 1 lines "
		::= { iqosy30CmdEntry 3993 }


	iqosy30GenlockVideoHdelay3994 OBJECT-TYPE
		SYNTAX		INTEGER
		MAX-ACCESS		read-write
		STATUS			current
		DESCRIPTION
				"TYPE: - Number
					Video H delay  cmdID= 3994  min= 0  max= 2640  step= 1  format= %.0f pixels  div_scale= 1 
					Min = 0 pixels  Max = 2640 pixels  Step = 1 pixels "
		::= { iqosy30CmdEntry 3994 }


	iqosy30GenlockVideoVdelay3995 OBJECT-TYPE
		SYNTAX		INTEGER
		MAX-ACCESS		read-write
		STATUS			current
		DESCRIPTION
				"TYPE: - Number
					Video V delay  cmdID= 3995  min= 0  max= 1125  step= 1  format= %.0f lines  div_scale= 1 
					Min = 0 lines  Max = 1125 lines  Step = 1 lines "
		::= { iqosy30CmdEntry 3995 }


	iqosy30ReferenceSelect OBJECT-TYPE
		SYNTAX		INTEGER {
							val-Module-Reference(0),
							val-Chassis-Reference-A(1),
							val-Chassis-Reference-B(2)
							}
		MAX-ACCESS		read-write
		STATUS			current
		DESCRIPTION
				"TYPE: - RadiobuttonList
					Reference Select  cmdID= 3792 
					Module Reference  value= 0  
					Chassis Reference A  value= 1  
					Chassis Reference B  value= 2  "
		::= { iqosy30CmdEntry 3792 }


	iqosy30StatusStatusDisplay OBJECT-TYPE
		SYNTAX		INTEGER {
							val-Input-Status(0),
							val-Video-Status(1),
							val-Audio-Input-Status(2),
							val-Reference-Status(3)
							}
		MAX-ACCESS		read-write
		STATUS			current
		DESCRIPTION
				"TYPE: - RadiobuttonList
					Status Display  cmdID= 1915 
					Input Status  value= 0  
					Video Status  value= 1  
					Audio Input Status  value= 2  
					Reference Status  value= 3  "
		::= { iqosy30CmdEntry 1915 }


	iqosy30StatusProduct OBJECT-TYPE
		SYNTAX		RollCallString
		MAX-ACCESS		read-only
		STATUS			current
		DESCRIPTION
				"TYPE: - Display
					Product  cmdID= 5000  format=   "
		::= { iqosy30CmdEntry 5000 }


	iqosy30StatusSoftwareVersion OBJECT-TYPE
		SYNTAX		RollCallString
		MAX-ACCESS		read-only
		STATUS			current
		DESCRIPTION
				"TYPE: - Display
					Software Version  cmdID= 2  format=   "
		::= { iqosy30CmdEntry 2 }


	iqosy30StatusSerialNo OBJECT-TYPE
		SYNTAX		RollCallString
		MAX-ACCESS		read-only
		STATUS			current
		DESCRIPTION
				"TYPE: - Display
					Serial No  cmdID= 1  format=   "
		::= { iqosy30CmdEntry 1 }


	iqosy30StatusFactoryDefaults OBJECT-TYPE
		SYNTAX		INTEGER { noAction(0),val-Factory-Defaults(1) }
		MAX-ACCESS		read-write
		STATUS			current
		DESCRIPTION
				"TYPE: - Button
					Factory Defaults  cmdID= 5020  value= 1  "
		::= { iqosy30CmdEntry 5020 }


	iqosy30StatusDefaultSetting OBJECT-TYPE
		SYNTAX		INTEGER { noAction(0),val-Default-Setting(1) }
		MAX-ACCESS		read-write
		STATUS			current
		DESCRIPTION
				"TYPE: - Button
					Default Setting  cmdID= 5021  value= 1  "
		::= { iqosy30CmdEntry 5021 }


	iqosy30StatusRestart OBJECT-TYPE
		SYNTAX		INTEGER { noAction(0),val-Restart(1) }
		MAX-ACCESS		read-write
		STATUS			current
		DESCRIPTION
				"TYPE: - Button
					Restart  cmdID= 4  value= 1  "
		::= { iqosy30CmdEntry 4 }


	iqosy30StatusBuild OBJECT-TYPE
		SYNTAX		RollCallString
		MAX-ACCESS		read-only
		STATUS			current
		DESCRIPTION
				"TYPE: - Display
					Build  cmdID= 5  format=   "
		::= { iqosy30CmdEntry 5 }


	iqosy30StatusPCB OBJECT-TYPE
		SYNTAX		RollCallString
		MAX-ACCESS		read-only
		STATUS			current
		DESCRIPTION
				"TYPE: - Display
					PCB  cmdID= 6  format=   "
		::= { iqosy30CmdEntry 6 }


	iqosy30StatusKOSVersion OBJECT-TYPE
		SYNTAX		RollCallString
		MAX-ACCESS		read-only
		STATUS			current
		DESCRIPTION
				"TYPE: - Display
					KOS Version  cmdID= 7  format=   "
		::= { iqosy30CmdEntry 7 }


	iqosy30StatusFirmwareVersion OBJECT-TYPE
		SYNTAX		RollCallString
		MAX-ACCESS		read-only
		STATUS			current
		DESCRIPTION
				"TYPE: - Display
					Firmware Version  cmdID= 5001  format=   "
		::= { iqosy30CmdEntry 5001 }


	iqosy30StatusUpTime OBJECT-TYPE
		SYNTAX		RollCallString
		MAX-ACCESS		read-only
		STATUS			current
		DESCRIPTION
				"TYPE: - Display
					Up Time  cmdID= 8  format=   "
		::= { iqosy30CmdEntry 8 }


	iqosy30MemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqosy30CmdEntry 37101 }


	iqosy30MemoriesSetMemName OBJECT-TYPE
		SYNTAX		RollCallString
		MAX-ACCESS		read-write
		STATUS			current
		DESCRIPTION
				"TYPE: - Editstring
					SetMemName  cmdID= 37103  "
		::= { iqosy30CmdEntry 37103 }


	iqosy30MemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqosy30CmdEntry 37100 }


	iqosy30MemoriesSaveMemory OBJECT-TYPE
		SYNTAX		INTEGER { noAction(0),val-Save-Memory(1) }
		MAX-ACCESS		read-write
		STATUS			current
		DESCRIPTION
				"TYPE: - Button
					Save Memory  cmdID= 37102  value= 1  "
		::= { iqosy30CmdEntry 37102 }


	iqosy30MemoriesLastUserMemory OBJECT-TYPE
		SYNTAX		RollCallString
		MAX-ACCESS		read-only
		STATUS			current
		DESCRIPTION
				"TYPE: - Display
					Last User Memory  cmdID= 37104  format=   "
		::= { iqosy30CmdEntry 37104 }


	iqosy30MemoriesClearMemory OBJECT-TYPE
		SYNTAX		INTEGER { noAction(0),val-Clear-Memory(1) }
		MAX-ACCESS		read-write
		STATUS			current
		DESCRIPTION
				"TYPE: - Button
					Clear Memory  cmdID= 37105  value= 1  "
		::= { iqosy30CmdEntry 37105 }


	iqosy30MemoriesMemoryNamesMemory1Name OBJECT-TYPE
		SYNTAX		RollCallString
		MAX-ACCESS		read-only
		STATUS			current
		DESCRIPTION
				"TYPE: - Display
					Memory 1 Name  cmdID= 37106  format=   "
		::= { iqosy30CmdEntry 37106 }


	iqosy30MemoriesMemoryNamesMemory2Name OBJECT-TYPE
		SYNTAX		RollCallString
		MAX-ACCESS		read-only
		STATUS			current
		DESCRIPTION
				"TYPE: - Display
					Memory 2 Name  cmdID= 37107  format=   "
		::= { iqosy30CmdEntry 37107 }


	iqosy30MemoriesMemoryNamesMemory3Name OBJECT-TYPE
		SYNTAX		RollCallString
		MAX-ACCESS		read-only
		STATUS			current
		DESCRIPTION
				"TYPE: - Display
					Memory 3 Name  cmdID= 37108  format=   "
		::= { iqosy30CmdEntry 37108 }


	iqosy30MemoriesMemoryNamesMemory4Name OBJECT-TYPE
		SYNTAX		RollCallString
		MAX-ACCESS		read-only
		STATUS			current
		DESCRIPTION
				"TYPE: - Display
					Memory 4 Name  cmdID= 37109  format=   "
		::= { iqosy30CmdEntry 37109 }


	iqosy30MemoriesMemoryNamesMemory5Name OBJECT-TYPE
		SYNTAX		RollCallString
		MAX-ACCESS		read-only
		STATUS			current
		DESCRIPTION
				"TYPE: - Display
					Memory 5 Name  cmdID= 37110  format=   "
		::= { iqosy30CmdEntry 37110 }


	iqosy30MemoriesMemoryNamesMemory6Name OBJECT-TYPE
		SYNTAX		RollCallString
		MAX-ACCESS		read-only
		STATUS			current
		DESCRIPTION
				"TYPE: - Display
					Memory 6 Name  cmdID= 37111  format=   "
		::= { iqosy30CmdEntry 37111 }


	iqosy30MemoriesMemoryNamesMemory7Name OBJECT-TYPE
		SYNTAX		RollCallString
		MAX-ACCESS		read-only
		STATUS			current
		DESCRIPTION
				"TYPE: - Display
					Memory 7 Name  cmdID= 37112  format=   "
		::= { iqosy30CmdEntry 37112 }


	iqosy30MemoriesMemoryNamesMemory8Name OBJECT-TYPE
		SYNTAX		RollCallString
		MAX-ACCESS		read-only
		STATUS			current
		DESCRIPTION
				"TYPE: - Display
					Memory 8 Name  cmdID= 37113  format=   "
		::= { iqosy30CmdEntry 37113 }


	iqosy30MemoriesMemoryNamesMemory9Name OBJECT-TYPE
		SYNTAX		RollCallString
		MAX-ACCESS		read-only
		STATUS			current
		DESCRIPTION
				"TYPE: - Display
					Memory 9 Name  cmdID= 37114  format=   "
		::= { iqosy30CmdEntry 37114 }


	iqosy30MemoriesMemoryNamesMemory10Name OBJECT-TYPE
		SYNTAX		RollCallString
		MAX-ACCESS		read-only
		STATUS			current
		DESCRIPTION
				"TYPE: - Display
					Memory 10 Name  cmdID= 37115  format=   "
		::= { iqosy30CmdEntry 37115 }


	iqosy30MemoriesMemoryNamesMemory11Name OBJECT-TYPE
		SYNTAX		RollCallString
		MAX-ACCESS		read-only
		STATUS			current
		DESCRIPTION
				"TYPE: - Display
					Memory 11 Name  cmdID= 37116  format=   "
		::= { iqosy30CmdEntry 37116 }


	iqosy30MemoriesMemoryNamesMemory12Name OBJECT-TYPE
		SYNTAX		RollCallString
		MAX-ACCESS		read-only
		STATUS			current
		DESCRIPTION
				"TYPE: - Display
					Memory 12 Name  cmdID= 37117  format=   "
		::= { iqosy30CmdEntry 37117 }


	iqosy30MemoriesMemoryNamesMemory13Name OBJECT-TYPE
		SYNTAX		RollCallString
		MAX-ACCESS		read-only
		STATUS			current
		DESCRIPTION
				"TYPE: - Display
					Memory 13 Name  cmdID= 37118  format=   "
		::= { iqosy30CmdEntry 37118 }


	iqosy30MemoriesMemoryNamesMemory14Name OBJECT-TYPE
		SYNTAX		RollCallString
		MAX-ACCESS		read-only
		STATUS			current
		DESCRIPTION
				"TYPE: - Display
					Memory 14 Name  cmdID= 37119  format=   "
		::= { iqosy30CmdEntry 37119 }


	iqosy30MemoriesMemoryNamesMemory15Name OBJECT-TYPE
		SYNTAX		RollCallString
		MAX-ACCESS		read-only
		STATUS			current
		DESCRIPTION
				"TYPE: - Display
					Memory 15 Name  cmdID= 37120  format=   "
		::= { iqosy30CmdEntry 37120 }


	iqosy30MemoriesMemoryNamesMemory16Name OBJECT-TYPE
		SYNTAX		RollCallString
		MAX-ACCESS		read-only
		STATUS			current
		DESCRIPTION
				"TYPE: - Display
					Memory 16 Name  cmdID= 37121  format=   "
		::= { iqosy30CmdEntry 37121 }


	iqosy30LoggingLogMiscSlotStarten OBJECT-TYPE
		SYNTAX		INTEGER { disable(0), enable(1) }
		MAX-ACCESS		read-write
		STATUS			current
		DESCRIPTION
				"TYPE: - Checkbox
				 PAGE: - Setup- Logging- Log Misc
					Slot Start_en  cmdID= 4976 "
		::= { iqosy30CmdEntry 4976 }


	iqosy30LoggingLogMiscSlotStart OBJECT-TYPE
		SYNTAX		RollCallString
		MAX-ACCESS		read-only
		STATUS			current
		DESCRIPTION
				"TYPE: - Display
				 PAGE: - Setup- Logging- Log Misc
					Slot Start  cmdID= 4977  format=   "
		::= { iqosy30CmdEntry 4977 }


	iqosy30LoggingLogMiscSlotWidthen OBJECT-TYPE
		SYNTAX		INTEGER { disable(0), enable(1) }
		MAX-ACCESS		read-write
		STATUS			current
		DESCRIPTION
				"TYPE: - Checkbox
				 PAGE: - Setup- Logging- Log Misc
					Slot Width_en  cmdID= 4978 "
		::= { iqosy30CmdEntry 4978 }


	iqosy30LoggingLogMiscSlotWidth OBJECT-TYPE
		SYNTAX		RollCallString
		MAX-ACCESS		read-only
		STATUS			current
		DESCRIPTION
				"TYPE: - Display
				 PAGE: - Setup- Logging- Log Misc
					Slot Width  cmdID= 4979  format=   "
		::= { iqosy30CmdEntry 4979 }


	iqosy30LoggingLogMiscRearStatusen OBJECT-TYPE
		SYNTAX		INTEGER { disable(0), enable(1) }
		MAX-ACCESS		read-write
		STATUS			current
		DESCRIPTION
				"TYPE: - Checkbox
				 PAGE: - Setup- Logging- Log Misc
					Rear Status_en  cmdID= 4980 "
		::= { iqosy30CmdEntry 4980 }


	iqosy30LoggingLogMiscRearStatus OBJECT-TYPE
		SYNTAX		RollCallString
		MAX-ACCESS		read-only
		STATUS			current
		DESCRIPTION
				"TYPE: - Display
				 PAGE: - Setup- Logging- Log Misc
					Rear Status  cmdID= 4981  format=   "
		::= { iqosy30CmdEntry 4981 }


	iqosy30LoggingLogMiscRearIDen OBJECT-TYPE
		SYNTAX		INTEGER { disable(0), enable(1) }
		MAX-ACCESS		read-write
		STATUS			current
		DESCRIPTION
				"TYPE: - Checkbox
				 PAGE: - Setup- Logging- Log Misc
					Rear ID_en  cmdID= 4982 "
		::= { iqosy30CmdEntry 4982 }


	iqosy30LoggingLogMiscRearID OBJECT-TYPE
		SYNTAX		RollCallString
		MAX-ACCESS		read-only
		STATUS			current
		DESCRIPTION
				"TYPE: - Display
				 PAGE: - Setup- Logging- Log Misc
					Rear ID  cmdID= 4983  format=   "
		::= { iqosy30CmdEntry 4983 }


	iqosy30LoggingLogMiscFirmwareVersionen OBJECT-TYPE
		SYNTAX		INTEGER { disable(0), enable(1) }
		MAX-ACCESS		read-write
		STATUS			current
		DESCRIPTION
				"TYPE: - Checkbox
				 PAGE: - Setup- Logging- Log Misc
					Firmware Version_en  cmdID= 4986 "
		::= { iqosy30CmdEntry 4986 }


	iqosy30LoggingLogMiscFirmwareVersion OBJECT-TYPE
		SYNTAX		RollCallString
		MAX-ACCESS		read-only
		STATUS			current
		DESCRIPTION
				"TYPE: - Display
				 PAGE: - Setup- Logging- Log Misc
					Firmware Version  cmdID= 4987  format=   "
		::= { iqosy30CmdEntry 4987 }


	iqosy30LoggingLogMiscLicensedOptionsen OBJECT-TYPE
		SYNTAX		INTEGER { disable(0), enable(1) }
		MAX-ACCESS		read-write
		STATUS			current
		DESCRIPTION
				"TYPE: - Checkbox
				 PAGE: - Setup- Logging- Log Misc
					Licensed Options_en  cmdID= 4988 "
		::= { iqosy30CmdEntry 4988 }


	iqosy30LoggingLogMiscLicensedOptions OBJECT-TYPE
		SYNTAX		RollCallString
		MAX-ACCESS		read-only
		STATUS			current
		DESCRIPTION
				"TYPE: - Display
				 PAGE: - Setup- Logging- Log Misc
					Licensed Options  cmdID= 4989  format=   "
		::= { iqosy30CmdEntry 4989 }


	iqosy30LoggingLogMiscBuildNumberen OBJECT-TYPE
		SYNTAX		INTEGER { disable(0), enable(1) }
		MAX-ACCESS		read-write
		STATUS			current
		DESCRIPTION
				"TYPE: - Checkbox
				 PAGE: - Setup- Logging- Log Misc
					Build Number_en  cmdID= 4992 "
		::= { iqosy30CmdEntry 4992 }


	iqosy30LoggingLogMiscBuildNumber OBJECT-TYPE
		SYNTAX		RollCallString
		MAX-ACCESS		read-only
		STATUS			current
		DESCRIPTION
				"TYPE: - Display
				 PAGE: - Setup- Logging- Log Misc
					Build Number  cmdID= 4993  format=   "
		::= { iqosy30CmdEntry 4993 }


	iqosy30LoggingLogMiscOSVersionen OBJECT-TYPE
		SYNTAX		INTEGER { disable(0), enable(1) }
		MAX-ACCESS		read-write
		STATUS			current
		DESCRIPTION
				"TYPE: - Checkbox
				 PAGE: - Setup- Logging- Log Misc
					OS Version_en  cmdID= 4994 "
		::= { iqosy30CmdEntry 4994 }


	iqosy30LoggingLogMiscOSVersion OBJECT-TYPE
		SYNTAX		RollCallString
		MAX-ACCESS		read-only
		STATUS			current
		DESCRIPTION
				"TYPE: - Display
				 PAGE: - Setup- Logging- Log Misc
					OS Version  cmdID= 4995  format=   "
		::= { iqosy30CmdEntry 4995 }


	iqosy30LoggingLogMiscHardwareVersionen OBJECT-TYPE
		SYNTAX		INTEGER { disable(0), enable(1) }
		MAX-ACCESS		read-write
		STATUS			current
		DESCRIPTION
				"TYPE: - Checkbox
				 PAGE: - Setup- Logging- Log Misc
					Hardware Version_en  cmdID= 4996 "
		::= { iqosy30CmdEntry 4996 }


	iqosy30LoggingLogMiscHardwareVersion OBJECT-TYPE
		SYNTAX		RollCallString
		MAX-ACCESS		read-only
		STATUS			current
		DESCRIPTION
				"TYPE: - Display
				 PAGE: - Setup- Logging- Log Misc
					Hardware Version  cmdID= 4997  format=   "
		::= { iqosy30CmdEntry 4997 }


	iqosy30LoggingLogMiscUptimeen OBJECT-TYPE
		SYNTAX		INTEGER { disable(0), enable(1) }
		MAX-ACCESS		read-write
		STATUS			current
		DESCRIPTION
				"TYPE: - Checkbox
				 PAGE: - Setup- Logging- Log Misc
					Uptime_en  cmdID= 4998 "
		::= { iqosy30CmdEntry 4998 }


	iqosy30LoggingLogMiscUptime OBJECT-TYPE
		SYNTAX		RollCallString
		MAX-ACCESS		read-only
		STATUS			current
		DESCRIPTION
				"TYPE: - Display
				 PAGE: - Setup- Logging- Log Misc
					Uptime  cmdID= 4999  format=   "
		::= { iqosy30CmdEntry 4999 }


	iqosy30LoggingLogMiscSerialNumberen OBJECT-TYPE
		SYNTAX		INTEGER { disable(0), enable(1) }
		MAX-ACCESS		read-write
		STATUS			current
		DESCRIPTION
				"TYPE: - Checkbox
				 PAGE: - Setup- Logging- Log Misc
					Serial Number_en  cmdID= 4990 "
		::= { iqosy30CmdEntry 4990 }


	iqosy30LoggingLogMiscSerialNumber OBJECT-TYPE
		SYNTAX		RollCallString
		MAX-ACCESS		read-only
		STATUS			current
		DESCRIPTION
				"TYPE: - Display
				 PAGE: - Setup- Logging- Log Misc
					Serial Number  cmdID= 4991  format=   "
		::= { iqosy30CmdEntry 4991 }


	iqosy30LoggingLogVideoInput1Input1en OBJECT-TYPE
		SYNTAX		INTEGER { disable(0), enable(1) }
		MAX-ACCESS		read-write
		STATUS			current
		DESCRIPTION
				"TYPE: - Checkbox
				 PAGE: - Setup- Logging- Log Video_Input_1
					Input1_en  cmdID= 4000 "
		::= { iqosy30CmdEntry 4000 }


	iqosy30LoggingLogVideoInput1Input1 OBJECT-TYPE
		SYNTAX		RollCallString
		MAX-ACCESS		read-only
		STATUS			current
		DESCRIPTION
				"TYPE: - Display
				 PAGE: - Setup- Logging- Log Video_Input_1
					Input1  cmdID= 4001  format=   "
		::= { iqosy30CmdEntry 4001 }


	iqosy30LoggingLogVideoInput1Input1Standarden OBJECT-TYPE
		SYNTAX		INTEGER { disable(0), enable(1) }
		MAX-ACCESS		read-write
		STATUS			current
		DESCRIPTION
				"TYPE: - Checkbox
				 PAGE: - Setup- Logging- Log Video_Input_1
					Input1 Standard_en  cmdID= 4004 "
		::= { iqosy30CmdEntry 4004 }


	iqosy30LoggingLogVideoInput1Input1Standard OBJECT-TYPE
		SYNTAX		RollCallString
		MAX-ACCESS		read-only
		STATUS			current
		DESCRIPTION
				"TYPE: - Display
				 PAGE: - Setup- Logging- Log Video_Input_1
					Input1 Standard  cmdID= 4005  format=   "
		::= { iqosy30CmdEntry 4005 }


	iqosy30LoggingLogVideoInput1In1SDIERRSen OBJECT-TYPE
		SYNTAX		INTEGER { disable(0), enable(1) }
		MAX-ACCESS		read-write
		STATUS			current
		DESCRIPTION
				"TYPE: - Checkbox
				 PAGE: - Setup- Logging- Log Video_Input_1
					In1 SDI ERRS_en  cmdID= 4012 "
		::= { iqosy30CmdEntry 4012 }


	iqosy30LoggingLogVideoInput1In1SDIERRS OBJECT-TYPE
		SYNTAX		RollCallString
		MAX-ACCESS		read-only
		STATUS			current
		DESCRIPTION
				"TYPE: - Display
				 PAGE: - Setup- Logging- Log Video_Input_1
					In1 SDI ERRS  cmdID= 4013  format=   "
		::= { iqosy30CmdEntry 4013 }


	iqosy30LoggingLogVideoInput1In1SDIANCERRSen OBJECT-TYPE
		SYNTAX		INTEGER { disable(0), enable(1) }
		MAX-ACCESS		read-write
		STATUS			current
		DESCRIPTION
				"TYPE: - Checkbox
				 PAGE: - Setup- Logging- Log Video_Input_1
					In1 SDI ANC ERRS_en  cmdID= 4020 "
		::= { iqosy30CmdEntry 4020 }


	iqosy30LoggingLogVideoInput1In1SDIANCERRS OBJECT-TYPE
		SYNTAX		RollCallString
		MAX-ACCESS		read-only
		STATUS			current
		DESCRIPTION
				"TYPE: - Display
				 PAGE: - Setup- Logging- Log Video_Input_1
					In1 SDI ANC ERRS  cmdID= 4021  format=   "
		::= { iqosy30CmdEntry 4021 }


	iqosy30LoggingLogVideoInput1Input1Typeen OBJECT-TYPE
		SYNTAX		INTEGER { disable(0), enable(1) }
		MAX-ACCESS		read-write
		STATUS			current
		DESCRIPTION
				"TYPE: - Checkbox
				 PAGE: - Setup- Logging- Log Video_Input_1
					Input1 Type_en  cmdID= 4024 "
		::= { iqosy30CmdEntry 4024 }


	iqosy30LoggingLogVideoInput1Input1Type OBJECT-TYPE
		SYNTAX		RollCallString
		MAX-ACCESS		read-only
		STATUS			current
		DESCRIPTION
				"TYPE: - Display
				 PAGE: - Setup- Logging- Log Video_Input_1
					Input1 Type  cmdID= 4025  format=   "
		::= { iqosy30CmdEntry 4025 }


	iqosy30LoggingLogVideoInput1Input1Identen OBJECT-TYPE
		SYNTAX		INTEGER { disable(0), enable(1) }
		MAX-ACCESS		read-write
		STATUS			current
		DESCRIPTION
				"TYPE: - Checkbox
				 PAGE: - Setup- Logging- Log Video_Input_1
					Input1 Ident_en  cmdID= 4028 "
		::= { iqosy30CmdEntry 4028 }


	iqosy30LoggingLogVideoInput1Input1Ident OBJECT-TYPE
		SYNTAX		RollCallString
		MAX-ACCESS		read-only
		STATUS			current
		DESCRIPTION
				"TYPE: - Display
				 PAGE: - Setup- Logging- Log Video_Input_1
					Input1 Ident  cmdID= 4029  format=   "
		::= { iqosy30CmdEntry 4029 }


	iqosy30LoggingLogVideoInput1Input3en OBJECT-TYPE
		SYNTAX		INTEGER { disable(0), enable(1) }
		MAX-ACCESS		read-write
		STATUS			current
		DESCRIPTION
				"TYPE: - Checkbox
				 PAGE: - Setup- Logging- Log Video_Input_1
					Input3_en  cmdID= 4244 "
		::= { iqosy30CmdEntry 4244 }


	iqosy30LoggingLogVideoInput1Input3 OBJECT-TYPE
		SYNTAX		RollCallString
		MAX-ACCESS		read-only
		STATUS			current
		DESCRIPTION
				"TYPE: - Display
				 PAGE: - Setup- Logging- Log Video_Input_1
					Input3  cmdID= 4245  format=   "
		::= { iqosy30CmdEntry 4245 }


	iqosy30LoggingLogVideoInput1Input3Standarden OBJECT-TYPE
		SYNTAX		INTEGER { disable(0), enable(1) }
		MAX-ACCESS		read-write
		STATUS			current
		DESCRIPTION
				"TYPE: - Checkbox
				 PAGE: - Setup- Logging- Log Video_Input_1
					Input3 Standard_en  cmdID= 4248 "
		::= { iqosy30CmdEntry 4248 }


	iqosy30LoggingLogVideoInput1Input3Standard OBJECT-TYPE
		SYNTAX		RollCallString
		MAX-ACCESS		read-only
		STATUS			current
		DESCRIPTION
				"TYPE: - Display
				 PAGE: - Setup- Logging- Log Video_Input_1
					Input3 Standard  cmdID= 4249  format=   "
		::= { iqosy30CmdEntry 4249 }


	iqosy30LoggingLogVideoInput1In3SDIERRSen OBJECT-TYPE
		SYNTAX		INTEGER { disable(0), enable(1) }
		MAX-ACCESS		read-write
		STATUS			current
		DESCRIPTION
				"TYPE: - Checkbox
				 PAGE: - Setup- Logging- Log Video_Input_1
					In3 SDI ERRS_en  cmdID= 4256 "
		::= { iqosy30CmdEntry 4256 }


	iqosy30LoggingLogVideoInput1In3SDIERRS OBJECT-TYPE
		SYNTAX		RollCallString
		MAX-ACCESS		read-only
		STATUS			current
		DESCRIPTION
				"TYPE: - Display
				 PAGE: - Setup- Logging- Log Video_Input_1
					In3 SDI ERRS  cmdID= 4257  format=   "
		::= { iqosy30CmdEntry 4257 }


	iqosy30LoggingLogVideoInput1In3SDIANCERRSen OBJECT-TYPE
		SYNTAX		INTEGER { disable(0), enable(1) }
		MAX-ACCESS		read-write
		STATUS			current
		DESCRIPTION
				"TYPE: - Checkbox
				 PAGE: - Setup- Logging- Log Video_Input_1
					In3 SDI ANC ERRS_en  cmdID= 4264 "
		::= { iqosy30CmdEntry 4264 }


	iqosy30LoggingLogVideoInput1In3SDIANCERRS OBJECT-TYPE
		SYNTAX		RollCallString
		MAX-ACCESS		read-only
		STATUS			current
		DESCRIPTION
				"TYPE: - Display
				 PAGE: - Setup- Logging- Log Video_Input_1
					In3 SDI ANC ERRS  cmdID= 4265  format=   "
		::= { iqosy30CmdEntry 4265 }


	iqosy30LoggingLogVideoInput1Input3Typeen OBJECT-TYPE
		SYNTAX		INTEGER { disable(0), enable(1) }
		MAX-ACCESS		read-write
		STATUS			current
		DESCRIPTION
				"TYPE: - Checkbox
				 PAGE: - Setup- Logging- Log Video_Input_1
					Input3 Type_en  cmdID= 4268 "
		::= { iqosy30CmdEntry 4268 }


	iqosy30LoggingLogVideoInput1Input3Type OBJECT-TYPE
		SYNTAX		RollCallString
		MAX-ACCESS		read-only
		STATUS			current
		DESCRIPTION
				"TYPE: - Display
				 PAGE: - Setup- Logging- Log Video_Input_1
					Input3 Type  cmdID= 4269  format=   "
		::= { iqosy30CmdEntry 4269 }


	iqosy30LoggingLogVideoInput1Input3Identen OBJECT-TYPE
		SYNTAX		INTEGER { disable(0), enable(1) }
		MAX-ACCESS		read-write
		STATUS			current
		DESCRIPTION
				"TYPE: - Checkbox
				 PAGE: - Setup- Logging- Log Video_Input_1
					Input3 Ident_en  cmdID= 4272 "
		::= { iqosy30CmdEntry 4272 }


	iqosy30LoggingLogVideoInput1Input3Ident OBJECT-TYPE
		SYNTAX		RollCallString
		MAX-ACCESS		read-only
		STATUS			current
		DESCRIPTION
				"TYPE: - Display
				 PAGE: - Setup- Logging- Log Video_Input_1
					Input3 Ident  cmdID= 4273  format=   "
		::= { iqosy30CmdEntry 4273 }


	iqosy30LoggingLogVideoInput2Input2en OBJECT-TYPE
		SYNTAX		INTEGER { disable(0), enable(1) }
		MAX-ACCESS		read-write
		STATUS			current
		DESCRIPTION
				"TYPE: - Checkbox
				 PAGE: - Setup- Logging- Log Video_Input_2
					Input2_en  cmdID= 4002 "
		::= { iqosy30CmdEntry 4002 }


	iqosy30LoggingLogVideoInput2Input2 OBJECT-TYPE
		SYNTAX		RollCallString
		MAX-ACCESS		read-only
		STATUS			current
		DESCRIPTION
				"TYPE: - Display
				 PAGE: - Setup- Logging- Log Video_Input_2
					Input2  cmdID= 4003  format=   "
		::= { iqosy30CmdEntry 4003 }


	iqosy30LoggingLogVideoInput2Input2Standarden OBJECT-TYPE
		SYNTAX		INTEGER { disable(0), enable(1) }
		MAX-ACCESS		read-write
		STATUS			current
		DESCRIPTION
				"TYPE: - Checkbox
				 PAGE: - Setup- Logging- Log Video_Input_2
					Input2 Standard_en  cmdID= 4006 "
		::= { iqosy30CmdEntry 4006 }


	iqosy30LoggingLogVideoInput2Input2Standard OBJECT-TYPE
		SYNTAX		RollCallString
		MAX-ACCESS		read-only
		STATUS			current
		DESCRIPTION
				"TYPE: - Display
				 PAGE: - Setup- Logging- Log Video_Input_2
					Input2 Standard  cmdID= 4007  format=   "
		::= { iqosy30CmdEntry 4007 }


	iqosy30LoggingLogVideoInput2In2SDIERRSen OBJECT-TYPE
		SYNTAX		INTEGER { disable(0), enable(1) }
		MAX-ACCESS		read-write
		STATUS			current
		DESCRIPTION
				"TYPE: - Checkbox
				 PAGE: - Setup- Logging- Log Video_Input_2
					In2 SDI ERRS_en  cmdID= 4014 "
		::= { iqosy30CmdEntry 4014 }


	iqosy30LoggingLogVideoInput2In2SDIERRS OBJECT-TYPE
		SYNTAX		RollCallString
		MAX-ACCESS		read-only
		STATUS			current
		DESCRIPTION
				"TYPE: - Display
				 PAGE: - Setup- Logging- Log Video_Input_2
					In2 SDI ERRS  cmdID= 4015  format=   "
		::= { iqosy30CmdEntry 4015 }


	iqosy30LoggingLogVideoInput2In2SDIANCERRSen OBJECT-TYPE
		SYNTAX		INTEGER { disable(0), enable(1) }
		MAX-ACCESS		read-write
		STATUS			current
		DESCRIPTION
				"TYPE: - Checkbox
				 PAGE: - Setup- Logging- Log Video_Input_2
					In2 SDI ANC ERRS_en  cmdID= 4022 "
		::= { iqosy30CmdEntry 4022 }


	iqosy30LoggingLogVideoInput2In2SDIANCERRS OBJECT-TYPE
		SYNTAX		RollCallString
		MAX-ACCESS		read-only
		STATUS			current
		DESCRIPTION
				"TYPE: - Display
				 PAGE: - Setup- Logging- Log Video_Input_2
					In2 SDI ANC ERRS  cmdID= 4023  format=   "
		::= { iqosy30CmdEntry 4023 }


	iqosy30LoggingLogVideoInput2Input2Typeen OBJECT-TYPE
		SYNTAX		INTEGER { disable(0), enable(1) }
		MAX-ACCESS		read-write
		STATUS			current
		DESCRIPTION
				"TYPE: - Checkbox
				 PAGE: - Setup- Logging- Log Video_Input_2
					Input2 Type_en  cmdID= 4026 "
		::= { iqosy30CmdEntry 4026 }


	iqosy30LoggingLogVideoInput2Input2Type OBJECT-TYPE
		SYNTAX		RollCallString
		MAX-ACCESS		read-only
		STATUS			current
		DESCRIPTION
				"TYPE: - Display
				 PAGE: - Setup- Logging- Log Video_Input_2
					Input2 Type  cmdID= 4027  format=   "
		::= { iqosy30CmdEntry 4027 }


	iqosy30LoggingLogVideoInput2Input2Identen OBJECT-TYPE
		SYNTAX		INTEGER { disable(0), enable(1) }
		MAX-ACCESS		read-write
		STATUS			current
		DESCRIPTION
				"TYPE: - Checkbox
				 PAGE: - Setup- Logging- Log Video_Input_2
					Input2 Ident_en  cmdID= 4030 "
		::= { iqosy30CmdEntry 4030 }


	iqosy30LoggingLogVideoInput2Input2Ident OBJECT-TYPE
		SYNTAX		RollCallString
		MAX-ACCESS		read-only
		STATUS			current
		DESCRIPTION
				"TYPE: - Display
				 PAGE: - Setup- Logging- Log Video_Input_2
					Input2 Ident  cmdID= 4031  format=   "
		::= { iqosy30CmdEntry 4031 }


	iqosy30LoggingLogVideoInput2Input4en OBJECT-TYPE
		SYNTAX		INTEGER { disable(0), enable(1) }
		MAX-ACCESS		read-write
		STATUS			current
		DESCRIPTION
				"TYPE: - Checkbox
				 PAGE: - Setup- Logging- Log Video_Input_2
					Input4_en  cmdID= 4246 "
		::= { iqosy30CmdEntry 4246 }


	iqosy30LoggingLogVideoInput2Input4 OBJECT-TYPE
		SYNTAX		RollCallString
		MAX-ACCESS		read-only
		STATUS			current
		DESCRIPTION
				"TYPE: - Display
				 PAGE: - Setup- Logging- Log Video_Input_2
					Input4  cmdID= 4247  format=   "
		::= { iqosy30CmdEntry 4247 }


	iqosy30LoggingLogVideoInput2Input4Standarden OBJECT-TYPE
		SYNTAX		INTEGER { disable(0), enable(1) }
		MAX-ACCESS		read-write
		STATUS			current
		DESCRIPTION
				"TYPE: - Checkbox
				 PAGE: - Setup- Logging- Log Video_Input_2
					Input4 Standard_en  cmdID= 4250 "
		::= { iqosy30CmdEntry 4250 }


	iqosy30LoggingLogVideoInput2Input4Standard OBJECT-TYPE
		SYNTAX		RollCallString
		MAX-ACCESS		read-only
		STATUS			current
		DESCRIPTION
				"TYPE: - Display
				 PAGE: - Setup- Logging- Log Video_Input_2
					Input4 Standard  cmdID= 4251  format=   "
		::= { iqosy30CmdEntry 4251 }


	iqosy30LoggingLogVideoInput2In4SDIERRSen OBJECT-TYPE
		SYNTAX		INTEGER { disable(0), enable(1) }
		MAX-ACCESS		read-write
		STATUS			current
		DESCRIPTION
				"TYPE: - Checkbox
				 PAGE: - Setup- Logging- Log Video_Input_2
					In4 SDI ERRS_en  cmdID= 4258 "
		::= { iqosy30CmdEntry 4258 }


	iqosy30LoggingLogVideoInput2In4SDIERRS OBJECT-TYPE
		SYNTAX		RollCallString
		MAX-ACCESS		read-only
		STATUS			current
		DESCRIPTION
				"TYPE: - Display
				 PAGE: - Setup- Logging- Log Video_Input_2
					In4 SDI ERRS  cmdID= 4259  format=   "
		::= { iqosy30CmdEntry 4259 }


	iqosy30LoggingLogVideoInput2In4SDIANCERRSen OBJECT-TYPE
		SYNTAX		INTEGER { disable(0), enable(1) }
		MAX-ACCESS		read-write
		STATUS			current
		DESCRIPTION
				"TYPE: - Checkbox
				 PAGE: - Setup- Logging- Log Video_Input_2
					In4 SDI ANC ERRS_en  cmdID= 4266 "
		::= { iqosy30CmdEntry 4266 }


	iqosy30LoggingLogVideoInput2In4SDIANCERRS OBJECT-TYPE
		SYNTAX		RollCallString
		MAX-ACCESS		read-only
		STATUS			current
		DESCRIPTION
				"TYPE: - Display
				 PAGE: - Setup- Logging- Log Video_Input_2
					In4 SDI ANC ERRS  cmdID= 4267  format=   "
		::= { iqosy30CmdEntry 4267 }


	iqosy30LoggingLogVideoInput2Input4Typeen OBJECT-TYPE
		SYNTAX		INTEGER { disable(0), enable(1) }
		MAX-ACCESS		read-write
		STATUS			current
		DESCRIPTION
				"TYPE: - Checkbox
				 PAGE: - Setup- Logging- Log Video_Input_2
					Input4 Type_en  cmdID= 4270 "
		::= { iqosy30CmdEntry 4270 }


	iqosy30LoggingLogVideoInput2Input4Type OBJECT-TYPE
		SYNTAX		RollCallString
		MAX-ACCESS		read-only
		STATUS			current
		DESCRIPTION
				"TYPE: - Display
				 PAGE: - Setup- Logging- Log Video_Input_2
					Input4 Type  cmdID= 4271  format=   "
		::= { iqosy30CmdEntry 4271 }


	iqosy30LoggingLogVideoInput2Input4Identen OBJECT-TYPE
		SYNTAX		INTEGER { disable(0), enable(1) }
		MAX-ACCESS		read-write
		STATUS			current
		DESCRIPTION
				"TYPE: - Checkbox
				 PAGE: - Setup- Logging- Log Video_Input_2
					Input4 Ident_en  cmdID= 4274 "
		::= { iqosy30CmdEntry 4274 }


	iqosy30LoggingLogVideoInput2Input4Ident OBJECT-TYPE
		SYNTAX		RollCallString
		MAX-ACCESS		read-only
		STATUS			current
		DESCRIPTION
				"TYPE: - Display
				 PAGE: - Setup- Logging- Log Video_Input_2
					Input4 Ident  cmdID= 4275  format=   "
		::= { iqosy30CmdEntry 4275 }


	iqosy30LoggingLogReferenceRef1Stateen OBJECT-TYPE
		SYNTAX		INTEGER { disable(0), enable(1) }
		MAX-ACCESS		read-write
		STATUS			current
		DESCRIPTION
				"TYPE: - Checkbox
				 PAGE: - Setup- Logging- Log Reference
					Ref1 State_en  cmdID= 4040 "
		::= { iqosy30CmdEntry 4040 }


	iqosy30LoggingLogReferenceRef1State OBJECT-TYPE
		SYNTAX		RollCallString
		MAX-ACCESS		read-only
		STATUS			current
		DESCRIPTION
				"TYPE: - Display
				 PAGE: - Setup- Logging- Log Reference
					Ref1 State  cmdID= 4041  format=   "
		::= { iqosy30CmdEntry 4041 }


	iqosy30LoggingLogReferenceRef1Standarden OBJECT-TYPE
		SYNTAX		INTEGER { disable(0), enable(1) }
		MAX-ACCESS		read-write
		STATUS			current
		DESCRIPTION
				"TYPE: - Checkbox
				 PAGE: - Setup- Logging- Log Reference
					Ref1 Standard_en  cmdID= 4044 "
		::= { iqosy30CmdEntry 4044 }


	iqosy30LoggingLogReferenceRef1Standard OBJECT-TYPE
		SYNTAX		RollCallString
		MAX-ACCESS		read-only
		STATUS			current
		DESCRIPTION
				"TYPE: - Display
				 PAGE: - Setup- Logging- Log Reference
					Ref1 Standard  cmdID= 4045  format=   "
		::= { iqosy30CmdEntry 4045 }


	iqosy30LoggingLogReferenceRef1Typeen OBJECT-TYPE
		SYNTAX		INTEGER { disable(0), enable(1) }
		MAX-ACCESS		read-write
		STATUS			current
		DESCRIPTION
				"TYPE: - Checkbox
				 PAGE: - Setup- Logging- Log Reference
					Ref1 Type_en  cmdID= 4048 "
		::= { iqosy30CmdEntry 4048 }


	iqosy30LoggingLogReferenceRef1Type OBJECT-TYPE
		SYNTAX		RollCallString
		MAX-ACCESS		read-only
		STATUS			current
		DESCRIPTION
				"TYPE: - Display
				 PAGE: - Setup- Logging- Log Reference
					Ref1 Type  cmdID= 4049  format=   "
		::= { iqosy30CmdEntry 4049 }


	iqosy30LoggingLogReferenceGenlock1Stateen OBJECT-TYPE
		SYNTAX		INTEGER { disable(0), enable(1) }
		MAX-ACCESS		read-write
		STATUS			current
		DESCRIPTION
				"TYPE: - Checkbox
				 PAGE: - Setup- Logging- Log Reference
					Genlock1 State_en  cmdID= 4052 "
		::= { iqosy30CmdEntry 4052 }


	iqosy30LoggingLogReferenceGenlock1State OBJECT-TYPE
		SYNTAX		RollCallString
		MAX-ACCESS		read-only
		STATUS			current
		DESCRIPTION
				"TYPE: - Display
				 PAGE: - Setup- Logging- Log Reference
					Genlock1 State  cmdID= 4053  format=   "
		::= { iqosy30CmdEntry 4053 }


	iqosy30LoggingLogAudioInput1Input1Audio1en OBJECT-TYPE
		SYNTAX		INTEGER { disable(0), enable(1) }
		MAX-ACCESS		read-write
		STATUS			current
		DESCRIPTION
				"TYPE: - Checkbox
				 PAGE: - Setup- Logging- Log Audio_Input_1
					Input1 Audio 1_en  cmdID= 3852 "
		::= { iqosy30CmdEntry 3852 }


	iqosy30LoggingLogAudioInput1Input1Audio1 OBJECT-TYPE
		SYNTAX		RollCallString
		MAX-ACCESS		read-only
		STATUS			current
		DESCRIPTION
				"TYPE: - Display
				 PAGE: - Setup- Logging- Log Audio_Input_1
					Input1 Audio 1  cmdID= 3853  format=   "
		::= { iqosy30CmdEntry 3853 }


	iqosy30LoggingLogAudioInput1Input1Audio2en OBJECT-TYPE
		SYNTAX		INTEGER { disable(0), enable(1) }
		MAX-ACCESS		read-write
		STATUS			current
		DESCRIPTION
				"TYPE: - Checkbox
				 PAGE: - Setup- Logging- Log Audio_Input_1
					Input1 Audio 2_en  cmdID= 3854 "
		::= { iqosy30CmdEntry 3854 }


	iqosy30LoggingLogAudioInput1Input1Audio2 OBJECT-TYPE
		SYNTAX		RollCallString
		MAX-ACCESS		read-only
		STATUS			current
		DESCRIPTION
				"TYPE: - Display
				 PAGE: - Setup- Logging- Log Audio_Input_1
					Input1 Audio 2  cmdID= 3855  format=   "
		::= { iqosy30CmdEntry 3855 }


	iqosy30LoggingLogAudioInput1Input1Audio3en OBJECT-TYPE
		SYNTAX		INTEGER { disable(0), enable(1) }
		MAX-ACCESS		read-write
		STATUS			current
		DESCRIPTION
				"TYPE: - Checkbox
				 PAGE: - Setup- Logging- Log Audio_Input_1
					Input1 Audio 3_en  cmdID= 3856 "
		::= { iqosy30CmdEntry 3856 }


	iqosy30LoggingLogAudioInput1Input1Audio3 OBJECT-TYPE
		SYNTAX		RollCallString
		MAX-ACCESS		read-only
		STATUS			current
		DESCRIPTION
				"TYPE: - Display
				 PAGE: - Setup- Logging- Log Audio_Input_1
					Input1 Audio 3  cmdID= 3857  format=   "
		::= { iqosy30CmdEntry 3857 }


	iqosy30LoggingLogAudioInput1Input1Audio4en OBJECT-TYPE
		SYNTAX		INTEGER { disable(0), enable(1) }
		MAX-ACCESS		read-write
		STATUS			current
		DESCRIPTION
				"TYPE: - Checkbox
				 PAGE: - Setup- Logging- Log Audio_Input_1
					Input1 Audio 4_en  cmdID= 3858 "
		::= { iqosy30CmdEntry 3858 }


	iqosy30LoggingLogAudioInput1Input1Audio4 OBJECT-TYPE
		SYNTAX		RollCallString
		MAX-ACCESS		read-only
		STATUS			current
		DESCRIPTION
				"TYPE: - Display
				 PAGE: - Setup- Logging- Log Audio_Input_1
					Input1 Audio 4  cmdID= 3859  format=   "
		::= { iqosy30CmdEntry 3859 }


	iqosy30LoggingLogAudioInput1Input1Audio5en OBJECT-TYPE
		SYNTAX		INTEGER { disable(0), enable(1) }
		MAX-ACCESS		read-write
		STATUS			current
		DESCRIPTION
				"TYPE: - Checkbox
				 PAGE: - Setup- Logging- Log Audio_Input_1
					Input1 Audio 5_en  cmdID= 3860 "
		::= { iqosy30CmdEntry 3860 }


	iqosy30LoggingLogAudioInput1Input1Audio5 OBJECT-TYPE
		SYNTAX		RollCallString
		MAX-ACCESS		read-only
		STATUS			current
		DESCRIPTION
				"TYPE: - Display
				 PAGE: - Setup- Logging- Log Audio_Input_1
					Input1 Audio 5  cmdID= 3861  format=   "
		::= { iqosy30CmdEntry 3861 }


	iqosy30LoggingLogAudioInput1Input1Audio6en OBJECT-TYPE
		SYNTAX		INTEGER { disable(0), enable(1) }
		MAX-ACCESS		read-write
		STATUS			current
		DESCRIPTION
				"TYPE: - Checkbox
				 PAGE: - Setup- Logging- Log Audio_Input_1
					Input1 Audio 6_en  cmdID= 3862 "
		::= { iqosy30CmdEntry 3862 }


	iqosy30LoggingLogAudioInput1Input1Audio6 OBJECT-TYPE
		SYNTAX		RollCallString
		MAX-ACCESS		read-only
		STATUS			current
		DESCRIPTION
				"TYPE: - Display
				 PAGE: - Setup- Logging- Log Audio_Input_1
					Input1 Audio 6  cmdID= 3863  format=   "
		::= { iqosy30CmdEntry 3863 }


	iqosy30LoggingLogAudioInput1Input1Audio7en OBJECT-TYPE
		SYNTAX		INTEGER { disable(0), enable(1) }
		MAX-ACCESS		read-write
		STATUS			current
		DESCRIPTION
				"TYPE: - Checkbox
				 PAGE: - Setup- Logging- Log Audio_Input_1
					Input1 Audio 7_en  cmdID= 3864 "
		::= { iqosy30CmdEntry 3864 }


	iqosy30LoggingLogAudioInput1Input1Audio7 OBJECT-TYPE
		SYNTAX		RollCallString
		MAX-ACCESS		read-only
		STATUS			current
		DESCRIPTION
				"TYPE: - Display
				 PAGE: - Setup- Logging- Log Audio_Input_1
					Input1 Audio 7  cmdID= 3865  format=   "
		::= { iqosy30CmdEntry 3865 }


	iqosy30LoggingLogAudioInput1Input1Audio8en OBJECT-TYPE
		SYNTAX		INTEGER { disable(0), enable(1) }
		MAX-ACCESS		read-write
		STATUS			current
		DESCRIPTION
				"TYPE: - Checkbox
				 PAGE: - Setup- Logging- Log Audio_Input_1
					Input1 Audio 8_en  cmdID= 3866 "
		::= { iqosy30CmdEntry 3866 }


	iqosy30LoggingLogAudioInput1Input1Audio8 OBJECT-TYPE
		SYNTAX		RollCallString
		MAX-ACCESS		read-only
		STATUS			current
		DESCRIPTION
				"TYPE: - Display
				 PAGE: - Setup- Logging- Log Audio_Input_1
					Input1 Audio 8  cmdID= 3867  format=   "
		::= { iqosy30CmdEntry 3867 }


	iqosy30LoggingLogAudioInput2Input2Audio1en OBJECT-TYPE
		SYNTAX		INTEGER { disable(0), enable(1) }
		MAX-ACCESS		read-write
		STATUS			current
		DESCRIPTION
				"TYPE: - Checkbox
				 PAGE: - Setup- Logging- Log Audio_Input_2
					Input2 Audio 1_en  cmdID= 3868 "
		::= { iqosy30CmdEntry 3868 }


	iqosy30LoggingLogAudioInput2Input2Audio1 OBJECT-TYPE
		SYNTAX		RollCallString
		MAX-ACCESS		read-only
		STATUS			current
		DESCRIPTION
				"TYPE: - Display
				 PAGE: - Setup- Logging- Log Audio_Input_2
					Input2 Audio 1  cmdID= 3869  format=   "
		::= { iqosy30CmdEntry 3869 }


	iqosy30LoggingLogAudioInput2Input2Audio2en OBJECT-TYPE
		SYNTAX		INTEGER { disable(0), enable(1) }
		MAX-ACCESS		read-write
		STATUS			current
		DESCRIPTION
				"TYPE: - Checkbox
				 PAGE: - Setup- Logging- Log Audio_Input_2
					Input2 Audio 2_en  cmdID= 3870 "
		::= { iqosy30CmdEntry 3870 }


	iqosy30LoggingLogAudioInput2Input2Audio2 OBJECT-TYPE
		SYNTAX		RollCallString
		MAX-ACCESS		read-only
		STATUS			current
		DESCRIPTION
				"TYPE: - Display
				 PAGE: - Setup- Logging- Log Audio_Input_2
					Input2 Audio 2  cmdID= 3871  format=   "
		::= { iqosy30CmdEntry 3871 }


	iqosy30LoggingLogAudioInput2Input2Audio3en OBJECT-TYPE
		SYNTAX		INTEGER { disable(0), enable(1) }
		MAX-ACCESS		read-write
		STATUS			current
		DESCRIPTION
				"TYPE: - Checkbox
				 PAGE: - Setup- Logging- Log Audio_Input_2
					Input2 Audio 3_en  cmdID= 3872 "
		::= { iqosy30CmdEntry 3872 }


	iqosy30LoggingLogAudioInput2Input2Audio3 OBJECT-TYPE
		SYNTAX		RollCallString
		MAX-ACCESS		read-only
		STATUS			current
		DESCRIPTION
				"TYPE: - Display
				 PAGE: - Setup- Logging- Log Audio_Input_2
					Input2 Audio 3  cmdID= 3873  format=   "
		::= { iqosy30CmdEntry 3873 }


	iqosy30LoggingLogAudioInput2Input2Audio4en OBJECT-TYPE
		SYNTAX		INTEGER { disable(0), enable(1) }
		MAX-ACCESS		read-write
		STATUS			current
		DESCRIPTION
				"TYPE: - Checkbox
				 PAGE: - Setup- Logging- Log Audio_Input_2
					Input2 Audio 4_en  cmdID= 3874 "
		::= { iqosy30CmdEntry 3874 }


	iqosy30LoggingLogAudioInput2Input2Audio4 OBJECT-TYPE
		SYNTAX		RollCallString
		MAX-ACCESS		read-only
		STATUS			current
		DESCRIPTION
				"TYPE: - Display
				 PAGE: - Setup- Logging- Log Audio_Input_2
					Input2 Audio 4  cmdID= 3875  format=   "
		::= { iqosy30CmdEntry 3875 }


	iqosy30LoggingLogAudioInput2Input2Audio5en OBJECT-TYPE
		SYNTAX		INTEGER { disable(0), enable(1) }
		MAX-ACCESS		read-write
		STATUS			current
		DESCRIPTION
				"TYPE: - Checkbox
				 PAGE: - Setup- Logging- Log Audio_Input_2
					Input2 Audio 5_en  cmdID= 3876 "
		::= { iqosy30CmdEntry 3876 }


	iqosy30LoggingLogAudioInput2Input2Audio5 OBJECT-TYPE
		SYNTAX		RollCallString
		MAX-ACCESS		read-only
		STATUS			current
		DESCRIPTION
				"TYPE: - Display
				 PAGE: - Setup- Logging- Log Audio_Input_2
					Input2 Audio 5  cmdID= 3877  format=   "
		::= { iqosy30CmdEntry 3877 }


	iqosy30LoggingLogAudioInput2Input2Audio6en OBJECT-TYPE
		SYNTAX		INTEGER { disable(0), enable(1) }
		MAX-ACCESS		read-write
		STATUS			current
		DESCRIPTION
				"TYPE: - Checkbox
				 PAGE: - Setup- Logging- Log Audio_Input_2
					Input2 Audio 6_en  cmdID= 3878 "
		::= { iqosy30CmdEntry 3878 }


	iqosy30LoggingLogAudioInput2Input2Audio6 OBJECT-TYPE
		SYNTAX		RollCallString
		MAX-ACCESS		read-only
		STATUS			current
		DESCRIPTION
				"TYPE: - Display
				 PAGE: - Setup- Logging- Log Audio_Input_2
					Input2 Audio 6  cmdID= 3879  format=   "
		::= { iqosy30CmdEntry 3879 }


	iqosy30LoggingLogAudioInput2Input2Audio7en OBJECT-TYPE
		SYNTAX		INTEGER { disable(0), enable(1) }
		MAX-ACCESS		read-write
		STATUS			current
		DESCRIPTION
				"TYPE: - Checkbox
				 PAGE: - Setup- Logging- Log Audio_Input_2
					Input2 Audio 7_en  cmdID= 3880 "
		::= { iqosy30CmdEntry 3880 }


	iqosy30LoggingLogAudioInput2Input2Audio7 OBJECT-TYPE
		SYNTAX		RollCallString
		MAX-ACCESS		read-only
		STATUS			current
		DESCRIPTION
				"TYPE: - Display
				 PAGE: - Setup- Logging- Log Audio_Input_2
					Input2 Audio 7  cmdID= 3881  format=   "
		::= { iqosy30CmdEntry 3881 }


	iqosy30LoggingLogAudioInput2Input2Audio8en OBJECT-TYPE
		SYNTAX		INTEGER { disable(0), enable(1) }
		MAX-ACCESS		read-write
		STATUS			current
		DESCRIPTION
				"TYPE: - Checkbox
				 PAGE: - Setup- Logging- Log Audio_Input_2
					Input2 Audio 8_en  cmdID= 3882 "
		::= { iqosy30CmdEntry 3882 }


	iqosy30LoggingLogAudioInput2Input2Audio8 OBJECT-TYPE
		SYNTAX		RollCallString
		MAX-ACCESS		read-only
		STATUS			current
		DESCRIPTION
				"TYPE: - Display
				 PAGE: - Setup- Logging- Log Audio_Input_2
					Input2 Audio 8  cmdID= 3883  format=   "
		::= { iqosy30CmdEntry 3883 }


	iqosy30LoggingLogAudioInput3Input3Audio1en OBJECT-TYPE
		SYNTAX		INTEGER { disable(0), enable(1) }
		MAX-ACCESS		read-write
		STATUS			current
		DESCRIPTION
				"TYPE: - Checkbox
				 PAGE: - Setup- Logging- Log Audio_Input_3
					Input3 Audio 1_en  cmdID= 3884 "
		::= { iqosy30CmdEntry 3884 }


	iqosy30LoggingLogAudioInput3Input3Audio1 OBJECT-TYPE
		SYNTAX		RollCallString
		MAX-ACCESS		read-only
		STATUS			current
		DESCRIPTION
				"TYPE: - Display
				 PAGE: - Setup- Logging- Log Audio_Input_3
					Input3 Audio 1  cmdID= 3885  format=   "
		::= { iqosy30CmdEntry 3885 }


	iqosy30LoggingLogAudioInput3Input3Audio2en OBJECT-TYPE
		SYNTAX		INTEGER { disable(0), enable(1) }
		MAX-ACCESS		read-write
		STATUS			current
		DESCRIPTION
				"TYPE: - Checkbox
				 PAGE: - Setup- Logging- Log Audio_Input_3
					Input3 Audio 2_en  cmdID= 3886 "
		::= { iqosy30CmdEntry 3886 }


	iqosy30LoggingLogAudioInput3Input3Audio2 OBJECT-TYPE
		SYNTAX		RollCallString
		MAX-ACCESS		read-only
		STATUS			current
		DESCRIPTION
				"TYPE: - Display
				 PAGE: - Setup- Logging- Log Audio_Input_3
					Input3 Audio 2  cmdID= 3887  format=   "
		::= { iqosy30CmdEntry 3887 }


	iqosy30LoggingLogAudioInput3Input3Audio3en OBJECT-TYPE
		SYNTAX		INTEGER { disable(0), enable(1) }
		MAX-ACCESS		read-write
		STATUS			current
		DESCRIPTION
				"TYPE: - Checkbox
				 PAGE: - Setup- Logging- Log Audio_Input_3
					Input3 Audio 3_en  cmdID= 3888 "
		::= { iqosy30CmdEntry 3888 }


	iqosy30LoggingLogAudioInput3Input3Audio3 OBJECT-TYPE
		SYNTAX		RollCallString
		MAX-ACCESS		read-only
		STATUS			current
		DESCRIPTION
				"TYPE: - Display
				 PAGE: - Setup- Logging- Log Audio_Input_3
					Input3 Audio 3  cmdID= 3889  format=   "
		::= { iqosy30CmdEntry 3889 }


	iqosy30LoggingLogAudioInput3Input3Audio4en OBJECT-TYPE
		SYNTAX		INTEGER { disable(0), enable(1) }
		MAX-ACCESS		read-write
		STATUS			current
		DESCRIPTION
				"TYPE: - Checkbox
				 PAGE: - Setup- Logging- Log Audio_Input_3
					Input3 Audio 4_en  cmdID= 3890 "
		::= { iqosy30CmdEntry 3890 }


	iqosy30LoggingLogAudioInput3Input3Audio4 OBJECT-TYPE
		SYNTAX		RollCallString
		MAX-ACCESS		read-only
		STATUS			current
		DESCRIPTION
				"TYPE: - Display
				 PAGE: - Setup- Logging- Log Audio_Input_3
					Input3 Audio 4  cmdID= 3891  format=   "
		::= { iqosy30CmdEntry 3891 }


	iqosy30LoggingLogAudioInput3Input3Audio5en OBJECT-TYPE
		SYNTAX		INTEGER { disable(0), enable(1) }
		MAX-ACCESS		read-write
		STATUS			current
		DESCRIPTION
				"TYPE: - Checkbox
				 PAGE: - Setup- Logging- Log Audio_Input_3
					Input3 Audio 5_en  cmdID= 3892 "
		::= { iqosy30CmdEntry 3892 }


	iqosy30LoggingLogAudioInput3Input3Audio5 OBJECT-TYPE
		SYNTAX		RollCallString
		MAX-ACCESS		read-only
		STATUS			current
		DESCRIPTION
				"TYPE: - Display
				 PAGE: - Setup- Logging- Log Audio_Input_3
					Input3 Audio 5  cmdID= 3893  format=   "
		::= { iqosy30CmdEntry 3893 }


	iqosy30LoggingLogAudioInput3Input3Audio6en OBJECT-TYPE
		SYNTAX		INTEGER { disable(0), enable(1) }
		MAX-ACCESS		read-write
		STATUS			current
		DESCRIPTION
				"TYPE: - Checkbox
				 PAGE: - Setup- Logging- Log Audio_Input_3
					Input3 Audio 6_en  cmdID= 3894 "
		::= { iqosy30CmdEntry 3894 }


	iqosy30LoggingLogAudioInput3Input3Audio6 OBJECT-TYPE
		SYNTAX		RollCallString
		MAX-ACCESS		read-only
		STATUS			current
		DESCRIPTION
				"TYPE: - Display
				 PAGE: - Setup- Logging- Log Audio_Input_3
					Input3 Audio 6  cmdID= 3895  format=   "
		::= { iqosy30CmdEntry 3895 }


	iqosy30LoggingLogAudioInput3Input3Audio7en OBJECT-TYPE
		SYNTAX		INTEGER { disable(0), enable(1) }
		MAX-ACCESS		read-write
		STATUS			current
		DESCRIPTION
				"TYPE: - Checkbox
				 PAGE: - Setup- Logging- Log Audio_Input_3
					Input3 Audio 7_en  cmdID= 3896 "
		::= { iqosy30CmdEntry 3896 }


	iqosy30LoggingLogAudioInput3Input3Audio7 OBJECT-TYPE
		SYNTAX		RollCallString
		MAX-ACCESS		read-only
		STATUS			current
		DESCRIPTION
				"TYPE: - Display
				 PAGE: - Setup- Logging- Log Audio_Input_3
					Input3 Audio 7  cmdID= 3897  format=   "
		::= { iqosy30CmdEntry 3897 }


	iqosy30LoggingLogAudioInput3Input3Audio8en OBJECT-TYPE
		SYNTAX		INTEGER { disable(0), enable(1) }
		MAX-ACCESS		read-write
		STATUS			current
		DESCRIPTION
				"TYPE: - Checkbox
				 PAGE: - Setup- Logging- Log Audio_Input_3
					Input3 Audio 8_en  cmdID= 3898 "
		::= { iqosy30CmdEntry 3898 }


	iqosy30LoggingLogAudioInput3Input3Audio8 OBJECT-TYPE
		SYNTAX		RollCallString
		MAX-ACCESS		read-only
		STATUS			current
		DESCRIPTION
				"TYPE: - Display
				 PAGE: - Setup- Logging- Log Audio_Input_3
					Input3 Audio 8  cmdID= 3899  format=   "
		::= { iqosy30CmdEntry 3899 }


	iqosy30LoggingLogAudioInput4Input4Audio1en OBJECT-TYPE
		SYNTAX		INTEGER { disable(0), enable(1) }
		MAX-ACCESS		read-write
		STATUS			current
		DESCRIPTION
				"TYPE: - Checkbox
				 PAGE: - Setup- Logging- Log Audio_Input_4
					Input4 Audio 1_en  cmdID= 3900 "
		::= { iqosy30CmdEntry 3900 }


	iqosy30LoggingLogAudioInput4Input4Audio1 OBJECT-TYPE
		SYNTAX		RollCallString
		MAX-ACCESS		read-only
		STATUS			current
		DESCRIPTION
				"TYPE: - Display
				 PAGE: - Setup- Logging- Log Audio_Input_4
					Input4 Audio 1  cmdID= 3901  format=   "
		::= { iqosy30CmdEntry 3901 }


	iqosy30LoggingLogAudioInput4Input4Audio2en OBJECT-TYPE
		SYNTAX		INTEGER { disable(0), enable(1) }
		MAX-ACCESS		read-write
		STATUS			current
		DESCRIPTION
				"TYPE: - Checkbox
				 PAGE: - Setup- Logging- Log Audio_Input_4
					Input4 Audio 2_en  cmdID= 3902 "
		::= { iqosy30CmdEntry 3902 }


	iqosy30LoggingLogAudioInput4Input4Audio2 OBJECT-TYPE
		SYNTAX		RollCallString
		MAX-ACCESS		read-only
		STATUS			current
		DESCRIPTION
				"TYPE: - Display
				 PAGE: - Setup- Logging- Log Audio_Input_4
					Input4 Audio 2  cmdID= 3903  format=   "
		::= { iqosy30CmdEntry 3903 }


	iqosy30LoggingLogAudioInput4Input4Audio3en OBJECT-TYPE
		SYNTAX		INTEGER { disable(0), enable(1) }
		MAX-ACCESS		read-write
		STATUS			current
		DESCRIPTION
				"TYPE: - Checkbox
				 PAGE: - Setup- Logging- Log Audio_Input_4
					Input4 Audio 3_en  cmdID= 3904 "
		::= { iqosy30CmdEntry 3904 }


	iqosy30LoggingLogAudioInput4Input4Audio3 OBJECT-TYPE
		SYNTAX		RollCallString
		MAX-ACCESS		read-only
		STATUS			current
		DESCRIPTION
				"TYPE: - Display
				 PAGE: - Setup- Logging- Log Audio_Input_4
					Input4 Audio 3  cmdID= 3905  format=   "
		::= { iqosy30CmdEntry 3905 }


	iqosy30LoggingLogAudioInput4Input4Audio4en OBJECT-TYPE
		SYNTAX		INTEGER { disable(0), enable(1) }
		MAX-ACCESS		read-write
		STATUS			current
		DESCRIPTION
				"TYPE: - Checkbox
				 PAGE: - Setup- Logging- Log Audio_Input_4
					Input4 Audio 4_en  cmdID= 3906 "
		::= { iqosy30CmdEntry 3906 }


	iqosy30LoggingLogAudioInput4Input4Audio4 OBJECT-TYPE
		SYNTAX		RollCallString
		MAX-ACCESS		read-only
		STATUS			current
		DESCRIPTION
				"TYPE: - Display
				 PAGE: - Setup- Logging- Log Audio_Input_4
					Input4 Audio 4  cmdID= 3907  format=   "
		::= { iqosy30CmdEntry 3907 }


	iqosy30LoggingLogAudioInput4Input4Audio5en OBJECT-TYPE
		SYNTAX		INTEGER { disable(0), enable(1) }
		MAX-ACCESS		read-write
		STATUS			current
		DESCRIPTION
				"TYPE: - Checkbox
				 PAGE: - Setup- Logging- Log Audio_Input_4
					Input4 Audio 5_en  cmdID= 3908 "
		::= { iqosy30CmdEntry 3908 }


	iqosy30LoggingLogAudioInput4Input4Audio5 OBJECT-TYPE
		SYNTAX		RollCallString
		MAX-ACCESS		read-only
		STATUS			current
		DESCRIPTION
				"TYPE: - Display
				 PAGE: - Setup- Logging- Log Audio_Input_4
					Input4 Audio 5  cmdID= 3909  format=   "
		::= { iqosy30CmdEntry 3909 }


	iqosy30LoggingLogAudioInput4Input4Audio6en OBJECT-TYPE
		SYNTAX		INTEGER { disable(0), enable(1) }
		MAX-ACCESS		read-write
		STATUS			current
		DESCRIPTION
				"TYPE: - Checkbox
				 PAGE: - Setup- Logging- Log Audio_Input_4
					Input4 Audio 6_en  cmdID= 3910 "
		::= { iqosy30CmdEntry 3910 }


	iqosy30LoggingLogAudioInput4Input4Audio6 OBJECT-TYPE
		SYNTAX		RollCallString
		MAX-ACCESS		read-only
		STATUS			current
		DESCRIPTION
				"TYPE: - Display
				 PAGE: - Setup- Logging- Log Audio_Input_4
					Input4 Audio 6  cmdID= 3911  format=   "
		::= { iqosy30CmdEntry 3911 }


	iqosy30LoggingLogAudioInput4Input4Audio7en OBJECT-TYPE
		SYNTAX		INTEGER { disable(0), enable(1) }
		MAX-ACCESS		read-write
		STATUS			current
		DESCRIPTION
				"TYPE: - Checkbox
				 PAGE: - Setup- Logging- Log Audio_Input_4
					Input4 Audio 7_en  cmdID= 3912 "
		::= { iqosy30CmdEntry 3912 }


	iqosy30LoggingLogAudioInput4Input4Audio7 OBJECT-TYPE
		SYNTAX		RollCallString
		MAX-ACCESS		read-only
		STATUS			current
		DESCRIPTION
				"TYPE: - Display
				 PAGE: - Setup- Logging- Log Audio_Input_4
					Input4 Audio 7  cmdID= 3913  format=   "
		::= { iqosy30CmdEntry 3913 }


	iqosy30LoggingLogAudioInput4Input4Audio8en OBJECT-TYPE
		SYNTAX		INTEGER { disable(0), enable(1) }
		MAX-ACCESS		read-write
		STATUS			current
		DESCRIPTION
				"TYPE: - Checkbox
				 PAGE: - Setup- Logging- Log Audio_Input_4
					Input4 Audio 8_en  cmdID= 3914 "
		::= { iqosy30CmdEntry 3914 }


	iqosy30LoggingLogAudioInput4Input4Audio8 OBJECT-TYPE
		SYNTAX		RollCallString
		MAX-ACCESS		read-only
		STATUS			current
		DESCRIPTION
				"TYPE: - Display
				 PAGE: - Setup- Logging- Log Audio_Input_4
					Input4 Audio 8  cmdID= 3915  format=   "
		::= { iqosy30CmdEntry 3915 }


	iqosy30LoggingLogVideoOutputOutput1Typeen OBJECT-TYPE
		SYNTAX		INTEGER { disable(0), enable(1) }
		MAX-ACCESS		read-write
		STATUS			current
		DESCRIPTION
				"TYPE: - Checkbox
				 PAGE: - Setup- Logging- Log Video_Output
					Output1 Type_en  cmdID= 4192 "
		::= { iqosy30CmdEntry 4192 }


	iqosy30LoggingLogVideoOutputOutput1Type OBJECT-TYPE
		SYNTAX		RollCallString
		MAX-ACCESS		read-only
		STATUS			current
		DESCRIPTION
				"TYPE: - Display
				 PAGE: - Setup- Logging- Log Video_Output
					Output1 Type  cmdID= 4193  format=   "
		::= { iqosy30CmdEntry 4193 }


	iqosy30LoggingLogVideoOutputOutput1Stateen OBJECT-TYPE
		SYNTAX		INTEGER { disable(0), enable(1) }
		MAX-ACCESS		read-write
		STATUS			current
		DESCRIPTION
				"TYPE: - Checkbox
				 PAGE: - Setup- Logging- Log Video_Output
					Output1 State_en  cmdID= 4196 "
		::= { iqosy30CmdEntry 4196 }


	iqosy30LoggingLogVideoOutputOutput1State OBJECT-TYPE
		SYNTAX		RollCallString
		MAX-ACCESS		read-only
		STATUS			current
		DESCRIPTION
				"TYPE: - Display
				 PAGE: - Setup- Logging- Log Video_Output
					Output1 State  cmdID= 4197  format=   "
		::= { iqosy30CmdEntry 4197 }


	iqosy30LoggingLogVideoOutputOutput1Stden OBJECT-TYPE
		SYNTAX		INTEGER { disable(0), enable(1) }
		MAX-ACCESS		read-write
		STATUS			current
		DESCRIPTION
				"TYPE: - Checkbox
				 PAGE: - Setup- Logging- Log Video_Output
					Output1 Std_en  cmdID= 4200 "
		::= { iqosy30CmdEntry 4200 }


	iqosy30LoggingLogVideoOutputOutput1Std OBJECT-TYPE
		SYNTAX		RollCallString
		MAX-ACCESS		read-only
		STATUS			current
		DESCRIPTION
				"TYPE: - Display
				 PAGE: - Setup- Logging- Log Video_Output
					Output1 Std  cmdID= 4201  format=   "
		::= { iqosy30CmdEntry 4201 }


	iqosy30LoggingLogVideoOutputOutput1Captionen OBJECT-TYPE
		SYNTAX		INTEGER { disable(0), enable(1) }
		MAX-ACCESS		read-write
		STATUS			current
		DESCRIPTION
				"TYPE: - Checkbox
				 PAGE: - Setup- Logging- Log Video_Output
					Output1 Caption_en  cmdID= 4204 "
		::= { iqosy30CmdEntry 4204 }


	iqosy30LoggingLogVideoOutputOutput1Caption OBJECT-TYPE
		SYNTAX		RollCallString
		MAX-ACCESS		read-only
		STATUS			current
		DESCRIPTION
				"TYPE: - Display
				 PAGE: - Setup- Logging- Log Video_Output
					Output1 Caption  cmdID= 4205  format=   "
		::= { iqosy30CmdEntry 4205 }


	iqosy30LoggingLogVideoOutputOutput1en OBJECT-TYPE
		SYNTAX		INTEGER { disable(0), enable(1) }
		MAX-ACCESS		read-write
		STATUS			current
		DESCRIPTION
				"TYPE: - Checkbox
				 PAGE: - Setup- Logging- Log Video_Output
					Output1_en  cmdID= 4208 "
		::= { iqosy30CmdEntry 4208 }


	iqosy30LoggingLogVideoOutputOutput1 OBJECT-TYPE
		SYNTAX		RollCallString
		MAX-ACCESS		read-only
		STATUS			current
		DESCRIPTION
				"TYPE: - Display
				 PAGE: - Setup- Logging- Log Video_Output
					Output1  cmdID= 4209  format=   "
		::= { iqosy30CmdEntry 4209 }


	iqosy30LoggingLogAudioOutputOutput1Embed11en OBJECT-TYPE
		SYNTAX		INTEGER { disable(0), enable(1) }
		MAX-ACCESS		read-write
		STATUS			current
		DESCRIPTION
				"TYPE: - Checkbox
				 PAGE: - Setup- Logging- Log Audio_Output
					Output1 Embed1 1_en  cmdID= 4064 "
		::= { iqosy30CmdEntry 4064 }


	iqosy30LoggingLogAudioOutputOutput1Embed11 OBJECT-TYPE
		SYNTAX		RollCallString
		MAX-ACCESS		read-only
		STATUS			current
		DESCRIPTION
				"TYPE: - Display
				 PAGE: - Setup- Logging- Log Audio_Output
					Output1 Embed1 1  cmdID= 4065  format=   "
		::= { iqosy30CmdEntry 4065 }


	iqosy30LoggingLogAudioOutputOutput1Embed12en OBJECT-TYPE
		SYNTAX		INTEGER { disable(0), enable(1) }
		MAX-ACCESS		read-write
		STATUS			current
		DESCRIPTION
				"TYPE: - Checkbox
				 PAGE: - Setup- Logging- Log Audio_Output
					Output1 Embed1 2_en  cmdID= 4068 "
		::= { iqosy30CmdEntry 4068 }


	iqosy30LoggingLogAudioOutputOutput1Embed12 OBJECT-TYPE
		SYNTAX		RollCallString
		MAX-ACCESS		read-only
		STATUS			current
		DESCRIPTION
				"TYPE: - Display
				 PAGE: - Setup- Logging- Log Audio_Output
					Output1 Embed1 2  cmdID= 4069  format=   "
		::= { iqosy30CmdEntry 4069 }


	iqosy30LoggingLogAudioOutputOutput1Embed21en OBJECT-TYPE
		SYNTAX		INTEGER { disable(0), enable(1) }
		MAX-ACCESS		read-write
		STATUS			current
		DESCRIPTION
				"TYPE: - Checkbox
				 PAGE: - Setup- Logging- Log Audio_Output
					Output1 Embed2 1_en  cmdID= 4072 "
		::= { iqosy30CmdEntry 4072 }


	iqosy30LoggingLogAudioOutputOutput1Embed21 OBJECT-TYPE
		SYNTAX		RollCallString
		MAX-ACCESS		read-only
		STATUS			current
		DESCRIPTION
				"TYPE: - Display
				 PAGE: - Setup- Logging- Log Audio_Output
					Output1 Embed2 1  cmdID= 4073  format=   "
		::= { iqosy30CmdEntry 4073 }


	iqosy30LoggingLogAudioOutputOutput1Embed22en OBJECT-TYPE
		SYNTAX		INTEGER { disable(0), enable(1) }
		MAX-ACCESS		read-write
		STATUS			current
		DESCRIPTION
				"TYPE: - Checkbox
				 PAGE: - Setup- Logging- Log Audio_Output
					Output1 Embed2 2_en  cmdID= 4076 "
		::= { iqosy30CmdEntry 4076 }


	iqosy30LoggingLogAudioOutputOutput1Embed22 OBJECT-TYPE
		SYNTAX		RollCallString
		MAX-ACCESS		read-only
		STATUS			current
		DESCRIPTION
				"TYPE: - Display
				 PAGE: - Setup- Logging- Log Audio_Output
					Output1 Embed2 2  cmdID= 4077  format=   "
		::= { iqosy30CmdEntry 4077 }


	iqosy30LoggingLogAudioOutputOutput1Embed31en OBJECT-TYPE
		SYNTAX		INTEGER { disable(0), enable(1) }
		MAX-ACCESS		read-write
		STATUS			current
		DESCRIPTION
				"TYPE: - Checkbox
				 PAGE: - Setup- Logging- Log Audio_Output
					Output1 Embed3 1_en  cmdID= 4080 "
		::= { iqosy30CmdEntry 4080 }


	iqosy30LoggingLogAudioOutputOutput1Embed31 OBJECT-TYPE
		SYNTAX		RollCallString
		MAX-ACCESS		read-only
		STATUS			current
		DESCRIPTION
				"TYPE: - Display
				 PAGE: - Setup- Logging- Log Audio_Output
					Output1 Embed3 1  cmdID= 4081  format=   "
		::= { iqosy30CmdEntry 4081 }


	iqosy30LoggingLogAudioOutputOutput1Embed32en OBJECT-TYPE
		SYNTAX		INTEGER { disable(0), enable(1) }
		MAX-ACCESS		read-write
		STATUS			current
		DESCRIPTION
				"TYPE: - Checkbox
				 PAGE: - Setup- Logging- Log Audio_Output
					Output1 Embed3 2_en  cmdID= 4084 "
		::= { iqosy30CmdEntry 4084 }


	iqosy30LoggingLogAudioOutputOutput1Embed32 OBJECT-TYPE
		SYNTAX		RollCallString
		MAX-ACCESS		read-only
		STATUS			current
		DESCRIPTION
				"TYPE: - Display
				 PAGE: - Setup- Logging- Log Audio_Output
					Output1 Embed3 2  cmdID= 4085  format=   "
		::= { iqosy30CmdEntry 4085 }


	iqosy30LoggingLogAudioOutputOutput1Embed41en OBJECT-TYPE
		SYNTAX		INTEGER { disable(0), enable(1) }
		MAX-ACCESS		read-write
		STATUS			current
		DESCRIPTION
				"TYPE: - Checkbox
				 PAGE: - Setup- Logging- Log Audio_Output
					Output1 Embed4 1_en  cmdID= 4088 "
		::= { iqosy30CmdEntry 4088 }


	iqosy30LoggingLogAudioOutputOutput1Embed41 OBJECT-TYPE
		SYNTAX		RollCallString
		MAX-ACCESS		read-only
		STATUS			current
		DESCRIPTION
				"TYPE: - Display
				 PAGE: - Setup- Logging- Log Audio_Output
					Output1 Embed4 1  cmdID= 4089  format=   "
		::= { iqosy30CmdEntry 4089 }


	iqosy30LoggingLogAudioOutputOutput1Embed42en OBJECT-TYPE
		SYNTAX		INTEGER { disable(0), enable(1) }
		MAX-ACCESS		read-write
		STATUS			current
		DESCRIPTION
				"TYPE: - Checkbox
				 PAGE: - Setup- Logging- Log Audio_Output
					Output1 Embed4 2_en  cmdID= 4092 "
		::= { iqosy30CmdEntry 4092 }


	iqosy30LoggingLogAudioOutputOutput1Embed42 OBJECT-TYPE
		SYNTAX		RollCallString
		MAX-ACCESS		read-only
		STATUS			current
		DESCRIPTION
				"TYPE: - Display
				 PAGE: - Setup- Logging- Log Audio_Output
					Output1 Embed4 2  cmdID= 4093  format=   "
		::= { iqosy30CmdEntry 4093 }


	iqosy30LoggingLogAudioOutputOutput1Embed51en OBJECT-TYPE
		SYNTAX		INTEGER { disable(0), enable(1) }
		MAX-ACCESS		read-write
		STATUS			current
		DESCRIPTION
				"TYPE: - Checkbox
				 PAGE: - Setup- Logging- Log Audio_Output
					Output1 Embed5 1_en  cmdID= 4096 "
		::= { iqosy30CmdEntry 4096 }


	iqosy30LoggingLogAudioOutputOutput1Embed51 OBJECT-TYPE
		SYNTAX		RollCallString
		MAX-ACCESS		read-only
		STATUS			current
		DESCRIPTION
				"TYPE: - Display
				 PAGE: - Setup- Logging- Log Audio_Output
					Output1 Embed5 1  cmdID= 4097  format=   "
		::= { iqosy30CmdEntry 4097 }


	iqosy30LoggingLogAudioOutputOutput1Embed52en OBJECT-TYPE
		SYNTAX		INTEGER { disable(0), enable(1) }
		MAX-ACCESS		read-write
		STATUS			current
		DESCRIPTION
				"TYPE: - Checkbox
				 PAGE: - Setup- Logging- Log Audio_Output
					Output1 Embed5 2_en  cmdID= 4100 "
		::= { iqosy30CmdEntry 4100 }


	iqosy30LoggingLogAudioOutputOutput1Embed52 OBJECT-TYPE
		SYNTAX		RollCallString
		MAX-ACCESS		read-only
		STATUS			current
		DESCRIPTION
				"TYPE: - Display
				 PAGE: - Setup- Logging- Log Audio_Output
					Output1 Embed5 2  cmdID= 4101  format=   "
		::= { iqosy30CmdEntry 4101 }


	iqosy30LoggingLogAudioOutputOutput1Embed61en OBJECT-TYPE
		SYNTAX		INTEGER { disable(0), enable(1) }
		MAX-ACCESS		read-write
		STATUS			current
		DESCRIPTION
				"TYPE: - Checkbox
				 PAGE: - Setup- Logging- Log Audio_Output
					Output1 Embed6 1_en  cmdID= 4104 "
		::= { iqosy30CmdEntry 4104 }


	iqosy30LoggingLogAudioOutputOutput1Embed61 OBJECT-TYPE
		SYNTAX		RollCallString
		MAX-ACCESS		read-only
		STATUS			current
		DESCRIPTION
				"TYPE: - Display
				 PAGE: - Setup- Logging- Log Audio_Output
					Output1 Embed6 1  cmdID= 4105  format=   "
		::= { iqosy30CmdEntry 4105 }


	iqosy30LoggingLogAudioOutputOutput1Embed62en OBJECT-TYPE
		SYNTAX		INTEGER { disable(0), enable(1) }
		MAX-ACCESS		read-write
		STATUS			current
		DESCRIPTION
				"TYPE: - Checkbox
				 PAGE: - Setup- Logging- Log Audio_Output
					Output1 Embed6 2_en  cmdID= 4108 "
		::= { iqosy30CmdEntry 4108 }


	iqosy30LoggingLogAudioOutputOutput1Embed62 OBJECT-TYPE
		SYNTAX		RollCallString
		MAX-ACCESS		read-only
		STATUS			current
		DESCRIPTION
				"TYPE: - Display
				 PAGE: - Setup- Logging- Log Audio_Output
					Output1 Embed6 2  cmdID= 4109  format=   "
		::= { iqosy30CmdEntry 4109 }


	iqosy30LoggingLogAudioOutputOutput1Embed71en OBJECT-TYPE
		SYNTAX		INTEGER { disable(0), enable(1) }
		MAX-ACCESS		read-write
		STATUS			current
		DESCRIPTION
				"TYPE: - Checkbox
				 PAGE: - Setup- Logging- Log Audio_Output
					Output1 Embed7 1_en  cmdID= 4112 "
		::= { iqosy30CmdEntry 4112 }


	iqosy30LoggingLogAudioOutputOutput1Embed71 OBJECT-TYPE
		SYNTAX		RollCallString
		MAX-ACCESS		read-only
		STATUS			current
		DESCRIPTION
				"TYPE: - Display
				 PAGE: - Setup- Logging- Log Audio_Output
					Output1 Embed7 1  cmdID= 4113  format=   "
		::= { iqosy30CmdEntry 4113 }


	iqosy30LoggingLogAudioOutputOutput1Embed72en OBJECT-TYPE
		SYNTAX		INTEGER { disable(0), enable(1) }
		MAX-ACCESS		read-write
		STATUS			current
		DESCRIPTION
				"TYPE: - Checkbox
				 PAGE: - Setup- Logging- Log Audio_Output
					Output1 Embed7 2_en  cmdID= 4116 "
		::= { iqosy30CmdEntry 4116 }


	iqosy30LoggingLogAudioOutputOutput1Embed72 OBJECT-TYPE
		SYNTAX		RollCallString
		MAX-ACCESS		read-only
		STATUS			current
		DESCRIPTION
				"TYPE: - Display
				 PAGE: - Setup- Logging- Log Audio_Output
					Output1 Embed7 2  cmdID= 4117  format=   "
		::= { iqosy30CmdEntry 4117 }


	iqosy30LoggingLogAudioOutputOutput1Embed81en OBJECT-TYPE
		SYNTAX		INTEGER { disable(0), enable(1) }
		MAX-ACCESS		read-write
		STATUS			current
		DESCRIPTION
				"TYPE: - Checkbox
				 PAGE: - Setup- Logging- Log Audio_Output
					Output1 Embed8 1_en  cmdID= 4120 "
		::= { iqosy30CmdEntry 4120 }


	iqosy30LoggingLogAudioOutputOutput1Embed81 OBJECT-TYPE
		SYNTAX		RollCallString
		MAX-ACCESS		read-only
		STATUS			current
		DESCRIPTION
				"TYPE: - Display
				 PAGE: - Setup- Logging- Log Audio_Output
					Output1 Embed8 1  cmdID= 4121  format=   "
		::= { iqosy30CmdEntry 4121 }


	iqosy30LoggingLogAudioOutputOutput1Embed82en OBJECT-TYPE
		SYNTAX		INTEGER { disable(0), enable(1) }
		MAX-ACCESS		read-write
		STATUS			current
		DESCRIPTION
				"TYPE: - Checkbox
				 PAGE: - Setup- Logging- Log Audio_Output
					Output1 Embed8 2_en  cmdID= 4124 "
		::= { iqosy30CmdEntry 4124 }


	iqosy30LoggingLogAudioOutputOutput1Embed82 OBJECT-TYPE
		SYNTAX		RollCallString
		MAX-ACCESS		read-only
		STATUS			current
		DESCRIPTION
				"TYPE: - Display
				 PAGE: - Setup- Logging- Log Audio_Output
					Output1 Embed8 2  cmdID= 4125  format=   "
		::= { iqosy30CmdEntry 4125 }


	iqosy30LoggingLogAudioOutputOutputEmbeden OBJECT-TYPE
		SYNTAX		INTEGER { disable(0), enable(1) }
		MAX-ACCESS		read-write
		STATUS			current
		DESCRIPTION
				"TYPE: - Checkbox
				 PAGE: - Setup- Logging- Log Audio_Output
					Output Embed_en  cmdID= 4456 "
		::= { iqosy30CmdEntry 4456 }


	iqosy30LoggingLogAudioOutputOutputEmbed OBJECT-TYPE
		SYNTAX		RollCallString
		MAX-ACCESS		read-only
		STATUS			current
		DESCRIPTION
				"TYPE: - Display
				 PAGE: - Setup- Logging- Log Audio_Output
					Output Embed  cmdID= 4457  format=   "
		::= { iqosy30CmdEntry 4457 }


	iqosy30LoggingLogFiberTx1BiasStateen OBJECT-TYPE
		SYNTAX		INTEGER { disable(0), enable(1) }
		MAX-ACCESS		read-write
		STATUS			current
		DESCRIPTION
				"TYPE: - Checkbox
				 PAGE: - Setup- Logging- Log Fiber
					Tx1 Bias State_en  cmdID= 4216 "
		::= { iqosy30CmdEntry 4216 }


	iqosy30LoggingLogFiberTx1BiasState OBJECT-TYPE
		SYNTAX		RollCallString
		MAX-ACCESS		read-only
		STATUS			current
		DESCRIPTION
				"TYPE: - Display
				 PAGE: - Setup- Logging- Log Fiber
					Tx1 Bias State  cmdID= 4217  format=   "
		::= { iqosy30CmdEntry 4217 }


	iqosy30LoggingLogFiberTx2BiasStateen OBJECT-TYPE
		SYNTAX		INTEGER { disable(0), enable(1) }
		MAX-ACCESS		read-write
		STATUS			current
		DESCRIPTION
				"TYPE: - Checkbox
				 PAGE: - Setup- Logging- Log Fiber
					Tx2 Bias State_en  cmdID= 4218 "
		::= { iqosy30CmdEntry 4218 }


	iqosy30LoggingLogFiberTx2BiasState OBJECT-TYPE
		SYNTAX		RollCallString
		MAX-ACCESS		read-only
		STATUS			current
		DESCRIPTION
				"TYPE: - Display
				 PAGE: - Setup- Logging- Log Fiber
					Tx2 Bias State  cmdID= 4219  format=   "
		::= { iqosy30CmdEntry 4219 }


	iqosy30LoggingLogFiberTx1Biasen OBJECT-TYPE
		SYNTAX		INTEGER { disable(0), enable(1) }
		MAX-ACCESS		read-write
		STATUS			current
		DESCRIPTION
				"TYPE: - Checkbox
				 PAGE: - Setup- Logging- Log Fiber
					Tx1 Bias_en  cmdID= 4220 "
		::= { iqosy30CmdEntry 4220 }


	iqosy30LoggingLogFiberTx1Bias OBJECT-TYPE
		SYNTAX		RollCallString
		MAX-ACCESS		read-only
		STATUS			current
		DESCRIPTION
				"TYPE: - Display
				 PAGE: - Setup- Logging- Log Fiber
					Tx1 Bias  cmdID= 4221  format=   "
		::= { iqosy30CmdEntry 4221 }


	iqosy30LoggingLogFiberTx2Biasen OBJECT-TYPE
		SYNTAX		INTEGER { disable(0), enable(1) }
		MAX-ACCESS		read-write
		STATUS			current
		DESCRIPTION
				"TYPE: - Checkbox
				 PAGE: - Setup- Logging- Log Fiber
					Tx2 Bias_en  cmdID= 4222 "
		::= { iqosy30CmdEntry 4222 }


	iqosy30LoggingLogFiberTx2Bias OBJECT-TYPE
		SYNTAX		RollCallString
		MAX-ACCESS		read-only
		STATUS			current
		DESCRIPTION
				"TYPE: - Display
				 PAGE: - Setup- Logging- Log Fiber
					Tx2 Bias  cmdID= 4223  format=   "
		::= { iqosy30CmdEntry 4223 }


	iqosy30LoggingLogFiberTx1PwrStateen OBJECT-TYPE
		SYNTAX		INTEGER { disable(0), enable(1) }
		MAX-ACCESS		read-write
		STATUS			current
		DESCRIPTION
				"TYPE: - Checkbox
				 PAGE: - Setup- Logging- Log Fiber
					Tx1 Pwr State_en  cmdID= 4224 "
		::= { iqosy30CmdEntry 4224 }


	iqosy30LoggingLogFiberTx1PwrState OBJECT-TYPE
		SYNTAX		RollCallString
		MAX-ACCESS		read-only
		STATUS			current
		DESCRIPTION
				"TYPE: - Display
				 PAGE: - Setup- Logging- Log Fiber
					Tx1 Pwr State  cmdID= 4225  format=   "
		::= { iqosy30CmdEntry 4225 }


	iqosy30LoggingLogFiberTx2PwrStateen OBJECT-TYPE
		SYNTAX		INTEGER { disable(0), enable(1) }
		MAX-ACCESS		read-write
		STATUS			current
		DESCRIPTION
				"TYPE: - Checkbox
				 PAGE: - Setup- Logging- Log Fiber
					Tx2 Pwr State_en  cmdID= 4226 "
		::= { iqosy30CmdEntry 4226 }


	iqosy30LoggingLogFiberTx2PwrState OBJECT-TYPE
		SYNTAX		RollCallString
		MAX-ACCESS		read-only
		STATUS			current
		DESCRIPTION
				"TYPE: - Display
				 PAGE: - Setup- Logging- Log Fiber
					Tx2 Pwr State  cmdID= 4227  format=   "
		::= { iqosy30CmdEntry 4227 }


	iqosy30LoggingLogFiberTx1Poweren OBJECT-TYPE
		SYNTAX		INTEGER { disable(0), enable(1) }
		MAX-ACCESS		read-write
		STATUS			current
		DESCRIPTION
				"TYPE: - Checkbox
				 PAGE: - Setup- Logging- Log Fiber
					Tx1 Power_en  cmdID= 4228 "
		::= { iqosy30CmdEntry 4228 }


	iqosy30LoggingLogFiberTx1Power OBJECT-TYPE
		SYNTAX		RollCallString
		MAX-ACCESS		read-only
		STATUS			current
		DESCRIPTION
				"TYPE: - Display
				 PAGE: - Setup- Logging- Log Fiber
					Tx1 Power  cmdID= 4229  format=   "
		::= { iqosy30CmdEntry 4229 }


	iqosy30LoggingLogFiberTx2Poweren OBJECT-TYPE
		SYNTAX		INTEGER { disable(0), enable(1) }
		MAX-ACCESS		read-write
		STATUS			current
		DESCRIPTION
				"TYPE: - Checkbox
				 PAGE: - Setup- Logging- Log Fiber
					Tx2 Power_en  cmdID= 4230 "
		::= { iqosy30CmdEntry 4230 }


	iqosy30LoggingLogFiberTx2Power OBJECT-TYPE
		SYNTAX		RollCallString
		MAX-ACCESS		read-only
		STATUS			current
		DESCRIPTION
				"TYPE: - Display
				 PAGE: - Setup- Logging- Log Fiber
					Tx2 Power  cmdID= 4231  format=   "
		::= { iqosy30CmdEntry 4231 }


	iqosy30LoggingLogFiberRx1Stateen OBJECT-TYPE
		SYNTAX		INTEGER { disable(0), enable(1) }
		MAX-ACCESS		read-write
		STATUS			current
		DESCRIPTION
				"TYPE: - Checkbox
				 PAGE: - Setup- Logging- Log Fiber
					Rx1 State_en  cmdID= 4236 "
		::= { iqosy30CmdEntry 4236 }


	iqosy30LoggingLogFiberRx1State OBJECT-TYPE
		SYNTAX		RollCallString
		MAX-ACCESS		read-only
		STATUS			current
		DESCRIPTION
				"TYPE: - Display
				 PAGE: - Setup- Logging- Log Fiber
					Rx1 State  cmdID= 4237  format=   "
		::= { iqosy30CmdEntry 4237 }


	iqosy30LoggingLogFiberRx2Stateen OBJECT-TYPE
		SYNTAX		INTEGER { disable(0), enable(1) }
		MAX-ACCESS		read-write
		STATUS			current
		DESCRIPTION
				"TYPE: - Checkbox
				 PAGE: - Setup- Logging- Log Fiber
					Rx2 State_en  cmdID= 4238 "
		::= { iqosy30CmdEntry 4238 }


	iqosy30LoggingLogFiberRx2State OBJECT-TYPE
		SYNTAX		RollCallString
		MAX-ACCESS		read-only
		STATUS			current
		DESCRIPTION
				"TYPE: - Display
				 PAGE: - Setup- Logging- Log Fiber
					Rx2 State  cmdID= 4239  format=   "
		::= { iqosy30CmdEntry 4239 }


	iqosy30LoggingLogFiberRx1Poweren OBJECT-TYPE
		SYNTAX		INTEGER { disable(0), enable(1) }
		MAX-ACCESS		read-write
		STATUS			current
		DESCRIPTION
				"TYPE: - Checkbox
				 PAGE: - Setup- Logging- Log Fiber
					Rx1 Power_en  cmdID= 4240 "
		::= { iqosy30CmdEntry 4240 }


	iqosy30LoggingLogFiberRx1Power OBJECT-TYPE
		SYNTAX		RollCallString
		MAX-ACCESS		read-only
		STATUS			current
		DESCRIPTION
				"TYPE: - Display
				 PAGE: - Setup- Logging- Log Fiber
					Rx1 Power  cmdID= 4241  format=   "
		::= { iqosy30CmdEntry 4241 }


	iqosy30LoggingLogFiberRx2Poweren OBJECT-TYPE
		SYNTAX		INTEGER { disable(0), enable(1) }
		MAX-ACCESS		read-write
		STATUS			current
		DESCRIPTION
				"TYPE: - Checkbox
				 PAGE: - Setup- Logging- Log Fiber
					Rx2 Power_en  cmdID= 4242 "
		::= { iqosy30CmdEntry 4242 }


	iqosy30LoggingLogFiberRx2Power OBJECT-TYPE
		SYNTAX		RollCallString
		MAX-ACCESS		read-only
		STATUS			current
		DESCRIPTION
				"TYPE: - Display
				 PAGE: - Setup- Logging- Log Fiber
					Rx2 Power  cmdID= 4243  format=   "
		::= { iqosy30CmdEntry 4243 }


	iqosy30SetupRollTracksRollTrackIndex1495 OBJECT-TYPE
		SYNTAX		INTEGER
		MAX-ACCESS		read-write
		STATUS			current
		DESCRIPTION
				"TYPE: - Number
				 PAGE: - Setup- RollTracks
					RollTrack Index  cmdID= 1495  min= 1  max= 70  step= 1  format= %.0f  div_scale= 1 
					Min = 1  Max = 70  Step = 1 "
		::= { iqosy30CmdEntry 1495 }


	iqosy30SetupRollTracksRollTrackSource1496 OBJECT-TYPE
		SYNTAX		INTEGER
		MAX-ACCESS		read-write
		STATUS			current
		DESCRIPTION
				"TYPE: - Number
				 PAGE: - Setup- RollTracks
					RollTrack Source  cmdID= 1496  min= -1  max= 102  step= 1  format= %.0f  div_scale= 1 
					Min = -1  Max = 102  Step = 1 "
		::= { iqosy30CmdEntry 1496 }


	iqosy30SetupRollTracksRollTrackDisable OBJECT-TYPE
		SYNTAX		INTEGER { disable(0), enable(1) }
		MAX-ACCESS		read-write
		STATUS			current
		DESCRIPTION
				"TYPE: - Checkbox
				 PAGE: - Setup- RollTracks
					RollTrack Disable  cmdID= 1513 "
		::= { iqosy30CmdEntry 1513 }


	iqosy30SetupRollTracksRollTrackAddress1497 OBJECT-TYPE
		SYNTAX		RollCallString
		MAX-ACCESS		read-write
		STATUS			current
		DESCRIPTION
				"TYPE: - Editstring
				 PAGE: - Setup- RollTracks
					RollTrack Address  cmdID= 1497  "
		::= { iqosy30CmdEntry 1497 }


	iqosy30SetupRollTracksRollTrackCommand1498 OBJECT-TYPE
		SYNTAX		RollCallString
		MAX-ACCESS		read-write
		STATUS			current
		DESCRIPTION
				"TYPE: - Editstring
				 PAGE: - Setup- RollTracks
					RollTrack Command  cmdID= 1498  "
		::= { iqosy30CmdEntry 1498 }


	iqosy30SetupRollTracksRollTrackSending OBJECT-TYPE
		SYNTAX		RollCallString
		MAX-ACCESS		read-only
		STATUS			current
		DESCRIPTION
				"TYPE: - Display
				 PAGE: - Setup- RollTracks
					RollTrack Sending  cmdID= 1514  format=   "
		::= { iqosy30CmdEntry 1514 }


	iqosy30SetupRollTracksRollTrackStatus OBJECT-TYPE
		SYNTAX		RollCallString
		MAX-ACCESS		read-only
		STATUS			current
		DESCRIPTION
				"TYPE: - Display
				 PAGE: - Setup- RollTracks
					RollTrack Status  cmdID= 1511  format=   "
		::= { iqosy30CmdEntry 1511 }


	iqosy30SetupRollTracksRollTrackIndex2870 OBJECT-TYPE
		SYNTAX		INTEGER
		MAX-ACCESS		read-write
		STATUS			current
		DESCRIPTION
				"TYPE: - Number
				 PAGE: - Setup- RollTracks
					RollTrack Index  cmdID= 2870  min= 1  max= 70  step= 1  format= %.0f  div_scale= 1 
					Min = 1  Max = 70  Step = 1 "
		::= { iqosy30CmdEntry 2870 }


	iqosy30SetupRollTracksRollTrackSource2871 OBJECT-TYPE
		SYNTAX		INTEGER
		MAX-ACCESS		read-write
		STATUS			current
		DESCRIPTION
				"TYPE: - Number
				 PAGE: - Setup- RollTracks
					RollTrack Source  cmdID= 2871  min= -1  max= 102  step= 1  format= %.0f  div_scale= 1 
					Min = -1  Max = 102  Step = 1 "
		::= { iqosy30CmdEntry 2871 }


	iqosy30SetupRollTracksRollTrackAddress2872 OBJECT-TYPE
		SYNTAX		RollCallString
		MAX-ACCESS		read-write
		STATUS			current
		DESCRIPTION
				"TYPE: - Editstring
				 PAGE: - Setup- RollTracks
					RollTrack Address  cmdID= 2872  "
		::= { iqosy30CmdEntry 2872 }


	iqosy30SetupRollTracksRollTrackCommand2873 OBJECT-TYPE
		SYNTAX		RollCallString
		MAX-ACCESS		read-write
		STATUS			current
		DESCRIPTION
				"TYPE: - Editstring
				 PAGE: - Setup- RollTracks
					RollTrack Command  cmdID= 2873  "
		::= { iqosy30CmdEntry 2873 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S51110765
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:02:00
--				: 
-- Comments		: 
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
-- Vary			: YES
--
-- Value(s)		: 90
--				: 
-- Comments		: 
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: INPUT_1
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				: 
-- Comments		: 
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
-- Vary			: YES
--
-- Value(s)		: Unknown
--				: 
-- Comments		: 
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
-- Vary			: YES
--
-- Value(s)		: Unknown
--				: 
-- Comments		: 
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
-- Vary			: YES
--
-- Value(s)		: WARN:Type Mismatch
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 4492.4492.4492
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD/SD/3G SDI
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: HD/SD/3G SDI
--				: 
-- Comments		: 
--
---------------------------------------------------------------------------------------------------
-- Header		: INPUT_3_TYPE
--
-- MIB ref		: swCardEventLogSlotXX       .12.73.78.80.85.84.95.51.95.84.89.80.69
-- absolute OID	: 1.3.6.1.4.1.7995.2.6.1.1.XX.12.73.78.80.85.84.95.51.95.84.89.80.69
-- Vary			: YES
--
-- Value(s)		: 
--				: 
-- Comments		: 
--
---------------------------------------------------------------------------------------------------
-- Header		: INPUT_4_TYPE
--
-- MIB ref		: swCardEventLogSlotXX       .12.73.78.80.85.84.95.52.95.84.89.80.69
-- absolute OID	: 1.3.6.1.4.1.7995.2.6.1.1.XX.12.73.78.80.85.84.95.52.95.84.89.80.69
-- Vary			: YES
--
-- Value(s)		: 
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2014-11-13T14:21:02Z
--				: 
-- Comments		: 
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: SERIAL IN 1
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: 
-- Comments		: 
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: SERIAL IN 2
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: 
-- Comments		: 
--
---------------------------------------------------------------------------------------------------
-- Header		: INPUT_3_IDENT
--
-- MIB ref		: swCardEventLogSlotXX       .13.73.78.80.85.84.95.51.95.73.68.69.78.84
-- absolute OID	: 1.3.6.1.4.1.7995.2.6.1.1.XX.13.73.78.80.85.84.95.51.95.73.68.69.78.84
-- Vary			: YES
--
-- Value(s)		: 
--				: 
-- Comments		: 
--
---------------------------------------------------------------------------------------------------
-- Header		: INPUT_3_STATE
--
-- MIB ref		: swCardEventLogSlotXX       .13.73.78.80.85.84.95.51.95.83.84.65.84.69
-- absolute OID	: 1.3.6.1.4.1.7995.2.6.1.1.XX.13.73.78.80.85.84.95.51.95.83.84.65.84.69
-- Vary			: YES
--
-- Value(s)		: 
--				: 
-- Comments		: 
--
---------------------------------------------------------------------------------------------------
-- Header		: INPUT_4_IDENT
--
-- MIB ref		: swCardEventLogSlotXX       .13.73.78.80.85.84.95.52.95.73.68.69.78.84
-- absolute OID	: 1.3.6.1.4.1.7995.2.6.1.1.XX.13.73.78.80.85.84.95.52.95.73.68.69.78.84
-- Vary			: YES
--
-- Value(s)		: 
--				: 
-- Comments		: 
--
---------------------------------------------------------------------------------------------------
-- Header		: INPUT_4_STATE
--
-- MIB ref		: swCardEventLogSlotXX       .13.73.78.80.85.84.95.52.95.83.84.65.84.69
-- absolute OID	: 1.3.6.1.4.1.7995.2.6.1.1.XX.13.73.78.80.85.84.95.52.95.83.84.65.84.69
-- Vary			: YES
--
-- Value(s)		: 
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 3G / HD / SD SDI
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: WARN:Black
--				: 
-- Comments		: 
--
---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
-- Vary			: YES
--
-- Value(s)		: WARN:Freerun
--				: 
-- Comments		: 
--
---------------------------------------------------------------------------------------------------
-- Header		: FIBER_RX_1_POWER
--
-- MIB ref		: swCardEventLogSlotXX       .16.70.73.66.69.82.95.82.88.95.49.95.80.79.87.69.82
-- absolute OID	: 1.3.6.1.4.1.7995.2.6.1.1.XX.16.70.73.66.69.82.95.82.88.95.49.95.80.79.87.69.82
-- Vary			: YES
--
-- Value(s)		: 
--				: 
-- Comments		: 
--
---------------------------------------------------------------------------------------------------
-- Header		: FIBER_RX_2_POWER
--
-- MIB ref		: swCardEventLogSlotXX       .16.70.73.66.69.82.95.82.88.95.50.95.80.79.87.69.82
-- absolute OID	: 1.3.6.1.4.1.7995.2.6.1.1.XX.16.70.73.66.69.82.95.82.88.95.50.95.80.79.87.69.82
-- Vary			: YES
--
-- Value(s)		: 
--				: 
-- Comments		: 
--
---------------------------------------------------------------------------------------------------
-- Header		: FIBER_TX_1_POWER
--
-- MIB ref		: swCardEventLogSlotXX       .16.70.73.66.69.82.95.84.88.95.49.95.80.79.87.69.82
-- absolute OID	: 1.3.6.1.4.1.7995.2.6.1.1.XX.16.70.73.66.69.82.95.84.88.95.49.95.80.79.87.69.82
-- Vary			: YES
--
-- Value(s)		: 
--				: 
-- Comments		: 
--
---------------------------------------------------------------------------------------------------
-- Header		: FIBER_TX_2_POWER
--
-- MIB ref		: swCardEventLogSlotXX       .16.70.73.66.69.82.95.84.88.95.50.95.80.79.87.69.82
-- absolute OID	: 1.3.6.1.4.1.7995.2.6.1.1.XX.16.70.73.66.69.82.95.84.88.95.50.95.80.79.87.69.82
-- Vary			: YES
--
-- Value(s)		: 
--				: 
-- Comments		: 
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 4488
--				: 
-- Comments		: 
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: HDBASP2B
--				: 
-- Comments		: 
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--				: 
-- Comments		: 
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
-- Vary			: YES
--
-- Value(s)		: OK
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: Unknown
--				: 
-- Comments		: 
--
---------------------------------------------------------------------------------------------------
-- Header		: INPUT_3_SDI_ERRS
--
-- MIB ref		: swCardEventLogSlotXX       .16.73.78.80.85.84.95.51.95.83.68.73.95.69.82.82.83
-- absolute OID	: 1.3.6.1.4.1.7995.2.6.1.1.XX.16.73.78.80.85.84.95.51.95.83.68.73.95.69.82.82.83
-- Vary			: YES
--
-- Value(s)		: 
--				: 
-- Comments		: 
--
---------------------------------------------------------------------------------------------------
-- Header		: INPUT_3_STANDARD
--
-- MIB ref		: swCardEventLogSlotXX       .16.73.78.80.85.84.95.51.95.83.84.65.78.68.65.82.68
-- absolute OID	: 1.3.6.1.4.1.7995.2.6.1.1.XX.16.73.78.80.85.84.95.51.95.83.84.65.78.68.65.82.68
-- Vary			: YES
--
-- Value(s)		: 
--				: 
-- Comments		: 
--
---------------------------------------------------------------------------------------------------
-- Header		: INPUT_4_SDI_ERRS
--
-- MIB ref		: swCardEventLogSlotXX       .16.73.78.80.85.84.95.52.95.83.68.73.95.69.82.82.83
-- absolute OID	: 1.3.6.1.4.1.7995.2.6.1.1.XX.16.73.78.80.85.84.95.52.95.83.68.73.95.69.82.82.83
-- Vary			: YES
--
-- Value(s)		: 
--				: 
-- Comments		: 
--
---------------------------------------------------------------------------------------------------
-- Header		: INPUT_4_STANDARD
--
-- MIB ref		: swCardEventLogSlotXX       .16.73.78.80.85.84.95.52.95.83.84.65.78.68.65.82.68
-- absolute OID	: 1.3.6.1.4.1.7995.2.6.1.1.XX.16.73.78.80.85.84.95.52.95.83.84.65.78.68.65.82.68
-- Vary			: YES
--
-- Value(s)		: 
--				: 
-- Comments		: 
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
-- Vary			: YES
--
-- Value(s)		: SDHD;3G
--				: 
-- Comments		: 
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
-- Vary			: YES
--
-- Value(s)		: OK:Off
--				: 
-- Comments		: 
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
-- Vary			: YES
--
-- Value(s)		: WARN:Unknown
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 625/25i
--				: 
-- Comments		: 
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
-- Vary			: YES
--
-- Value(s)		: FAIL:Lost
--				: 
-- Comments		: 
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: 
-- Comments		: 
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
-- Vary			: YES
--
-- Value(s)		: OK
--				: 
-- Comments		: 
--
---------------------------------------------------------------------------------------------------
-- Header		: INPUT_3_SDI_ANC_ERRS
--
-- MIB ref		: swCardEventLogSlotXX       .20.73.78.80.85.84.95.51.95.83.68.73.95.65.78.67.95.69.82.82.83
-- absolute OID	: 1.3.6.1.4.1.7995.2.6.1.1.XX.20.73.78.80.85.84.95.51.95.83.68.73.95.65.78.67.95.69.82.82.83
-- Vary			: YES
--
-- Value(s)		: 
--				: 
-- Comments		: 
--
---------------------------------------------------------------------------------------------------
-- Header		: INPUT_4_SDI_ANC_ERRS
--
-- MIB ref		: swCardEventLogSlotXX       .20.73.78.80.85.84.95.52.95.83.68.73.95.65.78.67.95.69.82.82.83
-- absolute OID	: 1.3.6.1.4.1.7995.2.6.1.1.XX.20.73.78.80.85.84.95.52.95.83.68.73.95.65.78.67.95.69.82.82.83
-- Vary			: YES
--
-- Value(s)		: 
--				: 
-- Comments		: 
--
---------------------------------------------------------------------------------------------------
-- Header		: OUTPUT_1_EMBED_AUDIO
--
-- MIB ref		: swCardEventLogSlotXX       .20.79.85.84.80.85.84.95.49.95.69.77.66.69.68.95.65.85.68.73.79
-- absolute OID	: 1.3.6.1.4.1.7995.2.6.1.1.XX.20.79.85.84.80.85.84.95.49.95.69.77.66.69.68.95.65.85.68.73.79
-- Vary			: YES
--
-- Value(s)		: INPUT_1
--				: 
-- Comments		: 
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
-- Vary			: YES
--
-- Value(s)		: Unknown
--				: 
-- Comments		: 
--
---------------------------------------------------------------------------------------------------
-- Header		: FIBER_TX_1_LASER_BIAS
--
-- MIB ref		: swCardEventLogSlotXX       .21.70.73.66.69.82.95.84.88.95.49.95.76.65.83.69.82.95.66.73.65.83
-- absolute OID	: 1.3.6.1.4.1.7995.2.6.1.1.XX.21.70.73.66.69.82.95.84.88.95.49.95.76.65.83.69.82.95.66.73.65.83
-- Vary			: YES
--
-- Value(s)		: 
--				: 
-- Comments		: 
--
---------------------------------------------------------------------------------------------------
-- Header		: FIBER_TX_2_LASER_BIAS
--
-- MIB ref		: swCardEventLogSlotXX       .21.70.73.66.69.82.95.84.88.95.50.95.76.65.83.69.82.95.66.73.65.83
-- absolute OID	: 1.3.6.1.4.1.7995.2.6.1.1.XX.21.70.73.66.69.82.95.84.88.95.50.95.76.65.83.69.82.95.66.73.65.83
-- Vary			: YES
--
-- Value(s)		: 
--				: 
-- Comments		: 
--
---------------------------------------------------------------------------------------------------
-- Header		: FIBER_RX_1_POWER_STATE
--
-- MIB ref		: swCardEventLogSlotXX       .22.70.73.66.69.82.95.82.88.95.49.95.80.79.87.69.82.95.83.84.65.84.69
-- absolute OID	: 1.3.6.1.4.1.7995.2.6.1.1.XX.22.70.73.66.69.82.95.82.88.95.49.95.80.79.87.69.82.95.83.84.65.84.69
-- Vary			: YES
--
-- Value(s)		: 
--				: 
-- Comments		: 
--
---------------------------------------------------------------------------------------------------
-- Header		: FIBER_RX_2_POWER_STATE
--
-- MIB ref		: swCardEventLogSlotXX       .22.70.73.66.69.82.95.82.88.95.50.95.80.79.87.69.82.95.83.84.65.84.69
-- absolute OID	: 1.3.6.1.4.1.7995.2.6.1.1.XX.22.70.73.66.69.82.95.82.88.95.50.95.80.79.87.69.82.95.83.84.65.84.69
-- Vary			: YES
--
-- Value(s)		: 
--				: 
-- Comments		: 
--
---------------------------------------------------------------------------------------------------
-- Header		: FIBER_TX_1_POWER_STATE
--
-- MIB ref		: swCardEventLogSlotXX       .22.70.73.66.69.82.95.84.88.95.49.95.80.79.87.69.82.95.83.84.65.84.69
-- absolute OID	: 1.3.6.1.4.1.7995.2.6.1.1.XX.22.70.73.66.69.82.95.84.88.95.49.95.80.79.87.69.82.95.83.84.65.84.69
-- Vary			: YES
--
-- Value(s)		: 
--				: 
-- Comments		: 
--
---------------------------------------------------------------------------------------------------
-- Header		: FIBER_TX_2_POWER_STATE
--
-- MIB ref		: swCardEventLogSlotXX       .22.70.73.66.69.82.95.84.88.95.50.95.80.79.87.69.82.95.83.84.65.84.69
-- absolute OID	: 1.3.6.1.4.1.7995.2.6.1.1.XX.22.70.73.66.69.82.95.84.88.95.50.95.80.79.87.69.82.95.83.84.65.84.69
-- Vary			: YES
--
-- Value(s)		: 
--				: 
-- Comments		: 
--
---------------------------------------------------------------------------------------------------
-- Header		: FIBER_TX_1_LASER_BIAS_STATE
--
-- MIB ref		: swCardEventLogSlotXX       .27.70.73.66.69.82.95.84.88.95.49.95.76.65.83.69.82.95.66.73.65.83.95.83.84.65.84.69
-- absolute OID	: 1.3.6.1.4.1.7995.2.6.1.1.XX.27.70.73.66.69.82.95.84.88.95.49.95.76.65.83.69.82.95.66.73.65.83.95.83.84.65.84.69
-- Vary			: YES
--
-- Value(s)		: 
--				: 
-- Comments		: 
--
---------------------------------------------------------------------------------------------------
-- Header		: FIBER_TX_2_LASER_BIAS_STATE
--
-- MIB ref		: swCardEventLogSlotXX       .27.70.73.66.69.82.95.84.88.95.50.95.76.65.83.69.82.95.66.73.65.83.95.83.84.65.84.69
-- absolute OID	: 1.3.6.1.4.1.7995.2.6.1.1.XX.27.70.73.66.69.82.95.84.88.95.50.95.76.65.83.69.82.95.66.73.65.83.95.83.84.65.84.69
-- Vary			: YES
--
-- Value(s)		: 
--				: 
-- Comments		: 
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: WARN:No Input
--				: 
-- Comments		: 
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: WARN:No Input
--				: 
-- Comments		: 
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: WARN:No Input
--				: 
-- Comments		: 
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: WARN:No Input
--				: 
-- Comments		: 
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: WARN:No Input
--				: 
-- Comments		: 
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: WARN:No Input
--				: 
-- Comments		: 
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: WARN:No Input
--				: 
-- Comments		: 
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: WARN:No Input
--				: 
-- Comments		: 
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
-- Vary			: YES
--
-- Value(s)		: WARN:Unknown
--				: 
-- Comments		: 
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
-- Vary			: YES
--
-- Value(s)		: WARN:Unknown
--				: 
-- Comments		: 
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
-- Vary			: YES
--
-- Value(s)		: WARN:Unknown
--				: 
-- Comments		: 
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
-- Vary			: YES
--
-- Value(s)		: WARN:Unknown
--				: 
-- Comments		: 
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
-- Vary			: YES
--
-- Value(s)		: WARN:Unknown
--				: 
-- Comments		: 
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
-- Vary			: YES
--
-- Value(s)		: WARN:Unknown
--				: 
-- Comments		: 
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
-- Vary			: YES
--
-- Value(s)		: WARN:Unknown
--				: 
-- Comments		: 
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
-- Vary			: YES
--
-- Value(s)		: WARN:Unknown
--				: 
-- Comments		: 
--
---------------------------------------------------------------------------------------------------
-- Header		: INPUT_3_EMBEDDED_AUDIO_1_STATE
--
-- MIB ref		: swCardEventLogSlotXX       .30.73.78.80.85.84.95.51.95.69.77.66.69.68.68.69.68.95.65.85.68.73.79.95.49.95.83.84.65.84.69
-- absolute OID	: 1.3.6.1.4.1.7995.2.6.1.1.XX.30.73.78.80.85.84.95.51.95.69.77.66.69.68.68.69.68.95.65.85.68.73.79.95.49.95.83.84.65.84.69
-- Vary			: YES
--
-- Value(s)		: 
--				: 
-- Comments		: 
--
---------------------------------------------------------------------------------------------------
-- Header		: INPUT_3_EMBEDDED_AUDIO_2_STATE
--
-- MIB ref		: swCardEventLogSlotXX       .30.73.78.80.85.84.95.51.95.69.77.66.69.68.68.69.68.95.65.85.68.73.79.95.50.95.83.84.65.84.69
-- absolute OID	: 1.3.6.1.4.1.7995.2.6.1.1.XX.30.73.78.80.85.84.95.51.95.69.77.66.69.68.68.69.68.95.65.85.68.73.79.95.50.95.83.84.65.84.69
-- Vary			: YES
--
-- Value(s)		: 
--				: 
-- Comments		: 
--
---------------------------------------------------------------------------------------------------
-- Header		: INPUT_3_EMBEDDED_AUDIO_3_STATE
--
-- MIB ref		: swCardEventLogSlotXX       .30.73.78.80.85.84.95.51.95.69.77.66.69.68.68.69.68.95.65.85.68.73.79.95.51.95.83.84.65.84.69
-- absolute OID	: 1.3.6.1.4.1.7995.2.6.1.1.XX.30.73.78.80.85.84.95.51.95.69.77.66.69.68.68.69.68.95.65.85.68.73.79.95.51.95.83.84.65.84.69
-- Vary			: YES
--
-- Value(s)		: 
--				: 
-- Comments		: 
--
---------------------------------------------------------------------------------------------------
-- Header		: INPUT_3_EMBEDDED_AUDIO_4_STATE
--
-- MIB ref		: swCardEventLogSlotXX       .30.73.78.80.85.84.95.51.95.69.77.66.69.68.68.69.68.95.65.85.68.73.79.95.52.95.83.84.65.84.69
-- absolute OID	: 1.3.6.1.4.1.7995.2.6.1.1.XX.30.73.78.80.85.84.95.51.95.69.77.66.69.68.68.69.68.95.65.85.68.73.79.95.52.95.83.84.65.84.69
-- Vary			: YES
--
-- Value(s)		: 
--				: 
-- Comments		: 
--
---------------------------------------------------------------------------------------------------
-- Header		: INPUT_3_EMBEDDED_AUDIO_5_STATE
--
-- MIB ref		: swCardEventLogSlotXX       .30.73.78.80.85.84.95.51.95.69.77.66.69.68.68.69.68.95.65.85.68.73.79.95.53.95.83.84.65.84.69
-- absolute OID	: 1.3.6.1.4.1.7995.2.6.1.1.XX.30.73.78.80.85.84.95.51.95.69.77.66.69.68.68.69.68.95.65.85.68.73.79.95.53.95.83.84.65.84.69
-- Vary			: YES
--
-- Value(s)		: 
--				: 
-- Comments		: 
--
---------------------------------------------------------------------------------------------------
-- Header		: INPUT_3_EMBEDDED_AUDIO_6_STATE
--
-- MIB ref		: swCardEventLogSlotXX       .30.73.78.80.85.84.95.51.95.69.77.66.69.68.68.69.68.95.65.85.68.73.79.95.54.95.83.84.65.84.69
-- absolute OID	: 1.3.6.1.4.1.7995.2.6.1.1.XX.30.73.78.80.85.84.95.51.95.69.77.66.69.68.68.69.68.95.65.85.68.73.79.95.54.95.83.84.65.84.69
-- Vary			: YES
--
-- Value(s)		: 
--				: 
-- Comments		: 
--
---------------------------------------------------------------------------------------------------
-- Header		: INPUT_3_EMBEDDED_AUDIO_7_STATE
--
-- MIB ref		: swCardEventLogSlotXX       .30.73.78.80.85.84.95.51.95.69.77.66.69.68.68.69.68.95.65.85.68.73.79.95.55.95.83.84.65.84.69
-- absolute OID	: 1.3.6.1.4.1.7995.2.6.1.1.XX.30.73.78.80.85.84.95.51.95.69.77.66.69.68.68.69.68.95.65.85.68.73.79.95.55.95.83.84.65.84.69
-- Vary			: YES
--
-- Value(s)		: 
--				: 
-- Comments		: 
--
---------------------------------------------------------------------------------------------------
-- Header		: INPUT_3_EMBEDDED_AUDIO_8_STATE
--
-- MIB ref		: swCardEventLogSlotXX       .30.73.78.80.85.84.95.51.95.69.77.66.69.68.68.69.68.95.65.85.68.73.79.95.56.95.83.84.65.84.69
-- absolute OID	: 1.3.6.1.4.1.7995.2.6.1.1.XX.30.73.78.80.85.84.95.51.95.69.77.66.69.68.68.69.68.95.65.85.68.73.79.95.56.95.83.84.65.84.69
-- Vary			: YES
--
-- Value(s)		: 
--				: 
-- Comments		: 
--
---------------------------------------------------------------------------------------------------
-- Header		: INPUT_4_EMBEDDED_AUDIO_1_STATE
--
-- MIB ref		: swCardEventLogSlotXX       .30.73.78.80.85.84.95.52.95.69.77.66.69.68.68.69.68.95.65.85.68.73.79.95.49.95.83.84.65.84.69
-- absolute OID	: 1.3.6.1.4.1.7995.2.6.1.1.XX.30.73.78.80.85.84.95.52.95.69.77.66.69.68.68.69.68.95.65.85.68.73.79.95.49.95.83.84.65.84.69
-- Vary			: YES
--
-- Value(s)		: 
--				: 
-- Comments		: 
--
---------------------------------------------------------------------------------------------------
-- Header		: INPUT_4_EMBEDDED_AUDIO_2_STATE
--
-- MIB ref		: swCardEventLogSlotXX       .30.73.78.80.85.84.95.52.95.69.77.66.69.68.68.69.68.95.65.85.68.73.79.95.50.95.83.84.65.84.69
-- absolute OID	: 1.3.6.1.4.1.7995.2.6.1.1.XX.30.73.78.80.85.84.95.52.95.69.77.66.69.68.68.69.68.95.65.85.68.73.79.95.50.95.83.84.65.84.69
-- Vary			: YES
--
-- Value(s)		: 
--				: 
-- Comments		: 
--
---------------------------------------------------------------------------------------------------
-- Header		: INPUT_4_EMBEDDED_AUDIO_3_STATE
--
-- MIB ref		: swCardEventLogSlotXX       .30.73.78.80.85.84.95.52.95.69.77.66.69.68.68.69.68.95.65.85.68.73.79.95.51.95.83.84.65.84.69
-- absolute OID	: 1.3.6.1.4.1.7995.2.6.1.1.XX.30.73.78.80.85.84.95.52.95.69.77.66.69.68.68.69.68.95.65.85.68.73.79.95.51.95.83.84.65.84.69
-- Vary			: YES
--
-- Value(s)		: 
--				: 
-- Comments		: 
--
---------------------------------------------------------------------------------------------------
-- Header		: INPUT_4_EMBEDDED_AUDIO_4_STATE
--
-- MIB ref		: swCardEventLogSlotXX       .30.73.78.80.85.84.95.52.95.69.77.66.69.68.68.69.68.95.65.85.68.73.79.95.52.95.83.84.65.84.69
-- absolute OID	: 1.3.6.1.4.1.7995.2.6.1.1.XX.30.73.78.80.85.84.95.52.95.69.77.66.69.68.68.69.68.95.65.85.68.73.79.95.52.95.83.84.65.84.69
-- Vary			: YES
--
-- Value(s)		: 
--				: 
-- Comments		: 
--
---------------------------------------------------------------------------------------------------
-- Header		: INPUT_4_EMBEDDED_AUDIO_5_STATE
--
-- MIB ref		: swCardEventLogSlotXX       .30.73.78.80.85.84.95.52.95.69.77.66.69.68.68.69.68.95.65.85.68.73.79.95.53.95.83.84.65.84.69
-- absolute OID	: 1.3.6.1.4.1.7995.2.6.1.1.XX.30.73.78.80.85.84.95.52.95.69.77.66.69.68.68.69.68.95.65.85.68.73.79.95.53.95.83.84.65.84.69
-- Vary			: YES
--
-- Value(s)		: 
--				: 
-- Comments		: 
--
---------------------------------------------------------------------------------------------------
-- Header		: INPUT_4_EMBEDDED_AUDIO_6_STATE
--
-- MIB ref		: swCardEventLogSlotXX       .30.73.78.80.85.84.95.52.95.69.77.66.69.68.68.69.68.95.65.85.68.73.79.95.54.95.83.84.65.84.69
-- absolute OID	: 1.3.6.1.4.1.7995.2.6.1.1.XX.30.73.78.80.85.84.95.52.95.69.77.66.69.68.68.69.68.95.65.85.68.73.79.95.54.95.83.84.65.84.69
-- Vary			: YES
--
-- Value(s)		: 
--				: 
-- Comments		: 
--
---------------------------------------------------------------------------------------------------
-- Header		: INPUT_4_EMBEDDED_AUDIO_7_STATE
--
-- MIB ref		: swCardEventLogSlotXX       .30.73.78.80.85.84.95.52.95.69.77.66.69.68.68.69.68.95.65.85.68.73.79.95.55.95.83.84.65.84.69
-- absolute OID	: 1.3.6.1.4.1.7995.2.6.1.1.XX.30.73.78.80.85.84.95.52.95.69.77.66.69.68.68.69.68.95.65.85.68.73.79.95.55.95.83.84.65.84.69
-- Vary			: YES
--
-- Value(s)		: 
--				: 
-- Comments		: 
--
---------------------------------------------------------------------------------------------------
-- Header		: INPUT_4_EMBEDDED_AUDIO_8_STATE
--
-- MIB ref		: swCardEventLogSlotXX       .30.73.78.80.85.84.95.52.95.69.77.66.69.68.68.69.68.95.65.85.68.73.79.95.56.95.83.84.65.84.69
-- absolute OID	: 1.3.6.1.4.1.7995.2.6.1.1.XX.30.73.78.80.85.84.95.52.95.69.77.66.69.68.68.69.68.95.65.85.68.73.79.95.56.95.83.84.65.84.69
-- Vary			: YES
--
-- Value(s)		: 
--				: 
-- Comments		: 
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
-- Vary			: YES
--
-- Value(s)		: WARN:Silent PCM
--				: 
-- Comments		: 
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
-- Vary			: YES
--
-- Value(s)		: WARN:Silent PCM
--				: 
-- Comments		: 
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
-- Vary			: YES
--
-- Value(s)		: WARN:Silent PCM
--				: 
-- Comments		: 
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
-- Vary			: YES
--
-- Value(s)		: WARN:Silent PCM
--				: 
-- Comments		: 
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
-- Vary			: YES
--
-- Value(s)		: WARN:Silent PCM
--				: 
-- Comments		: 
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
-- Vary			: YES
--
-- Value(s)		: WARN:Silent PCM
--				: 
-- Comments		: 
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
-- Vary			: YES
--
-- Value(s)		: OK:Data
--				: 
-- Comments		: 
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
-- Vary			: YES
--
-- Value(s)		: OK:Data
--				: 
-- Comments		: 
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
-- Vary			: YES
--
-- Value(s)		: WARN:Silent PCM
--				: 
-- Comments		: 
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
-- Vary			: YES
--
-- Value(s)		: WARN:Silent PCM
--				: 
-- Comments		: 
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
-- Vary			: YES
--
-- Value(s)		: WARN:Silent PCM
--				: 
-- Comments		: 
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
-- Vary			: YES
--
-- Value(s)		: WARN:Silent PCM
--				: 
-- Comments		: 
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
-- Vary			: YES
--
-- Value(s)		: WARN:Silent PCM
--				: 
-- Comments		: 
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
-- Vary			: YES
--
-- Value(s)		: WARN:Silent PCM
--				: 
-- Comments		: 
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
-- Vary			: YES
--
-- Value(s)		: WARN:Silent PCM
--				: 
-- Comments		: 
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
-- Vary			: YES
--
-- Value(s)		: WARN:Silent PCM
--				: 
-- Comments		: 
--
---------------------------------------------------------------------------------------------------
