-- ************************************************************************************
--        Snell Card:IQSYN20
--        Module Id#:344
--       Command Set:24
--          Filename:SNELL-IQSYN20-CMD-MIB.mib
--       Source File:syncombined.xml
--        Source Ver:10.5.24
--    Logging Source:logsyn20.csv
--            Author:robinbrown
--              Date:14/03/2011
--              Time:15:56
--
-- Copyright (c) 2010 Snell Ltd
-- All rights reserved.
--
-- ************************************************************************************

SNELL-IQSYN20-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQSYN20,
    moduleIQSYN20MIB
        FROM SNELL-WILCOX-PRODUCT-REG;

moduleIQSYN20CmdMi MODULE-IDENTITY
    LAST-UPDATED "1103141556Z"
    ORGANIZATION "Snell Ltd"
    CONTACT-INFO
        "Primary Author:robinbrown

         postal:    Hartman House
                    Danehill
                    Lower Earley,
                    Reading, Berks
                    RG6 4PB
         phone:     +44 (0)118 9866123
         email:     support.uk@snellgroup.com"
    DESCRIPTION
        "This file defines the Snell card, command set translations."
    ::= { moduleIQSYN20MIB 1 }




--********************************************************************************
--*
--*  Snell Card:
--*  command set:
--*  list commands/menus:
--*
--******************************************************************************
    iqsyn20CmdTable OBJECT-TYPE
        SYNTAX          SEQUENCE OF Iqsyn20CmdEntry
        MAX-ACCESS      not-accessible
        STATUS          current
        DESCRIPTION
                "Note the instance of this table is relected in the command set Version"
        ::= { moduleIQSYN20 1 }

    iqsyn20CmdEntry OBJECT-TYPE
        SYNTAX          Iqsyn20CmdEntry
        MAX-ACCESS      not-accessible
        STATUS          current
        DESCRIPTION
                "Entry in command table."
        INDEX   { iqsyn20SlotIndex }
        ::= { iqsyn20CmdTable 1 }

    Iqsyn20CmdEntry ::=
        SEQUENCE {
            iqsyn20SlotIndex
                Unsigned32,
            iqsyn20InputIPSelect
                INTEGER,
            iqsyn20InputIPLoss
                INTEGER,
            iqsyn20InputValidStandardsAllValid
                INTEGER,
            iqsyn20InputValidStandardsAllInvalid
                INTEGER,
            iqsyn20InputValidStandards108023sF
                INTEGER,
            iqsyn20InputValidStandards108023p
                INTEGER,
            iqsyn20InputValidStandards108024sF
                INTEGER,
            iqsyn20InputValidStandards108024p
                INTEGER,
            iqsyn20InputValidStandards108025i
                INTEGER,
            iqsyn20InputValidStandards108025p
                INTEGER,
            iqsyn20InputValidStandards103529i
                INTEGER,
            iqsyn20InputValidStandards108029i
                INTEGER,
            iqsyn20InputValidStandards108029p
                INTEGER,
            iqsyn20InputValidStandards103530i
                INTEGER,
            iqsyn20InputValidStandards108030i
                INTEGER,
            iqsyn20InputValidStandards108030p
                INTEGER,
            iqsyn20InputValidStandards72050p
                INTEGER,
            iqsyn20InputValidStandards72059p
                INTEGER,
            iqsyn20InputValidStandards72060p
                INTEGER,
            iqsyn20InputValidStandards62525i
                INTEGER,
            iqsyn20InputValidStandards52529i
                INTEGER,
            iqsyn20InputAgileVLock
                INTEGER,
            iqsyn20InputErrorsCRCErrs
                RollCallString,
            iqsyn20InputErrorsCRCErrSec
                RollCallString,
            iqsyn20InputErrorsANCErrs
                RollCallString,
            iqsyn20InputErrorsANCErrSec
                RollCallString,
            iqsyn20InputErrorsResetSec
                RollCallString,
            iqsyn20InputErrorsErrorReset
                INTEGER,
            iqsyn20OutputOPStd
                INTEGER,
            iqsyn20OutputVideoProcMasterGain
                INTEGER,
            iqsyn20OutputVideoProcYGain
                INTEGER,
            iqsyn20OutputVideoProcCGain
                INTEGER,
            iqsyn20OutputVideoProcBlackLevel
                INTEGER,
            iqsyn20OutputDefaultOutput
                INTEGER,
            iqsyn20OutputOutputStandard
                INTEGER,
            iqsyn20OutputDefaultOPStd
                INTEGER,
            iqsyn20AudioDelaysRollTrack14
                RollCallString,
            iqsyn20AudioDelaysRollTrack15
                RollCallString,
            iqsyn20AudioDelaysRollTrack16
                RollCallString,
            iqsyn20AudioDelaysRollTrack17
                RollCallString,
            iqsyn20GenlockDelayMode
                INTEGER,
            iqsyn20GenlockRefTimeVerticalTiming
                INTEGER,
            iqsyn20GenlockRefTimeHorizontalTiming
                INTEGER,
            iqsyn20GenlockRefTimeCurrentDelay
                RollCallString,
            iqsyn20GenlockSyncAmplitude
                RollCallString,
            iqsyn20BackupEnable
                INTEGER,
            iqsyn20BackupORInput1State
                RollCallString,
            iqsyn20BackupORInput2State
                RollCallString,
            iqsyn20BackupRevertDelay
                INTEGER,
            iqsyn20BackupPriority
                INTEGER,
            iqsyn20BackupQualifyCRCErr
                INTEGER,
            iqsyn20BackupQualifyANCErr
                INTEGER,
            iqsyn20BackupInput1SelStatInp1OK
                RollCallString,
            iqsyn20BackupInput1SelStatInp2FAIL
                RollCallString,
            iqsyn20BackupInput1SelStatInp2Err
                RollCallString,
            iqsyn20BackupInput1SelStatAUDFail2
                RollCallString,
            iqsyn20BackupInput1SelStatStd2
                RollCallString,
            iqsyn20BackupInput1SelStatGPI1
                RollCallString,
            iqsyn20BackupInput1SelStatGPI2
                RollCallString,
            iqsyn20BackupInput1SelEnblInp1OK
                INTEGER,
            iqsyn20BackupInput1SelEnblInp2FAIL
                INTEGER,
            iqsyn20BackupInput1SelEnblInp2Err
                INTEGER,
            iqsyn20BackupInput1SelEnblAudInp2Err
                INTEGER,
            iqsyn20BackupInput1SelEnblStdInp2
                INTEGER,
            iqsyn20BackupInput1SelEnblGPI1
                INTEGER,
            iqsyn20BackupInput1SelEnblGPI2
                INTEGER,
            iqsyn20BackupInput1SelDlyInp1OK
                INTEGER,
            iqsyn20BackupInput1SelDlyInp2FAIL
                INTEGER,
            iqsyn20BackupInput1SelDlyInp2Err
                INTEGER,
            iqsyn20BackupInput1SelDlyGPI1
                INTEGER,
            iqsyn20BackupInput1SelDlyGPI2
                INTEGER,
            iqsyn20BackupInput1SelDlyAud2FAIL
                INTEGER,
            iqsyn20BackupInput1SelDlyStd2
                INTEGER,
            iqsyn20BackupInput1SelGPI1State
                INTEGER,
            iqsyn20BackupInput1SelGPI2State
                INTEGER,
            iqsyn20BackupInput1SelInp12AudFailG1C1
                INTEGER,
            iqsyn20BackupInput1SelInp12AudFailG1C2
                INTEGER,
            iqsyn20BackupInput1SelInp12AudFailG2C1
                INTEGER,
            iqsyn20BackupInput1SelInp12AudFailG2C2
                INTEGER,
            iqsyn20BackupInput1SelInp12AudFailG3C1
                INTEGER,
            iqsyn20BackupInput1SelInp12AudFailG3C2
                INTEGER,
            iqsyn20BackupInput1SelInp12AudFailG4C1
                INTEGER,
            iqsyn20BackupInput1SelInp12AudFailG4C2
                INTEGER,
            iqsyn20BackupInput1SelInp12AudFailLockGrp
                INTEGER,
            iqsyn20BackupInput1SelSelAll
                INTEGER,
            iqsyn20BackupInput1SelSelNone
                INTEGER,
            iqsyn20BackupInput2SelStatInp2OK
                RollCallString,
            iqsyn20BackupInput2SelStatInp1FAIL
                RollCallString,
            iqsyn20BackupInput2SelStatInp1Err
                RollCallString,
            iqsyn20BackupInput2SelStatAUDFail1
                RollCallString,
            iqsyn20BackupInput2SelStatStd1
                RollCallString,
            iqsyn20BackupInput2SelStatGPI1
                RollCallString,
            iqsyn20BackupInput2SelStatGPI2
                RollCallString,
            iqsyn20BackupInput2SelEnblInp2OK
                INTEGER,
            iqsyn20BackupInput2SelEnblInp1FAIL
                INTEGER,
            iqsyn20BackupInput2SelEnblInp1Err
                INTEGER,
            iqsyn20BackupInput2SelEnblGPI1
                INTEGER,
            iqsyn20BackupInput2SelEnblGPI2
                INTEGER,
            iqsyn20BackupInput2SelEnblAudInp1Err
                INTEGER,
            iqsyn20BackupInput2SelEnblStdInp1
                INTEGER,
            iqsyn20BackupInput2SelDlyInp2OK
                INTEGER,
            iqsyn20BackupInput2SelDlyInp1FAIL
                INTEGER,
            iqsyn20BackupInput2SelDlyInp1Err
                INTEGER,
            iqsyn20BackupInput2SelDlyAud2FAIL
                INTEGER,
            iqsyn20BackupInput2SelDlyStd1
                INTEGER,
            iqsyn20BackupInput2SelDlyGPI1
                INTEGER,
            iqsyn20BackupInput2SelDlyGPI2
                INTEGER,
            iqsyn20BackupInput2SelGPI1State
                INTEGER,
            iqsyn20BackupInput2SelGPI2State
                INTEGER,
            iqsyn20BackupInput2SelInp21AudFailG1C1
                INTEGER,
            iqsyn20BackupInput2SelInp21AudFailG1C2
                INTEGER,
            iqsyn20BackupInput2SelInp21AudFailG2C1
                INTEGER,
            iqsyn20BackupInput2SelInp21AudFailG2C2
                INTEGER,
            iqsyn20BackupInput2SelInp21AudFailG3C1
                INTEGER,
            iqsyn20BackupInput2SelInp21AudFailG3C2
                INTEGER,
            iqsyn20BackupInput2SelInp21AudFailG4C1
                INTEGER,
            iqsyn20BackupInput2SelInp21AudFailG4C2
                INTEGER,
            iqsyn20BackupInput2SelInp21AudFailLockGrp
                INTEGER,
            iqsyn20BackupInput2SelSelAll
                INTEGER,
            iqsyn20BackupInput2SelSelNone
                INTEGER,
            iqsyn20UtilsPatternsPatternEnable
                INTEGER,
            iqsyn20UtilsPatternsScrollPattern
                INTEGER,
            iqsyn20UtilsPatternsPatternType
                INTEGER,
            iqsyn20UtilsANCblankonMismat
                INTEGER,
            iqsyn20UtilsFreezeForceFreeze
                INTEGER,
            iqsyn20UtilsFreezeFreezeType
                INTEGER,
            iqsyn20UtilsMonochrome
                INTEGER,
            iqsyn20UtilsMonochromeMonochromeType
                INTEGER,
            iqsyn20UtilsHANCVBIBlankingANCMode
                INTEGER,
            iqsyn20UtilsHANCVBIBlankingStandard
                INTEGER,
            iqsyn20UtilsHANCVBIBlankingBlankAll
                INTEGER,
            iqsyn20UtilsHANCVBIBlankingPassAll
                INTEGER,
            iqsyn20UtilsHANCVBIBlankingBlank1
                INTEGER,
            iqsyn20UtilsHANCVBIBlankingBlank2
                INTEGER,
            iqsyn20UtilsHANCVBIBlankingBlank3
                INTEGER,
            iqsyn20UtilsHANCVBIBlankingBlank4
                INTEGER,
            iqsyn20UtilsHANCVBIBlankingBlank5
                INTEGER,
            iqsyn20UtilsHANCVBIBlankingBlank6
                INTEGER,
            iqsyn20UtilsHANCVBIBlankingBlank7
                INTEGER,
            iqsyn20UtilsHANCVBIBlankingBlank8
                INTEGER,
            iqsyn20UtilsHANCVBIBlankingBlank9
                INTEGER,
            iqsyn20UtilsHANCVBIBlankingBlank10
                INTEGER,
            iqsyn20UtilsHANCVBIBlankingBlank11
                INTEGER,
            iqsyn20UtilsHANCVBIBlankingBlank12
                INTEGER,
            iqsyn20UtilsHANCVBIBlankingBlank13
                INTEGER,
            iqsyn20UtilsHANCVBIBlankingBlank14
                INTEGER,
            iqsyn20UtilsHANCVBIBlankingBlank15
                INTEGER,
            iqsyn20UtilsHANCVBIBlankingBlank16
                INTEGER,
            iqsyn20UtilsHANCVBIBlankingBlank17
                INTEGER,
            iqsyn20UtilsHANCVBIBlankingBlank18
                INTEGER,
            iqsyn20UtilsHANCVBIBlankingBlank19
                INTEGER,
            iqsyn20UtilsHANCVBIBlankingBlank20
                INTEGER,
            iqsyn20UtilsHANCVBIBlankingBlank21
                INTEGER,
            iqsyn20UtilsHANCVBIBlankingBlank22
                INTEGER,
            iqsyn20UtilsHANCVBIBlankingBlank23
                INTEGER,
            iqsyn20UtilsHANCVBIBlankingBlank24
                INTEGER,
            iqsyn20UtilsHANCVBIBlankingBlank25
                INTEGER,
            iqsyn20UtilsHANCVBIBlankingBlank26
                INTEGER,
            iqsyn20UtilsHANCVBIBlankingBlank27
                INTEGER,
            iqsyn20UtilsHANCVBIBlankingBlank28
                INTEGER,
            iqsyn20UtilsHANCVBIBlankingBlank29
                INTEGER,
            iqsyn20UtilsHANCVBIBlankingBlank30
                INTEGER,
            iqsyn20UtilsHANCVBIBlankingBlank31
                INTEGER,
            iqsyn20UtilsHANCVBIBlankingBlank32
                INTEGER,
            iqsyn20UtilsHANCVBIBlankingBlank33
                INTEGER,
            iqsyn20UtilsHANCVBIBlankingBlank34
                INTEGER,
            iqsyn20UtilsSmpte2016Line2ReadAFD
                RollCallString,
            iqsyn20UtilsSmpte2016Line2ReadAR
                RollCallString,
            iqsyn20UtilsSmpte2016Line2WriteAFD
                RollCallString,
            iqsyn20UtilsSmpte2016Line2WriteAR
                RollCallString,
            iqsyn20GPIGPI1GPIO1Mode
                INTEGER,
            iqsyn20GPIGPI1GPI1ipSelect
                INTEGER,
            iqsyn20GPIGPI1GPO1opSelect
                INTEGER,
            iqsyn20GPIGPI1InvertGPIO1
                INTEGER,
            iqsyn20GPIGPI2GPIO2Mode
                INTEGER,
            iqsyn20GPIGPI2GPI2ipSelect
                INTEGER,
            iqsyn20GPIGPI2GPO2opSelect
                INTEGER,
            iqsyn20GPIGPI2InvertGPIO2
                INTEGER,
            iqsyn20MemoriesRecallMemory
                INTEGER,
            iqsyn20MemoriesSelMemory
                INTEGER,
            iqsyn20MemoriesSaveMemory
                INTEGER,
            iqsyn20MemoriesClearMemory
                INTEGER,
            iqsyn20MemoriesMemoryNameChangeName
                RollCallString,
            iqsyn20MemoriesLastUserMemory
                RollCallString,
            iqsyn20MemoriesMemoryName1
                RollCallString,
            iqsyn20MemoriesMemoryName2
                RollCallString,
            iqsyn20MemoriesMemoryName3
                RollCallString,
            iqsyn20MemoriesMemoryName4
                RollCallString,
            iqsyn20MemoriesMemoryName5
                RollCallString,
            iqsyn20MemoriesMemoryName6
                RollCallString,
            iqsyn20MemoriesMemoryName7
                RollCallString,
            iqsyn20MemoriesMemoryName8
                RollCallString,
            iqsyn20MemoriesMemoryName9
                RollCallString,
            iqsyn20MemoriesMemoryName10
                RollCallString,
            iqsyn20MemoriesMemoryName11
                RollCallString,
            iqsyn20MemoriesMemoryName12
                RollCallString,
            iqsyn20MemoriesMemoryName13
                RollCallString,
            iqsyn20MemoriesMemoryName14
                RollCallString,
            iqsyn20MemoriesMemoryName15
                RollCallString,
            iqsyn20MemoriesMemoryName16
                RollCallString,
            iqsyn20LoggingVideoInputLogInput1Type
                INTEGER,
            iqsyn20LoggingVideoInputInput1Type
                RollCallString,
            iqsyn20LoggingVideoInputLogInput1Status
                INTEGER,
            iqsyn20LoggingVideoInputInput1Status
                RollCallString,
            iqsyn20LoggingVideoInputLogInput1Std
                INTEGER,
            iqsyn20LoggingVideoInputInput1Std
                RollCallString,
            iqsyn20LoggingVideoInputLogInput1Errors
                INTEGER,
            iqsyn20LoggingVideoInputInput1Errors
                RollCallString,
            iqsyn20LoggingVideoInputLogInput1ErrSecs
                INTEGER,
            iqsyn20LoggingVideoInputInput1ErrSecs
                RollCallString,
            iqsyn20LoggingVideoInputLogInput1ANCErr
                INTEGER,
            iqsyn20LoggingVideoInputInput1ANCErrors
                RollCallString,
            iqsyn20LoggingVideoInputLogInput1ANCErrSecs
                INTEGER,
            iqsyn20LoggingVideoInputInput1ANCErrSecs
                RollCallString,
            iqsyn20LoggingVideoInputLogInput2Type
                INTEGER,
            iqsyn20LoggingVideoInputInput2Type
                RollCallString,
            iqsyn20LoggingVideoInputLogInput2Status
                INTEGER,
            iqsyn20LoggingVideoInputInput2Status
                RollCallString,
            iqsyn20LoggingVideoInputLogInput2Std
                INTEGER,
            iqsyn20LoggingVideoInputInput2Std
                RollCallString,
            iqsyn20LoggingVideoInputLogInput2Errors
                INTEGER,
            iqsyn20LoggingVideoInputInput2Errors
                RollCallString,
            iqsyn20LoggingVideoInputLogInput2ErrSecs
                INTEGER,
            iqsyn20LoggingVideoInputInput2ErrSecs
                RollCallString,
            iqsyn20LoggingVideoInputLogInput2ANCErr
                INTEGER,
            iqsyn20LoggingVideoInputInput2ANCErrors
                RollCallString,
            iqsyn20LoggingVideoInputLogInput2ANCErrSecs
                INTEGER,
            iqsyn20LoggingVideoInputInput2ANCErrSecs
                RollCallString,
            iqsyn20LoggingRefOutputLogOutputState
                INTEGER,
            iqsyn20LoggingRefOutputOutputState
                RollCallString,
            iqsyn20LoggingRefOutputLogOutputType
                INTEGER,
            iqsyn20LoggingRefOutputOutputType
                RollCallString,
            iqsyn20LoggingRefOutputLogOutputStandard
                INTEGER,
            iqsyn20LoggingRefOutputOutputStandard
                RollCallString,
            iqsyn20LoggingRefOutputLogOutputSource
                INTEGER,
            iqsyn20LoggingRefOutputOutputSource
                RollCallString,
            iqsyn20LoggingIn1AudStateLogInp1Emb1stat
                INTEGER,
            iqsyn20LoggingIn1AudStateInp1Emb1state
                RollCallString,
            iqsyn20LoggingIn1AudStateLogInp1Emb2stat
                INTEGER,
            iqsyn20LoggingIn1AudStateInp1Emb2state
                RollCallString,
            iqsyn20LoggingIn1AudStateLogInp1Emb3stat
                INTEGER,
            iqsyn20LoggingIn1AudStateInp1Emb3state
                RollCallString,
            iqsyn20LoggingIn1AudStateLogInp1Emb4stat
                INTEGER,
            iqsyn20LoggingIn1AudStateInp1Emb4state
                RollCallString,
            iqsyn20LoggingIn1AudStateLogInp1Emb5stat
                INTEGER,
            iqsyn20LoggingIn1AudStateInp1Emb5state
                RollCallString,
            iqsyn20LoggingIn1AudStateLogInp1Emb6stat
                INTEGER,
            iqsyn20LoggingIn1AudStateInp1Emb6state
                RollCallString,
            iqsyn20LoggingIn1AudStateLogInp1Emb7stat
                INTEGER,
            iqsyn20LoggingIn1AudStateInp1Emb7state
                RollCallString,
            iqsyn20LoggingIn1AudStateLogInp1Emb8stat
                INTEGER,
            iqsyn20LoggingIn1AudStateInp1Emb8state
                RollCallString,
            iqsyn20LoggingIn1AudTypeLogInp1Emb1type
                INTEGER,
            iqsyn20LoggingIn1AudTypeInp1Emb1type
                RollCallString,
            iqsyn20LoggingIn1AudTypeLogInp1Emb2type
                INTEGER,
            iqsyn20LoggingIn1AudTypeInp1Emb2type
                RollCallString,
            iqsyn20LoggingIn1AudTypeLogInp1Emb3type
                INTEGER,
            iqsyn20LoggingIn1AudTypeInp1Emb3type
                RollCallString,
            iqsyn20LoggingIn1AudTypeLogInp1Emb4type
                INTEGER,
            iqsyn20LoggingIn1AudTypeInp1Emb4type
                RollCallString,
            iqsyn20LoggingIn1AudTypeLogInp1Emb5type
                INTEGER,
            iqsyn20LoggingIn1AudTypeInp1Emb5type
                RollCallString,
            iqsyn20LoggingIn1AudTypeLogInp1Emb6type
                INTEGER,
            iqsyn20LoggingIn1AudTypeInp1Emb6type
                RollCallString,
            iqsyn20LoggingIn1AudTypeLogInp1Emb7type
                INTEGER,
            iqsyn20LoggingIn1AudTypeInp1Emb7type
                RollCallString,
            iqsyn20LoggingIn1AudTypeLogInp1Emb8type
                INTEGER,
            iqsyn20LoggingIn1AudTypeInp1Emb8type
                RollCallString,
            iqsyn20LoggingIn2AudStateLogInp2Emb1stat
                INTEGER,
            iqsyn20LoggingIn2AudStateInp2Emb1state
                RollCallString,
            iqsyn20LoggingIn2AudStateLogInp2Emb2stat
                INTEGER,
            iqsyn20LoggingIn2AudStateInp2Emb2state
                RollCallString,
            iqsyn20LoggingIn2AudStateLogInp2Emb3stat
                INTEGER,
            iqsyn20LoggingIn2AudStateInp2Emb3state
                RollCallString,
            iqsyn20LoggingIn2AudStateLogInp2Emb4stat
                INTEGER,
            iqsyn20LoggingIn2AudStateInp2Emb4state
                RollCallString,
            iqsyn20LoggingIn2AudStateLogInp2Emb5stat
                INTEGER,
            iqsyn20LoggingIn2AudStateInp2Emb5state
                RollCallString,
            iqsyn20LoggingIn2AudStateLogInp2Emb6stat
                INTEGER,
            iqsyn20LoggingIn2AudStateInp2Emb6state
                RollCallString,
            iqsyn20LoggingIn2AudStateLogInp2Emb7stat
                INTEGER,
            iqsyn20LoggingIn2AudStateInp2Emb7state
                RollCallString,
            iqsyn20LoggingIn2AudStateLogInp2Emb8stat
                INTEGER,
            iqsyn20LoggingIn2AudStateInp2Emb8state
                RollCallString,
            iqsyn20LoggingIn1AudTypeLogInp2Emb1type
                INTEGER,
            iqsyn20LoggingIn1AudTypeInp2Emb1type
                RollCallString,
            iqsyn20LoggingIn1AudTypeLogInp2Emb2type
                INTEGER,
            iqsyn20LoggingIn1AudTypeInp2Emb2type
                RollCallString,
            iqsyn20LoggingIn1AudTypeLogInp2Emb3type
                INTEGER,
            iqsyn20LoggingIn1AudTypeInp2Emb3type
                RollCallString,
            iqsyn20LoggingIn1AudTypeLogInp2Emb4type
                INTEGER,
            iqsyn20LoggingIn1AudTypeInp2Emb4type
                RollCallString,
            iqsyn20LoggingIn1AudTypeLogInp2Emb5type
                INTEGER,
            iqsyn20LoggingIn1AudTypeInp2Emb5type
                RollCallString,
            iqsyn20LoggingIn1AudTypeLogInp2Emb6type
                INTEGER,
            iqsyn20LoggingIn1AudTypeInp2Emb6type
                RollCallString,
            iqsyn20LoggingIn1AudTypeLogInp2Emb7type
                INTEGER,
            iqsyn20LoggingIn1AudTypeInp2Emb7type
                RollCallString,
            iqsyn20LoggingIn1AudTypeLogInp2Emb8type
                INTEGER,
            iqsyn20LoggingIn1AudTypeInp2Emb8type
                RollCallString,
            iqsyn20LoggingMiscLogSerialNo
                INTEGER,
            iqsyn20LoggingMiscSerialNo
                RollCallString,
            iqsyn20LoggingMiscLogOSVersion
                INTEGER,
            iqsyn20LoggingMiscOSVersion
                RollCallString,
            iqsyn20LoggingMiscLogBuildNo
                INTEGER,
            iqsyn20LoggingMiscBuildNo
                RollCallString,
            iqsyn20LoggingMiscLogHardwareVer
                INTEGER,
            iqsyn20LoggingMiscHardwareVer
                RollCallString,
            iqsyn20LoggingMiscLogFirmwareVer
                INTEGER,
            iqsyn20LoggingMiscFirmwareVer
                RollCallString,
            iqsyn20LoggingMiscLogUpTime
                INTEGER,
            iqsyn20LoggingMiscUpTime
                RollCallString,
            iqsyn20LoggingRefOutputLogReferenceType
                INTEGER,
            iqsyn20LoggingRefOutputReferenceType
                RollCallString,
            iqsyn20LoggingRefOutputLogReferenceState
                INTEGER,
            iqsyn20LoggingRefOutputReferenceState
                RollCallString,
            iqsyn20LoggingRefOutputLogReferenceStand
                INTEGER,
            iqsyn20LoggingRefOutputReferenceStandard
                RollCallString,
            iqsyn20RollCallRollTrackDisableAll
                INTEGER,
            iqsyn20RollCallRollTrackIndex
                INTEGER,
            iqsyn20RollCallRollTrackSource
                INTEGER,
            iqsyn20RollCallRollTrackAddress
                RollCallString,
            iqsyn20RollCallRollTrackCommand
                RollCallString,
            iqsyn20RollCallRollTrackStatus
                RollCallString,
            iqsyn20RollCallRollTrackSending
                RollCallString,
            iqsyn20SetupProduct
                RollCallString,
            iqsyn20SetupRelease
                RollCallString,
            iqsyn20SetupBuild
                RollCallString,
            iqsyn20SetupKOS
                RollCallString,
            iqsyn20SetupSerial
                RollCallString,
            iqsyn20SetupFirmware
                RollCallString,
            iqsyn20SetupPCB
                RollCallString,
            iqsyn20SetupFactoryDefault
                INTEGER,
            iqsyn20SetupRestart
                INTEGER,
            iqsyn20MemoriesMemorySave
                INTEGER,
            iqsyn20SetupDisplay
                INTEGER,
            iqsyn20SetupSerialNumber
                RollCallString,
            iqsyn20SetupBoardID
                INTEGER,
            iqsyn20SetupSaveID
                INTEGER,
            iqsyn20EngineerPassword
                RollCallString,
            iqsyn20EngineerShowEngineer
                INTEGER,
            iqsyn20EngineerPageUndoChanges
                INTEGER,
            iqsyn20EngineerShowEngineer2
                INTEGER,
            iqsyn20EngineerShowEngineer3
                INTEGER
        }

    iqsyn20SlotIndex OBJECT-TYPE
        SYNTAX            Unsigned32
        MAX-ACCESS        not-accessible
        STATUS            current
        DESCRIPTION
                "The unique Index value for each slot.  Its value
                ranges between 1 and the value of slotNumber."
        ::= { iqsyn20CmdEntry 99999 }


    iqsyn20InputIPSelect OBJECT-TYPE
        SYNTAX            INTEGER {
                            valInput1(1),
                            valInput2(2),
                            valInputAnalog(2)
                            }
        MAX-ACCESS        read-write
        STATUS            current
        DESCRIPTION
                "CMNT: - Select video input
                 TYPE: - RadiobuttonList
                 PAGE: - Input
                    I/P Select  cmdID= 32930
                    Input 1  value= 1
                    Input 2  value= 2
                    Input Analog  value= 2  "
        ::= { iqsyn20CmdEntry 32930 }


    iqsyn20InputIPLoss OBJECT-TYPE
        SYNTAX            INTEGER {
                            valNoInput(0),
                            valInOutStdMismatch(1)
                            }
        MAX-ACCESS        read-write
        STATUS            current
        DESCRIPTION
                "CMNT: - Input loss on standard mismatch enable
                 TYPE: - RadiobuttonList
                 PAGE: - Input
                    I/P Loss  cmdID= 33030
                    No Input  value= 0
                    In/Out Std.Mismatch  value= 1  "
        ::= { iqsyn20CmdEntry 33030 }


    iqsyn20InputValidStandardsAllValid OBJECT-TYPE
        SYNTAX            INTEGER { noAction(0),valAllValid(1) }
        MAX-ACCESS        read-write
        STATUS            current
        DESCRIPTION
                "CMNT: - All input standards valid
                 TYPE: - Button
                 PAGE: - Input
                    All Valid  cmdID= 32900
                    value= 1  "
        ::= { iqsyn20CmdEntry 32900 }


    iqsyn20InputValidStandardsAllInvalid OBJECT-TYPE
        SYNTAX            INTEGER { noAction(0),valAllInvalid(1) }
        MAX-ACCESS        read-write
        STATUS            current
        DESCRIPTION
                "CMNT: - NO input standards valid
                 TYPE: - Button
                 PAGE: - Input
                    AllInvalid  cmdID= 32901
                    value= 1  "
        ::= { iqsyn20CmdEntry 32901 }


    iqsyn20InputValidStandards108023sF OBJECT-TYPE
        SYNTAX            INTEGER { disable(0), enable(1)  }
        MAX-ACCESS        read-write
        STATUS            current
        DESCRIPTION
                "CMNT: - Select valid input standards
                 TYPE: - Checkbox
                 PAGE: - Input
                    1080/23sF  cmdID= 32916  "
        ::= { iqsyn20CmdEntry 32916 }


    iqsyn20InputValidStandards108023p OBJECT-TYPE
        SYNTAX            INTEGER { disable(0), enable(1)  }
        MAX-ACCESS        read-write
        STATUS            current
        DESCRIPTION
                "CMNT: - Select valid input standards
                 TYPE: - Checkbox
                 PAGE: - Input
                    1080/23p  cmdID= 32915  "
        ::= { iqsyn20CmdEntry 32915 }


    iqsyn20InputValidStandards108024sF OBJECT-TYPE
        SYNTAX            INTEGER { disable(0), enable(1)  }
        MAX-ACCESS        read-write
        STATUS            current
        DESCRIPTION
                "CMNT: - Select valid input standards
                 TYPE: - Checkbox
                 PAGE: - Input
                    1080/24sF  cmdID= 32917  "
        ::= { iqsyn20CmdEntry 32917 }


    iqsyn20InputValidStandards108024p OBJECT-TYPE
        SYNTAX            INTEGER { disable(0), enable(1)  }
        MAX-ACCESS        read-write
        STATUS            current
        DESCRIPTION
                "CMNT: - Select valid input standards
                 TYPE: - Checkbox
                 PAGE: - Input
                    1080/24p  cmdID= 32914  "
        ::= { iqsyn20CmdEntry 32914 }


    iqsyn20InputValidStandards108025i OBJECT-TYPE
        SYNTAX            INTEGER { disable(0), enable(1)  }
        MAX-ACCESS        read-write
        STATUS            current
        DESCRIPTION
                "CMNT: - Select valid input standards
                 TYPE: - Checkbox
                 PAGE: - Input
                    1080/25i  cmdID= 32910  "
        ::= { iqsyn20CmdEntry 32910 }


    iqsyn20InputValidStandards108025p OBJECT-TYPE
        SYNTAX            INTEGER { disable(0), enable(1)  }
        MAX-ACCESS        read-write
        STATUS            current
        DESCRIPTION
                "CMNT: - Select valid input standards
                 TYPE: - Checkbox
                 PAGE: - Input
                    1080/25p  cmdID= 32911  "
        ::= { iqsyn20CmdEntry 32911 }


    iqsyn20InputValidStandards103529i OBJECT-TYPE
        SYNTAX            INTEGER { disable(0), enable(1)  }
        MAX-ACCESS        read-write
        STATUS            current
        DESCRIPTION
                "CMNT: - Select valid input standards
                 TYPE: - Checkbox
                 PAGE: - Input
                    1035/29i  cmdID= 32921  "
        ::= { iqsyn20CmdEntry 32921 }


    iqsyn20InputValidStandards108029i OBJECT-TYPE
        SYNTAX            INTEGER { disable(0), enable(1)  }
        MAX-ACCESS        read-write
        STATUS            current
        DESCRIPTION
                "CMNT: - Select valid input standards
                 TYPE: - Checkbox
                 PAGE: - Input
                    1080/29i  cmdID= 32919  "
        ::= { iqsyn20CmdEntry 32919 }


    iqsyn20InputValidStandards108029p OBJECT-TYPE
        SYNTAX            INTEGER { disable(0), enable(1)  }
        MAX-ACCESS        read-write
        STATUS            current
        DESCRIPTION
                "CMNT: - Select valid input standards
                 TYPE: - Checkbox
                 PAGE: - Input
                    1080/29p  cmdID= 32918  "
        ::= { iqsyn20CmdEntry 32918 }


    iqsyn20InputValidStandards103530i OBJECT-TYPE
        SYNTAX            INTEGER { disable(0), enable(1)  }
        MAX-ACCESS        read-write
        STATUS            current
        DESCRIPTION
                "CMNT: - Select valid input standards
                 TYPE: - Checkbox
                 PAGE: - Input
                    1035/30i  cmdID= 32920  "
        ::= { iqsyn20CmdEntry 32920 }


    iqsyn20InputValidStandards108030i OBJECT-TYPE
        SYNTAX            INTEGER { disable(0), enable(1)  }
        MAX-ACCESS        read-write
        STATUS            current
        DESCRIPTION
                "CMNT: - Select valid input standards
                 TYPE: - Checkbox
                 PAGE: - Input
                    1080/30i  cmdID= 32912  "
        ::= { iqsyn20CmdEntry 32912 }


    iqsyn20InputValidStandards108030p OBJECT-TYPE
        SYNTAX            INTEGER { disable(0), enable(1)  }
        MAX-ACCESS        read-write
        STATUS            current
        DESCRIPTION
                "CMNT: - Select valid input standards
                 TYPE: - Checkbox
                 PAGE: - Input
                    1080/30p  cmdID= 32913  "
        ::= { iqsyn20CmdEntry 32913 }


    iqsyn20InputValidStandards72050p OBJECT-TYPE
        SYNTAX            INTEGER { disable(0), enable(1)  }
        MAX-ACCESS        read-write
        STATUS            current
        DESCRIPTION
                "CMNT: - Select valid input standards
                 TYPE: - Checkbox
                 PAGE: - Input
                    720/50p  cmdID= 32922  "
        ::= { iqsyn20CmdEntry 32922 }


    iqsyn20InputValidStandards72059p OBJECT-TYPE
        SYNTAX            INTEGER { disable(0), enable(1)  }
        MAX-ACCESS        read-write
        STATUS            current
        DESCRIPTION
                "CMNT: - Select valid input standards
                 TYPE: - Checkbox
                 PAGE: - Input
                    720/59p  cmdID= 32924  "
        ::= { iqsyn20CmdEntry 32924 }


    iqsyn20InputValidStandards72060p OBJECT-TYPE
        SYNTAX            INTEGER { disable(0), enable(1)  }
        MAX-ACCESS        read-write
        STATUS            current
        DESCRIPTION
                "CMNT: - Select valid input standards
                 TYPE: - Checkbox
                 PAGE: - Input
                    720/60p  cmdID= 32923  "
        ::= { iqsyn20CmdEntry 32923 }


    iqsyn20InputValidStandards62525i OBJECT-TYPE
        SYNTAX            INTEGER { disable(0), enable(1)  }
        MAX-ACCESS        read-write
        STATUS            current
        DESCRIPTION
                "CMNT: - Select valid input standards
                 TYPE: - Checkbox
                 PAGE: - Input
                    625/25i  cmdID= 32925  "
        ::= { iqsyn20CmdEntry 32925 }


    iqsyn20InputValidStandards52529i OBJECT-TYPE
        SYNTAX            INTEGER { disable(0), enable(1)  }
        MAX-ACCESS        read-write
        STATUS            current
        DESCRIPTION
                "CMNT: - Select valid input standards
                 TYPE: - Checkbox
                 PAGE: - Input
                    525/29i  cmdID= 32926  "
        ::= { iqsyn20CmdEntry 32926 }


    iqsyn20InputAgileVLock OBJECT-TYPE
        SYNTAX            INTEGER { disable(0), enable(1)  }
        MAX-ACCESS        read-write
        STATUS            current
        DESCRIPTION
                "CMNT: - Select Agile V-Lock for an input
                 TYPE: - Checkbox
                 PAGE: - Input
                    Agile V-Lock  cmdID= 32932  "
        ::= { iqsyn20CmdEntry 32932 }


    iqsyn20InputErrorsCRCErrs OBJECT-TYPE
        SYNTAX            RollCallString
        MAX-ACCESS        read-only
        STATUS            current
        DESCRIPTION
                "CMNT: - 
                 TYPE: - Display
                 PAGE: - Input
                    CRC Errs  cmdID= 33050  "
        ::= { iqsyn20CmdEntry 33050 }


    iqsyn20InputErrorsCRCErrSec OBJECT-TYPE
        SYNTAX            RollCallString
        MAX-ACCESS        read-only
        STATUS            current
        DESCRIPTION
                "CMNT: - 
                 TYPE: - Display
                 PAGE: - Input
                    CRC ErrSec  cmdID= 33051  "
        ::= { iqsyn20CmdEntry 33051 }


    iqsyn20InputErrorsANCErrs OBJECT-TYPE
        SYNTAX            RollCallString
        MAX-ACCESS        read-only
        STATUS            current
        DESCRIPTION
                "CMNT: - 
                 TYPE: - Display
                 PAGE: - Input
                    ANC Errs  cmdID= 33053  "
        ::= { iqsyn20CmdEntry 33053 }


    iqsyn20InputErrorsANCErrSec OBJECT-TYPE
        SYNTAX            RollCallString
        MAX-ACCESS        read-only
        STATUS            current
        DESCRIPTION
                "CMNT: - 
                 TYPE: - Display
                 PAGE: - Input
                    ANC ErrSec  cmdID= 33054  "
        ::= { iqsyn20CmdEntry 33054 }


    iqsyn20InputErrorsResetSec OBJECT-TYPE
        SYNTAX            RollCallString
        MAX-ACCESS        read-only
        STATUS            current
        DESCRIPTION
                "CMNT: - 
                 TYPE: - Display
                 PAGE: - Input
                    ResetSec  cmdID= 33055  "
        ::= { iqsyn20CmdEntry 33055 }


    iqsyn20InputErrorsErrorReset OBJECT-TYPE
        SYNTAX            INTEGER { noAction(0),valErrorReset(1) }
        MAX-ACCESS        read-write
        STATUS            current
        DESCRIPTION
                "CMNT: - 
                 TYPE: - Button
                 PAGE: - Input
                    Error Reset  cmdID= 33052
                    value= 1  "
        ::= { iqsyn20CmdEntry 33052 }


    iqsyn20OutputOPStd OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select output standard
                 TYPE: - RadiobuttonList
                 PAGE: - Output
                    O/P Std.  cmdID= 33010
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn20CmdEntry 33010 }


    iqsyn20OutputVideoProcMasterGain OBJECT-TYPE
        SYNTAX            INTEGER
        MAX-ACCESS        read-write
        STATUS            current
        DESCRIPTION
                "CMNT: - Video Master Gain
                 TYPE: - Number
                 PAGE: - Output
                    Master Gain  cmdID= 33000
                    min= -600  max= 600  step= 10  format= %0.1f dB  div_scale= 100  preset= 0
                    Min = -6.0 dB  Max = 6.0 dB  Step = 0.1 dB  Preset = 0.0 dB  "
        ::= { iqsyn20CmdEntry 33000 }


    iqsyn20OutputVideoProcYGain OBJECT-TYPE
        SYNTAX            INTEGER
        MAX-ACCESS        read-write
        STATUS            current
        DESCRIPTION
                "CMNT: - Video Luminance gain
                 TYPE: - Number
                 PAGE: - Output
                    Y Gain  cmdID= 33001
                    min= -600  max= 600  step= 10  format= %0.1f dB  div_scale= 100  preset= 0
                    Min = -6.0 dB  Max = 6.0 dB  Step = 0.1 dB  Preset = 0.0 dB  "
        ::= { iqsyn20CmdEntry 33001 }


    iqsyn20OutputVideoProcCGain OBJECT-TYPE
        SYNTAX            INTEGER
        MAX-ACCESS        read-write
        STATUS            current
        DESCRIPTION
                "CMNT: - Video CbCr Gain
                 TYPE: - Number
                 PAGE: - Output
                    C Gain  cmdID= 33003
                    min= -600  max= 600  step= 10  format= %0.1f dB  div_scale= 100  preset= 0
                    Min = -6.0 dB  Max = 6.0 dB  Step = 0.1 dB  Preset = 0.0 dB  "
        ::= { iqsyn20CmdEntry 33003 }


    iqsyn20OutputVideoProcBlackLevel OBJECT-TYPE
        SYNTAX            INTEGER
        MAX-ACCESS        read-write
        STATUS            current
        DESCRIPTION
                "CMNT: - Video Black Level
                 TYPE: - Number
                 PAGE: - Output
                    Black Level  cmdID= 33002
                    min= -200  max= 200  step= 1  format= %0.0f mV  div_scale= 1  preset= 0
                    Min = -200 mV  Max = 200 mV  Step = 1 mV  Preset = 0 mV  "
        ::= { iqsyn20CmdEntry 33002 }


    iqsyn20OutputDefaultOutput OBJECT-TYPE
        SYNTAX            INTEGER {
                            valFreezeFrame(1),
                            valFreezeField(5),
                            valBlack(2),
                            valInput(3),
                            valOutPattern(4)
                            }
        MAX-ACCESS        read-write
        STATUS            current
        DESCRIPTION
                "CMNT: - What to do on input loss
                 TYPE: - RadiobuttonList
                 PAGE: - Output
                    Default Output  cmdID= 33031
                    Freeze Frame  value= 1
                    Freeze Field  value= 5
                    Black  value= 2
                    Input  value= 3
                    Out Pattern  value= 4  "
        ::= { iqsyn20CmdEntry 33031 }


    iqsyn20OutputOutputStandard OBJECT-TYPE
        SYNTAX            INTEGER {
                            valManualSelection(0),
                            valFollowsInputStd(1),
                            valFollowsRefStd(2)
                            }
        MAX-ACCESS        read-write
        STATUS            current
        DESCRIPTION
                "CMNT: - Output follows std: Man/Input/Ext.Reference
                 TYPE: - RadiobuttonList
                 PAGE: - Output
                    Output Standard  cmdID= 33011
                    Manual Selection  value= 0
                    Follows Input Std.  value= 1
                    Follows Ref. Std.  value= 2  "
        ::= { iqsyn20CmdEntry 33011 }


    iqsyn20OutputDefaultOPStd OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - 
                 TYPE: - RadiobuttonList
                 PAGE: - Output
                    Default O/P Std.  cmdID= 33012
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn20CmdEntry 33012 }


    iqsyn20AudioDelaysRollTrack14 OBJECT-TYPE
        SYNTAX            RollCallString
        MAX-ACCESS        read-only
        STATUS            current
        DESCRIPTION
                "CMNT: - Rolltrack input command for delays
                 TYPE: - Display
                 PAGE: - Audio
                    RollTrack14  cmdID= 14  "
        ::= { iqsyn20CmdEntry 14 }


    iqsyn20AudioDelaysRollTrack15 OBJECT-TYPE
        SYNTAX            RollCallString
        MAX-ACCESS        read-only
        STATUS            current
        DESCRIPTION
                "CMNT: - Rolltrack input command for delays
                 TYPE: - Display
                 PAGE: - Audio
                    RollTrack15  cmdID= 15  "
        ::= { iqsyn20CmdEntry 15 }


    iqsyn20AudioDelaysRollTrack16 OBJECT-TYPE
        SYNTAX            RollCallString
        MAX-ACCESS        read-only
        STATUS            current
        DESCRIPTION
                "CMNT: - Rolltrack input command for delays
                 TYPE: - Display
                 PAGE: - Audio
                    RollTrack16  cmdID= 16  "
        ::= { iqsyn20CmdEntry 16 }


    iqsyn20AudioDelaysRollTrack17 OBJECT-TYPE
        SYNTAX            RollCallString
        MAX-ACCESS        read-only
        STATUS            current
        DESCRIPTION
                "CMNT: - Rolltrack input command for delays
                 TYPE: - Display
                 PAGE: - Audio
                    RollTrack17  cmdID= 17  "
        ::= { iqsyn20CmdEntry 17 }


    iqsyn20GenlockDelayMode OBJECT-TYPE
        SYNTAX            INTEGER {
                            valFreeRun(0),
                            valLocktoReference(1),
                            valManualHV(5)
                            }
        MAX-ACCESS        read-write
        STATUS            current
        DESCRIPTION
                "CMNT: - Video Reference Mode source: Free Run/LockRef/LockRef(Delay Mismatch)/Minimum/Frames/Manual/Manual ms
                 TYPE: - RadiobuttonList
                 PAGE: - Genlock
                    Delay Mode  cmdID= 33026
                    Free Run  value= 0
                    Lock to Reference  value= 1
                    Manual H/V  value= 5  "
        ::= { iqsyn20CmdEntry 33026 }


    iqsyn20GenlockRefTimeVerticalTiming OBJECT-TYPE
        SYNTAX            INTEGER
        MAX-ACCESS        read-write
        STATUS            current
        DESCRIPTION
                "CMNT: - Reference vertical timing
                 TYPE: - Number
                 PAGE: - Genlock
                    Vertical Timing  cmdID= 33022
                    min= -1500  max= 1500  step= 1  format= %0.0f lines  div_scale= 1  preset= 0
                    Min = -1500 lines  Max = 1500 lines  Step = 1 lines  Preset = 0 lines  "
        ::= { iqsyn20CmdEntry 33022 }


    iqsyn20GenlockRefTimeHorizontalTiming OBJECT-TYPE
        SYNTAX            INTEGER
        MAX-ACCESS        read-write
        STATUS            current
        DESCRIPTION
                "CMNT: - Reference horizontal timing
                 TYPE: - Number
                 PAGE: - Genlock
                    Horizontal Timing  cmdID= 33021
                    min= -3000  max= 3000  step= 1  format= %0.0f pixels  div_scale= 1  preset= 0
                    Min = -3000 pixels  Max = 3000 pixels  Step = 1 pixels  Preset = 0 pixels  "
        ::= { iqsyn20CmdEntry 33021 }


    iqsyn20GenlockRefTimeCurrentDelay OBJECT-TYPE
        SYNTAX            RollCallString
        MAX-ACCESS        read-only
        STATUS            current
        DESCRIPTION
                "CMNT: - 
                 TYPE: - Display
                 PAGE: - Genlock
                    Internal Delay  cmdID= 33025  "
        ::= { iqsyn20CmdEntry 33025 }


    iqsyn20GenlockSyncAmplitude OBJECT-TYPE
        SYNTAX            RollCallString
        MAX-ACCESS        read-only
        STATUS            current
        DESCRIPTION
                "CMNT: - External reference amplitude
                 TYPE: - Display
                 PAGE: - Genlock
                    Sync Amplitude  cmdID= 33023  "
        ::= { iqsyn20CmdEntry 33023 }


    iqsyn20BackupEnable OBJECT-TYPE
        SYNTAX            INTEGER { disable(0), enable(1)  }
        MAX-ACCESS        read-write
        STATUS            current
        DESCRIPTION
                "CMNT: - Input Backup Enable
                 TYPE: - Checkbox
                 PAGE: - Backup
                    Backup Enable  cmdID= 39100  "
        ::= { iqsyn20CmdEntry 39100 }


    iqsyn20BackupORInput1State OBJECT-TYPE
        SYNTAX            RollCallString
        MAX-ACCESS        read-only
        STATUS            current
        DESCRIPTION
                "CMNT: - Input 1 OR State
                 TYPE: - Display
                 PAGE: - Backup
                    OR Input1 State  cmdID= 39101  "
        ::= { iqsyn20CmdEntry 39101 }


    iqsyn20BackupORInput2State OBJECT-TYPE
        SYNTAX            RollCallString
        MAX-ACCESS        read-only
        STATUS            current
        DESCRIPTION
                "CMNT: - Input 2 OR State
                 TYPE: - Display
                 PAGE: - Backup
                    OR Input2 State  cmdID= 39102  "
        ::= { iqsyn20CmdEntry 39102 }


    iqsyn20BackupRevertDelay OBJECT-TYPE
        SYNTAX            INTEGER
        MAX-ACCESS        read-write
        STATUS            current
        DESCRIPTION
                "CMNT: - Backup Reversion Delay
                 TYPE: - Number
                 PAGE: - Backup
                    Revert Delay  cmdID= 39141
                    min= 0  max= 1000  step= 10  format= %0.0f s  div_scale= 10  preset= 0
                    Min = 0 s  Max = 100 s  Step = 1 s  Preset = 0 s  "
        ::= { iqsyn20CmdEntry 39141 }


    iqsyn20BackupPriority OBJECT-TYPE
        SYNTAX            INTEGER {
                            valNone(0),
                            valPriority1(1),
                            valPriority2(2)
                            }
        MAX-ACCESS        read-write
        STATUS            current
        DESCRIPTION
                "CMNT: - Input Backup Priority
                 TYPE: - RadiobuttonList
                 PAGE: - Backup
                    Priority  cmdID= 39103
                    None  value= 0
                    Priority 1  value= 1
                    Priority 2  value= 2  "
        ::= { iqsyn20CmdEntry 39103 }


    iqsyn20BackupQualifyCRCErr OBJECT-TYPE
        SYNTAX            INTEGER { disable(0), enable(1)  }
        MAX-ACCESS        read-write
        STATUS            current
        DESCRIPTION
                "CMNT: - Backup CRC Error
                 TYPE: - Checkbox
                 PAGE: - Backup
                    Qualify CRC Err  cmdID= 39105  "
        ::= { iqsyn20CmdEntry 39105 }


    iqsyn20BackupQualifyANCErr OBJECT-TYPE
        SYNTAX            INTEGER { disable(0), enable(1)  }
        MAX-ACCESS        read-write
        STATUS            current
        DESCRIPTION
                "CMNT: - Backup ANC Error
                 TYPE: - Checkbox
                 PAGE: - Backup
                    Qualify ANC Err  cmdID= 39106  "
        ::= { iqsyn20CmdEntry 39106 }


    iqsyn20BackupInput1SelStatInp1OK OBJECT-TYPE
        SYNTAX            RollCallString
        MAX-ACCESS        read-only
        STATUS            current
        DESCRIPTION
                "CMNT: - Backup Sel 1 Inp 1 OK Status
                 TYPE: - Display
                 PAGE: - Backup
                    Stat Inp1 OK  cmdID= 39127  "
        ::= { iqsyn20CmdEntry 39127 }


    iqsyn20BackupInput1SelStatInp2FAIL OBJECT-TYPE
        SYNTAX            RollCallString
        MAX-ACCESS        read-only
        STATUS            current
        DESCRIPTION
                "CMNT: - Backup Sel 1 Inp 2 FAIL Status
                 TYPE: - Display
                 PAGE: - Backup
                    Stat Inp2 FAIL  cmdID= 39128  "
        ::= { iqsyn20CmdEntry 39128 }


    iqsyn20BackupInput1SelStatInp2Err OBJECT-TYPE
        SYNTAX            RollCallString
        MAX-ACCESS        read-only
        STATUS            current
        DESCRIPTION
                "CMNT: - Backup Sel 1 Inp 2 ERR Status
                 TYPE: - Display
                 PAGE: - Backup
                    Stat Inp2 Err  cmdID= 39139  "
        ::= { iqsyn20CmdEntry 39139 }


    iqsyn20BackupInput1SelStatAUDFail2 OBJECT-TYPE
        SYNTAX            RollCallString
        MAX-ACCESS        read-only
        STATUS            current
        DESCRIPTION
                "CMNT: - Backup Reversion Delay
                 TYPE: - Display
                 PAGE: - Backup
                    Stat AUD Fail 2  cmdID= 39144  "
        ::= { iqsyn20CmdEntry 39144 }


    iqsyn20BackupInput1SelStatStd2 OBJECT-TYPE
        SYNTAX            RollCallString
        MAX-ACCESS        read-only
        STATUS            current
        DESCRIPTION
                "CMNT: - Backup Inp2 1 Aud Fail G4C2
                 TYPE: - Display
                 PAGE: - Backup
                    Stat Std 2  cmdID= 39172  "
        ::= { iqsyn20CmdEntry 39172 }


    iqsyn20BackupInput1SelStatGPI1 OBJECT-TYPE
        SYNTAX            RollCallString
        MAX-ACCESS        read-only
        STATUS            current
        DESCRIPTION
                "CMNT: - Backup Sel 1 GPI 1 Status
                 TYPE: - Display
                 PAGE: - Backup
                    Stat GPI 1  cmdID= 39129  "
        ::= { iqsyn20CmdEntry 39129 }


    iqsyn20BackupInput1SelStatGPI2 OBJECT-TYPE
        SYNTAX            RollCallString
        MAX-ACCESS        read-only
        STATUS            current
        DESCRIPTION
                "CMNT: - Backup Sel 1 GPI 2 Status
                 TYPE: - Display
                 PAGE: - Backup
                    Stat GPI 2  cmdID= 39130  "
        ::= { iqsyn20CmdEntry 39130 }


    iqsyn20BackupInput1SelEnblInp1OK OBJECT-TYPE
        SYNTAX            INTEGER { disable(0), enable(1)  }
        MAX-ACCESS        read-write
        STATUS            current
        DESCRIPTION
                "CMNT: - Backup Sel 1 Inp 1 OK
                 TYPE: - Checkbox
                 PAGE: - Backup
                    Enbl Inp1 OK  cmdID= 39107  "
        ::= { iqsyn20CmdEntry 39107 }


    iqsyn20BackupInput1SelEnblInp2FAIL OBJECT-TYPE
        SYNTAX            INTEGER { disable(0), enable(1)  }
        MAX-ACCESS        read-write
        STATUS            current
        DESCRIPTION
                "CMNT: - Backup Sel 1 Inp 2 FAIL
                 TYPE: - Checkbox
                 PAGE: - Backup
                    Enbl Inp2 FAIL  cmdID= 39108  "
        ::= { iqsyn20CmdEntry 39108 }


    iqsyn20BackupInput1SelEnblInp2Err OBJECT-TYPE
        SYNTAX            INTEGER { disable(0), enable(1)  }
        MAX-ACCESS        read-write
        STATUS            current
        DESCRIPTION
                "CMNT: - Backup Sel 1 Inp 2 ERR
                 TYPE: - Checkbox
                 PAGE: - Backup
                    Enbl Inp2 Err  cmdID= 39135  "
        ::= { iqsyn20CmdEntry 39135 }


    iqsyn20BackupInput1SelEnblAudInp2Err OBJECT-TYPE
        SYNTAX            INTEGER { disable(0), enable(1)  }
        MAX-ACCESS        read-write
        STATUS            current
        DESCRIPTION
                "CMNT: - Backup Inp1 2 Aud Fail Enable
                 TYPE: - Checkbox
                 PAGE: - Backup
                    Enbl Aud Inp2 Err  cmdID= 39143  "
        ::= { iqsyn20CmdEntry 39143 }


    iqsyn20BackupInput1SelEnblStdInp2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Enbl Std Inp 2  cmdID= 39171  "
        ::= { iqsyn20CmdEntry 39171 }


    iqsyn20BackupInput1SelEnblGPI1 OBJECT-TYPE
        SYNTAX            INTEGER { disable(0), enable(1)  }
        MAX-ACCESS        read-write
        STATUS            current
        DESCRIPTION
                "CMNT: - Backup Sel 1 GPI 1
                 TYPE: - Checkbox
                 PAGE: - Backup
                    Enbl GPI 1  cmdID= 39109  "
        ::= { iqsyn20CmdEntry 39109 }


    iqsyn20BackupInput1SelEnblGPI2 OBJECT-TYPE
        SYNTAX            INTEGER { disable(0), enable(1)  }
        MAX-ACCESS        read-write
        STATUS            current
        DESCRIPTION
                "CMNT: - Backup Sel 1 GPI 2
                 TYPE: - Checkbox
                 PAGE: - Backup
                    Enbl GPI 2  cmdID= 39110  "
        ::= { iqsyn20CmdEntry 39110 }


    iqsyn20BackupInput1SelDlyInp1OK OBJECT-TYPE
        SYNTAX            INTEGER
        MAX-ACCESS        read-write
        STATUS            current
        DESCRIPTION
                "CMNT: - Backup Sel 1 Inp 1 OK Delay
                 TYPE: - Number
                 PAGE: - Backup
                    Dly Inp1 OK  cmdID= 39115
                    min= 10  max= 100  step= 1  format= %0.1f s  div_scale= 10  preset= 10
                    Min = 1.0 s  Max = 10.0 s  Step = 0.1 s  Preset = 1.0 s  "
        ::= { iqsyn20CmdEntry 39115 }


    iqsyn20BackupInput1SelDlyInp2FAIL OBJECT-TYPE
        SYNTAX            INTEGER
        MAX-ACCESS        read-write
        STATUS            current
        DESCRIPTION
                "CMNT: - Backup Sel 1 Inp 2 FAIL Delay
                 TYPE: - Number
                 PAGE: - Backup
                    Dly Inp2 FAIL  cmdID= 39116
                    min= 5  max= 100  step= 1  format= %0.1f s  div_scale= 10  preset= 5
                    Min = 0.5 s  Max = 10.0 s  Step = 0.1 s  Preset = 0.5 s  "
        ::= { iqsyn20CmdEntry 39116 }


    iqsyn20BackupInput1SelDlyInp2Err OBJECT-TYPE
        SYNTAX            INTEGER
        MAX-ACCESS        read-write
        STATUS            current
        DESCRIPTION
                "CMNT: - Backup Sel 1 Inp 2 ERR Delay
                 TYPE: - Number
                 PAGE: - Backup
                    Dly Inp2 Err  cmdID= 39137
                    min= 10  max= 100  step= 10  format= %0.0f s  div_scale= 10  preset= 50
                    Min = 1 s  Max = 10 s  Step = 1 s  Preset = 5 s  "
        ::= { iqsyn20CmdEntry 39137 }


    iqsyn20BackupInput1SelDlyGPI1 OBJECT-TYPE
        SYNTAX            INTEGER
        MAX-ACCESS        read-write
        STATUS            current
        DESCRIPTION
                "CMNT: - Backup Sel 1 GPI 1 Delay
                 TYPE: - Number
                 PAGE: - Backup
                    Dly GPI 1  cmdID= 39117
                    min= 0  max= 100  step= 1  format= %0.1f s  div_scale= 10  preset= 0
                    Min = 0.0 s  Max = 10.0 s  Step = 0.1 s  Preset = 0.0 s  "
        ::= { iqsyn20CmdEntry 39117 }


    iqsyn20BackupInput1SelDlyGPI2 OBJECT-TYPE
        SYNTAX            INTEGER
        MAX-ACCESS        read-write
        STATUS            current
        DESCRIPTION
                "CMNT: - Backup Sel 1 GPI 2 Delay
                 TYPE: - Number
                 PAGE: - Backup
                    Dly GPI 2  cmdID= 39118
                    min= 0  max= 100  step= 1  format= %0.1f s  div_scale= 10  preset= 0
                    Min = 0.0 s  Max = 10.0 s  Step = 0.1 s  Preset = 0.0 s  "
        ::= { iqsyn20CmdEntry 39118 }


    iqsyn20BackupInput1SelDlyAud2FAIL OBJECT-TYPE
        SYNTAX            INTEGER
        MAX-ACCESS        read-write
        STATUS            current
        DESCRIPTION
                "CMNT: - Backup Inp1 2 aud Fail Delay
                 TYPE: - Number
                 PAGE: - Backup
                    Dly Aud2 FAIL  cmdID= 39145
                    min= 10  max= 100  step= 1  format= %0.1f s  div_scale= 10  preset= 10
                    Min = 1.0 s  Max = 10.0 s  Step = 0.1 s  Preset = 1.0 s  "
        ::= { iqsyn20CmdEntry 39145 }


    iqsyn20BackupInput1SelDlyStd2 OBJECT-TYPE
        SYNTAX            INTEGER
        MAX-ACCESS        read-write
        STATUS            current
        DESCRIPTION
                "CMNT: - Backup Inp2 1 Aud Fail G4C2
                 TYPE: - Number
                 PAGE: - Backup
                    Dly Std 2  cmdID= 39173
                    min= 10  max= 100  step= 1  format= %0.1f s  div_scale= 10  preset= 10
                    Min = 1.0 s  Max = 10.0 s  Step = 0.1 s  Preset = 1.0 s  "
        ::= { iqsyn20CmdEntry 39173 }


    iqsyn20BackupInput1SelGPI1State OBJECT-TYPE
        SYNTAX            INTEGER {
                            valHigh(1),
                            valLow(0)
                            }
        MAX-ACCESS        read-write
        STATUS            current
        DESCRIPTION
                "CMNT: - Backup Sel 1 GPI 1 val
                 TYPE: - RadiobuttonList
                 PAGE: - Backup
                    GPI 1 State  cmdID= 39123
                    High  value= 1
                    Low  value= 0  "
        ::= { iqsyn20CmdEntry 39123 }


    iqsyn20BackupInput1SelGPI2State OBJECT-TYPE
        SYNTAX            INTEGER {
                            valHigh(1),
                            valLow(0)
                            }
        MAX-ACCESS        read-write
        STATUS            current
        DESCRIPTION
                "CMNT: - Backup Sel 1 GPI 2 val
                 TYPE: - RadiobuttonList
                 PAGE: - Backup
                    GPI 2 State  cmdID= 39124
                    High  value= 1
                    Low  value= 0  "
        ::= { iqsyn20CmdEntry 39124 }


    iqsyn20BackupInput1SelInp12AudFailG1C1 OBJECT-TYPE
        SYNTAX            INTEGER { disable(0), enable(1)  }
        MAX-ACCESS        read-write
        STATUS            current
        DESCRIPTION
                "CMNT: - Backup Inp1 2 Aud Fail G1C1
                 TYPE: - Checkbox
                 PAGE: - Backup
                    Inp1 2 Aud Fail G1C1  cmdID= 39149  "
        ::= { iqsyn20CmdEntry 39149 }


    iqsyn20BackupInput1SelInp12AudFailG1C2 OBJECT-TYPE
        SYNTAX            INTEGER { disable(0), enable(1)  }
        MAX-ACCESS        read-write
        STATUS            current
        DESCRIPTION
                "CMNT: - Backup Inp1 2 Aud Fail G1C2
                 TYPE: - Checkbox
                 PAGE: - Backup
                    Inp1 2 Aud Fail G1C2  cmdID= 39150  "
        ::= { iqsyn20CmdEntry 39150 }


    iqsyn20BackupInput1SelInp12AudFailG2C1 OBJECT-TYPE
        SYNTAX            INTEGER { disable(0), enable(1)  }
        MAX-ACCESS        read-write
        STATUS            current
        DESCRIPTION
                "CMNT: - Backup Inp1 2 Aud Fail G2C1
                 TYPE: - Checkbox
                 PAGE: - Backup
                    Inp1 2 Aud Fail G2C1  cmdID= 39151  "
        ::= { iqsyn20CmdEntry 39151 }


    iqsyn20BackupInput1SelInp12AudFailG2C2 OBJECT-TYPE
        SYNTAX            INTEGER { disable(0), enable(1)  }
        MAX-ACCESS        read-write
        STATUS            current
        DESCRIPTION
                "CMNT: - Backup Inp1 2 Aud Fail G2C2
                 TYPE: - Checkbox
                 PAGE: - Backup
                    Inp1 2 Aud Fail G2C2  cmdID= 39152  "
        ::= { iqsyn20CmdEntry 39152 }


    iqsyn20BackupInput1SelInp12AudFailG3C1 OBJECT-TYPE
        SYNTAX            INTEGER { disable(0), enable(1)  }
        MAX-ACCESS        read-write
        STATUS            current
        DESCRIPTION
                "CMNT: - Backup Inp1 2 Aud Fail G3C1
                 TYPE: - Checkbox
                 PAGE: - Backup
                    Inp1 2 Aud Fail G3C1  cmdID= 39153  "
        ::= { iqsyn20CmdEntry 39153 }


    iqsyn20BackupInput1SelInp12AudFailG3C2 OBJECT-TYPE
        SYNTAX            INTEGER { disable(0), enable(1)  }
        MAX-ACCESS        read-write
        STATUS            current
        DESCRIPTION
                "CMNT: - Backup Inp1 2 Aud Fail G3C2
                 TYPE: - Checkbox
                 PAGE: - Backup
                    Inp1 2 Aud Fail G3C2  cmdID= 39154  "
        ::= { iqsyn20CmdEntry 39154 }


    iqsyn20BackupInput1SelInp12AudFailG4C1 OBJECT-TYPE
        SYNTAX            INTEGER { disable(0), enable(1)  }
        MAX-ACCESS        read-write
        STATUS            current
        DESCRIPTION
                "CMNT: - Backup Inp1 2 Aud Fail G4C1
                 TYPE: - Checkbox
                 PAGE: - Backup
                    Inp1 2 Aud Fail G4C1  cmdID= 39155  "
        ::= { iqsyn20CmdEntry 39155 }


    iqsyn20BackupInput1SelInp12AudFailG4C2 OBJECT-TYPE
        SYNTAX            INTEGER { disable(0), enable(1)  }
        MAX-ACCESS        read-write
        STATUS            current
        DESCRIPTION
                "CMNT: - Backup Inp1 2 Aud Fail G4C2
                 TYPE: - Checkbox
                 PAGE: - Backup
                    Inp1 2 Aud Fail G4C2  cmdID= 39156  "
        ::= { iqsyn20CmdEntry 39156 }


    iqsyn20BackupInput1SelInp12AudFailLockGrp OBJECT-TYPE
        SYNTAX            INTEGER { disable(0), enable(1)  }
        MAX-ACCESS        read-write
        STATUS            current
        DESCRIPTION
                "CMNT: - Backup Inp1 2 Aud Fail Lock Grp
                 TYPE: - Checkbox
                 PAGE: - Backup
                    Inp1 2 Aud Fail Lock Grp  cmdID= 39148  "
        ::= { iqsyn20CmdEntry 39148 }


    iqsyn20BackupInput1SelSelAll OBJECT-TYPE
        SYNTAX            INTEGER { noAction(0),valSelAll(1) }
        MAX-ACCESS        read-write
        STATUS            current
        DESCRIPTION
                "CMNT: - Backup Inp1 2 Aud Fail Sel All
                 TYPE: - Button
                 PAGE: - Backup
                    Sel All  cmdID= 39146
                    value= 1  "
        ::= { iqsyn20CmdEntry 39146 }


    iqsyn20BackupInput1SelSelNone OBJECT-TYPE
        SYNTAX            INTEGER { noAction(0),valSelNone(1) }
        MAX-ACCESS        read-write
        STATUS            current
        DESCRIPTION
                "CMNT: - Backup Inp1 2 Aud Fail Sel None
                 TYPE: - Button
                 PAGE: - Backup
                    Sel None  cmdID= 39147
                    value= 1  "
        ::= { iqsyn20CmdEntry 39147 }


    iqsyn20BackupInput2SelStatInp2OK OBJECT-TYPE
        SYNTAX            RollCallString
        MAX-ACCESS        read-only
        STATUS            current
        DESCRIPTION
                "CMNT: - Backup Sel 2 Inp 2 OK Status
                 TYPE: - Display
                 PAGE: - Backup
                    Stat Inp2 OK  cmdID= 39131  "
        ::= { iqsyn20CmdEntry 39131 }


    iqsyn20BackupInput2SelStatInp1FAIL OBJECT-TYPE
        SYNTAX            RollCallString
        MAX-ACCESS        read-only
        STATUS            current
        DESCRIPTION
                "CMNT: - Backup Sel 2 Inp 1 FAIL Status
                 TYPE: - Display
                 PAGE: - Backup
                    Stat Inp1 FAIL  cmdID= 39132  "
        ::= { iqsyn20CmdEntry 39132 }


    iqsyn20BackupInput2SelStatInp1Err OBJECT-TYPE
        SYNTAX            RollCallString
        MAX-ACCESS        read-only
        STATUS            current
        DESCRIPTION
                "CMNT: - Backup Sel 2 Inp 1 ERR Status
                 TYPE: - Display
                 PAGE: - Backup
                    Stat Inp1 Err  cmdID= 39140  "
        ::= { iqsyn20CmdEntry 39140 }


    iqsyn20BackupInput2SelStatAUDFail1 OBJECT-TYPE
        SYNTAX            RollCallString
        MAX-ACCESS        read-only
        STATUS            current
        DESCRIPTION
                "CMNT: - Backup Reversion Delay
                 TYPE: - Display
                 PAGE: - Backup
                    Stat AUD Fail 1  cmdID= 39158  "
        ::= { iqsyn20CmdEntry 39158 }


    iqsyn20BackupInput2SelStatStd1 OBJECT-TYPE
        SYNTAX            RollCallString
        MAX-ACCESS        read-only
        STATUS            current
        DESCRIPTION
                "CMNT: - Backup Inp2 1 Aud Fail G4C2
                 TYPE: - Display
                 PAGE: - Backup
                    Stat Std 1  cmdID= 39175  "
        ::= { iqsyn20CmdEntry 39175 }


    iqsyn20BackupInput2SelStatGPI1 OBJECT-TYPE
        SYNTAX            RollCallString
        MAX-ACCESS        read-only
        STATUS            current
        DESCRIPTION
                "CMNT: - Backup Sel 2 GPI 1 Status
                 TYPE: - Display
                 PAGE: - Backup
                    Stat GPI 1  cmdID= 39133  "
        ::= { iqsyn20CmdEntry 39133 }


    iqsyn20BackupInput2SelStatGPI2 OBJECT-TYPE
        SYNTAX            RollCallString
        MAX-ACCESS        read-only
        STATUS            current
        DESCRIPTION
                "CMNT: - Backup Sel 2 GPI 2 Status
                 TYPE: - Display
                 PAGE: - Backup
                    Stat GPI 2  cmdID= 39134  "
        ::= { iqsyn20CmdEntry 39134 }


    iqsyn20BackupInput2SelEnblInp2OK OBJECT-TYPE
        SYNTAX            INTEGER { disable(0), enable(1)  }
        MAX-ACCESS        read-write
        STATUS            current
        DESCRIPTION
                "CMNT: - Backup Sel 2 Inp 2 OK
                 TYPE: - Checkbox
                 PAGE: - Backup
                    Enbl Inp2 OK  cmdID= 39111  "
        ::= { iqsyn20CmdEntry 39111 }


    iqsyn20BackupInput2SelEnblInp1FAIL OBJECT-TYPE
        SYNTAX            INTEGER { disable(0), enable(1)  }
        MAX-ACCESS        read-write
        STATUS            current
        DESCRIPTION
                "CMNT: - Backup Sel 2 Inp 1 FAIL
                 TYPE: - Checkbox
                 PAGE: - Backup
                    Enbl Inp1 FAIL  cmdID= 39112  "
        ::= { iqsyn20CmdEntry 39112 }


    iqsyn20BackupInput2SelEnblInp1Err OBJECT-TYPE
        SYNTAX            INTEGER { disable(0), enable(1)  }
        MAX-ACCESS        read-write
        STATUS            current
        DESCRIPTION
                "CMNT: - Backup Sel 2 Inp 1 ERR
                 TYPE: - Checkbox
                 PAGE: - Backup
                    Enbl Inp1 Err  cmdID= 39136  "
        ::= { iqsyn20CmdEntry 39136 }


    iqsyn20BackupInput2SelEnblGPI1 OBJECT-TYPE
        SYNTAX            INTEGER { disable(0), enable(1)  }
        MAX-ACCESS        read-write
        STATUS            current
        DESCRIPTION
                "CMNT: - Backup Sel 2 GPI 1
                 TYPE: - Checkbox
                 PAGE: - Backup
                    Enbl GPI 1  cmdID= 39113  "
        ::= { iqsyn20CmdEntry 39113 }


    iqsyn20BackupInput2SelEnblGPI2 OBJECT-TYPE
        SYNTAX            INTEGER { disable(0), enable(1)  }
        MAX-ACCESS        read-write
        STATUS            current
        DESCRIPTION
                "CMNT: - Backup Sel 2 GPI 2
                 TYPE: - Checkbox
                 PAGE: - Backup
                    Enbl GPI 2  cmdID= 39114  "
        ::= { iqsyn20CmdEntry 39114 }


    iqsyn20BackupInput2SelEnblAudInp1Err OBJECT-TYPE
        SYNTAX            INTEGER { disable(0), enable(1)  }
        MAX-ACCESS        read-write
        STATUS            current
        DESCRIPTION
                "CMNT: - Backup Inp2 1 Aud Fail Enable
                 TYPE: - Checkbox
                 PAGE: - Backup
                    Enbl Aud Inp1 Err  cmdID= 39157  "
        ::= { iqsyn20CmdEntry 39157 }


    iqsyn20BackupInput2SelEnblStdInp1 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Enbl Std Inp 1  cmdID= 39174  "
        ::= { iqsyn20CmdEntry 39174 }


    iqsyn20BackupInput2SelDlyInp2OK OBJECT-TYPE
        SYNTAX            INTEGER
        MAX-ACCESS        read-write
        STATUS            current
        DESCRIPTION
                "CMNT: - Backup Sel 2 Inp 2 OK Delay
                 TYPE: - Number
                 PAGE: - Backup
                    Dly Inp2 OK  cmdID= 39119
                    min= 10  max= 100  step= 1  format= %0.1f s  div_scale= 10  preset= 10
                    Min = 1.0 s  Max = 10.0 s  Step = 0.1 s  Preset = 1.0 s  "
        ::= { iqsyn20CmdEntry 39119 }


    iqsyn20BackupInput2SelDlyInp1FAIL OBJECT-TYPE
        SYNTAX            INTEGER
        MAX-ACCESS        read-write
        STATUS            current
        DESCRIPTION
                "CMNT: - Backup Sel 2 Inp 1 FAIL Delay
                 TYPE: - Number
                 PAGE: - Backup
                    Dly Inp1 FAIL  cmdID= 39120
                    min= 5  max= 100  step= 1  format= %0.1f s  div_scale= 10  preset= 5
                    Min = 0.5 s  Max = 10.0 s  Step = 0.1 s  Preset = 0.5 s  "
        ::= { iqsyn20CmdEntry 39120 }


    iqsyn20BackupInput2SelDlyInp1Err OBJECT-TYPE
        SYNTAX            INTEGER
        MAX-ACCESS        read-write
        STATUS            current
        DESCRIPTION
                "CMNT: - Backup Sel 2 Inp 1 ERR Delay
                 TYPE: - Number
                 PAGE: - Backup
                    Dly Inp1 Err  cmdID= 39138
                    min= 10  max= 100  step= 10  format= %0.0f s  div_scale= 10  preset= 50
                    Min = 1 s  Max = 10 s  Step = 1 s  Preset = 5 s  "
        ::= { iqsyn20CmdEntry 39138 }


    iqsyn20BackupInput2SelDlyAud2FAIL OBJECT-TYPE
        SYNTAX            INTEGER
        MAX-ACCESS        read-write
        STATUS            current
        DESCRIPTION
                "CMNT: - Backup Inp2 1 Aud Fail Delay
                 TYPE: - Number
                 PAGE: - Backup
                    Dly Aud2 FAIL  cmdID= 39159
                    min= 10  max= 100  step= 1  format= %0.1f s  div_scale= 10  preset= 10
                    Min = 1.0 s  Max = 10.0 s  Step = 0.1 s  Preset = 1.0 s  "
        ::= { iqsyn20CmdEntry 39159 }


    iqsyn20BackupInput2SelDlyStd1 OBJECT-TYPE
        SYNTAX            INTEGER
        MAX-ACCESS        read-write
        STATUS            current
        DESCRIPTION
                "CMNT: - Backup Inp2 1 Aud Fail G4C2
                 TYPE: - Number
                 PAGE: - Backup
                    Dly Std 1  cmdID= 39176
                    min= 10  max= 100  step= 1  format= %0.1f s  div_scale= 10  preset= 10
                    Min = 1.0 s  Max = 10.0 s  Step = 0.1 s  Preset = 1.0 s  "
        ::= { iqsyn20CmdEntry 39176 }


    iqsyn20BackupInput2SelDlyGPI1 OBJECT-TYPE
        SYNTAX            INTEGER
        MAX-ACCESS        read-write
        STATUS            current
        DESCRIPTION
                "CMNT: - Backup Sel 2 GPI 1 Delay
                 TYPE: - Number
                 PAGE: - Backup
                    Dly GPI 1  cmdID= 39121
                    min= 0  max= 100  step= 1  format= %0.1f s  div_scale= 10  preset= 0
                    Min = 0.0 s  Max = 10.0 s  Step = 0.1 s  Preset = 0.0 s  "
        ::= { iqsyn20CmdEntry 39121 }


    iqsyn20BackupInput2SelDlyGPI2 OBJECT-TYPE
        SYNTAX            INTEGER
        MAX-ACCESS        read-write
        STATUS            current
        DESCRIPTION
                "CMNT: - Backup Sel 2 GPI 2 Delay
                 TYPE: - Number
                 PAGE: - Backup
                    Dly GPI 2  cmdID= 39122
                    min= 0  max= 100  step= 1  format= %0.1f s  div_scale= 10  preset= 0
                    Min = 0.0 s  Max = 10.0 s  Step = 0.1 s  Preset = 0.0 s  "
        ::= { iqsyn20CmdEntry 39122 }


    iqsyn20BackupInput2SelGPI1State OBJECT-TYPE
        SYNTAX            INTEGER {
                            valOn(0),
                            valOff(1)
                            }
        MAX-ACCESS        read-write
        STATUS            current
        DESCRIPTION
                "CMNT: - Backup Sel 2 GPI 1 val
                 TYPE: - RadiobuttonList
                 PAGE: - Backup
                    GPI 1 State  cmdID= 39125
                    On  value= 0
                    Off  value= 1  "
        ::= { iqsyn20CmdEntry 39125 }


    iqsyn20BackupInput2SelGPI2State OBJECT-TYPE
        SYNTAX            INTEGER {
                            valOn(0),
                            valOff(1)
                            }
        MAX-ACCESS        read-write
        STATUS            current
        DESCRIPTION
                "CMNT: - Backup Sel 2 GPI 2 val
                 TYPE: - RadiobuttonList
                 PAGE: - Backup
                    GPI 2 State  cmdID= 39126
                    On  value= 0
                    Off  value= 1  "
        ::= { iqsyn20CmdEntry 39126 }


    iqsyn20BackupInput2SelInp21AudFailG1C1 OBJECT-TYPE
        SYNTAX            INTEGER { disable(0), enable(1)  }
        MAX-ACCESS        read-write
        STATUS            current
        DESCRIPTION
                "CMNT: - Backup Inp2 1 Aud Fail G1C1
                 TYPE: - Checkbox
                 PAGE: - Backup
                    Inp2 1 Aud Fail G1C1  cmdID= 39163  "
        ::= { iqsyn20CmdEntry 39163 }


    iqsyn20BackupInput2SelInp21AudFailG1C2 OBJECT-TYPE
        SYNTAX            INTEGER { disable(0), enable(1)  }
        MAX-ACCESS        read-write
        STATUS            current
        DESCRIPTION
                "CMNT: - Backup Inp2 1 Aud Fail G1C2
                 TYPE: - Checkbox
                 PAGE: - Backup
                    Inp2 1 Aud Fail G1C2  cmdID= 39164  "
        ::= { iqsyn20CmdEntry 39164 }


    iqsyn20BackupInput2SelInp21AudFailG2C1 OBJECT-TYPE
        SYNTAX            INTEGER { disable(0), enable(1)  }
        MAX-ACCESS        read-write
        STATUS            current
        DESCRIPTION
                "CMNT: - Backup Inp2 1 Aud Fail G2C1
                 TYPE: - Checkbox
                 PAGE: - Backup
                    Inp2 1 Aud Fail G2C1  cmdID= 39165  "
        ::= { iqsyn20CmdEntry 39165 }


    iqsyn20BackupInput2SelInp21AudFailG2C2 OBJECT-TYPE
        SYNTAX            INTEGER { disable(0), enable(1)  }
        MAX-ACCESS        read-write
        STATUS            current
        DESCRIPTION
                "CMNT: - Backup Inp2 1 Aud Fail G2C2
                 TYPE: - Checkbox
                 PAGE: - Backup
                    Inp2 1 Aud Fail G2C2  cmdID= 39166  "
        ::= { iqsyn20CmdEntry 39166 }


    iqsyn20BackupInput2SelInp21AudFailG3C1 OBJECT-TYPE
        SYNTAX            INTEGER { disable(0), enable(1)  }
        MAX-ACCESS        read-write
        STATUS            current
        DESCRIPTION
                "CMNT: - Backup Inp2 1 Aud Fail G3C1
                 TYPE: - Checkbox
                 PAGE: - Backup
                    Inp2 1 Aud Fail G3C1  cmdID= 39167  "
        ::= { iqsyn20CmdEntry 39167 }


    iqsyn20BackupInput2SelInp21AudFailG3C2 OBJECT-TYPE
        SYNTAX            INTEGER { disable(0), enable(1)  }
        MAX-ACCESS        read-write
        STATUS            current
        DESCRIPTION
                "CMNT: - Backup Inp2 1 Aud Fail G3C2
                 TYPE: - Checkbox
                 PAGE: - Backup
                    Inp2 1 Aud Fail G3C2  cmdID= 39168  "
        ::= { iqsyn20CmdEntry 39168 }


    iqsyn20BackupInput2SelInp21AudFailG4C1 OBJECT-TYPE
        SYNTAX            INTEGER { disable(0), enable(1)  }
        MAX-ACCESS        read-write
        STATUS            current
        DESCRIPTION
                "CMNT: - Backup Inp2 1 Aud Fail G4C1
                 TYPE: - Checkbox
                 PAGE: - Backup
                    Inp2 1 Aud Fail G4C1  cmdID= 39169  "
        ::= { iqsyn20CmdEntry 39169 }


    iqsyn20BackupInput2SelInp21AudFailG4C2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Inp2 1 Aud Fail G4C2  cmdID= 39170  "
        ::= { iqsyn20CmdEntry 39170 }


    iqsyn20BackupInput2SelInp21AudFailLockGrp OBJECT-TYPE
        SYNTAX            INTEGER { disable(0), enable(1)  }
        MAX-ACCESS        read-write
        STATUS            current
        DESCRIPTION
                "CMNT: - Backup Inp2 1 Aud Fail Lock Grp
                 TYPE: - Checkbox
                 PAGE: - Backup
                    Inp2 1 Aud Fail Lock Grp  cmdID= 39162  "
        ::= { iqsyn20CmdEntry 39162 }


    iqsyn20BackupInput2SelSelAll OBJECT-TYPE
        SYNTAX            INTEGER { noAction(0),valSelAll(1) }
        MAX-ACCESS        read-write
        STATUS            current
        DESCRIPTION
                "CMNT: - Backup Inp2 1 Aud Fail Sel All
                 TYPE: - Button
                 PAGE: - Backup
                    Sel All  cmdID= 39160
                    value= 1  "
        ::= { iqsyn20CmdEntry 39160 }


    iqsyn20BackupInput2SelSelNone OBJECT-TYPE
        SYNTAX            INTEGER { noAction(0),valSelNone(1) }
        MAX-ACCESS        read-write
        STATUS            current
        DESCRIPTION
                "CMNT: - Backup Inp2 1 Aud Fail Sel None
                 TYPE: - Button
                 PAGE: - Backup
                    Sel None  cmdID= 39161
                    value= 1  "
        ::= { iqsyn20CmdEntry 39161 }


    iqsyn20UtilsPatternsPatternEnable OBJECT-TYPE
        SYNTAX            INTEGER { disable(0), enable(1)  }
        MAX-ACCESS        read-write
        STATUS            current
        DESCRIPTION
                "CMNT: - TPG pattern enable
                 TYPE: - Checkbox
                 PAGE: - Utils
                    Pattern Enable  cmdID= 33038  "
        ::= { iqsyn20CmdEntry 33038 }


    iqsyn20UtilsPatternsScrollPattern OBJECT-TYPE
        SYNTAX            INTEGER { disable(0), enable(1)  }
        MAX-ACCESS        read-write
        STATUS            current
        DESCRIPTION
                "CMNT: - Scroll test pattern horizontally
                 TYPE: - Checkbox
                 PAGE: - Utils
                    Scroll Pattern  cmdID= 33040  "
        ::= { iqsyn20CmdEntry 33040 }


    iqsyn20UtilsPatternsPatternType OBJECT-TYPE
        SYNTAX            INTEGER {
                            val100ColorBars(1),
                            val75ColorBars(2),
                            valSMPTEBars(3),
                            valTartanBars(4),
                            valPluge(5),
                            valRamp(6),
                            valSweep(7),
                            valPulseBar(8),
                            valBurst(9),
                            valBlack(10)
                            }
        MAX-ACCESS        read-write
        STATUS            current
        DESCRIPTION
                "CMNT: - TPG pattern type
                 TYPE: - RadiobuttonList
                 PAGE: - Utils
                    Pattern Type  cmdID= 33039
                    100% Color Bars  value= 1
                    75% Color Bars  value= 2
                    SMPTE Bars  value= 3
                    Tartan Bars  value= 4
                    Pluge  value= 5
                    Ramp  value= 6
                    Sweep  value= 7
                    Pulse & Bar  value= 8
                    Burst  value= 9
                    Black  value= 10  "
        ::= { iqsyn20CmdEntry 33039 }


    iqsyn20UtilsANCblankonMismat OBJECT-TYPE
        SYNTAX            INTEGER { disable(0), enable(1)  }
        MAX-ACCESS        read-write
        STATUS            current
        DESCRIPTION
                "CMNT: - Blank all ANC if standard mismatch
                 TYPE: - Checkbox
                 PAGE: - Utils
                    ANC blank on Mismatch  cmdID= 33036  "
        ::= { iqsyn20CmdEntry 33036 }


    iqsyn20UtilsFreezeForceFreeze OBJECT-TYPE
        SYNTAX            INTEGER { disable(0), enable(1)  }
        MAX-ACCESS        read-write
        STATUS            current
        DESCRIPTION
                "CMNT: - Freeze output picture
                 TYPE: - Checkbox
                 PAGE: - Utils
                    Force Freeze  cmdID= 33032  "
        ::= { iqsyn20CmdEntry 33032 }


    iqsyn20UtilsFreezeFreezeType OBJECT-TYPE
        SYNTAX            INTEGER {
                            valFrame(0),
                            valField(1)
                            }
        MAX-ACCESS        read-write
        STATUS            current
        DESCRIPTION
                "CMNT: - Type of Frozen output: Frame/Field
                 TYPE: - RadiobuttonList
                 PAGE: - Utils
                    Freeze Type  cmdID= 33033
                    Frame  value= 0
                    Field  value= 1  "
        ::= { iqsyn20CmdEntry 33033 }


    iqsyn20UtilsMonochrome OBJECT-TYPE
        SYNTAX            INTEGER { disable(0), enable(1)  }
        MAX-ACCESS        read-write
        STATUS            current
        DESCRIPTION
                "CMNT: - Monochrome enable
                 TYPE: - Checkbox
                 PAGE: - Utils
                    Monochrome  cmdID= 33034  "
        ::= { iqsyn20CmdEntry 33034 }


    iqsyn20UtilsMonochromeMonochromeType OBJECT-TYPE
        SYNTAX            INTEGER {
                            valYonly(0),
                            valConly(1)
                            }
        MAX-ACCESS        read-write
        STATUS            current
        DESCRIPTION
                "CMNT: - Type of Monochrome output
                 TYPE: - RadiobuttonList
                 PAGE: - Utils
                    Monochrome Type  cmdID= 33035
                    Y only  value= 0
                    C only  value= 1  "
        ::= { iqsyn20CmdEntry 33035 }


    iqsyn20UtilsHANCVBIBlankingANCMode OBJECT-TYPE
        SYNTAX            INTEGER {
                            valPassInputANC(0),
                            valBlankHANC(2),
                            valBlankAllANC(1)
                            }
        MAX-ACCESS        read-write
        STATUS            current
        DESCRIPTION
                "CMNT: - Blank ANC on output (All/HANC/Pass)
                 TYPE: - RadiobuttonList
                 PAGE: - Utils
                    ANC Mode  cmdID= 33037
                    Pass Input ANC  value= 0
                    Blank HANC  value= 2
                    Blank All ANC  value= 1  "
        ::= { iqsyn20CmdEntry 33037 }


    iqsyn20UtilsHANCVBIBlankingStandard OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select std for VBI blank display/set
                 TYPE: - RadiobuttonList
                 PAGE: - Utils
                    Standard  cmdID= 37200
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn20CmdEntry 37200 }


    iqsyn20UtilsHANCVBIBlankingBlankAll OBJECT-TYPE
        SYNTAX            INTEGER { noAction(0),valBlankAll(1) }
        MAX-ACCESS        read-write
        STATUS            current
        DESCRIPTION
                "CMNT: - Blank all valid lines
                 TYPE: - Button
                 PAGE: - Utils
                    Blank All  cmdID= 37201
                    value= 1  "
        ::= { iqsyn20CmdEntry 37201 }


    iqsyn20UtilsHANCVBIBlankingPassAll OBJECT-TYPE
        SYNTAX            INTEGER { noAction(0),valPassAll(1) }
        MAX-ACCESS        read-write
        STATUS            current
        DESCRIPTION
                "CMNT: - Blank no lines
                 TYPE: - Button
                 PAGE: - Utils
                    Pass All  cmdID= 37202
                    value= 1  "
        ::= { iqsyn20CmdEntry 37202 }


    iqsyn20UtilsHANCVBIBlankingBlank1 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 1  cmdID= 37210  "
        ::= { iqsyn20CmdEntry 37210 }


    iqsyn20UtilsHANCVBIBlankingBlank2 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 2  cmdID= 37211  "
        ::= { iqsyn20CmdEntry 37211 }


    iqsyn20UtilsHANCVBIBlankingBlank3 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 3  cmdID= 37212  "
        ::= { iqsyn20CmdEntry 37212 }


    iqsyn20UtilsHANCVBIBlankingBlank4 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 4  cmdID= 37213  "
        ::= { iqsyn20CmdEntry 37213 }


    iqsyn20UtilsHANCVBIBlankingBlank5 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 5  cmdID= 37214  "
        ::= { iqsyn20CmdEntry 37214 }


    iqsyn20UtilsHANCVBIBlankingBlank6 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 6  cmdID= 37215  "
        ::= { iqsyn20CmdEntry 37215 }


    iqsyn20UtilsHANCVBIBlankingBlank7 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 7  cmdID= 37216  "
        ::= { iqsyn20CmdEntry 37216 }


    iqsyn20UtilsHANCVBIBlankingBlank8 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 8  cmdID= 37217  "
        ::= { iqsyn20CmdEntry 37217 }


    iqsyn20UtilsHANCVBIBlankingBlank9 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 9  cmdID= 37218  "
        ::= { iqsyn20CmdEntry 37218 }


    iqsyn20UtilsHANCVBIBlankingBlank10 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 10  cmdID= 37219  "
        ::= { iqsyn20CmdEntry 37219 }


    iqsyn20UtilsHANCVBIBlankingBlank11 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 11  cmdID= 37220  "
        ::= { iqsyn20CmdEntry 37220 }


    iqsyn20UtilsHANCVBIBlankingBlank12 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 12  cmdID= 37221  "
        ::= { iqsyn20CmdEntry 37221 }


    iqsyn20UtilsHANCVBIBlankingBlank13 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 13  cmdID= 37222  "
        ::= { iqsyn20CmdEntry 37222 }


    iqsyn20UtilsHANCVBIBlankingBlank14 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 14  cmdID= 37223  "
        ::= { iqsyn20CmdEntry 37223 }


    iqsyn20UtilsHANCVBIBlankingBlank15 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 15  cmdID= 37224  "
        ::= { iqsyn20CmdEntry 37224 }


    iqsyn20UtilsHANCVBIBlankingBlank16 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 16  cmdID= 37225  "
        ::= { iqsyn20CmdEntry 37225 }


    iqsyn20UtilsHANCVBIBlankingBlank17 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 17  cmdID= 37226  "
        ::= { iqsyn20CmdEntry 37226 }


    iqsyn20UtilsHANCVBIBlankingBlank18 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 18  cmdID= 37227  "
        ::= { iqsyn20CmdEntry 37227 }


    iqsyn20UtilsHANCVBIBlankingBlank19 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 19  cmdID= 37228  "
        ::= { iqsyn20CmdEntry 37228 }


    iqsyn20UtilsHANCVBIBlankingBlank20 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 20  cmdID= 37229  "
        ::= { iqsyn20CmdEntry 37229 }


    iqsyn20UtilsHANCVBIBlankingBlank21 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 21  cmdID= 37230  "
        ::= { iqsyn20CmdEntry 37230 }


    iqsyn20UtilsHANCVBIBlankingBlank22 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 22  cmdID= 37231  "
        ::= { iqsyn20CmdEntry 37231 }


    iqsyn20UtilsHANCVBIBlankingBlank23 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 23  cmdID= 37232  "
        ::= { iqsyn20CmdEntry 37232 }


    iqsyn20UtilsHANCVBIBlankingBlank24 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 24  cmdID= 37233  "
        ::= { iqsyn20CmdEntry 37233 }


    iqsyn20UtilsHANCVBIBlankingBlank25 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 25  cmdID= 37234  "
        ::= { iqsyn20CmdEntry 37234 }


    iqsyn20UtilsHANCVBIBlankingBlank26 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 26  cmdID= 37235  "
        ::= { iqsyn20CmdEntry 37235 }


    iqsyn20UtilsHANCVBIBlankingBlank27 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 27  cmdID= 37236  "
        ::= { iqsyn20CmdEntry 37236 }


    iqsyn20UtilsHANCVBIBlankingBlank28 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 28  cmdID= 37237  "
        ::= { iqsyn20CmdEntry 37237 }


    iqsyn20UtilsHANCVBIBlankingBlank29 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 29  cmdID= 37238  "
        ::= { iqsyn20CmdEntry 37238 }


    iqsyn20UtilsHANCVBIBlankingBlank30 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 30  cmdID= 37239  "
        ::= { iqsyn20CmdEntry 37239 }


    iqsyn20UtilsHANCVBIBlankingBlank31 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 31  cmdID= 37240  "
        ::= { iqsyn20CmdEntry 37240 }


    iqsyn20UtilsHANCVBIBlankingBlank32 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 32  cmdID= 37241  "
        ::= { iqsyn20CmdEntry 37241 }


    iqsyn20UtilsHANCVBIBlankingBlank33 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 33  cmdID= 37242  "
        ::= { iqsyn20CmdEntry 37242 }


    iqsyn20UtilsHANCVBIBlankingBlank34 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 34  cmdID= 37243  "
        ::= { iqsyn20CmdEntry 37243 }


    iqsyn20UtilsSmpte2016Line2ReadAFD OBJECT-TYPE
        SYNTAX            RollCallString
        MAX-ACCESS        read-only
        STATUS            current
        DESCRIPTION
                "CMNT: - SMTPE2016 Reader Line 2 AFD
                 TYPE: - Display
                 PAGE: - Utils
                    Line2 Read AFD  cmdID= 39006  "
        ::= { iqsyn20CmdEntry 39006 }


    iqsyn20UtilsSmpte2016Line2ReadAR OBJECT-TYPE
        SYNTAX            RollCallString
        MAX-ACCESS        read-only
        STATUS            current
        DESCRIPTION
                "CMNT: - SMTPE2016 Reader Line 2 AR
                 TYPE: - Display
                 PAGE: - Utils
                    Line2 Read AR  cmdID= 39007  "
        ::= { iqsyn20CmdEntry 39007 }


    iqsyn20UtilsSmpte2016Line2WriteAFD OBJECT-TYPE
        SYNTAX            RollCallString
        MAX-ACCESS        read-only
        STATUS            current
        DESCRIPTION
                "CMNT: - SMTPE2016 Writer Line 2 AFD
                 TYPE: - Display
                 PAGE: - Utils
                    Line2 Write AFD  cmdID= 39013  "
        ::= { iqsyn20CmdEntry 39013 }


    iqsyn20UtilsSmpte2016Line2WriteAR OBJECT-TYPE
        SYNTAX            RollCallString
        MAX-ACCESS        read-only
        STATUS            current
        DESCRIPTION
                "CMNT: - SMTPE2016 Writer Line 2 AR
                 TYPE: - Display
                 PAGE: - Utils
                    Line2 Write AR  cmdID= 39014  "
        ::= { iqsyn20CmdEntry 39014 }


    iqsyn20GPIGPI1GPIO1Mode OBJECT-TYPE
        SYNTAX            INTEGER {
                            valUnused(0),
                            valInputGPI1(1),
                            valOutputGPO1(2)
                            }
        MAX-ACCESS        read-write
        STATUS            current
        DESCRIPTION
                "CMNT: - GPIO-1 Input/Output
                 TYPE: - RadiobuttonList
                 PAGE: - GPI
                    GPI/O 1 Mode  cmdID= 36120
                    Unused  value= 0
                    Input (GPI1)  value= 1
                    Output (GPO1)  value= 2  "
        ::= { iqsyn20CmdEntry 36120 }


    iqsyn20GPIGPI1GPI1ipSelect OBJECT-TYPE
        SYNTAX            INTEGER {
                            valUnused(-1),
                            valFreeze(0),
                            valPattern(1),
                            valBlack(2),
                            valBlankAncillary(3),
                            valMonoChrmYOnly(4),
                            valMonoChrmCbCrOnly(5),
                            valUseIPRef(6),
                            valUseExtRef(7),
                            valSelectInp1(50),
                            valSelectInp2(51),
                            valSelectInput(8),
                            valSelectBackup(9),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115)
                            }
        MAX-ACCESS        read-write
        STATUS            current
        DESCRIPTION
                "CMNT: - GPI-1 Input action
                 TYPE: - RadiobuttonList
                 PAGE: - GPI
                    GPI 1-i/p Select  cmdID= 36121
                    Unused  value= -1
                    Freeze  value= 0
                    Pattern  value= 1
                    Black  value= 2
                    Blank Ancillary  value= 3
                    MonoChrm Y Only  value= 4
                    MonoChrm CbCr Only  value= 5
                    Use I/P Ref  value= 6
                    Use Ext Ref  value= 7
                    Select Inp 1  value= 50
                    Select Inp 2  value= 51
                    Select Input  value= 8
                    Select Backup  value= 9
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115  "
        ::= { iqsyn20CmdEntry 36121 }


    iqsyn20GPIGPI1GPO1opSelect OBJECT-TYPE
        SYNTAX            INTEGER {
                            valInput1OK(50),
                            valInput2OK(51),
                            valReferenceOK(0),
                            valFreeze(1),
                            valPattern(2),
                            valBlack(3),
                            valMonochrome(4),
                            valInput2Selected(52)
                            }
        MAX-ACCESS        read-write
        STATUS            current
        DESCRIPTION
                "CMNT: - GPI-1 Output action
                 TYPE: - RadiobuttonList
                 PAGE: - GPI
                    GPO 1-o/p Select  cmdID= 36122
                    Input 1 OK  value= 50
                    Input 2 OK  value= 51
                    Reference OK  value= 0
                    Freeze  value= 1
                    Pattern  value= 2
                    Black  value= 3
                    Monochrome  value= 4
                    Input 2 Selected  value= 52  "
        ::= { iqsyn20CmdEntry 36122 }


    iqsyn20GPIGPI1InvertGPIO1 OBJECT-TYPE
        SYNTAX            INTEGER { disable(0), enable(1)  }
        MAX-ACCESS        read-write
        STATUS            current
        DESCRIPTION
                "CMNT: - GPI-1 Port Invert
                 TYPE: - Checkbox
                 PAGE: - GPI
                    Invert GPIO 1  cmdID= 36123  "
        ::= { iqsyn20CmdEntry 36123 }


    iqsyn20GPIGPI2GPIO2Mode OBJECT-TYPE
        SYNTAX            INTEGER {
                            valUnused(0),
                            valInputGPI2(1),
                            valOutputGPO2(2)
                            }
        MAX-ACCESS        read-write
        STATUS            current
        DESCRIPTION
                "CMNT: - GPIO-2 Input/Output
                 TYPE: - RadiobuttonList
                 PAGE: - GPI
                    GPI/O 2 Mode  cmdID= 36130
                    Unused  value= 0
                    Input (GPI2)  value= 1
                    Output (GPO2)  value= 2  "
        ::= { iqsyn20CmdEntry 36130 }


    iqsyn20GPIGPI2GPI2ipSelect OBJECT-TYPE
        SYNTAX            INTEGER {
                            valUnused(-1),
                            valFreeze(0),
                            valPattern(1),
                            valBlack(2),
                            valBlankAncillary(3),
                            valMonoChrmYOnly(4),
                            valMonoChrmCbCrOnly(5),
                            valUseIPRef(6),
                            valUseExtRef(7),
                            valSelectInp1(50),
                            valSelectInp2(51),
                            valSelectInput(8),
                            valSelectBackup(9),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115)
                            }
        MAX-ACCESS        read-write
        STATUS            current
        DESCRIPTION
                "CMNT: - GPI-2 Input action
                 TYPE: - RadiobuttonList
                 PAGE: - GPI
                    GPI 2-i/p Select  cmdID= 36131
                    Unused  value= -1
                    Freeze  value= 0
                    Pattern  value= 1
                    Black  value= 2
                    Blank Ancillary  value= 3
                    MonoChrm Y Only  value= 4
                    MonoChrm CbCr Only  value= 5
                    Use I/P Ref  value= 6
                    Use Ext Ref  value= 7
                    Select Inp 1  value= 50
                    Select Inp 2  value= 51
                    Select Input  value= 8
                    Select Backup  value= 9
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115  "
        ::= { iqsyn20CmdEntry 36131 }


    iqsyn20GPIGPI2GPO2opSelect OBJECT-TYPE
        SYNTAX            INTEGER {
                            valInput1OK(50),
                            valInput2OK(51),
                            valReferenceOK(0),
                            valFreeze(1),
                            valPattern(2),
                            valBlack(3),
                            valMonochrome(4),
                            valInput2Selected(52)
                            }
        MAX-ACCESS        read-write
        STATUS            current
        DESCRIPTION
                "CMNT: - GPI-2 Output action
                 TYPE: - RadiobuttonList
                 PAGE: - GPI
                    GPO 2-o/p Select  cmdID= 36132
                    Input 1 OK  value= 50
                    Input 2 OK  value= 51
                    Reference OK  value= 0
                    Freeze  value= 1
                    Pattern  value= 2
                    Black  value= 3
                    Monochrome  value= 4
                    Input 2 Selected  value= 52  "
        ::= { iqsyn20CmdEntry 36132 }


    iqsyn20GPIGPI2InvertGPIO2 OBJECT-TYPE
        SYNTAX            INTEGER { disable(0), enable(1)  }
        MAX-ACCESS        read-write
        STATUS            current
        DESCRIPTION
                "CMNT: - GPI-2 Port Invert
                 TYPE: - Checkbox
                 PAGE: - GPI
                    Invert GPIO 2  cmdID= 36133  "
        ::= { iqsyn20CmdEntry 36133 }


    iqsyn20MemoriesRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Recall Memory  cmdID= 37100
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqsyn20CmdEntry 37100 }


    iqsyn20MemoriesSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqsyn20CmdEntry 37101 }


    iqsyn20MemoriesSaveMemory OBJECT-TYPE
        SYNTAX            INTEGER { noAction(0),valSaveMemory(1) }
        MAX-ACCESS        read-write
        STATUS            current
        DESCRIPTION
                "CMNT: - 
                 TYPE: - Button
                 PAGE: - Memories
                    Save Memory  cmdID= 37102
                    value= 1  "
        ::= { iqsyn20CmdEntry 37102 }


    iqsyn20MemoriesClearMemory OBJECT-TYPE
        SYNTAX            INTEGER { noAction(0),valClearMemory(1) }
        MAX-ACCESS        read-write
        STATUS            current
        DESCRIPTION
                "CMNT: - Delete User Memory
                 TYPE: - Button
                 PAGE: - Memories
                    Clear Memory  cmdID= 37105
                    value= 1  "
        ::= { iqsyn20CmdEntry 37105 }


    iqsyn20MemoriesMemoryNameChangeName OBJECT-TYPE
        SYNTAX            RollCallString
        MAX-ACCESS        read-write
        STATUS            current
        DESCRIPTION
                "CMNT: - 
                 TYPE: - Editstring
                 PAGE: - Memories
                    Change Name  cmdID= 37103
                    preset= Display Memory"
        ::= { iqsyn20CmdEntry 37103 }


    iqsyn20MemoriesLastUserMemory OBJECT-TYPE
        SYNTAX            RollCallString
        MAX-ACCESS        read-only
        STATUS            current
        DESCRIPTION
                "CMNT: - 
                 TYPE: - Display
                 PAGE: - Memories
                    Last User Memory  cmdID= 37104  "
        ::= { iqsyn20CmdEntry 37104 }


    iqsyn20MemoriesMemoryName1 OBJECT-TYPE
        SYNTAX            RollCallString
        MAX-ACCESS        read-only
        STATUS            current
        DESCRIPTION
                "CMNT: - 
                 TYPE: - Display
                 PAGE: - Memories
                    Memory Name1  cmdID= 37106  "
        ::= { iqsyn20CmdEntry 37106 }


    iqsyn20MemoriesMemoryName2 OBJECT-TYPE
        SYNTAX            RollCallString
        MAX-ACCESS        read-only
        STATUS            current
        DESCRIPTION
                "CMNT: - 
                 TYPE: - Display
                 PAGE: - Memories
                    Memory Name2  cmdID= 37107  "
        ::= { iqsyn20CmdEntry 37107 }


    iqsyn20MemoriesMemoryName3 OBJECT-TYPE
        SYNTAX            RollCallString
        MAX-ACCESS        read-only
        STATUS            current
        DESCRIPTION
                "CMNT: - 
                 TYPE: - Display
                 PAGE: - Memories
                    Memory Name3  cmdID= 37108  "
        ::= { iqsyn20CmdEntry 37108 }


    iqsyn20MemoriesMemoryName4 OBJECT-TYPE
        SYNTAX            RollCallString
        MAX-ACCESS        read-only
        STATUS            current
        DESCRIPTION
                "CMNT: - 
                 TYPE: - Display
                 PAGE: - Memories
                    Memory Name4  cmdID= 37109  "
        ::= { iqsyn20CmdEntry 37109 }


    iqsyn20MemoriesMemoryName5 OBJECT-TYPE
        SYNTAX            RollCallString
        MAX-ACCESS        read-only
        STATUS            current
        DESCRIPTION
                "CMNT: - 
                 TYPE: - Display
                 PAGE: - Memories
                    Memory Name5  cmdID= 37110  "
        ::= { iqsyn20CmdEntry 37110 }


    iqsyn20MemoriesMemoryName6 OBJECT-TYPE
        SYNTAX            RollCallString
        MAX-ACCESS        read-only
        STATUS            current
        DESCRIPTION
                "CMNT: - 
                 TYPE: - Display
                 PAGE: - Memories
                    Memory Name6  cmdID= 37111  "
        ::= { iqsyn20CmdEntry 37111 }


    iqsyn20MemoriesMemoryName7 OBJECT-TYPE
        SYNTAX            RollCallString
        MAX-ACCESS        read-only
        STATUS            current
        DESCRIPTION
                "CMNT: - 
                 TYPE: - Display
                 PAGE: - Memories
                    Memory Name7  cmdID= 37112  "
        ::= { iqsyn20CmdEntry 37112 }


    iqsyn20MemoriesMemoryName8 OBJECT-TYPE
        SYNTAX            RollCallString
        MAX-ACCESS        read-only
        STATUS            current
        DESCRIPTION
                "CMNT: - 
                 TYPE: - Display
                 PAGE: - Memories
                    Memory Name8  cmdID= 37113  "
        ::= { iqsyn20CmdEntry 37113 }


    iqsyn20MemoriesMemoryName9 OBJECT-TYPE
        SYNTAX            RollCallString
        MAX-ACCESS        read-only
        STATUS            current
        DESCRIPTION
                "CMNT: - 
                 TYPE: - Display
                 PAGE: - Memories
                    Memory Name9  cmdID= 37114  "
        ::= { iqsyn20CmdEntry 37114 }


    iqsyn20MemoriesMemoryName10 OBJECT-TYPE
        SYNTAX            RollCallString
        MAX-ACCESS        read-only
        STATUS            current
        DESCRIPTION
                "CMNT: - 
                 TYPE: - Display
                 PAGE: - Memories
                    Memory Name10  cmdID= 37115  "
        ::= { iqsyn20CmdEntry 37115 }


    iqsyn20MemoriesMemoryName11 OBJECT-TYPE
        SYNTAX            RollCallString
        MAX-ACCESS        read-only
        STATUS            current
        DESCRIPTION
                "CMNT: - 
                 TYPE: - Display
                 PAGE: - Memories
                    Memory Name11  cmdID= 37116  "
        ::= { iqsyn20CmdEntry 37116 }


    iqsyn20MemoriesMemoryName12 OBJECT-TYPE
        SYNTAX            RollCallString
        MAX-ACCESS        read-only
        STATUS            current
        DESCRIPTION
                "CMNT: - 
                 TYPE: - Display
                 PAGE: - Memories
                    Memory Name12  cmdID= 37117  "
        ::= { iqsyn20CmdEntry 37117 }


    iqsyn20MemoriesMemoryName13 OBJECT-TYPE
        SYNTAX            RollCallString
        MAX-ACCESS        read-only
        STATUS            current
        DESCRIPTION
                "CMNT: - 
                 TYPE: - Display
                 PAGE: - Memories
                    Memory Name13  cmdID= 37118  "
        ::= { iqsyn20CmdEntry 37118 }


    iqsyn20MemoriesMemoryName14 OBJECT-TYPE
        SYNTAX            RollCallString
        MAX-ACCESS        read-only
        STATUS            current
        DESCRIPTION
                "CMNT: - 
                 TYPE: - Display
                 PAGE: - Memories
                    Memory Name14  cmdID= 37119  "
        ::= { iqsyn20CmdEntry 37119 }


    iqsyn20MemoriesMemoryName15 OBJECT-TYPE
        SYNTAX            RollCallString
        MAX-ACCESS        read-only
        STATUS            current
        DESCRIPTION
                "CMNT: - 
                 TYPE: - Display
                 PAGE: - Memories
                    Memory Name15  cmdID= 37120  "
        ::= { iqsyn20CmdEntry 37120 }


    iqsyn20MemoriesMemoryName16 OBJECT-TYPE
        SYNTAX            RollCallString
        MAX-ACCESS        read-only
        STATUS            current
        DESCRIPTION
                "CMNT: - 
                 TYPE: - Display
                 PAGE: - Memories
                    Memory Name16  cmdID= 37121  "
        ::= { iqsyn20CmdEntry 37121 }


    iqsyn20LoggingVideoInputLogInput1Type OBJECT-TYPE
        SYNTAX            INTEGER { disable(0), enable(1)  }
        MAX-ACCESS        read-write
        STATUS            current
        DESCRIPTION
                "CMNT: - Enable/Disable logging for Input 1 Type
                 TYPE: - Checkbox
                 PAGE: - Logging
                    Log Input 1 Type  cmdID= 35017  "
        ::= { iqsyn20CmdEntry 35017 }


    iqsyn20LoggingVideoInputInput1Type OBJECT-TYPE
        SYNTAX            RollCallString
        MAX-ACCESS        read-only
        STATUS            current
        DESCRIPTION
                "CMNT: - Logging state for Input 1 Type
                 TYPE: - Display
                 PAGE: - Logging
                    Input 1 Type=  cmdID= 36017  "
        ::= { iqsyn20CmdEntry 36017 }


    iqsyn20LoggingVideoInputLogInput1Status OBJECT-TYPE
        SYNTAX            INTEGER { disable(0), enable(1)  }
        MAX-ACCESS        read-write
        STATUS            current
        DESCRIPTION
                "CMNT: - Enable/Disable logging for Input 1 Status
                 TYPE: - Checkbox
                 PAGE: - Logging
                    Log Input 1 Status  cmdID= 35005  "
        ::= { iqsyn20CmdEntry 35005 }


    iqsyn20LoggingVideoInputInput1Status OBJECT-TYPE
        SYNTAX            RollCallString
        MAX-ACCESS        read-only
        STATUS            current
        DESCRIPTION
                "CMNT: - Logging state for Input 1 Status
                 TYPE: - Display
                 PAGE: - Logging
                    Input 1 Status=  cmdID= 36005  "
        ::= { iqsyn20CmdEntry 36005 }


    iqsyn20LoggingVideoInputLogInput1Std OBJECT-TYPE
        SYNTAX            INTEGER { disable(0), enable(1)  }
        MAX-ACCESS        read-write
        STATUS            current
        DESCRIPTION
                "CMNT: - Enable/Disable logging for Input 1 Std.
                 TYPE: - Checkbox
                 PAGE: - Logging
                    Log Input 1 Std.  cmdID= 35016  "
        ::= { iqsyn20CmdEntry 35016 }


    iqsyn20LoggingVideoInputInput1Std OBJECT-TYPE
        SYNTAX            RollCallString
        MAX-ACCESS        read-only
        STATUS            current
        DESCRIPTION
                "CMNT: - Logging state for Input 1 Std.
                 TYPE: - Display
                 PAGE: - Logging
                    Input 1 Std.=  cmdID= 36016  "
        ::= { iqsyn20CmdEntry 36016 }


    iqsyn20LoggingVideoInputLogInput1Errors OBJECT-TYPE
        SYNTAX            INTEGER { disable(0), enable(1)  }
        MAX-ACCESS        read-write
        STATUS            current
        DESCRIPTION
                "CMNT: - Enable/Disable logging for Input 1 Errors
                 TYPE: - Checkbox
                 PAGE: - Logging
                    Log Input 1 Errors  cmdID= 35002  "
        ::= { iqsyn20CmdEntry 35002 }


    iqsyn20LoggingVideoInputInput1Errors OBJECT-TYPE
        SYNTAX            RollCallString
        MAX-ACCESS        read-only
        STATUS            current
        DESCRIPTION
                "CMNT: - Logging state for Input 1 Errors
                 TYPE: - Display
                 PAGE: - Logging
                    Input 1 Errors=  cmdID= 36002  "
        ::= { iqsyn20CmdEntry 36002 }


    iqsyn20LoggingVideoInputLogInput1ErrSecs OBJECT-TYPE
        SYNTAX            INTEGER { disable(0), enable(1)  }
        MAX-ACCESS        read-write
        STATUS            current
        DESCRIPTION
                "CMNT: - Enable/Disable logging for Input 1 ErrSecs
                 TYPE: - Checkbox
                 PAGE: - Logging
                    Log Input 1 ErrSecs  cmdID= 35003  "
        ::= { iqsyn20CmdEntry 35003 }


    iqsyn20LoggingVideoInputInput1ErrSecs OBJECT-TYPE
        SYNTAX            RollCallString
        MAX-ACCESS        read-only
        STATUS            current
        DESCRIPTION
                "CMNT: - Logging state for Input 1 ErrSecs
                 TYPE: - Display
                 PAGE: - Logging
                    Input 1 ErrSecs=  cmdID= 36003  "
        ::= { iqsyn20CmdEntry 36003 }


    iqsyn20LoggingVideoInputLogInput1ANCErr OBJECT-TYPE
        SYNTAX            INTEGER { disable(0), enable(1)  }
        MAX-ACCESS        read-write
        STATUS            current
        DESCRIPTION
                "CMNT: - Enable/Disable logging for Input 1 ANC Errors
                 TYPE: - Checkbox
                 PAGE: - Logging
                    Log Input 1 ANC Errors  cmdID= 35000  "
        ::= { iqsyn20CmdEntry 35000 }


    iqsyn20LoggingVideoInputInput1ANCErrors OBJECT-TYPE
        SYNTAX            RollCallString
        MAX-ACCESS        read-only
        STATUS            current
        DESCRIPTION
                "CMNT: - Logging state for Input 1 ANC Errors
                 TYPE: - Display
                 PAGE: - Logging
                    Input 1 ANC Errors=  cmdID= 36000  "
        ::= { iqsyn20CmdEntry 36000 }


    iqsyn20LoggingVideoInputLogInput1ANCErrSecs OBJECT-TYPE
        SYNTAX            INTEGER { disable(0), enable(1)  }
        MAX-ACCESS        read-write
        STATUS            current
        DESCRIPTION
                "CMNT: - Enable/Disable logging for Input 1 ANC ErrSecs
                 TYPE: - Checkbox
                 PAGE: - Logging
                    Log Input 1 ANC ErrSecs  cmdID= 35001  "
        ::= { iqsyn20CmdEntry 35001 }


    iqsyn20LoggingVideoInputInput1ANCErrSecs OBJECT-TYPE
        SYNTAX            RollCallString
        MAX-ACCESS        read-only
        STATUS            current
        DESCRIPTION
                "CMNT: - Logging state for Input 1 ANC ErrSecs
                 TYPE: - Display
                 PAGE: - Logging
                    Input 1 ANC ErrSecs=  cmdID= 36001  "
        ::= { iqsyn20CmdEntry 36001 }


    iqsyn20LoggingVideoInputLogInput2Type OBJECT-TYPE
        SYNTAX            INTEGER { disable(0), enable(1)  }
        MAX-ACCESS        read-write
        STATUS            current
        DESCRIPTION
                "CMNT: - Enable/Disable logging for Input 2 Type
                 TYPE: - Checkbox
                 PAGE: - Logging
                    Log Input 2 Type  cmdID= 35047  "
        ::= { iqsyn20CmdEntry 35047 }


    iqsyn20LoggingVideoInputInput2Type OBJECT-TYPE
        SYNTAX            RollCallString
        MAX-ACCESS        read-only
        STATUS            current
        DESCRIPTION
                "CMNT: - Logging state for Input 2 Type
                 TYPE: - Display
                 PAGE: - Logging
                    Input 2 Type=  cmdID= 36047  "
        ::= { iqsyn20CmdEntry 36047 }


    iqsyn20LoggingVideoInputLogInput2Status OBJECT-TYPE
        SYNTAX            INTEGER { disable(0), enable(1)  }
        MAX-ACCESS        read-write
        STATUS            current
        DESCRIPTION
                "CMNT: - Enable/Disable logging for Input 2 Status
                 TYPE: - Checkbox
                 PAGE: - Logging
                    Log Input 2 Status  cmdID= 35035  "
        ::= { iqsyn20CmdEntry 35035 }


    iqsyn20LoggingVideoInputInput2Status OBJECT-TYPE
        SYNTAX            RollCallString
        MAX-ACCESS        read-only
        STATUS            current
        DESCRIPTION
                "CMNT: - Logging state for Input 2 Status
                 TYPE: - Display
                 PAGE: - Logging
                    Input 2 Status=  cmdID= 36035  "
        ::= { iqsyn20CmdEntry 36035 }


    iqsyn20LoggingVideoInputLogInput2Std OBJECT-TYPE
        SYNTAX            INTEGER { disable(0), enable(1)  }
        MAX-ACCESS        read-write
        STATUS            current
        DESCRIPTION
                "CMNT: - Enable/Disable logging for Input 2 Std.
                 TYPE: - Checkbox
                 PAGE: - Logging
                    Log Input 2 Std.  cmdID= 35046  "
        ::= { iqsyn20CmdEntry 35046 }


    iqsyn20LoggingVideoInputInput2Std OBJECT-TYPE
        SYNTAX            RollCallString
        MAX-ACCESS        read-only
        STATUS            current
        DESCRIPTION
                "CMNT: - Logging state for Input 2 Std.
                 TYPE: - Display
                 PAGE: - Logging
                    Input 2 Std.=  cmdID= 36046  "
        ::= { iqsyn20CmdEntry 36046 }


    iqsyn20LoggingVideoInputLogInput2Errors OBJECT-TYPE
        SYNTAX            INTEGER { disable(0), enable(1)  }
        MAX-ACCESS        read-write
        STATUS            current
        DESCRIPTION
                "CMNT: - Enable/Disable logging for Input 2 Errors
                 TYPE: - Checkbox
                 PAGE: - Logging
                    Log Input 2 Errors  cmdID= 35032  "
        ::= { iqsyn20CmdEntry 35032 }


    iqsyn20LoggingVideoInputInput2Errors OBJECT-TYPE
        SYNTAX            RollCallString
        MAX-ACCESS        read-only
        STATUS            current
        DESCRIPTION
                "CMNT: - Logging state for Input 2 Errors
                 TYPE: - Display
                 PAGE: - Logging
                    Input 2 Errors=  cmdID= 36032  "
        ::= { iqsyn20CmdEntry 36032 }


    iqsyn20LoggingVideoInputLogInput2ErrSecs OBJECT-TYPE
        SYNTAX            INTEGER { disable(0), enable(1)  }
        MAX-ACCESS        read-write
        STATUS            current
        DESCRIPTION
                "CMNT: - Enable/Disable logging for Input 2 ErrSecs
                 TYPE: - Checkbox
                 PAGE: - Logging
                    Log Input 2 ErrSecs  cmdID= 35033  "
        ::= { iqsyn20CmdEntry 35033 }


    iqsyn20LoggingVideoInputInput2ErrSecs OBJECT-TYPE
        SYNTAX            RollCallString
        MAX-ACCESS        read-only
        STATUS            current
        DESCRIPTION
                "CMNT: - Logging state for Input 2 ErrSecs
                 TYPE: - Display
                 PAGE: - Logging
                    Input 2 ErrSecs=  cmdID= 36033  "
        ::= { iqsyn20CmdEntry 36033 }


    iqsyn20LoggingVideoInputLogInput2ANCErr OBJECT-TYPE
        SYNTAX            INTEGER { disable(0), enable(1)  }
        MAX-ACCESS        read-write
        STATUS            current
        DESCRIPTION
                "CMNT: - Enable/Disable logging for Input 2 ANC Errors
                 TYPE: - Checkbox
                 PAGE: - Logging
                    Log Input 2 ANC Errors  cmdID= 35030  "
        ::= { iqsyn20CmdEntry 35030 }


    iqsyn20LoggingVideoInputInput2ANCErrors OBJECT-TYPE
        SYNTAX            RollCallString
        MAX-ACCESS        read-only
        STATUS            current
        DESCRIPTION
                "CMNT: - Logging state for Input 2 ANC Errors
                 TYPE: - Display
                 PAGE: - Logging
                    Input 2 ANC Errors=  cmdID= 36030  "
        ::= { iqsyn20CmdEntry 36030 }


    iqsyn20LoggingVideoInputLogInput2ANCErrSecs OBJECT-TYPE
        SYNTAX            INTEGER { disable(0), enable(1)  }
        MAX-ACCESS        read-write
        STATUS            current
        DESCRIPTION
                "CMNT: - Enable/Disable logging for Input 2 ANC ErrSecs
                 TYPE: - Checkbox
                 PAGE: - Logging
                    Log Input 2 ANC ErrSecs  cmdID= 35031  "
        ::= { iqsyn20CmdEntry 35031 }


    iqsyn20LoggingVideoInputInput2ANCErrSecs OBJECT-TYPE
        SYNTAX            RollCallString
        MAX-ACCESS        read-only
        STATUS            current
        DESCRIPTION
                "CMNT: - Logging state for Input 2 ANC ErrSecs
                 TYPE: - Display
                 PAGE: - Logging
                    Input 2 ANC ErrSecs=  cmdID= 36031  "
        ::= { iqsyn20CmdEntry 36031 }


    iqsyn20LoggingRefOutputLogOutputState OBJECT-TYPE
        SYNTAX            INTEGER { disable(0), enable(1)  }
        MAX-ACCESS        read-write
        STATUS            current
        DESCRIPTION
                "CMNT: - Enable/Disable logging for Output State
                 TYPE: - Checkbox
                 PAGE: - Logging
                    Log Output State  cmdID= 35941  "
        ::= { iqsyn20CmdEntry 35941 }


    iqsyn20LoggingRefOutputOutputState OBJECT-TYPE
        SYNTAX            RollCallString
        MAX-ACCESS        read-only
        STATUS            current
        DESCRIPTION
                "CMNT: - Logging state for Output State
                 TYPE: - Display
                 PAGE: - Logging
                    Output State=  cmdID= 36941  "
        ::= { iqsyn20CmdEntry 36941 }


    iqsyn20LoggingRefOutputLogOutputType OBJECT-TYPE
        SYNTAX            INTEGER { disable(0), enable(1)  }
        MAX-ACCESS        read-write
        STATUS            current
        DESCRIPTION
                "CMNT: - Enable/Disable logging for Output Type
                 TYPE: - Checkbox
                 PAGE: - Logging
                    Log Output Type  cmdID= 35942  "
        ::= { iqsyn20CmdEntry 35942 }


    iqsyn20LoggingRefOutputOutputType OBJECT-TYPE
        SYNTAX            RollCallString
        MAX-ACCESS        read-only
        STATUS            current
        DESCRIPTION
                "CMNT: - Logging state for Output Type
                 TYPE: - Display
                 PAGE: - Logging
                    Output Type=  cmdID= 36942  "
        ::= { iqsyn20CmdEntry 36942 }


    iqsyn20LoggingRefOutputLogOutputStandard OBJECT-TYPE
        SYNTAX            INTEGER { disable(0), enable(1)  }
        MAX-ACCESS        read-write
        STATUS            current
        DESCRIPTION
                "CMNT: - Enable/Disable logging for Output Standard
                 TYPE: - Checkbox
                 PAGE: - Logging
                    Log Output Standard  cmdID= 35940  "
        ::= { iqsyn20CmdEntry 35940 }


    iqsyn20LoggingRefOutputOutputStandard OBJECT-TYPE
        SYNTAX            RollCallString
        MAX-ACCESS        read-only
        STATUS            current
        DESCRIPTION
                "CMNT: - Logging state for Output Standard
                 TYPE: - Display
                 PAGE: - Logging
                    Output Standard=  cmdID= 36940  "
        ::= { iqsyn20CmdEntry 36940 }


    iqsyn20LoggingRefOutputLogOutputSource OBJECT-TYPE
        SYNTAX            INTEGER { disable(0), enable(1)  }
        MAX-ACCESS        read-write
        STATUS            current
        DESCRIPTION
                "CMNT: - Enable/Disable logging for Output Source
                 TYPE: - Checkbox
                 PAGE: - Logging
                    Log output Source  cmdID= 35943  "
        ::= { iqsyn20CmdEntry 35943 }


    iqsyn20LoggingRefOutputOutputSource OBJECT-TYPE
        SYNTAX            RollCallString
        MAX-ACCESS        read-only
        STATUS            current
        DESCRIPTION
                "CMNT: - Logging state for Output Source
                 TYPE: - Display
                 PAGE: - Logging
                    Output Source=  cmdID= 36943  "
        ::= { iqsyn20CmdEntry 36943 }


    iqsyn20LoggingIn1AudStateLogInp1Emb1stat OBJECT-TYPE
        SYNTAX            INTEGER { disable(0), enable(1)  }
        MAX-ACCESS        read-write
        STATUS            current
        DESCRIPTION
                "CMNT: - Enable/Disable logging for Input 1 Emb.Pair 1 state
                 TYPE: - Checkbox
                 PAGE: - Logging
                    Log Inp1 Emb.1 state  cmdID= 35006  "
        ::= { iqsyn20CmdEntry 35006 }


    iqsyn20LoggingIn1AudStateInp1Emb1state OBJECT-TYPE
        SYNTAX            RollCallString
        MAX-ACCESS        read-only
        STATUS            current
        DESCRIPTION
                "CMNT: - Logging state for Input 1 Emb.Pair 1 state
                 TYPE: - Display
                 PAGE: - Logging
                    Inp1 Emb.1 state=  cmdID= 36006  "
        ::= { iqsyn20CmdEntry 36006 }


    iqsyn20LoggingIn1AudStateLogInp1Emb2stat OBJECT-TYPE
        SYNTAX            INTEGER { disable(0), enable(1)  }
        MAX-ACCESS        read-write
        STATUS            current
        DESCRIPTION
                "CMNT: - Enable/Disable logging for Input 1 Emb.Pair 2 state
                 TYPE: - Checkbox
                 PAGE: - Logging
                    Log Inp1 Emb.2 state  cmdID= 35007  "
        ::= { iqsyn20CmdEntry 35007 }


    iqsyn20LoggingIn1AudStateInp1Emb2state OBJECT-TYPE
        SYNTAX            RollCallString
        MAX-ACCESS        read-only
        STATUS            current
        DESCRIPTION
                "CMNT: - Logging state for Input 1 Emb.Pair 2 state
                 TYPE: - Display
                 PAGE: - Logging
                    Inp1 Emb.2 state=  cmdID= 36007  "
        ::= { iqsyn20CmdEntry 36007 }


    iqsyn20LoggingIn1AudStateLogInp1Emb3stat OBJECT-TYPE
        SYNTAX            INTEGER { disable(0), enable(1)  }
        MAX-ACCESS        read-write
        STATUS            current
        DESCRIPTION
                "CMNT: - Enable/Disable logging for Input 1 Emb.Pair 3 state
                 TYPE: - Checkbox
                 PAGE: - Logging
                    Log Inp1 Emb.3 state  cmdID= 35008  "
        ::= { iqsyn20CmdEntry 35008 }


    iqsyn20LoggingIn1AudStateInp1Emb3state OBJECT-TYPE
        SYNTAX            RollCallString
        MAX-ACCESS        read-only
        STATUS            current
        DESCRIPTION
                "CMNT: - Logging state for Input 1 Emb.Pair 3 state
                 TYPE: - Display
                 PAGE: - Logging
                    Inp1 Emb.3 state=  cmdID= 36008  "
        ::= { iqsyn20CmdEntry 36008 }


    iqsyn20LoggingIn1AudStateLogInp1Emb4stat OBJECT-TYPE
        SYNTAX            INTEGER { disable(0), enable(1)  }
        MAX-ACCESS        read-write
        STATUS            current
        DESCRIPTION
                "CMNT: - Enable/Disable logging for Input 1 Emb.Pair 4 state
                 TYPE: - Checkbox
                 PAGE: - Logging
                    Log Inp1 Emb.4 state  cmdID= 35009  "
        ::= { iqsyn20CmdEntry 35009 }


    iqsyn20LoggingIn1AudStateInp1Emb4state OBJECT-TYPE
        SYNTAX            RollCallString
        MAX-ACCESS        read-only
        STATUS            current
        DESCRIPTION
                "CMNT: - Logging state for Input 1 Emb.Pair 4 state
                 TYPE: - Display
                 PAGE: - Logging
                    Inp1 Emb.4 state=  cmdID= 36009  "
        ::= { iqsyn20CmdEntry 36009 }


    iqsyn20LoggingIn1AudStateLogInp1Emb5stat OBJECT-TYPE
        SYNTAX            INTEGER { disable(0), enable(1)  }
        MAX-ACCESS        read-write
        STATUS            current
        DESCRIPTION
                "CMNT: - Enable/Disable logging for Input 1 Emb.Pair 5 state
                 TYPE: - Checkbox
                 PAGE: - Logging
                    Log Inp1 Emb.5 state  cmdID= 35010  "
        ::= { iqsyn20CmdEntry 35010 }


    iqsyn20LoggingIn1AudStateInp1Emb5state OBJECT-TYPE
        SYNTAX            RollCallString
        MAX-ACCESS        read-only
        STATUS            current
        DESCRIPTION
                "CMNT: - Logging state for Input 1 Emb.Pair 5 state
                 TYPE: - Display
                 PAGE: - Logging
                    Inp1 Emb.5 state=  cmdID= 36010  "
        ::= { iqsyn20CmdEntry 36010 }


    iqsyn20LoggingIn1AudStateLogInp1Emb6stat OBJECT-TYPE
        SYNTAX            INTEGER { disable(0), enable(1)  }
        MAX-ACCESS        read-write
        STATUS            current
        DESCRIPTION
                "CMNT: - Enable/Disable logging for Input 1 Emb.Pair 6 state
                 TYPE: - Checkbox
                 PAGE: - Logging
                    Log Inp1 Emb.6 state  cmdID= 35011  "
        ::= { iqsyn20CmdEntry 35011 }


    iqsyn20LoggingIn1AudStateInp1Emb6state OBJECT-TYPE
        SYNTAX            RollCallString
        MAX-ACCESS        read-only
        STATUS            current
        DESCRIPTION
                "CMNT: - Logging state for Input 1 Emb.Pair 6 state
                 TYPE: - Display
                 PAGE: - Logging
                    Inp1 Emb.6 state=  cmdID= 36011  "
        ::= { iqsyn20CmdEntry 36011 }


    iqsyn20LoggingIn1AudStateLogInp1Emb7stat OBJECT-TYPE
        SYNTAX            INTEGER { disable(0), enable(1)  }
        MAX-ACCESS        read-write
        STATUS            current
        DESCRIPTION
                "CMNT: - Enable/Disable logging for Input 1 Emb.Pair 7 state
                 TYPE: - Checkbox
                 PAGE: - Logging
                    Log Inp1 Emb.7 state  cmdID= 35012  "
        ::= { iqsyn20CmdEntry 35012 }


    iqsyn20LoggingIn1AudStateInp1Emb7state OBJECT-TYPE
        SYNTAX            RollCallString
        MAX-ACCESS        read-only
        STATUS            current
        DESCRIPTION
                "CMNT: - Logging state for Input 1 Emb.Pair 7 state
                 TYPE: - Display
                 PAGE: - Logging
                    Inp1 Emb.7 state=  cmdID= 36012  "
        ::= { iqsyn20CmdEntry 36012 }


    iqsyn20LoggingIn1AudStateLogInp1Emb8stat OBJECT-TYPE
        SYNTAX            INTEGER { disable(0), enable(1)  }
        MAX-ACCESS        read-write
        STATUS            current
        DESCRIPTION
                "CMNT: - Enable/Disable logging for Input 1 Emb.Pair 8 state
                 TYPE: - Checkbox
                 PAGE: - Logging
                    Log Inp1 Emb.8 state  cmdID= 35013  "
        ::= { iqsyn20CmdEntry 35013 }


    iqsyn20LoggingIn1AudStateInp1Emb8state OBJECT-TYPE
        SYNTAX            RollCallString
        MAX-ACCESS        read-only
        STATUS            current
        DESCRIPTION
                "CMNT: - Logging state for Input 1 Emb.Pair 8 state
                 TYPE: - Display
                 PAGE: - Logging
                    Inp1 Emb.8 state=  cmdID= 36013  "
        ::= { iqsyn20CmdEntry 36013 }


    iqsyn20LoggingIn1AudTypeLogInp1Emb1type OBJECT-TYPE
        SYNTAX            INTEGER { disable(0), enable(1)  }
        MAX-ACCESS        read-write
        STATUS            current
        DESCRIPTION
                "CMNT: - Enable/Disable logging for Input 1 Emb.Pair 1 type
                 TYPE: - Checkbox
                 PAGE: - Logging
                    Log Inp1 Emb.1 type  cmdID= 35018  "
        ::= { iqsyn20CmdEntry 35018 }


    iqsyn20LoggingIn1AudTypeInp1Emb1type OBJECT-TYPE
        SYNTAX            RollCallString
        MAX-ACCESS        read-only
        STATUS            current
        DESCRIPTION
                "CMNT: - Logging state for Input 1 Emb.Pair 1 type
                 TYPE: - Display
                 PAGE: - Logging
                    Inp1 Emb.1 type=  cmdID= 36018  "
        ::= { iqsyn20CmdEntry 36018 }


    iqsyn20LoggingIn1AudTypeLogInp1Emb2type OBJECT-TYPE
        SYNTAX            INTEGER { disable(0), enable(1)  }
        MAX-ACCESS        read-write
        STATUS            current
        DESCRIPTION
                "CMNT: - Enable/Disable logging for Input 1 Emb.Pair 2 type
                 TYPE: - Checkbox
                 PAGE: - Logging
                    Log Inp1 Emb.2 type  cmdID= 35019  "
        ::= { iqsyn20CmdEntry 35019 }


    iqsyn20LoggingIn1AudTypeInp1Emb2type OBJECT-TYPE
        SYNTAX            RollCallString
        MAX-ACCESS        read-only
        STATUS            current
        DESCRIPTION
                "CMNT: - Logging state for Input 1 Emb.Pair 2 type
                 TYPE: - Display
                 PAGE: - Logging
                    Inp1 Emb.2 type=  cmdID= 36019  "
        ::= { iqsyn20CmdEntry 36019 }


    iqsyn20LoggingIn1AudTypeLogInp1Emb3type OBJECT-TYPE
        SYNTAX            INTEGER { disable(0), enable(1)  }
        MAX-ACCESS        read-write
        STATUS            current
        DESCRIPTION
                "CMNT: - Enable/Disable logging for Input 1 Emb.Pair 3 type
                 TYPE: - Checkbox
                 PAGE: - Logging
                    Log Inp1 Emb.3 type  cmdID= 35020  "
        ::= { iqsyn20CmdEntry 35020 }


    iqsyn20LoggingIn1AudTypeInp1Emb3type OBJECT-TYPE
        SYNTAX            RollCallString
        MAX-ACCESS        read-only
        STATUS            current
        DESCRIPTION
                "CMNT: - Logging state for Input 1 Emb.Pair 3 type
                 TYPE: - Display
                 PAGE: - Logging
                    Inp1 Emb.3 type=  cmdID= 36020  "
        ::= { iqsyn20CmdEntry 36020 }


    iqsyn20LoggingIn1AudTypeLogInp1Emb4type OBJECT-TYPE
        SYNTAX            INTEGER { disable(0), enable(1)  }
        MAX-ACCESS        read-write
        STATUS            current
        DESCRIPTION
                "CMNT: - Enable/Disable logging for Input 1 Emb.Pair 4 type
                 TYPE: - Checkbox
                 PAGE: - Logging
                    Log Inp1 Emb.4 type  cmdID= 35021  "
        ::= { iqsyn20CmdEntry 35021 }


    iqsyn20LoggingIn1AudTypeInp1Emb4type OBJECT-TYPE
        SYNTAX            RollCallString
        MAX-ACCESS        read-only
        STATUS            current
        DESCRIPTION
                "CMNT: - Logging state for Input 1 Emb.Pair 4 type
                 TYPE: - Display
                 PAGE: - Logging
                    Inp1 Emb.4 type=  cmdID= 36021  "
        ::= { iqsyn20CmdEntry 36021 }


    iqsyn20LoggingIn1AudTypeLogInp1Emb5type OBJECT-TYPE
        SYNTAX            INTEGER { disable(0), enable(1)  }
        MAX-ACCESS        read-write
        STATUS            current
        DESCRIPTION
                "CMNT: - Enable/Disable logging for Input 1 Emb.Pair 4 type
                 TYPE: - Checkbox
                 PAGE: - Logging
                    Log Inp1 Emb.5 type  cmdID= 35022  "
        ::= { iqsyn20CmdEntry 35022 }


    iqsyn20LoggingIn1AudTypeInp1Emb5type OBJECT-TYPE
        SYNTAX            RollCallString
        MAX-ACCESS        read-only
        STATUS            current
        DESCRIPTION
                "CMNT: - Logging state for Input 1 Emb.Pair 5 type
                 TYPE: - Display
                 PAGE: - Logging
                    Inp1 Emb.5 type=  cmdID= 36022  "
        ::= { iqsyn20CmdEntry 36022 }


    iqsyn20LoggingIn1AudTypeLogInp1Emb6type OBJECT-TYPE
        SYNTAX            INTEGER { disable(0), enable(1)  }
        MAX-ACCESS        read-write
        STATUS            current
        DESCRIPTION
                "CMNT: - Enable/Disable logging for Input 1 Emb.Pair 6 type
                 TYPE: - Checkbox
                 PAGE: - Logging
                    Log Inp1 Emb.6 type  cmdID= 35023  "
        ::= { iqsyn20CmdEntry 35023 }


    iqsyn20LoggingIn1AudTypeInp1Emb6type OBJECT-TYPE
        SYNTAX            RollCallString
        MAX-ACCESS        read-only
        STATUS            current
        DESCRIPTION
                "CMNT: - Logging state for Input 1 Emb.Pair 6 type
                 TYPE: - Display
                 PAGE: - Logging
                    Inp1 Emb.6 type=  cmdID= 36023  "
        ::= { iqsyn20CmdEntry 36023 }


    iqsyn20LoggingIn1AudTypeLogInp1Emb7type OBJECT-TYPE
        SYNTAX            INTEGER { disable(0), enable(1)  }
        MAX-ACCESS        read-write
        STATUS            current
        DESCRIPTION
                "CMNT: - Enable/Disable logging for Input 1 Emb.Pair 7 type
                 TYPE: - Checkbox
                 PAGE: - Logging
                    Log Inp1 Emb.7 type  cmdID= 35024  "
        ::= { iqsyn20CmdEntry 35024 }


    iqsyn20LoggingIn1AudTypeInp1Emb7type OBJECT-TYPE
        SYNTAX            RollCallString
        MAX-ACCESS        read-only
        STATUS            current
        DESCRIPTION
                "CMNT: - Logging state for Input 1 Emb.Pair 7 type
                 TYPE: - Display
                 PAGE: - Logging
                    Inp1 Emb.7 type=  cmdID= 36024  "
        ::= { iqsyn20CmdEntry 36024 }


    iqsyn20LoggingIn1AudTypeLogInp1Emb8type OBJECT-TYPE
        SYNTAX            INTEGER { disable(0), enable(1)  }
        MAX-ACCESS        read-write
        STATUS            current
        DESCRIPTION
                "CMNT: - Enable/Disable logging for Input 1 Emb.Pair 8 type
                 TYPE: - Checkbox
                 PAGE: - Logging
                    Log Inp1 Emb.8 type  cmdID= 35025  "
        ::= { iqsyn20CmdEntry 35025 }


    iqsyn20LoggingIn1AudTypeInp1Emb8type OBJECT-TYPE
        SYNTAX            RollCallString
        MAX-ACCESS        read-only
        STATUS            current
        DESCRIPTION
                "CMNT: - Logging state for Input 1 Emb.Pair 8 type
                 TYPE: - Display
                 PAGE: - Logging
                    Inp1 Emb.8 type=  cmdID= 36025  "
        ::= { iqsyn20CmdEntry 36025 }


    iqsyn20LoggingIn2AudStateLogInp2Emb1stat OBJECT-TYPE
        SYNTAX            INTEGER { disable(0), enable(1)  }
        MAX-ACCESS        read-write
        STATUS            current
        DESCRIPTION
                "CMNT: - Enable/Disable logging for Input 2 Emb.Pair 1 state
                 TYPE: - Checkbox
                 PAGE: - Logging
                    Log Inp2 Emb.1 state  cmdID= 35036  "
        ::= { iqsyn20CmdEntry 35036 }


    iqsyn20LoggingIn2AudStateInp2Emb1state OBJECT-TYPE
        SYNTAX            RollCallString
        MAX-ACCESS        read-only
        STATUS            current
        DESCRIPTION
                "CMNT: - Logging state for Input 2 Emb.Pair 1 state
                 TYPE: - Display
                 PAGE: - Logging
                    Inp2 Emb.1 state=  cmdID= 36036  "
        ::= { iqsyn20CmdEntry 36036 }


    iqsyn20LoggingIn2AudStateLogInp2Emb2stat OBJECT-TYPE
        SYNTAX            INTEGER { disable(0), enable(1)  }
        MAX-ACCESS        read-write
        STATUS            current
        DESCRIPTION
                "CMNT: - Enable/Disable logging for Input 2 Emb.Pair 2 state
                 TYPE: - Checkbox
                 PAGE: - Logging
                    Log Inp2 Emb.2 state  cmdID= 35037  "
        ::= { iqsyn20CmdEntry 35037 }


    iqsyn20LoggingIn2AudStateInp2Emb2state OBJECT-TYPE
        SYNTAX            RollCallString
        MAX-ACCESS        read-only
        STATUS            current
        DESCRIPTION
                "CMNT: - Logging state for Input 2 Emb.Pair 2 state
                 TYPE: - Display
                 PAGE: - Logging
                    Inp2 Emb.2 state=  cmdID= 36037  "
        ::= { iqsyn20CmdEntry 36037 }


    iqsyn20LoggingIn2AudStateLogInp2Emb3stat OBJECT-TYPE
        SYNTAX            INTEGER { disable(0), enable(1)  }
        MAX-ACCESS        read-write
        STATUS            current
        DESCRIPTION
                "CMNT: - Enable/Disable logging for Input 2 Emb.Pair 3 state
                 TYPE: - Checkbox
                 PAGE: - Logging
                    Log Inp2 Emb.3 state  cmdID= 35038  "
        ::= { iqsyn20CmdEntry 35038 }


    iqsyn20LoggingIn2AudStateInp2Emb3state OBJECT-TYPE
        SYNTAX            RollCallString
        MAX-ACCESS        read-only
        STATUS            current
        DESCRIPTION
                "CMNT: - Logging state for Input 2 Emb.Pair 3 state
                 TYPE: - Display
                 PAGE: - Logging
                    Inp2 Emb.3 state=  cmdID= 36038  "
        ::= { iqsyn20CmdEntry 36038 }


    iqsyn20LoggingIn2AudStateLogInp2Emb4stat OBJECT-TYPE
        SYNTAX            INTEGER { disable(0), enable(1)  }
        MAX-ACCESS        read-write
        STATUS            current
        DESCRIPTION
                "CMNT: - Enable/Disable logging for Input 2 Emb.Pair 4 state
                 TYPE: - Checkbox
                 PAGE: - Logging
                    Log Inp2 Emb.4 state  cmdID= 35039  "
        ::= { iqsyn20CmdEntry 35039 }


    iqsyn20LoggingIn2AudStateInp2Emb4state OBJECT-TYPE
        SYNTAX            RollCallString
        MAX-ACCESS        read-only
        STATUS            current
        DESCRIPTION
                "CMNT: - Logging state for Input 2 Emb.Pair 4 state
                 TYPE: - Display
                 PAGE: - Logging
                    Inp2 Emb.4 state=  cmdID= 36039  "
        ::= { iqsyn20CmdEntry 36039 }


    iqsyn20LoggingIn2AudStateLogInp2Emb5stat OBJECT-TYPE
        SYNTAX            INTEGER { disable(0), enable(1)  }
        MAX-ACCESS        read-write
        STATUS            current
        DESCRIPTION
                "CMNT: - Enable/Disable logging for Input 2 Emb.Pair 5 state
                 TYPE: - Checkbox
                 PAGE: - Logging
                    Log Inp2 Emb.5 state  cmdID= 35040  "
        ::= { iqsyn20CmdEntry 35040 }


    iqsyn20LoggingIn2AudStateInp2Emb5state OBJECT-TYPE
        SYNTAX            RollCallString
        MAX-ACCESS        read-only
        STATUS            current
        DESCRIPTION
                "CMNT: - Logging state for Input 2 Emb.Pair 5 state
                 TYPE: - Display
                 PAGE: - Logging
                    Inp2 Emb.5 state=  cmdID= 36040  "
        ::= { iqsyn20CmdEntry 36040 }


    iqsyn20LoggingIn2AudStateLogInp2Emb6stat OBJECT-TYPE
        SYNTAX            INTEGER { disable(0), enable(1)  }
        MAX-ACCESS        read-write
        STATUS            current
        DESCRIPTION
                "CMNT: - Enable/Disable logging for Input 2 Emb.Pair 6 state
                 TYPE: - Checkbox
                 PAGE: - Logging
                    Log Inp2 Emb.6 state  cmdID= 35041  "
        ::= { iqsyn20CmdEntry 35041 }


    iqsyn20LoggingIn2AudStateInp2Emb6state OBJECT-TYPE
        SYNTAX            RollCallString
        MAX-ACCESS        read-only
        STATUS            current
        DESCRIPTION
                "CMNT: - Logging state for Input 2 Emb.Pair 6 state
                 TYPE: - Display
                 PAGE: - Logging
                    Inp2 Emb.6 state=  cmdID= 36041  "
        ::= { iqsyn20CmdEntry 36041 }


    iqsyn20LoggingIn2AudStateLogInp2Emb7stat OBJECT-TYPE
        SYNTAX            INTEGER { disable(0), enable(1)  }
        MAX-ACCESS        read-write
        STATUS            current
        DESCRIPTION
                "CMNT: - Enable/Disable logging for Input 2 Emb.Pair 7 state
                 TYPE: - Checkbox
                 PAGE: - Logging
                    Log Inp2 Emb.7 state  cmdID= 35042  "
        ::= { iqsyn20CmdEntry 35042 }


    iqsyn20LoggingIn2AudStateInp2Emb7state OBJECT-TYPE
        SYNTAX            RollCallString
        MAX-ACCESS        read-only
        STATUS            current
        DESCRIPTION
                "CMNT: - Logging state for Input 2 Emb.Pair 7 state
                 TYPE: - Display
                 PAGE: - Logging
                    Inp2 Emb.7 state=  cmdID= 36042  "
        ::= { iqsyn20CmdEntry 36042 }


    iqsyn20LoggingIn2AudStateLogInp2Emb8stat OBJECT-TYPE
        SYNTAX            INTEGER { disable(0), enable(1)  }
        MAX-ACCESS        read-write
        STATUS            current
        DESCRIPTION
                "CMNT: - Enable/Disable logging for Input 2 Emb.Pair 8 state
                 TYPE: - Checkbox
                 PAGE: - Logging
                    Log Inp2 Emb.8 state  cmdID= 35043  "
        ::= { iqsyn20CmdEntry 35043 }


    iqsyn20LoggingIn2AudStateInp2Emb8state OBJECT-TYPE
        SYNTAX            RollCallString
        MAX-ACCESS        read-only
        STATUS            current
        DESCRIPTION
                "CMNT: - Logging state for Input 2 Emb.Pair 8 state
                 TYPE: - Display
                 PAGE: - Logging
                    Inp2 Emb.8 state=  cmdID= 36043  "
        ::= { iqsyn20CmdEntry 36043 }


    iqsyn20LoggingIn1AudTypeLogInp2Emb1type OBJECT-TYPE
        SYNTAX            INTEGER { disable(0), enable(1)  }
        MAX-ACCESS        read-write
        STATUS            current
        DESCRIPTION
                "CMNT: - Enable/Disable logging for Input 2 Emb.Pair 1 type
                 TYPE: - Checkbox
                 PAGE: - Logging
                    Log Inp2 Emb.1 type  cmdID= 35048  "
        ::= { iqsyn20CmdEntry 35048 }


    iqsyn20LoggingIn1AudTypeInp2Emb1type OBJECT-TYPE
        SYNTAX            RollCallString
        MAX-ACCESS        read-only
        STATUS            current
        DESCRIPTION
                "CMNT: - Logging state for Input 2 Emb.Pair 1 type
                 TYPE: - Display
                 PAGE: - Logging
                    Inp2 Emb.1 type=  cmdID= 36048  "
        ::= { iqsyn20CmdEntry 36048 }


    iqsyn20LoggingIn1AudTypeLogInp2Emb2type OBJECT-TYPE
        SYNTAX            INTEGER { disable(0), enable(1)  }
        MAX-ACCESS        read-write
        STATUS            current
        DESCRIPTION
                "CMNT: - Enable/Disable logging for Input 1 Emb.Pair 2 type
                 TYPE: - Checkbox
                 PAGE: - Logging
                    Log Inp2 Emb.2 type  cmdID= 35049  "
        ::= { iqsyn20CmdEntry 35049 }


    iqsyn20LoggingIn1AudTypeInp2Emb2type OBJECT-TYPE
        SYNTAX            RollCallString
        MAX-ACCESS        read-only
        STATUS            current
        DESCRIPTION
                "CMNT: - Logging state for Input 2 Emb.Pair 2 type
                 TYPE: - Display
                 PAGE: - Logging
                    Inp2 Emb.2 type=  cmdID= 36049  "
        ::= { iqsyn20CmdEntry 36049 }


    iqsyn20LoggingIn1AudTypeLogInp2Emb3type OBJECT-TYPE
        SYNTAX            INTEGER { disable(0), enable(1)  }
        MAX-ACCESS        read-write
        STATUS            current
        DESCRIPTION
                "CMNT: - Enable/Disable logging for Input 2 Emb.Pair 3 type
                 TYPE: - Checkbox
                 PAGE: - Logging
                    Log Inp2 Emb.3 type  cmdID= 35050  "
        ::= { iqsyn20CmdEntry 35050 }


    iqsyn20LoggingIn1AudTypeInp2Emb3type OBJECT-TYPE
        SYNTAX            RollCallString
        MAX-ACCESS        read-only
        STATUS            current
        DESCRIPTION
                "CMNT: - Logging state for Input 2 Emb.Pair 3 type
                 TYPE: - Display
                 PAGE: - Logging
                    Inp2 Emb.3 type=  cmdID= 36050  "
        ::= { iqsyn20CmdEntry 36050 }


    iqsyn20LoggingIn1AudTypeLogInp2Emb4type OBJECT-TYPE
        SYNTAX            INTEGER { disable(0), enable(1)  }
        MAX-ACCESS        read-write
        STATUS            current
        DESCRIPTION
                "CMNT: - Enable/Disable logging for Input 2 Emb.Pair 4 type
                 TYPE: - Checkbox
                 PAGE: - Logging
                    Log Inp2 Emb.4 type  cmdID= 35051  "
        ::= { iqsyn20CmdEntry 35051 }


    iqsyn20LoggingIn1AudTypeInp2Emb4type OBJECT-TYPE
        SYNTAX            RollCallString
        MAX-ACCESS        read-only
        STATUS            current
        DESCRIPTION
                "CMNT: - Logging state for Input 2 Emb.Pair 4 type
                 TYPE: - Display
                 PAGE: - Logging
                    Inp2 Emb.4 type=  cmdID= 36051  "
        ::= { iqsyn20CmdEntry 36051 }


    iqsyn20LoggingIn1AudTypeLogInp2Emb5type OBJECT-TYPE
        SYNTAX            INTEGER { disable(0), enable(1)  }
        MAX-ACCESS        read-write
        STATUS            current
        DESCRIPTION
                "CMNT: - Enable/Disable logging for Input 2 Emb.Pair 5 type
                 TYPE: - Checkbox
                 PAGE: - Logging
                    Log Inp2 Emb.5 type  cmdID= 35052  "
        ::= { iqsyn20CmdEntry 35052 }


    iqsyn20LoggingIn1AudTypeInp2Emb5type OBJECT-TYPE
        SYNTAX            RollCallString
        MAX-ACCESS        read-only
        STATUS            current
        DESCRIPTION
                "CMNT: - Logging state for Input 2 Emb.Pair 5 type
                 TYPE: - Display
                 PAGE: - Logging
                    Inp2 Emb.5 type=  cmdID= 36052  "
        ::= { iqsyn20CmdEntry 36052 }


    iqsyn20LoggingIn1AudTypeLogInp2Emb6type OBJECT-TYPE
        SYNTAX            INTEGER { disable(0), enable(1)  }
        MAX-ACCESS        read-write
        STATUS            current
        DESCRIPTION
                "CMNT: - Enable/Disable logging for Input 2 Emb.Pair 6 type
                 TYPE: - Checkbox
                 PAGE: - Logging
                    Log Inp2 Emb.6 type  cmdID= 35053  "
        ::= { iqsyn20CmdEntry 35053 }


    iqsyn20LoggingIn1AudTypeInp2Emb6type OBJECT-TYPE
        SYNTAX            RollCallString
        MAX-ACCESS        read-only
        STATUS            current
        DESCRIPTION
                "CMNT: - Logging state for Input 2 Emb.Pair 6 type
                 TYPE: - Display
                 PAGE: - Logging
                    Inp2 Emb.6 type=  cmdID= 36053  "
        ::= { iqsyn20CmdEntry 36053 }


    iqsyn20LoggingIn1AudTypeLogInp2Emb7type OBJECT-TYPE
        SYNTAX            INTEGER { disable(0), enable(1)  }
        MAX-ACCESS        read-write
        STATUS            current
        DESCRIPTION
                "CMNT: - Enable/Disable logging for Input 2 Emb.Pair 7 type
                 TYPE: - Checkbox
                 PAGE: - Logging
                    Log Inp2 Emb.7 type  cmdID= 35054  "
        ::= { iqsyn20CmdEntry 35054 }


    iqsyn20LoggingIn1AudTypeInp2Emb7type OBJECT-TYPE
        SYNTAX            RollCallString
        MAX-ACCESS        read-only
        STATUS            current
        DESCRIPTION
                "CMNT: - Logging state for Input 2 Emb.Pair 7 type
                 TYPE: - Display
                 PAGE: - Logging
                    Inp2 Emb.7 type=  cmdID= 36054  "
        ::= { iqsyn20CmdEntry 36054 }


    iqsyn20LoggingIn1AudTypeLogInp2Emb8type OBJECT-TYPE
        SYNTAX            INTEGER { disable(0), enable(1)  }
        MAX-ACCESS        read-write
        STATUS            current
        DESCRIPTION
                "CMNT: - Enable/Disable logging for Input 2 Emb.Pair 8 type
                 TYPE: - Checkbox
                 PAGE: - Logging
                    Log Inp2 Emb.8 type  cmdID= 35055  "
        ::= { iqsyn20CmdEntry 35055 }


    iqsyn20LoggingIn1AudTypeInp2Emb8type OBJECT-TYPE
        SYNTAX            RollCallString
        MAX-ACCESS        read-only
        STATUS            current
        DESCRIPTION
                "CMNT: - Logging state for Input 2 Emb.Pair 8 type
                 TYPE: - Display
                 PAGE: - Logging
                    Inp2 Emb.8 type=  cmdID= 36055  "
        ::= { iqsyn20CmdEntry 36055 }


    iqsyn20LoggingMiscLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging
                    Log Serial No.  cmdID= 35015  "
        ::= { iqsyn20CmdEntry 35015 }


    iqsyn20LoggingMiscSerialNo OBJECT-TYPE
        SYNTAX            RollCallString
        MAX-ACCESS        read-only
        STATUS            current
        DESCRIPTION
                "CMNT: - Logging state for Serial No.
                 TYPE: - Display
                 PAGE: - Logging
                    Serial No.=  cmdID= 36015  "
        ::= { iqsyn20CmdEntry 36015 }


    iqsyn20LoggingMiscLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging
                    Log OS Version  cmdID= 35993  "
        ::= { iqsyn20CmdEntry 35993 }


    iqsyn20LoggingMiscOSVersion OBJECT-TYPE
        SYNTAX            RollCallString
        MAX-ACCESS        read-only
        STATUS            current
        DESCRIPTION
                "CMNT: - Logging state for OS Version
                 TYPE: - Display
                 PAGE: - Logging
                    OS Version=  cmdID= 36993  "
        ::= { iqsyn20CmdEntry 36993 }


    iqsyn20LoggingMiscLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging
                    Log Build No.  cmdID= 35990  "
        ::= { iqsyn20CmdEntry 35990 }


    iqsyn20LoggingMiscBuildNo OBJECT-TYPE
        SYNTAX            RollCallString
        MAX-ACCESS        read-only
        STATUS            current
        DESCRIPTION
                "CMNT: - Logging state for Build No.
                 TYPE: - Display
                 PAGE: - Logging
                    Build No.=  cmdID= 36990  "
        ::= { iqsyn20CmdEntry 36990 }


    iqsyn20LoggingMiscLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging
                    Log Hardware Ver.  cmdID= 35992  "
        ::= { iqsyn20CmdEntry 35992 }


    iqsyn20LoggingMiscHardwareVer OBJECT-TYPE
        SYNTAX            RollCallString
        MAX-ACCESS        read-only
        STATUS            current
        DESCRIPTION
                "CMNT: - Logging state for Hardware Ver.
                 TYPE: - Display
                 PAGE: - Logging
                    Hardware Ver.=  cmdID= 36992  "
        ::= { iqsyn20CmdEntry 36992 }


    iqsyn20LoggingMiscLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging
                    Log Firmware Ver.  cmdID= 35991  "
        ::= { iqsyn20CmdEntry 35991 }


    iqsyn20LoggingMiscFirmwareVer OBJECT-TYPE
        SYNTAX            RollCallString
        MAX-ACCESS        read-only
        STATUS            current
        DESCRIPTION
                "CMNT: - Logging state for Firmware Ver.
                 TYPE: - Display
                 PAGE: - Logging
                    Firmware Ver.=  cmdID= 36991  "
        ::= { iqsyn20CmdEntry 36991 }


    iqsyn20LoggingMiscLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging
                    Log Up Time  cmdID= 35994  "
        ::= { iqsyn20CmdEntry 35994 }


    iqsyn20LoggingMiscUpTime OBJECT-TYPE
        SYNTAX            RollCallString
        MAX-ACCESS        read-only
        STATUS            current
        DESCRIPTION
                "CMNT: - Logging state for Up Time
                 TYPE: - Display
                 PAGE: - Logging
                    Up Time=  cmdID= 36994  "
        ::= { iqsyn20CmdEntry 36994 }


    iqsyn20LoggingRefOutputLogReferenceType OBJECT-TYPE
        SYNTAX            INTEGER { disable(0), enable(1)  }
        MAX-ACCESS        read-write
        STATUS            current
        DESCRIPTION
                "CMNT: - Enable/Disable logging for Reference Type
                 TYPE: - Checkbox
                 PAGE: - Logging
                    Log Reference Type  cmdID= 35995  "
        ::= { iqsyn20CmdEntry 35995 }


    iqsyn20LoggingRefOutputReferenceType OBJECT-TYPE
        SYNTAX            RollCallString
        MAX-ACCESS        read-only
        STATUS            current
        DESCRIPTION
                "CMNT: - Logging state for Reference Type
                 TYPE: - Display
                 PAGE: - Logging
                    Reference Type=  cmdID= 36995  "
        ::= { iqsyn20CmdEntry 36995 }


    iqsyn20LoggingRefOutputLogReferenceState OBJECT-TYPE
        SYNTAX            INTEGER { disable(0), enable(1)  }
        MAX-ACCESS        read-write
        STATUS            current
        DESCRIPTION
                "CMNT: - Enable/Disable logging for Reference State
                 TYPE: - Checkbox
                 PAGE: - Logging
                    Log Reference State  cmdID= 35004  "
        ::= { iqsyn20CmdEntry 35004 }


    iqsyn20LoggingRefOutputReferenceState OBJECT-TYPE
        SYNTAX            RollCallString
        MAX-ACCESS        read-only
        STATUS            current
        DESCRIPTION
                "CMNT: - Logging state for Reference State
                 TYPE: - Display
                 PAGE: - Logging
                    Reference State=  cmdID= 36004  "
        ::= { iqsyn20CmdEntry 36004 }


    iqsyn20LoggingRefOutputLogReferenceStand OBJECT-TYPE
        SYNTAX            INTEGER { disable(0), enable(1)  }
        MAX-ACCESS        read-write
        STATUS            current
        DESCRIPTION
                "CMNT: - Enable/Disable logging for Reference Standard
                 TYPE: - Checkbox
                 PAGE: - Logging
                    Log Reference Standard  cmdID= 35014  "
        ::= { iqsyn20CmdEntry 35014 }


    iqsyn20LoggingRefOutputReferenceStandard OBJECT-TYPE
        SYNTAX            RollCallString
        MAX-ACCESS        read-only
        STATUS            current
        DESCRIPTION
                "CMNT: - Logging state for Reference Standard
                 TYPE: - Display
                 PAGE: - Logging
                    Reference Standard=  cmdID= 36014  "
        ::= { iqsyn20CmdEntry 36014 }


    iqsyn20RollCallRollTrackDisableAll OBJECT-TYPE
        SYNTAX            INTEGER { disable(0), enable(1)  }
        MAX-ACCESS        read-write
        STATUS            current
        DESCRIPTION
                "CMNT: - Disable all rolltrack outputs
                 TYPE: - Checkbox
                 PAGE: - RollTrack
                    Disable All  cmdID= 36104  "
        ::= { iqsyn20CmdEntry 36104 }


    iqsyn20RollCallRollTrackIndex OBJECT-TYPE
        SYNTAX            INTEGER
        MAX-ACCESS        read-write
        STATUS            current
        DESCRIPTION
                "CMNT: - Select rolltrack to edit
                 TYPE: - BarGraph
                 PAGE: - RollTrack
                    Index  cmdID= 36100
                    min= 1  max= 16  step= 1  format= %0.0f  div_scale= 1  preset= 1
                    Min = 1  Max = 16  Step = 1  Preset = 1  "
        ::= { iqsyn20CmdEntry 36100 }


    iqsyn20RollCallRollTrackSource OBJECT-TYPE
        SYNTAX            INTEGER {
                            valUnused(-1),
                            valVideoDelay(0),
                            valInputPresent(1),
                            valInputLoss(2),
                            valReferenceOK(3),
                            valReferenceLost(4),
                            valOpFreeze(5),
                            valOpUnFreeze(6),
                            valINP1Select(54),
                            valINP2Select(55),
                            valGPI1High(32),
                            valGPI1Low(33),
                            valGPI1InActive(31),
                            valGPI2High(35),
                            valGPI2Low(36),
                            valGPI2InActive(34),
                            valDenembed1Data(7),
                            valDenembed1Pcm(8),
                            valDenembed1Lost(9),
                            valDenembed2Data(10),
                            valDenembed2Pcm(11),
                            valDenembed2Lost(12),
                            valDenembed3Data(13),
                            valDenembed3Pcm(14),
                            valDenembed3Lost(15),
                            valDenembed4Data(16),
                            valDenembed4Pcm(17),
                            valDenembed4Lost(18),
                            valDenembed5Data(19),
                            valDenembed5Pcm(20),
                            valDenembed5Lost(21),
                            valDenembed6Data(22),
                            valDenembed6Pcm(23),
                            valDenembed6Lost(24),
                            valDenembed7Data(25),
                            valDenembed7Pcm(26),
                            valDenembed7Lost(27),
                            valDenembed8Data(28),
                            valDenembed8Pcm(29),
                            valDenembed8Lost(30),
                            valOut1125108030i(37),
                            valOut1125108030p(38),
                            valOut1125108029i(39),
                            valOut1125108029p(40),
                            valOut1125108025i(41),
                            valOut1125108025p(42),
                            valOut1125108024p(43),
                            valOut1125108024sf(44),
                            valOut1125108023p(45),
                            valOut1125108023sf(46),
                            valOut1125103530i(47),
                            valOut1125103529i(48),
                            valOut75072060p(49),
                            valOut75072059p(50),
                            valOut75072050p(51),
                            valOut52548029i(52),
                            valOut62557625i(53)
                            }
        MAX-ACCESS        read-write
        STATUS            current
        DESCRIPTION
                "CMNT: - Source for Rolltrack
                 TYPE: - RadiobuttonList
                 PAGE: - RollTrack
                    Source  cmdID= 36101
                    Unused  value= -1
                    Video Delay  value= 0
                    Input Present  value= 1
                    Input Loss  value= 2
                    Reference OK  value= 3
                    Reference Lost  value= 4
                    O/p Freeze  value= 5
                    O/p UnFreeze  value= 6
                    INP1 Select  value= 54
                    INP2 Select  value= 55
                    GPI 1 High  value= 32
                    GPI 1 Low  value= 33
                    GPI 1 InActive  value= 31
                    GPI 2 High  value= 35
                    GPI 2 Low  value= 36
                    GPI 2 InActive  value= 34
                    De-embed 1 Data  value= 7
                    De-embed 1 Pcm  value= 8
                    De-embed 1 Lost  value= 9
                    De-embed 2 Data  value= 10
                    De-embed 2 Pcm  value= 11
                    De-embed 2 Lost  value= 12
                    De-embed 3 Data  value= 13
                    De-embed 3 Pcm  value= 14
                    De-embed 3 Lost  value= 15
                    De-embed 4 Data  value= 16
                    De-embed 4 Pcm  value= 17
                    De-embed 4 Lost  value= 18
                    De-embed 5 Data  value= 19
                    De-embed 5 Pcm  value= 20
                    De-embed 5 Lost  value= 21
                    De-embed 6 Data  value= 22
                    De-embed 6 Pcm  value= 23
                    De-embed 6 Lost  value= 24
                    De-embed 7 Data  value= 25
                    De-embed 7 Pcm  value= 26
                    De-embed 7 Lost  value= 27
                    De-embed 8 Data  value= 28
                    De-embed 8 Pcm  value= 29
                    De-embed 8 Lost  value= 30
                    Out 1125(1080)/30i  value= 37
                    Out 1125(1080)/30p  value= 38
                    Out 1125(1080)/29i  value= 39
                    Out 1125(1080)/29p  value= 40
                    Out 1125(1080)/25i  value= 41
                    Out 1125(1080)/25p  value= 42
                    Out 1125(1080)/24p  value= 43
                    Out 1125(1080)/24sf  value= 44
                    Out 1125(1080)/23p  value= 45
                    Out 1125(1080)/23sf  value= 46
                    Out 1125(1035)/30i  value= 47
                    Out 1125(1035)/29i  value= 48
                    Out 750(720)/60p  value= 49
                    Out 750(720)/59p  value= 50
                    Out 750(720)/50p  value= 51
                    Out 525(480)/29i  value= 52
                    Out 625(576)/25i  value= 53  "
        ::= { iqsyn20CmdEntry 36101 }


    iqsyn20RollCallRollTrackAddress OBJECT-TYPE
        SYNTAX            RollCallString
        MAX-ACCESS        read-write
        STATUS            current
        DESCRIPTION
                "CMNT: - Unit address for Rolltrack message
                 TYPE: - Editstring
                 PAGE: - RollTrack
                    Address  cmdID= 36102
                    preset= 0000:00:00*0\0*"
        ::= { iqsyn20CmdEntry 36102 }


    iqsyn20RollCallRollTrackCommand OBJECT-TYPE
        SYNTAX            RollCallString
        MAX-ACCESS        read-write
        STATUS            current
        DESCRIPTION
                "CMNT: - Command to send for Rolltrack message
                 TYPE: - Editstring
                 PAGE: - RollTrack
                    Command  cmdID= 36103
                    preset= 000:000\0"
        ::= { iqsyn20CmdEntry 36103 }


    iqsyn20RollCallRollTrackStatus OBJECT-TYPE
        SYNTAX            RollCallString
        MAX-ACCESS        read-only
        STATUS            current
        DESCRIPTION
                "CMNT: - Rolltrack status
                 TYPE: - Display
                 PAGE: - RollTrack
                    Status  cmdID= 36105  "
        ::= { iqsyn20CmdEntry 36105 }


    iqsyn20RollCallRollTrackSending OBJECT-TYPE
        SYNTAX            RollCallString
        MAX-ACCESS        read-only
        STATUS            current
        DESCRIPTION
                "CMNT: - Rolltrack sending status: true/false
                 TYPE: - Display
                 PAGE: - RollTrack
                    Sending  cmdID= 36106  "
        ::= { iqsyn20CmdEntry 36106 }


    iqsyn20SetupProduct OBJECT-TYPE
        SYNTAX            RollCallString
        MAX-ACCESS        read-only
        STATUS            current
        DESCRIPTION
                "CMNT: - 
                 TYPE: - Display
                 PAGE: - Setup
                    Product  cmdID= 32771  "
        ::= { iqsyn20CmdEntry 32771 }


    iqsyn20SetupRelease OBJECT-TYPE
        SYNTAX            RollCallString
        MAX-ACCESS        read-only
        STATUS            current
        DESCRIPTION
                "CMNT: - Unit version number
                 TYPE: - Display
                 PAGE: - Setup
                    Release  cmdID= 2  "
        ::= { iqsyn20CmdEntry 2 }


    iqsyn20SetupBuild OBJECT-TYPE
        SYNTAX            RollCallString
        MAX-ACCESS        read-only
        STATUS            current
        DESCRIPTION
                "CMNT: - Unit build number
                 TYPE: - Display
                 PAGE: - Setup
                    Build  cmdID= 5  "
        ::= { iqsyn20CmdEntry 5 }


    iqsyn20SetupKOS OBJECT-TYPE
        SYNTAX            RollCallString
        MAX-ACCESS        read-only
        STATUS            current
        DESCRIPTION
                "CMNT: - 
                 TYPE: - Display
                 PAGE: - Setup
                    KOS  cmdID= 32772  "
        ::= { iqsyn20CmdEntry 32772 }


    iqsyn20SetupSerial OBJECT-TYPE
        SYNTAX            RollCallString
        MAX-ACCESS        read-only
        STATUS            current
        DESCRIPTION
                "CMNT: - Unit serial number
                 TYPE: - Display
                 PAGE: - Setup
                    Serial No.  cmdID= 1  "
        ::= { iqsyn20CmdEntry 1 }


    iqsyn20SetupFirmware OBJECT-TYPE
        SYNTAX            RollCallString
        MAX-ACCESS        read-only
        STATUS            current
        DESCRIPTION
                "CMNT: - Display firmware version
                 TYPE: - Display
                 PAGE: - Setup
                    Firmware  cmdID= 32769  "
        ::= { iqsyn20CmdEntry 32769 }


    iqsyn20SetupPCB OBJECT-TYPE
        SYNTAX            RollCallString
        MAX-ACCESS        read-only
        STATUS            current
        DESCRIPTION
                "CMNT: - Display PCB revision
                 TYPE: - Display
                 PAGE: - Setup
                    PCB  cmdID= 32770  "
        ::= { iqsyn20CmdEntry 32770 }


    iqsyn20SetupFactoryDefault OBJECT-TYPE
        SYNTAX            INTEGER { noAction(0),valFactoryDefault(1) }
        MAX-ACCESS        read-write
        STATUS            current
        DESCRIPTION
                "CMNT: - Recall factory defaults
                 TYPE: - Button
                 PAGE: - Setup
                    Factory Default  cmdID= 37002
                    value= 1  "
        ::= { iqsyn20CmdEntry 37002 }


    iqsyn20SetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 4
                    value= 1  "
        ::= { iqsyn20CmdEntry 4 }


    iqsyn20MemoriesMemorySave OBJECT-TYPE
        SYNTAX            INTEGER { noAction(0),valDefaultSettings(1) }
        MAX-ACCESS        read-write
        STATUS            current
        DESCRIPTION
                "CMNT: - Recall factory defaults-KeepMemories
                 TYPE: - Button
                 PAGE: - Setup
                    Default Settings  cmdID= 37001
                    value= 1  "
        ::= { iqsyn20CmdEntry 37001 }


    iqsyn20SetupDisplay OBJECT-TYPE
        SYNTAX            INTEGER {
                            valVideoStatus(0),
                            valAudioStatus(1),
                            valMetadataStatus(2)
                            }
        MAX-ACCESS        read-write
        STATUS            current
        DESCRIPTION
                "CMNT: - Select Info display to show
                 TYPE: - RadiobuttonList
                 PAGE: - Setup
                    Display  cmdID= 32773
                    Video Status  value= 0
                    Audio Status  value= 1
                    Metadata Status  value= 2  "
        ::= { iqsyn20CmdEntry 32773 }


    iqsyn20SetupSerialNumber OBJECT-TYPE
        SYNTAX            RollCallString
        MAX-ACCESS        read-write
        STATUS            current
        DESCRIPTION
                "CMNT: - Edit serial number (On Factory Test Only)
                 TYPE: - Editstring
                 PAGE: - Setup
                    Serial Number  cmdID= 32774
                    preset= unknown"
        ::= { iqsyn20CmdEntry 32774 }


    iqsyn20SetupBoardID OBJECT-TYPE
        SYNTAX            INTEGER {
                            valIQSYN20(344),
                            valIQSYN21(387),
                            valIQSYN22(538)
                            }
        MAX-ACCESS        read-write
        STATUS            current
        DESCRIPTION
                "CMNT: - Edit product type (On Factory Test Only)
                 TYPE: - RadiobuttonList
                 PAGE: - Setup
                    BoardID  cmdID= 32776
                    IQSYN20  value= 344
                    IQSYN21  value= 387
                    IQSYN22  value= 538  "
        ::= { iqsyn20CmdEntry 32776 }


    iqsyn20SetupSaveID OBJECT-TYPE
        SYNTAX            INTEGER { noAction(0),valSaveID(1) }
        MAX-ACCESS        read-write
        STATUS            current
        DESCRIPTION
                "CMNT: - Save serial number/board type (On Factory Test Only)
                 TYPE: - Button
                 PAGE: - Setup
                    Save ID  cmdID= 32775
                    value= 1  "
        ::= { iqsyn20CmdEntry 32775 }


    iqsyn20EngineerPassword OBJECT-TYPE
        SYNTAX            RollCallString
        MAX-ACCESS        read-write
        STATUS            current
        DESCRIPTION
                "CMNT: - 
                 TYPE: - Editstring
                 PAGE: - Engineer
                    Engineer Password  cmdID= 34011
                    preset= -"
        ::= { iqsyn20CmdEntry 34011 }


    iqsyn20EngineerShowEngineer OBJECT-TYPE
        SYNTAX            INTEGER { disable(0), enable(1)  }
        MAX-ACCESS        read-write
        STATUS            current
        DESCRIPTION
                "CMNT: - 
                 TYPE: - Checkbox
                 PAGE: - Engineer
                    Show Engineer  cmdID= 34012  "
        ::= { iqsyn20CmdEntry 34012 }


    iqsyn20EngineerPageUndoChanges OBJECT-TYPE
        SYNTAX            INTEGER { noAction(0),valUndoChanges(1) }
        MAX-ACCESS        read-write
        STATUS            current
        DESCRIPTION
                "CMNT: - 
                 TYPE: - Button
                 PAGE: - Engineer
                    Undo Changes  cmdID= 34013
                    value= 1  "
        ::= { iqsyn20CmdEntry 34013 }


    iqsyn20EngineerShowEngineer2 OBJECT-TYPE
        SYNTAX            INTEGER { disable(0), enable(1)  }
        MAX-ACCESS        read-write
        STATUS            current
        DESCRIPTION
                "CMNT: - 
                 TYPE: - Checkbox
                 PAGE: - Engineer
                    Show Engineer2  cmdID= 34050  "
        ::= { iqsyn20CmdEntry 34050 }


    iqsyn20EngineerShowEngineer3 OBJECT-TYPE
        SYNTAX            INTEGER { disable(0), enable(1)  }
        MAX-ACCESS        read-write
        STATUS            current
        DESCRIPTION
                "CMNT: - 
                 TYPE: - Checkbox
                 PAGE: - Engineer
                    Show Engineer3  cmdID= 34051  "
        ::= { iqsyn20CmdEntry 34051 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S34091041
-- Comments		: Runtime string Serial Number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 00-00-00 01:30Z
-- Comments		: Uptime in formated date-time string
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
--
-- Value(s)		: INP 1
--				: INP 2
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: K_OS: V115 Release
-- Comments		: String
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 0003102405
-- Comments		: String of current Software build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD / SD SDI
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD / SD SDI
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: FAIL:Lost
--				: OK
--				: FAIL:Error
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: FAIL:Lost
--				: OK
--				: FAIL:Error
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: HD / SD SDI
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 2.122
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: 1
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: NONE
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: NONE
--				: WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: Tri/Bi-Level
--				: TriLevel
--				: BiLevel
--				: BlackBurst
--				: Analog
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: FAIL:Lost
--				: FAIL:Error
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
--
-- Value(s)		: 0
-- Comments		: Number
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
--
-- Value(s)		: 0
-- Comments		: Number
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: NONE
--				: WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: NONE
--				: WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
--
-- Value(s)		: 0
-- Comments		: Number
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
--
-- Value(s)		: 0
-- Comments		: Number
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
--
-- Value(s)		: WARN: No Input
--				: PCM
--				: NONPCM
--				: Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
--
-- Value(s)		: WARN: No Input
--				: PCM
--				: NONPCM
--				: Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
--
-- Value(s)		: WARN: No Input
--				: PCM
--				: NONPCM
--				: Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
--
-- Value(s)		: WARN: No Input
--				: PCM
--				: NONPCM
--				: Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
--
-- Value(s)		: WARN: No Input
--				: PCM
--				: NONPCM
--				: Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
--
-- Value(s)		: WARN: No Input
--				: PCM
--				: NONPCM
--				: Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
--
-- Value(s)		: WARN: No Input
--				: PCM
--				: NONPCM
--				: Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
--
-- Value(s)		: WARN: No Input
--				: PCM
--				: NONPCM
--				: Unknown
-- Comments		:
--
---------------------------------------------------------------------------------------------------
-- Header		: INPUT_2_EMBEDDED_AUDIO_1_TYPE
--
-- MIB ref		: swCardEventLogSlotXX       .29.73.78.80.85.84.95.50.95.69.77.66.69.68.68.69.68.95.65.85.68.73.79.95.49.95.84.89.80.69
-- absolute OID	: 1.3.6.1.4.1.7995.2.6.1.1.XX.29.73.78.80.85.84.95.50.95.69.77.66.69.68.68.69.68.95.65.85.68.73.79.95.49.95.84.89.80.69
--
-- Value(s)		: WARN: No Input
--				: PCM
--				: NONPCM
--				: Unknown
-- Comments		:
--
---------------------------------------------------------------------------------------------------
-- Header		: INPUT_2_EMBEDDED_AUDIO_2_TYPE
--
-- MIB ref		: swCardEventLogSlotXX       .29.73.78.80.85.84.95.50.95.69.77.66.69.68.68.69.68.95.65.85.68.73.79.95.50.95.84.89.80.69
-- absolute OID	: 1.3.6.1.4.1.7995.2.6.1.1.XX.29.73.78.80.85.84.95.50.95.69.77.66.69.68.68.69.68.95.65.85.68.73.79.95.50.95.84.89.80.69
--
-- Value(s)		: WARN: No Input
--				: PCM
--				: NONPCM
--				: Unknown
-- Comments		:
--
---------------------------------------------------------------------------------------------------
-- Header		: INPUT_2_EMBEDDED_AUDIO_3_TYPE
--
-- MIB ref		: swCardEventLogSlotXX       .29.73.78.80.85.84.95.50.95.69.77.66.69.68.68.69.68.95.65.85.68.73.79.95.51.95.84.89.80.69
-- absolute OID	: 1.3.6.1.4.1.7995.2.6.1.1.XX.29.73.78.80.85.84.95.50.95.69.77.66.69.68.68.69.68.95.65.85.68.73.79.95.51.95.84.89.80.69
--
-- Value(s)		: WARN: No Input
--				: PCM
--				: NONPCM
--				: Unknown
-- Comments		:
--
---------------------------------------------------------------------------------------------------
-- Header		: INPUT_2_EMBEDDED_AUDIO_4_TYPE
--
-- MIB ref		: swCardEventLogSlotXX       .29.73.78.80.85.84.95.50.95.69.77.66.69.68.68.69.68.95.65.85.68.73.79.95.52.95.84.89.80.69
-- absolute OID	: 1.3.6.1.4.1.7995.2.6.1.1.XX.29.73.78.80.85.84.95.50.95.69.77.66.69.68.68.69.68.95.65.85.68.73.79.95.52.95.84.89.80.69
--
-- Value(s)		: WARN: No Input
--				: PCM
--				: NONPCM
--				: Unknown
-- Comments		:
--
---------------------------------------------------------------------------------------------------
-- Header		: INPUT_2_EMBEDDED_AUDIO_5_TYPE
--
-- MIB ref		: swCardEventLogSlotXX       .29.73.78.80.85.84.95.50.95.69.77.66.69.68.68.69.68.95.65.85.68.73.79.95.53.95.84.89.80.69
-- absolute OID	: 1.3.6.1.4.1.7995.2.6.1.1.XX.29.73.78.80.85.84.95.50.95.69.77.66.69.68.68.69.68.95.65.85.68.73.79.95.53.95.84.89.80.69
--
-- Value(s)		: WARN: No Input
--				: PCM
--				: NONPCM
--				: Unknown
-- Comments		:
--
---------------------------------------------------------------------------------------------------
-- Header		: INPUT_2_EMBEDDED_AUDIO_6_TYPE
--
-- MIB ref		: swCardEventLogSlotXX       .29.73.78.80.85.84.95.50.95.69.77.66.69.68.68.69.68.95.65.85.68.73.79.95.54.95.84.89.80.69
-- absolute OID	: 1.3.6.1.4.1.7995.2.6.1.1.XX.29.73.78.80.85.84.95.50.95.69.77.66.69.68.68.69.68.95.65.85.68.73.79.95.54.95.84.89.80.69
--
-- Value(s)		: WARN: No Input
--				: PCM
--				: NONPCM
--				: Unknown
-- Comments		:
--
---------------------------------------------------------------------------------------------------
-- Header		: INPUT_2_EMBEDDED_AUDIO_7_TYPE
--
-- MIB ref		: swCardEventLogSlotXX       .29.73.78.80.85.84.95.50.95.69.77.66.69.68.68.69.68.95.65.85.68.73.79.95.55.95.84.89.80.69
-- absolute OID	: 1.3.6.1.4.1.7995.2.6.1.1.XX.29.73.78.80.85.84.95.50.95.69.77.66.69.68.68.69.68.95.65.85.68.73.79.95.55.95.84.89.80.69
--
-- Value(s)		: WARN: No Input
--				: PCM
--				: NONPCM
--				: Unknown
-- Comments		:
--
---------------------------------------------------------------------------------------------------
-- Header		: INPUT_2_EMBEDDED_AUDIO_8_TYPE
--
-- MIB ref		: swCardEventLogSlotXX       .29.73.78.80.85.84.95.50.95.69.77.66.69.68.68.69.68.95.65.85.68.73.79.95.56.95.84.89.80.69
-- absolute OID	: 1.3.6.1.4.1.7995.2.6.1.1.XX.29.73.78.80.85.84.95.50.95.69.77.66.69.68.68.69.68.95.65.85.68.73.79.95.56.95.84.89.80.69
--
-- Value(s)		: WARN: No Input
--				: PCM
--				: NONPCM
--				: Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: LOST
--				: FAIL:Lost
--				: OK
--				: Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: LOST
--				: FAIL:Lost
--				: OK
--				: Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: LOST
--				: FAIL:Lost
--				: OK
--				: Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: LOST
--				: FAIL:Lost
--				: OK
--				: Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: LOST
--				: FAIL:Lost
--				: OK
--				: Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: LOST
--				: FAIL:Lost
--				: OK
--				: Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: LOST
--				: FAIL:Lost
--				: OK
--				: Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: LOST
--				: FAIL:Lost
--				: OK
--				: Unknown
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: LOST
--				: FAIL:Lost
--				: OK
--				: Unknown
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: LOST
--				: FAIL:Lost
--				: OK
--				: Unknown
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: LOST
--				: FAIL:Lost
--				: OK
--				: Unknown
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: LOST
--				: FAIL:Lost
--				: OK
--				: Unknown
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: LOST
--				: FAIL:Lost
--				: OK
--				: Unknown
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: LOST
--				: FAIL:Lost
--				: OK
--				: Unknown
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: LOST
--				: FAIL:Lost
--				: OK
--				: Unknown
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: LOST
--				: FAIL:Lost
--				: OK
--				: Unknown
-- Comments		:
--
---------------------------------------------------------------------------------------------------
