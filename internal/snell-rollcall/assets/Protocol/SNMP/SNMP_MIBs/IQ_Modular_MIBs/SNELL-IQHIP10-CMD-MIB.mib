-- ************************************************************************************
--        Snell Card:IQHIP10
--        Module Id#:668
--       Command Set:5
--          Filename:SNELL-IQHIP10-CMD-MIB.mib
--       Source File:hipcom.xml
--        Source Ver:5.0.5
--    Logging Source:hip10logging.csv
--            Author:RobinBrown
--              Date:02/04/2014
--              Time:10:14
--
-- Copyright (c) 2010 Snell Ltd
-- All rights reserved.
--
-- ************************************************************************************

SNELL-IQHIP10-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQHIP10,
    moduleIQHIP10MIB
        FROM SNELL-WILCOX-PRODUCT-REG;

 moduleIQHIP10CmdMi MODULE-IDENTITY
    LAST-UPDATED "1404021014Z"
    ORGANIZATION "Snell Ltd"
    CONTACT-INFO
        "Primary Author:RobinBrown

         postal:    Hartman House
                    Danehill
                    Lower Earley,
                    Reading, Berks
                    RG6 4PB
         phone:     +44 (0)118 9866123
         email:     support.uk@snellgroup.com"
    DESCRIPTION
        "This file defines the Snell card, command set translations."
    ::= { moduleIQHIP10MIB 1 }




--********************************************************************************
--*
--*  Snell Card:
--*  command set:
--*  list commands/menus:
--*
--******************************************************************************
    iqhip10CmdTable OBJECT-TYPE
        SYNTAX          SEQUENCE OF Iqhip10CmdEntry
        MAX-ACCESS      not-accessible
        STATUS          current
        DESCRIPTION
                "Note the instance of this table is relected in the command set Version"
        ::= { moduleIQHIP10 1 }

    iqhip10CmdEntry OBJECT-TYPE
        SYNTAX          Iqhip10CmdEntry
        MAX-ACCESS      not-accessible
        STATUS          current
        DESCRIPTION
                "Entry in command table."
        INDEX   { iqhip10SlotIndex }
        ::= { iqhip10CmdTable 1 }

    Iqhip10CmdEntry ::=
        SEQUENCE {
            iqhip10SlotIndex
                Unsigned32,
            iqhip10Input
                INTEGER,
            iqhip10InputSERIALIO
                INTEGER,
            iqhip10InputMuteOutput1
                INTEGER,
            iqhip10InputMuteOutput2
                INTEGER,
            iqhip10InputMuteOutput3
                INTEGER,
            iqhip10InputMuteOutput4
                INTEGER,
            iqhip10InputMuteOnInputErrorOutput1
                INTEGER,
            iqhip10InputMuteOnInputErrorOutput2
                INTEGER,
            iqhip10InputMuteOnInputErrorOutput3
                INTEGER,
            iqhip10InputMuteOnInputErrorOutput4
                INTEGER,
            iqhip10HyperionRegionsRegionSelect
                INTEGER,
            iqhip10RegionsRegionEnables
                INTEGER,
            iqhip10RegionDetectorsDetectorWindowWindowMode
                INTEGER,
            iqhip10RegionDetectorsDetectorWindowFullScreen
                INTEGER,
            iqhip10RegionDetectorsDetectorWindowXPosition
                INTEGER,
            iqhip10RegionDetectorsDetectorWindowWidth
                INTEGER,
            iqhip10RegionDetectorsDetectorWindowYPosition
                INTEGER,
            iqhip10RegionDetectorsDetectorWindowHeight
                INTEGER,
            iqhip10RegionDetectorsBlackEnable
                INTEGER,
            iqhip10RegionDetectorsBlackAlarmcount
                RollCallString,
            iqhip10RegionDetectorsBlackReset
                INTEGER,
            iqhip10RegionDetectorsBlackResetWhenOK
                INTEGER,
            iqhip10RegionDetectorsBlackWarningCount
                INTEGER,
            iqhip10RegionDetectorsBlackFailCount
                INTEGER,
            iqhip10RegionDetectorsBlackFailHoldCount
                INTEGER,
            iqhip10RegionDetectorsBlackishEnable
                INTEGER,
            iqhip10RegionDetectorsBlackishAlarmcount
                RollCallString,
            iqhip10RegionDetectorsBlackishReset
                INTEGER,
            iqhip10RegionDetectorsBlackishResetWhenOK
                INTEGER,
            iqhip10RegionDetectorsBlackishCurrentDetectedLevel
                RollCallString,
            iqhip10RegionDetectorsBlackishMaxLevelThreshold
                INTEGER,
            iqhip10RegionDetectorsBlackishWarningCount
                INTEGER,
            iqhip10RegionDetectorsBlackishFailCount
                INTEGER,
            iqhip10RegionDetectorsBlackishFailHoldCount
                INTEGER,
            iqhip10RegionDetectorsFreezeEnable
                INTEGER,
            iqhip10RegionDetectorsFreezeAlarmcount
                RollCallString,
            iqhip10RegionDetectorsFreezeReset
                INTEGER,
            iqhip10RegionDetectorsFreezeResetWhenOK
                INTEGER,
            iqhip10RegionsRegionDetectorsFreezeTolerance
                INTEGER,
            iqhip10RegionDetectorsFreezeWarningCount
                INTEGER,
            iqhip10RegionDetectorsFreezeFailCount
                INTEGER,
            iqhip10RegionDetectorsFreezeFailHoldCount
                INTEGER,
            iqhip10RegionDetectorsStillishEnable
                INTEGER,
            iqhip10RegionDetectorsStillishAlarmcount
                RollCallString,
            iqhip10RegionDetectorsStillishReset
                INTEGER,
            iqhip10RegionDetectorsStillishResetWhenOK
                INTEGER,
            iqhip10RegionDetectorsStillishCurrentDetectedLevel
                RollCallString,
            iqhip10RegionDetectorsStillishMaxLevelThreshold
                INTEGER,
            iqhip10RegionDetectorsStillishWarningCount
                INTEGER,
            iqhip10RegionDetectorsStillishFailCount
                INTEGER,
            iqhip10RegionDetectorsStillishFailHoldCount
                INTEGER,
            iqhip10VideoMonitorAveragePictureLvlEnableAlarm
                INTEGER,
            iqhip10HyperionVideoMonitorAveragePictureLvl
                RollCallString,
            iqhip10VideoMonitorAveragePictureLvlMaxLoggingThres
                INTEGER,
            iqhip10VideoMonitorAveragePictureLvlMinLoggingThres
                INTEGER,
            iqhip10LumaVideoLevelOverloadStatus
                RollCallString,
            iqhip10LumaVideoLevelOverloadMaximumReading
                RollCallString,
            iqhip10LumaVideoLevelOverloadEnableAlarm
                INTEGER,
            iqhip10VideoMonitorLumaVideoLevelOverloadThreshold
                INTEGER,
            iqhip10LumaVideoLevelOverloadAvePicAboveThres
                INTEGER,
            iqhip10LumaVideoLevelUnderloadStatus
                RollCallString,
            iqhip10LumaVideoLevelUnderloadMinimumReading
                RollCallString,
            iqhip10LumaVideoLevelUnderloadEnableAlarm
                INTEGER,
            iqhip10VideoMonitorLumaVideoLevelUnderloadThreshold
                INTEGER,
            iqhip10LumaVideoLevelUnderloadAvePicBelowThres
                INTEGER,
            iqhip10ChromaVideoLevelOverloadStatus
                RollCallString,
            iqhip10ChromaVideoLevelOverloadMaximumReading
                RollCallString,
            iqhip10ChromaVideoLevelOverloadEnableAlarm
                INTEGER,
            iqhip10VideoMonitorChromaVideoLevelOverloadThreshold
                INTEGER,
            iqhip10ChromaVideoLevelOverloadAvePicAboveThres
                INTEGER,
            iqhip10ChromaVideoLevelUnderloadStatus
                RollCallString,
            iqhip10ChromaVideoLevelUnderloadMinimumReading
                RollCallString,
            iqhip10ChromaVideoLevelUnderloadEnableAlarm
                INTEGER,
            iqhip10VideoMonitorChromaVideoLevelUnderloadThreshold
                INTEGER,
            iqhip10ChromaVideoLevelUnderloadAvePicBelowThres
                INTEGER,
            iqhip10HyperionVideoMonitorChromaBitDepth
                RollCallString,
            iqhip10HyperionVideoMonitorLumaBitDepth
                RollCallString,
            iqhip10HyperionVideoMonitorRGBLegalizerEnable
                INTEGER,
            iqhip10HyperionVideoMonitorRGBLegalizerRange
                INTEGER,
            iqhip10ClosedCaptionsCCCEA608BState
                RollCallString,
            iqhip10ClosedCaptionsCCCEA608BTitle1
                RollCallString,
            iqhip10ClosedCaptionsCCCEA608BTitle2
                RollCallString,
            iqhip10ClosedCaptionsCCCEA708BField1
                RollCallString,
            iqhip10ClosedCaptionsCCCEA708BField2
                RollCallString,
            iqhip10ClosedCaptionsTemporalControlEnableAlarm
                INTEGER,
            iqhip10ClosedCaptionsTemporalControlResetWhenOK
                INTEGER,
            iqhip10ClosedCaptionsTemporalControlAlarm
                RollCallString,
            iqhip10ClosedCaptionsTemporalControlFailCount
                INTEGER,
            iqhip10ClosedCaptionsTemporalControlWarningCount
                INTEGER,
            iqhip10ClosedCaptionsTemporalControlFailHoldCount
                INTEGER,
            iqhip10ClosedCaptionsTemporalControlResetAlarm
                INTEGER,
            iqhip10AncillaryDataContentAdvisoryEnableAlarm
                INTEGER,
            iqhip10AncillaryDataContentAdvisorySystem
                RollCallString,
            iqhip10AncillaryDataContentAdvisoryRating
                RollCallString,
            iqhip10TimeCodeAncTimeCodeEnableAlarm
                INTEGER,
            iqhip10TimeCodeAncTimeCodeField1
                RollCallString,
            iqhip10TimeCodeAncTimeCodeField2
                RollCallString,
            iqhip10TimeCodeVITCEnableAlarm
                INTEGER,
            iqhip10TimeCodeVITCField1
                RollCallString,
            iqhip10TimeCodeVITCField2
                RollCallString,
            iqhip10AncillaryDataTimeCodeCurrentTimeCode
                RollCallString,
            iqhip10AncillaryDataTimeCodeSDTimeCodeSel
                INTEGER,
            iqhip10AncillaryDataTimeCodeDisconEnableAlarm
                INTEGER,
            iqhip10AncillaryDataTimeCodeDisconFail
                INTEGER,
            iqhip10AncillaryDataTimeCodeDisconHold
                INTEGER,
            iqhip10AncillaryDataTimeCodeDisconErrorAt
                RollCallString,
            iqhip10AncillaryDataTimeCodeDisconOKAt
                RollCallString,
            iqhip10AncillaryDataTimeCodeForceTCUpdates
                INTEGER,
            iqhip10AncillaryDataUserAncDet1EnableAlarm
                INTEGER,
            iqhip10AncillaryDataUserAncDet1DIDType
                INTEGER,
            iqhip10AncillaryDataUserAncDet1DIDselect
                INTEGER,
            iqhip10AncillaryDataUserAncDet1SDIDselect
                INTEGER,
            iqhip10AncillaryDataUserAncDet1Field1
                RollCallString,
            iqhip10AncillaryDataUserAncDet1Field2
                RollCallString,
            iqhip10AncillaryDataUserAncDet1Name
                RollCallString,
            iqhip10AncillaryDataUserAncDet2EnableAlarm
                INTEGER,
            iqhip10AncillaryDataUserAncDet2DIDType
                INTEGER,
            iqhip10AncillaryDataUserAncDet2DIDselect
                INTEGER,
            iqhip10AncillaryDataUserAncDet2SDIDselect
                INTEGER,
            iqhip10AncillaryDataUserAncDet2Field1
                RollCallString,
            iqhip10AncillaryDataUserAncDet2Field2
                RollCallString,
            iqhip10AncillaryDataUserAncDet2Name
                RollCallString,
            iqhip10AncillaryDataWSSVIInputWSSPresence
                RollCallString,
            iqhip10AncillaryDataWSSVIInputWSSEnableAlarm
                INTEGER,
            iqhip10AncillaryDataWSSVIInputWSSData
                RollCallString,
            iqhip10AncillaryDataWSSVIInputWSSScanSys
                RollCallString,
            iqhip10AncillaryDataWSSVIInputETSIData
                RollCallString,
            iqhip10AncillaryDataWSSVIInputWSSType
                INTEGER,
            iqhip10AncillaryDataWSSVIInputVIPresence
                RollCallString,
            iqhip10AncillaryDataWSSVIInputVIEnableAlarm
                INTEGER,
            iqhip10AncillaryDataWSSVIInputVIType
                INTEGER,
            iqhip10AncillaryDataWSSVIInputVIData
                RollCallString,
            iqhip10AncillaryDataWSSVIInputVIScanSys
                RollCallString,
            iqhip10AncillaryDataAFDSMPTE20162016Presence
                RollCallString,
            iqhip10AncillaryDataAFDSMPTE20162016EnableAlarm
                INTEGER,
            iqhip10AncillaryDataAFDSMPTE20162016Data
                RollCallString,
            iqhip10AncillaryDataAFDSMPTE20162016ScanSys
                RollCallString,
            iqhip10HyperionAudioDataActiveAudioCh
                RollCallString,
            iqhip10AudioDataGroup1EnableAlarmCh1
                INTEGER,
            iqhip10AudioDataGroup1TypeCh1
                RollCallString,
            iqhip10AudioDataGroup1BitdepthCh1
                RollCallString,
            iqhip10AudioDataGroup1EnableAlarmCh2
                INTEGER,
            iqhip10AudioDataGroup1TypeCh2
                RollCallString,
            iqhip10AudioDataGroup1BitdepthCh2
                RollCallString,
            iqhip10AudioDataGroup1EnableAlarmCh3
                INTEGER,
            iqhip10AudioDataGroup1TypeCh3
                RollCallString,
            iqhip10AudioDataGroup1BitdepthCh3
                RollCallString,
            iqhip10AudioDataGroup1EnableAlarmCh4
                INTEGER,
            iqhip10AudioDataGroup1TypeCh4
                RollCallString,
            iqhip10AudioDataGroup1BitdepthCh4
                RollCallString,
            iqhip10AudioDataGroup2EnableAlarmCh5
                INTEGER,
            iqhip10AudioDataGroup2TypeCh5
                RollCallString,
            iqhip10AudioDataGroup2BitdepthCh5
                RollCallString,
            iqhip10AudioDataGroup2EnableAlarmCh6
                INTEGER,
            iqhip10AudioDataGroup2TypeCh6
                RollCallString,
            iqhip10AudioDataGroup2BitdepthCh6
                RollCallString,
            iqhip10AudioDataGroup2EnableAlarmCh7
                INTEGER,
            iqhip10AudioDataGroup2TypeCh7
                RollCallString,
            iqhip10AudioDataGroup2BitdepthCh7
                RollCallString,
            iqhip10AudioDataGroup2EnableAlarmCh8
                INTEGER,
            iqhip10AudioDataGroup2TypeCh8
                RollCallString,
            iqhip10AudioDataGroup2BitdepthCh8
                RollCallString,
            iqhip10AudioDataGroup3EnableAlarmCh9
                INTEGER,
            iqhip10AudioDataGroup3TypeCh9
                RollCallString,
            iqhip10AudioDataGroup3BitdepthCh9
                RollCallString,
            iqhip10AudioDataGroup3EnableAlarmCh10
                INTEGER,
            iqhip10AudioDataGroup3TypeCh10
                RollCallString,
            iqhip10AudioDataGroup3BitdepthCh10
                RollCallString,
            iqhip10AudioDataGroup3EnableAlarmCh11
                INTEGER,
            iqhip10AudioDataGroup3TypeCh11
                RollCallString,
            iqhip10AudioDataGroup3BitdepthCh11
                RollCallString,
            iqhip10AudioDataGroup3EnableAlarmCh12
                INTEGER,
            iqhip10AudioDataGroup3TypeCh12
                RollCallString,
            iqhip10AudioDataGroup3BitdepthCh12
                RollCallString,
            iqhip10AudioDataGroup4EnableAlarmCh13
                INTEGER,
            iqhip10AudioDataGroup4TypeCh13
                RollCallString,
            iqhip10AudioDataGroup4BitdepthCh13
                RollCallString,
            iqhip10AudioDataGroup4EnableAlarmCh14
                INTEGER,
            iqhip10AudioDataGroup4TypeCh14
                RollCallString,
            iqhip10AudioDataGroup4BitdepthCh14
                RollCallString,
            iqhip10AudioDataGroup4EnableAlarmCh15
                INTEGER,
            iqhip10AudioDataGroup4TypeCh15
                RollCallString,
            iqhip10AudioDataGroup4BitdepthCh15
                RollCallString,
            iqhip10AudioDataGroup4EnableAlarmCh16
                INTEGER,
            iqhip10AudioDataGroup4TypeCh16
                RollCallString,
            iqhip10AudioDataGroup4BitdepthCh16
                RollCallString,
            iqhip10AudioDataDolbyEStatusEnableAlarmPair1
                INTEGER,
            iqhip10AudioDataDolbyEStatusStatusPair1
                RollCallString,
            iqhip10AudioDataDolbyEStatusEnableAlarmPair2
                INTEGER,
            iqhip10AudioDataDolbyEStatusStatusPair2
                RollCallString,
            iqhip10AudioDataDolbyEStatusEnableAlarmPair3
                INTEGER,
            iqhip10AudioDataDolbyEStatusStatusPair3
                RollCallString,
            iqhip10AudioDataDolbyEStatusEnableAlarmPair4
                INTEGER,
            iqhip10AudioDataDolbyEStatusStatusPair4
                RollCallString,
            iqhip10AudioDataDolbyEStatusEnableAlarmPair5
                INTEGER,
            iqhip10AudioDataDolbyEStatusStatusPair5
                RollCallString,
            iqhip10AudioDataDolbyEStatusEnableAlarmPair6
                INTEGER,
            iqhip10AudioDataDolbyEStatusStatusPair6
                RollCallString,
            iqhip10AudioDataDolbyEStatusEnableAlarmPair7
                INTEGER,
            iqhip10AudioDataDolbyEStatusStatusPair7
                RollCallString,
            iqhip10AudioDataDolbyEStatusEnableAlarmPair8
                INTEGER,
            iqhip10AudioDataDolbyEStatusStatusPair8
                RollCallString,
            iqhip10HyperionAudioLevelDetChannelIndex
                INTEGER,
            iqhip10HyperionAudioLevelDetAverageAudioLevel
                RollCallString,
            iqhip10AudioLevelDetOverloadDetectorEnableAlarm
                INTEGER,
            iqhip10AudioLevelDetOverloadDetectorAlarm
                RollCallString,
            iqhip10AudioLevelDetOverloadDetectorLeveldB
                INTEGER,
            iqhip10AudioLevelDetOverloadDetectorWarningsecs
                INTEGER,
            iqhip10AudioLevelDetOverloadDetectorFailsecs
                INTEGER,
            iqhip10AudioLevelDetOverloadDetectorFailHoldsecs
                INTEGER,
            iqhip10AudioLevelDetectorAlarmReset
                INTEGER,
            iqhip10AudioLevelDetLoudDetectorEnableAlarm
                INTEGER,
            iqhip10AudioLevelDetLoudDetectorAlarm
                RollCallString,
            iqhip10AudioLevelDetLoudDetectorLeveldB
                INTEGER,
            iqhip10AudioLevelDetLoudDetectorWarningsecs
                INTEGER,
            iqhip10AudioLevelDetLoudDetectorFailsecs
                INTEGER,
            iqhip10AudioLevelDetLoudDetectorFailHoldsecs
                INTEGER,
            iqhip10AudioLevelDetQuietDetectorEnableAlarm
                INTEGER,
            iqhip10AudioLevelDetQuietDetectorAlarm
                RollCallString,
            iqhip10AudioLevelDetQuietDetectorLeveldB
                INTEGER,
            iqhip10AudioLevelDetQuietDetectorWarningsecs
                INTEGER,
            iqhip10AudioLevelDetQuietDetectorFailsecs
                INTEGER,
            iqhip10AudioLevelDetQuietDetectorFailHoldsecs
                INTEGER,
            iqhip10AudioLevelDetSilenceDetectorEnableAlarm
                INTEGER,
            iqhip10AudioLevelDetSilenceDetectorAlarm
                RollCallString,
            iqhip10AudioLevelDetSilenceDetectorLeveldB
                INTEGER,
            iqhip10AudioLevelDetSilenceDetectorWarningsecs
                INTEGER,
            iqhip10AudioLevelDetSilenceDetectorFailsecs
                INTEGER,
            iqhip10AudioLevelDetSilenceDetectorFailHoldsecs
                INTEGER,
            iqhip10AudioLevelDetDuplicateSettingsCopyFromChannel
                INTEGER,
            iqhip10AudioLevelDetDuplicateSettingsCopySettings
                INTEGER,
            iqhip10AudioLevelDetAlarmChansEnableChanDet
                INTEGER,
            iqhip10AudioLevelDetAlarmAllChansResetonOK
                INTEGER,
            iqhip10HyperionAudioLevelIndRollMapAudLvlEn
                INTEGER,
            iqhip10HyperionAudioLevelIndOSDMarker
                INTEGER,
            iqhip10HyperionAudioLevelIndRollMapAudLvl
                RollCallString,
            iqhip10HyperionAudioLevelIndEnableChannel1
                INTEGER,
            iqhip10HyperionAudioLevelIndChannel1
                RollCallString,
            iqhip10HyperionAudioLevelIndEnableChannel2
                INTEGER,
            iqhip10HyperionAudioLevelIndChannel2
                RollCallString,
            iqhip10HyperionAudioLevelIndEnableChannel3
                INTEGER,
            iqhip10HyperionAudioLevelIndChannel3
                RollCallString,
            iqhip10HyperionAudioLevelIndEnableChannel4
                INTEGER,
            iqhip10HyperionAudioLevelIndChannel4
                RollCallString,
            iqhip10HyperionAudioLevelIndEnableChannel5
                INTEGER,
            iqhip10HyperionAudioLevelIndChannel5
                RollCallString,
            iqhip10HyperionAudioLevelIndEnableChannel6
                INTEGER,
            iqhip10HyperionAudioLevelIndChannel6
                RollCallString,
            iqhip10HyperionAudioLevelIndEnableChannel7
                INTEGER,
            iqhip10HyperionAudioLevelIndChannel7
                RollCallString,
            iqhip10HyperionAudioLevelIndEnableChannel8
                INTEGER,
            iqhip10HyperionAudioLevelIndChannel8
                RollCallString,
            iqhip10HyperionAudioLevelIndEnableChannel9
                INTEGER,
            iqhip10HyperionAudioLevelIndChannel9
                RollCallString,
            iqhip10HyperionAudioLevelIndEnableChannel10
                INTEGER,
            iqhip10HyperionAudioLevelIndChannel10
                RollCallString,
            iqhip10HyperionAudioLevelIndEnableChannel11
                INTEGER,
            iqhip10HyperionAudioLevelIndChannel11
                RollCallString,
            iqhip10HyperionAudioLevelIndEnableChannel12
                INTEGER,
            iqhip10HyperionAudioLevelIndChannel12
                RollCallString,
            iqhip10HyperionAudioLevelIndEnableChannel13
                INTEGER,
            iqhip10HyperionAudioLevelIndChannel13
                RollCallString,
            iqhip10HyperionAudioLevelIndEnableChannel14
                INTEGER,
            iqhip10HyperionAudioLevelIndChannel14
                RollCallString,
            iqhip10HyperionAudioLevelIndEnableChannel15
                INTEGER,
            iqhip10HyperionAudioLevelIndChannel15
                RollCallString,
            iqhip10HyperionAudioLevelIndEnableChannel16
                INTEGER,
            iqhip10HyperionAudioLevelIndChannel16
                RollCallString,
            iqhip10HyperionClippingDetectorThreshold
                INTEGER,
            iqhip10HyperionClippingDetectorSensitivity
                INTEGER,
            iqhip10HyperionClippingDetectorStatusCh1
                RollCallString,
            iqhip10HyperionClippingDetectorEnableAlarmCh1
                INTEGER,
            iqhip10HyperionClippingDetectorStatusCh2
                RollCallString,
            iqhip10HyperionClippingDetectorEnableAlarmCh2
                INTEGER,
            iqhip10HyperionClippingDetectorStatusCh3
                RollCallString,
            iqhip10HyperionClippingDetectorEnableAlarmCh3
                INTEGER,
            iqhip10HyperionClippingDetectorStatusCh4
                RollCallString,
            iqhip10HyperionClippingDetectorEnableAlarmCh4
                INTEGER,
            iqhip10HyperionClippingDetectorStatusCh5
                RollCallString,
            iqhip10HyperionClippingDetectorEnableAlarmCh5
                INTEGER,
            iqhip10HyperionClippingDetectorStatusCh6
                RollCallString,
            iqhip10HyperionClippingDetectorEnableAlarmCh6
                INTEGER,
            iqhip10HyperionClippingDetectorStatusCh7
                RollCallString,
            iqhip10HyperionClippingDetectorEnableAlarmCh7
                INTEGER,
            iqhip10HyperionClippingDetectorStatusCh8
                RollCallString,
            iqhip10HyperionClippingDetectorEnableAlarmCh8
                INTEGER,
            iqhip10HyperionClippingDetectorStatusCh9
                RollCallString,
            iqhip10HyperionClippingDetectorEnableAlarmCh9
                INTEGER,
            iqhip10HyperionClippingDetectorStatusCh10
                RollCallString,
            iqhip10HyperionClippingDetectorEnableAlarmCh10
                INTEGER,
            iqhip10HyperionClippingDetectorStatusCh11
                RollCallString,
            iqhip10HyperionClippingDetectorEnableAlarmCh11
                INTEGER,
            iqhip10HyperionClippingDetectorStatusCh12
                RollCallString,
            iqhip10HyperionClippingDetectorEnableAlarmCh12
                INTEGER,
            iqhip10HyperionClippingDetectorStatusCh13
                RollCallString,
            iqhip10HyperionClippingDetectorEnableAlarmCh13
                INTEGER,
            iqhip10HyperionClippingDetectorStatusCh14
                RollCallString,
            iqhip10HyperionClippingDetectorEnableAlarmCh14
                INTEGER,
            iqhip10HyperionClippingDetectorStatusCh15
                RollCallString,
            iqhip10HyperionClippingDetectorEnableAlarmCh15
                INTEGER,
            iqhip10HyperionClippingDetectorStatusCh16
                RollCallString,
            iqhip10HyperionClippingDetectorEnableAlarmCh16
                INTEGER,
            iqhip10AudioLikenessDetector1Likeness
                RollCallString,
            iqhip10AudioLikenessDetector1State
                RollCallString,
            iqhip10AudioLikenessDetector1SelectChannelA
                INTEGER,
            iqhip10AudioLikenessDetector1SelectChannelB
                INTEGER,
            iqhip10AudioLikenessDetector1EnableAlarm
                INTEGER,
            iqhip10AudioLikenessDetector2Likeness
                RollCallString,
            iqhip10AudioLikenessDetector2State
                RollCallString,
            iqhip10AudioLikenessDetector2SelectChannelA
                INTEGER,
            iqhip10AudioLikenessDetector2SelectChannelB
                INTEGER,
            iqhip10AudioLikenessDetector2AlarmEnable
                INTEGER,
            iqhip10AudioLikenessDetector3Likeness
                RollCallString,
            iqhip10AudioLikenessDetector3State
                RollCallString,
            iqhip10AudioLikenessDetector3SelectChannelA
                INTEGER,
            iqhip10AudioLikenessDetector3SelectChannelB
                INTEGER,
            iqhip10AudioLikenessDetector3AlarmEnable
                INTEGER,
            iqhip10AudioLikenessDetector4Likeness
                RollCallString,
            iqhip10AudioLikenessDetector4State
                RollCallString,
            iqhip10AudioLikenessDetector4SelectChannelA
                INTEGER,
            iqhip10AudioLikenessDetector4SelectChannelB
                INTEGER,
            iqhip10AudioLikenessDetector4AlarmEnable
                INTEGER,
            iqhip10UMIDReaderDetectonYOnly
                INTEGER,
            iqhip10UMIDReaderUMIDPresence
                RollCallString,
            iqhip10UMIDReaderFoundOnLine
                RollCallString,
            iqhip10ReaderUniversalLabelVersionNumber
                RollCallString,
            iqhip10ReaderUniversalLabelMaterialType
                RollCallString,
            iqhip10ReaderUniversalLabelIdentMatNumGen
                RollCallString,
            iqhip10ReaderUniversalLabelIdentInstNumGen
                RollCallString,
            iqhip10UMIDReaderInstanceNumber
                RollCallString,
            iqhip10ReaderMaterialNumberMaterialNum14
                RollCallString,
            iqhip10ReaderMaterialNumberMaterialNum58
                RollCallString,
            iqhip10ReaderMaterialNumberMaterialNum912
                RollCallString,
            iqhip10ReaderMaterialNumberMaterialNum1316
                RollCallString,
            iqhip10UMIDReaderCount
                RollCallString,
            iqhip10HyperionUMIDDelete
                INTEGER,
            iqhip10UMIDGeneratorEnable
                INTEGER,
            iqhip10HyperionUMIDGeneratorStatus
                RollCallString,
            iqhip10UMIDGeneratorGenerateonYOnly
                INTEGER,
            iqhip10UMIDGeneratorTake
                INTEGER,
            iqhip10UMIDGeneratorLineNumber
                INTEGER,
            iqhip10GeneratorUniversalLabelVersionNumber
                INTEGER,
            iqhip10GeneratorUniversalLabelMaterialType
                INTEGER,
            iqhip10GeneratorUniversalLabelIdentofMaterial
                INTEGER,
            iqhip10GeneratorUniversalLabelIdentofInstance
                INTEGER,
            iqhip10UMIDGeneratorInstanceNum
                RollCallString,
            iqhip10UMIDGeneratorMaterialNum14
                RollCallString,
            iqhip10UMIDGeneratorMaterialNum58
                RollCallString,
            iqhip10UMIDGeneratorMaterialNum912
                RollCallString,
            iqhip10UMIDGeneratorMaterialNum1316
                RollCallString,
            iqhip10HyperionUMIDAlarmEnable
                INTEGER,
            iqhip10PIDReaderPIDPresence
                RollCallString,
            iqhip10PIDReaderFoundOnLine
                RollCallString,
            iqhip10PIDReaderHouseID
                RollCallString,
            iqhip10PIDReaderProgramTitle
                RollCallString,
            iqhip10PIDReaderSegmentNumber
                RollCallString,
            iqhip10PIDReaderDuration
                RollCallString,
            iqhip10PIDReaderFrameRate
                RollCallString,
            iqhip10PIDReaderCount
                RollCallString,
            iqhip10HyperionPIDDelete
                INTEGER,
            iqhip10PIDGeneratorEnable
                INTEGER,
            iqhip10HyperionPIDGeneratorStatus
                RollCallString,
            iqhip10PIDGeneratorTake
                INTEGER,
            iqhip10PIDGeneratorLineNumber
                INTEGER,
            iqhip10PIDGeneratorHouseID
                RollCallString,
            iqhip10PIDGeneratorProgramTitle
                RollCallString,
            iqhip10PIDGeneratorProgramTitleEn
                INTEGER,
            iqhip10PIDGeneratorSegmentNumber
                RollCallString,
            iqhip10PIDGeneratorSegmentNumberEn
                INTEGER,
            iqhip10PIDGeneratorDuration
                RollCallString,
            iqhip10PIDGeneratorDurationEn
                INTEGER,
            iqhip10PIDGeneratorFrameRateEn
                INTEGER,
            iqhip10PIDGeneratorFrameRate
                INTEGER,
            iqhip10HyperionPIDAlarmEnable
                INTEGER,
            iqhip10HyperionOSDPassword
                RollCallString,
            iqhip10HyperionOSDEnable
                INTEGER,
            iqhip10HyperionOSDHold
                INTEGER,
            iqhip10OSDOnScreenDispEnIndicators
                INTEGER,
            iqhip10OSDOnScreenDispEnAudioLevelInds
                INTEGER,
            iqhip10OSDOnScreenDispEnTimecode
                INTEGER,
            iqhip10OSDOnScreenDispEnGreyBackground
                INTEGER,
            iqhip10OSDOnScreenDispEnInputModeEn
                INTEGER,
            iqhip10OSDOnScreenDispEnInput1NameEn
                INTEGER,
            iqhip10OSDOnScreenDispEnSFPRxANameEn
                INTEGER,
            iqhip10OSDOnScreenDispEnCaption1Edit
                RollCallString,
            iqhip10OSDOnScreenDispEnCaption1Enable
                INTEGER,
            iqhip10OSDOnScreenDispEnCaption2Edit
                RollCallString,
            iqhip10OSDOnScreenDispEnCaption2Enable
                INTEGER,
            iqhip10OSDOnScreenDispEnContentAdvisory
                INTEGER,
            iqhip10OSDOnScreenDispEnIncomingPID
                INTEGER,
            iqhip10OSDOnScreenDispEnOutgoingPID
                INTEGER,
            iqhip10OSDOnScreenDispEnAudioLvlIndZoom
                INTEGER,
            iqhip10OSDOnScreenDispEnRegion1DetWindow
                INTEGER,
            iqhip10OSDOnScreenDispEnRegion2DetWindow
                INTEGER,
            iqhip10OSDOutputEnablesOutput1
                INTEGER,
            iqhip10OSDOutputEnablesOutput2
                INTEGER,
            iqhip10OSDOutputEnablesOutput3
                INTEGER,
            iqhip10OSDOutputEnablesOutput4
                INTEGER,
            iqhip10HyperionEnableDisables
                INTEGER,
            iqhip10HyperionDisplayStatusHyperionDispEn
                INTEGER,
            iqhip10HyperionDisplayStatusDisplayTimeout
                RollCallString,
            iqhip10HyperionDisplayStatusHyperionDetStatus
                INTEGER,
            iqhip10LoggingMiscTimecodelogEn
                INTEGER,
            iqhip10LoggingMiscLogSerialNo
                INTEGER,
            iqhip10LoggingMiscSerialNo
                RollCallString,
            iqhip10LoggingMiscLogOSVersion
                INTEGER,
            iqhip10LoggingMiscOSVersion
                RollCallString,
            iqhip10LoggingMiscLogBuildNo
                INTEGER,
            iqhip10LoggingMiscBuildNo
                RollCallString,
            iqhip10LoggingMiscLogHardwareVer
                INTEGER,
            iqhip10LoggingMiscHardwareVer
                RollCallString,
            iqhip10LoggingMiscLogFirmwareVer
                INTEGER,
            iqhip10LoggingMiscFirmwareVer
                RollCallString,
            iqhip10LoggingMiscLogUpTime
                INTEGER,
            iqhip10LoggingMiscUpTime
                RollCallString,
            iqhip10LoggingMiscLogRollTracks
                INTEGER,
            iqhip10LoggingMiscRollTracks
                RollCallString,
            iqhip10LoggingMiscLogOSDStatus
                INTEGER,
            iqhip10LoggingMiscOSDStatus
                RollCallString,
            iqhip10LoggingMiscLogCaption1
                INTEGER,
            iqhip10LoggingMiscInput1Caption1
                RollCallString,
            iqhip10LoggingMiscLogCaption2
                INTEGER,
            iqhip10LoggingMiscInput1Caption2
                RollCallString,
            iqhip10LoggingMiscLogLastRecallMem
                INTEGER,
            iqhip10LoggingMiscLastRecallMem
                RollCallString,
            iqhip10LoggingMiscLogRearID
                INTEGER,
            iqhip10LoggingMiscRearID
                RollCallString,
            iqhip10LoggingMiscLogSlotWidth
                INTEGER,
            iqhip10LoggingMiscSlotWidth
                RollCallString,
            iqhip10LoggingMiscLogSlotStart
                INTEGER,
            iqhip10LoggingMiscSlotStart
                RollCallString,
            iqhip10LoggingMiscLogRearStatus
                INTEGER,
            iqhip10LoggingMiscRearSTATUS
                RollCallString,
            iqhip10LoggingMiscLogPowerUsage
                INTEGER,
            iqhip10LoggingMiscPowerUsage
                RollCallString,
            iqhip10LoggingMiscLogLicensedOpt
                INTEGER,
            iqhip10LoggingMiscLicensedOptions
                RollCallString,
            iqhip10LoggingInput1LogInputIdent
                INTEGER,
            iqhip10LoggingInput1InputIdent
                RollCallString,
            iqhip10LoggingInput1LogInputName
                INTEGER,
            iqhip10LoggingInput1InputName
                RollCallString,
            iqhip10LoggingInput1LogInputType
                INTEGER,
            iqhip10LoggingInput1InputType
                RollCallString,
            iqhip10LoggingInput1LogInputState
                INTEGER,
            iqhip10LoggingInput1InputState
                RollCallString,
            iqhip10LoggingInput1LogInputStandard
                INTEGER,
            iqhip10LoggingInput1InputStandard
                RollCallString,
            iqhip10LoggingInput1LogEDH
                INTEGER,
            iqhip10LoggingInput1EDH
                RollCallString,
            iqhip10LoggingInput1LogCRC
                INTEGER,
            iqhip10LoggingInput1CRC
                RollCallString,
            iqhip10LoggingSFPLogType
                INTEGER,
            iqhip10LoggingSFP1Type
                RollCallString,
            iqhip10LoggingSFPLogStatus
                INTEGER,
            iqhip10LoggingSFPStatus
                RollCallString,
            iqhip10LoggingSFPLogConnector
                INTEGER,
            iqhip10LoggingSFPConnector
                RollCallString,
            iqhip10LoggingSFPARxLogRxIdent
                INTEGER,
            iqhip10LoggingSFPARxRxIdent
                RollCallString,
            iqhip10LoggingSFPARxLogRxName
                INTEGER,
            iqhip10LoggingSFPARxRxName
                RollCallString,
            iqhip10LoggingSFPARxLogRxPowerState
                INTEGER,
            iqhip10LoggingSFPARxRxPowerState
                RollCallString,
            iqhip10LoggingSFPARxLogRxPower
                INTEGER,
            iqhip10LoggingSFPARxRxPower
                RollCallString,
            iqhip10LoggingSFPATxLogTxPowerState
                INTEGER,
            iqhip10LoggingSFPATxTxPowerState
                RollCallString,
            iqhip10LoggingSFPATxLogTxPower
                INTEGER,
            iqhip10LoggingSFPATxTxPower
                RollCallString,
            iqhip10LoggingSFPATxLogWavelength
                INTEGER,
            iqhip10LoggingSFPATxWavelength
                RollCallString,
            iqhip10LoggingSFPATxLogLaserBias
                INTEGER,
            iqhip10LoggingSFPATxLaserBias
                RollCallString,
            iqhip10LoggingSFPATxLogLaserBiasState
                INTEGER,
            iqhip10LoggingSFPATxLaserBiasState
                RollCallString,
            iqhip10LoggingSFPBTxLogTxPowerState
                INTEGER,
            iqhip10LoggingSFPBTxTxPowerState
                RollCallString,
            iqhip10LoggingSFPBTxLogTxPower
                INTEGER,
            iqhip10LoggingSFPBTxTxPower
                RollCallString,
            iqhip10LoggingSFPBTxLogWavelength
                INTEGER,
            iqhip10LoggingSFPBTxWavelength
                RollCallString,
            iqhip10LoggingSFPBTxLogLaserBias
                INTEGER,
            iqhip10LoggingSFPBTxLaserBias
                RollCallString,
            iqhip10LoggingSFPBTxLogLaserBiasState
                INTEGER,
            iqhip10LoggingSFPBTxLaserBiasState
                RollCallString,
            iqhip10LoggingMonitorLogHyperionSummary
                INTEGER,
            iqhip10LoggingMonitorHyperionSummary
                RollCallString,
            iqhip10MonitorRegion1LogReg1Black
                INTEGER,
            iqhip10MonitorRegion1Reg1Black
                RollCallString,
            iqhip10MonitorRegion1Reg1BlackLogOpt
                INTEGER,
            iqhip10MonitorRegion1LogReg1Blackish
                INTEGER,
            iqhip10MonitorRegion1Reg1Blackish
                RollCallString,
            iqhip10MonitorRegion1Reg1BlackishLogOpt
                INTEGER,
            iqhip10MonitorRegion1LogReg1Stillish
                INTEGER,
            iqhip10MonitorRegion1Reg1Stillish
                RollCallString,
            iqhip10MonitorRegion1Reg1StillishLogOpt
                INTEGER,
            iqhip10MonitorRegion1LogReg1Freeze
                INTEGER,
            iqhip10MonitorRegion1Reg1Freeze
                RollCallString,
            iqhip10MonitorRegion1Reg1FreezeLogOpt
                INTEGER,
            iqhip10MonitorRegion2LogReg2Black
                INTEGER,
            iqhip10MonitorRegion2Reg1Black
                RollCallString,
            iqhip10MonitorRegion2Reg2BlackLogOpt
                INTEGER,
            iqhip10MonitorRegion2LogReg2Blackish
                INTEGER,
            iqhip10MonitorRegion2Reg2Blackish
                RollCallString,
            iqhip10MonitorRegion2Reg2BlackishLogOpt
                INTEGER,
            iqhip10MonitorRegion2LogReg2Stillish
                INTEGER,
            iqhip10MonitorRegion2Reg2Stillish
                RollCallString,
            iqhip10MonitorRegion2Reg2StillishLogOpt
                INTEGER,
            iqhip10MonitorRegion2LogReg2Freeze
                INTEGER,
            iqhip10MonitorRegion2Reg2Freeze
                RollCallString,
            iqhip10MonitorRegion2Reg2FreezeLogOpt
                INTEGER,
            iqhip10LoggingMonitorLogCldCapState
                INTEGER,
            iqhip10LoggingMonitorClosedCapState
                RollCallString,
            iqhip10LoggingMonitorClosedCapLogOpt
                INTEGER,
            iqhip10LoggingMonitorLogCldCapType
                INTEGER,
            iqhip10LoggingMonitorClosedCapType
                RollCallString,
            iqhip10LoggingMonitorLogCldCapTitle
                INTEGER,
            iqhip10LoggingMonitorClosedCapTitle
                RollCallString,
            iqhip10LoggingMonitorLogYBitDepth
                INTEGER,
            iqhip10LoggingMonitorYBitDepth
                RollCallString,
            iqhip10LoggingMonitorLogCBitDepth
                INTEGER,
            iqhip10LoggingMonitorCBitDepth
                RollCallString,
            iqhip10LoggingMonitorLogVideoYLvlHigh
                INTEGER,
            iqhip10LoggingMonitorVideoYLevelHigh
                RollCallString,
            iqhip10LoggingMonitorLogVideoCLvlHigh
                INTEGER,
            iqhip10LoggingMonitorVideoCLevelHigh
                RollCallString,
            iqhip10LoggingMonitorLogVideoYLvlLow
                INTEGER,
            iqhip10LoggingMonitorVideoYLevelLow
                RollCallString,
            iqhip10LoggingMonitorLogVideoCLvlLow
                INTEGER,
            iqhip10LoggingMonitorVideoCLevelLow
                RollCallString,
            iqhip10LoggingMonitorLogAPL
                INTEGER,
            iqhip10LoggingMonitorAPL
                RollCallString,
            iqhip10LoggingMonitorLogVITCState
                INTEGER,
            iqhip10LoggingMonitorVITCState
                RollCallString,
            iqhip10LoggingMonitorLogCAState
                INTEGER,
            iqhip10LoggingMonitorCAState
                RollCallString,
            iqhip10LoggingMonitorLogCASystem
                INTEGER,
            iqhip10LoggingMonitorCASystem
                RollCallString,
            iqhip10LoggingMonitorLogCAAgeRating
                INTEGER,
            iqhip10LoggingMonitorCAAgeRating
                RollCallString,
            iqhip10LoggingMonitorLogANCTCState
                INTEGER,
            iqhip10LoggingMonitorANCTimecodeState
                RollCallString,
            iqhip10LoggingMonitorLogTimecodeDiscon
                INTEGER,
            iqhip10LoggingMonitorTimecodeDiscon
                RollCallString,
            iqhip10LoggingMonitorLogUser1DIDName
                INTEGER,
            iqhip10LoggingMonitorUser1DIDName
                RollCallString,
            iqhip10LoggingMonitorLogUser1DIDState
                INTEGER,
            iqhip10LoggingMonitorUser1DIDState
                RollCallString,
            iqhip10LoggingMonitorLogUser2DIDName
                INTEGER,
            iqhip10LoggingMonitorUser2DIDName
                RollCallString,
            iqhip10LoggingMonitorLogUser2DIDState
                INTEGER,
            iqhip10LoggingMonitorUser2DIDState
                RollCallString,
            iqhip10MonitorInp1WideScreenLogVIState
                INTEGER,
            iqhip10MonitorInp1WideScreenVIState
                RollCallString,
            iqhip10MonitorInp1WideScreenLogVIAspect
                INTEGER,
            iqhip10MonitorInp1WideScreenVIAspect
                RollCallString,
            iqhip10MonitorInp1WideScreenLogVI
                INTEGER,
            iqhip10MonitorInp1WideScreenVI
                RollCallString,
            iqhip10MonitorInp1WideScreenLogWSSState
                INTEGER,
            iqhip10MonitorInp1WideScreenWSSState
                RollCallString,
            iqhip10MonitorInp1WideScreenLogWSSAspect
                INTEGER,
            iqhip10MonitorInp1WideScreenWSSAspect
                RollCallString,
            iqhip10MonitorInp1WideScreenLogWSS
                INTEGER,
            iqhip10MonitorInp1WideScreenWSS
                RollCallString,
            iqhip10MonitorInp1WideScreenLogETSIData
                INTEGER,
            iqhip10MonitorInp1WideScreenETSIData
                RollCallString,
            iqhip10MonitorInp1WideScreenLogAFD2016State
                INTEGER,
            iqhip10MonitorInp1WideScreenAFD2016State
                RollCallString,
            iqhip10MonitorInp1WideScreenLogAFD2016Aspect
                INTEGER,
            iqhip10MonitorInp1WideScreenAFD2016Aspect
                RollCallString,
            iqhip10MonitorInp1WideScreenLogAFD2016
                INTEGER,
            iqhip10MonitorInp1WideScreenAFD2016
                RollCallString,
            iqhip10LoggingInp1AudStateLogEmbCh1State
                INTEGER,
            iqhip10LoggingInp1AudStateEmbCh1State
                RollCallString,
            iqhip10LoggingInp1AudStateLogEmbCh2State
                INTEGER,
            iqhip10LoggingInp1AudStateEmbCh2State
                RollCallString,
            iqhip10LoggingInp1AudStateLogEmbCh3State
                INTEGER,
            iqhip10LoggingInp1AudStateEmbCh3State
                RollCallString,
            iqhip10LoggingInp1AudStateLogEmbCh4State
                INTEGER,
            iqhip10LoggingInp1AudStateEmbCh4State
                RollCallString,
            iqhip10LoggingInp1AudStateLogEmbCh5State
                INTEGER,
            iqhip10LoggingInp1AudStateEmbCh5State
                RollCallString,
            iqhip10LoggingInp1AudStateLogEmbCh6State
                INTEGER,
            iqhip10LoggingInp1AudStateEmbCh6State
                RollCallString,
            iqhip10LoggingInp1AudStateLogEmbCh7State
                INTEGER,
            iqhip10LoggingInp1AudStateEmbCh7State
                RollCallString,
            iqhip10LoggingInp1AudStateLogEmbCh8State
                INTEGER,
            iqhip10LoggingInp1AudStateEmbCh8State
                RollCallString,
            iqhip10LoggingInp1AudStateLogEmbCh9State
                INTEGER,
            iqhip10LoggingInp1AudStateEmbCh9State
                RollCallString,
            iqhip10LoggingInp1AudStateLogEmbCh10State
                INTEGER,
            iqhip10LoggingInp1AudStateEmbCh10State
                RollCallString,
            iqhip10LoggingInp1AudStateLogEmbCh11State
                INTEGER,
            iqhip10LoggingInp1AudStateEmbCh11State
                RollCallString,
            iqhip10LoggingInp1AudStateLogEmbCh12State
                INTEGER,
            iqhip10LoggingInp1AudStateEmbCh12State
                RollCallString,
            iqhip10LoggingInp1AudStateLogEmbCh13State
                INTEGER,
            iqhip10LoggingInp1AudStateEmbCh13State
                RollCallString,
            iqhip10LoggingInp1AudStateLogEmbCh14State
                INTEGER,
            iqhip10LoggingInp1AudStateEmbCh14State
                RollCallString,
            iqhip10LoggingInp1AudStateLogEmbCh15State
                INTEGER,
            iqhip10LoggingInp1AudStateEmbCh15State
                RollCallString,
            iqhip10LoggingInp1AudStateLogEmbCh16State
                INTEGER,
            iqhip10LoggingInp1AudStateEmbCh16State
                RollCallString,
            iqhip10LoggingInp1AudTypeLogEmbCh1Type
                INTEGER,
            iqhip10LoggingInp1AudTypeEmbCh1Type
                RollCallString,
            iqhip10LoggingInp1AudTypeLogEmbCh2Type
                INTEGER,
            iqhip10LoggingInp1AudTypeEmbCh2Type
                RollCallString,
            iqhip10LoggingInp1AudTypeLogEmbCh3Type
                INTEGER,
            iqhip10LoggingInp1AudTypeEmbCh3Type
                RollCallString,
            iqhip10LoggingInp1AudTypeLogEmbCh4Type
                INTEGER,
            iqhip10LoggingInp1AudTypeEmbCh4Type
                RollCallString,
            iqhip10LoggingInp1AudTypeLogEmbCh5Type
                INTEGER,
            iqhip10LoggingInp1AudTypeEmbCh5Type
                RollCallString,
            iqhip10LoggingInp1AudTypeLogEmbCh6Type
                INTEGER,
            iqhip10LoggingInp1AudTypeEmbCh6Type
                RollCallString,
            iqhip10LoggingInp1AudTypeLogEmbCh7Type
                INTEGER,
            iqhip10LoggingInp1AudTypeEmbCh7Type
                RollCallString,
            iqhip10LoggingInp1AudTypeLogEmbCh8Type
                INTEGER,
            iqhip10LoggingInp1AudTypeEmbCh8Type
                RollCallString,
            iqhip10LoggingInp1AudTypeLogEmbCh9Type
                INTEGER,
            iqhip10LoggingInp1AudTypeEmbCh9Type
                RollCallString,
            iqhip10LoggingInp1AudTypeLogEmbCh10Type
                INTEGER,
            iqhip10LoggingInp1AudTypeEmbCh10Type
                RollCallString,
            iqhip10LoggingInp1AudTypeLogEmbCh11Type
                INTEGER,
            iqhip10LoggingInp1AudTypeEmbCh11Type
                RollCallString,
            iqhip10LoggingInp1AudTypeLogEmbCh12Type
                INTEGER,
            iqhip10LoggingInp1AudTypeEmbCh12Type
                RollCallString,
            iqhip10LoggingInp1AudTypeLogEmbCh13Type
                INTEGER,
            iqhip10LoggingInp1AudTypeEmbCh13Type
                RollCallString,
            iqhip10LoggingInp1AudTypeLogEmbCh14Type
                INTEGER,
            iqhip10LoggingInp1AudTypeEmbCh14Type
                RollCallString,
            iqhip10LoggingInp1AudTypeLogEmbCh15Type
                INTEGER,
            iqhip10LoggingInp1AudTypeEmbCh15Type
                RollCallString,
            iqhip10LoggingInp1AudTypeLogEmbCh16Type
                INTEGER,
            iqhip10LoggingInp1AudTypeEmbCh16Type
                RollCallString,
            iqhip10LoggingInp1DolbyEStateLogPair1
                INTEGER,
            iqhip10LoggingInp1DolbyEStatePair1State
                RollCallString,
            iqhip10LoggingInp1DolbyEStateLogPair2
                INTEGER,
            iqhip10LoggingInp1DolbyEStatePair2State
                RollCallString,
            iqhip10LoggingInp1DolbyEStateLogPair3
                INTEGER,
            iqhip10LoggingInp1DolbyEStatePair3State
                RollCallString,
            iqhip10LoggingInp1DolbyEStateLogPair4
                INTEGER,
            iqhip10LoggingInp1DolbyEStatePair4State
                RollCallString,
            iqhip10LoggingInp1DolbyEStateLogPair5
                INTEGER,
            iqhip10LoggingInp1DolbyEStatePair5State
                RollCallString,
            iqhip10LoggingInp1DolbyEStateLogPair6
                INTEGER,
            iqhip10LoggingInp1DolbyEStatePair6State
                RollCallString,
            iqhip10LoggingInp1DolbyEStateLogPair7
                INTEGER,
            iqhip10LoggingInp1DolbyEStatePair7State
                RollCallString,
            iqhip10LoggingInp1DolbyEStateLogPair8
                INTEGER,
            iqhip10LoggingInp1DolbyEStatePair8State
                RollCallString,
            iqhip10LoggingInp1BitDepthLogEmbCh1BitDepth
                INTEGER,
            iqhip10LoggingInp1BitDepthEmbCh1BitDepth
                RollCallString,
            iqhip10LoggingInp1BitDepthLogEmbCh2BitDepth
                INTEGER,
            iqhip10LoggingInp1BitDepthEmbCh2BitDepth
                RollCallString,
            iqhip10LoggingInp1BitDepthLogEmbCh3BitDepth
                INTEGER,
            iqhip10LoggingInp1BitDepthEmbCh3BitDepth
                RollCallString,
            iqhip10LoggingInp1BitDepthLogEmbCh4BitDepth
                INTEGER,
            iqhip10LoggingInp1BitDepthEmbCh4BitDepth
                RollCallString,
            iqhip10LoggingInp1BitDepthLogEmbCh5BitDepth
                INTEGER,
            iqhip10LoggingInp1BitDepthEmbCh5BitDepth
                RollCallString,
            iqhip10LoggingInp1BitDepthLogEmbCh6BitDepth
                INTEGER,
            iqhip10LoggingInp1BitDepthEmbCh6BitDepth
                RollCallString,
            iqhip10LoggingInp1BitDepthLogEmbCh7BitDepth
                INTEGER,
            iqhip10LoggingInp1BitDepthEmbCh7BitDepth
                RollCallString,
            iqhip10LoggingInp1BitDepthLogEmbCh8BitDepth
                INTEGER,
            iqhip10LoggingInp1BitDepthEmbCh8BitDepth
                RollCallString,
            iqhip10LoggingInp1BitDepthLogEmbCh9BitDepth
                INTEGER,
            iqhip10LoggingInp1BitDepthEmbCh9BitDepth
                RollCallString,
            iqhip10LoggingInp1BitDepthLogEmbCh10BitDepth
                INTEGER,
            iqhip10LoggingInp1BitDepthEmbCh10BitDep
                RollCallString,
            iqhip10LoggingInp1BitDepthLogEmbCh11BitDepth
                INTEGER,
            iqhip10LoggingInp1BitDepthEmbCh11BitDep
                RollCallString,
            iqhip10LoggingInp1BitDepthLogEmbCh12BitDepth
                INTEGER,
            iqhip10LoggingInp1BitDepthEmbCh12BitDep
                RollCallString,
            iqhip10LoggingInp1BitDepthLogEmbCh13BitDepth
                INTEGER,
            iqhip10LoggingInp1BitDepthEmbCh13BitDep
                RollCallString,
            iqhip10LoggingInp1BitDepthLogEmbCh14BitDepth
                INTEGER,
            iqhip10LoggingInp1BitDepthEmbCh14BitDep
                RollCallString,
            iqhip10LoggingInp1BitDepthLogEmbCh15BitDepth
                INTEGER,
            iqhip10LoggingInp1BitDepthEmbCh15BitDep
                RollCallString,
            iqhip10LoggingInp1BitDepthLogEmbCh16BitDepth
                INTEGER,
            iqhip10LoggingInp1BitDepthEmbCh16BitDep
                RollCallString,
            iqhip10LoggingInp1LevelLogEmbCh1Level
                INTEGER,
            iqhip10LoggingInp1LevelEmbCh1Level
                RollCallString,
            iqhip10LoggingInp1LevelLogEmbCh2Level
                INTEGER,
            iqhip10LoggingInp1LevelEmbCh2Level
                RollCallString,
            iqhip10LoggingInp1LevelLogEmbCh3Level
                INTEGER,
            iqhip10LoggingInp1LevelEmbCh3Level
                RollCallString,
            iqhip10LoggingInp1LevelLogEmbCh4Level
                INTEGER,
            iqhip10LoggingInp1LevelEmbCh4Level
                RollCallString,
            iqhip10LoggingInp1LevelLogEmbCh5Level
                INTEGER,
            iqhip10LoggingInp1LevelEmbCh5Level
                RollCallString,
            iqhip10LoggingInp1LevelLogEmbCh6Level
                INTEGER,
            iqhip10LoggingInp1LevelEmbCh6Level
                RollCallString,
            iqhip10LoggingInp1LevelLogEmbCh7Level
                INTEGER,
            iqhip10LoggingInp1LevelEmbCh7Level
                RollCallString,
            iqhip10LoggingInp1LevelLogEmbCh8Level
                INTEGER,
            iqhip10LoggingInp1LevelEmbCh8Level
                RollCallString,
            iqhip10LoggingInp1LevelLogEmbCh9Level
                INTEGER,
            iqhip10LoggingInp1LevelEmbCh9Level
                RollCallString,
            iqhip10LoggingInp1LevelLogEmbCh10Level
                INTEGER,
            iqhip10LoggingInp1LevelEmbCh10Level
                RollCallString,
            iqhip10LoggingInp1LevelLogEmbCh11Level
                INTEGER,
            iqhip10LoggingInp1LevelEmbCh11Level
                RollCallString,
            iqhip10LoggingInp1LevelLogEmbCh12Level
                INTEGER,
            iqhip10LoggingInp1LevelEmbCh12Level
                RollCallString,
            iqhip10LoggingInp1LevelLogEmbCh13Level
                INTEGER,
            iqhip10LoggingInp1LevelEmbCh13Level
                RollCallString,
            iqhip10LoggingInp1LevelLogEmbCh14Level
                INTEGER,
            iqhip10LoggingInp1LevelEmbCh14Level
                RollCallString,
            iqhip10LoggingInp1LevelLogEmbCh15Level
                INTEGER,
            iqhip10LoggingInp1LevelEmbCh15Level
                RollCallString,
            iqhip10LoggingInp1LevelLogEmbCh16Level
                INTEGER,
            iqhip10LoggingInp1LevelEmbCh16Level
                RollCallString,
            iqhip10LoggingInp1ClippingLogEmbCh1Clipping
                INTEGER,
            iqhip10LoggingInp1ClippingEmbCh1Clipping
                RollCallString,
            iqhip10LoggingInp1ClippingLogEmbCh2Clipping
                INTEGER,
            iqhip10LoggingInp1ClippingEmbCh2Clipping
                RollCallString,
            iqhip10LoggingInp1ClippingLogEmbCh3Clipping
                INTEGER,
            iqhip10LoggingInp1ClippingEmbCh3Clipping
                RollCallString,
            iqhip10LoggingInp1ClippingLogEmbCh4Clipping
                INTEGER,
            iqhip10LoggingInp1ClippingEmbCh4Clipping
                RollCallString,
            iqhip10LoggingInp1ClippingLogEmbCh5Clipping
                INTEGER,
            iqhip10LoggingInp1ClippingEmbCh5Clipping
                RollCallString,
            iqhip10LoggingInp1ClippingLogEmbCh6Clipping
                INTEGER,
            iqhip10LoggingInp1ClippingEmbCh6Clipping
                RollCallString,
            iqhip10LoggingInp1ClippingLogEmbCh7Clipping
                INTEGER,
            iqhip10LoggingInp1ClippingEmbCh7Clipping
                RollCallString,
            iqhip10LoggingInp1ClippingLogEmbCh8Clipping
                INTEGER,
            iqhip10LoggingInp1ClippingEmbCh8Clipping
                RollCallString,
            iqhip10LoggingInp1ClippingLogEmbCh9Clipping
                INTEGER,
            iqhip10LoggingInp1ClippingEmbCh9Clipping
                RollCallString,
            iqhip10LoggingInp1ClippingLogEmbCh10Clipping
                INTEGER,
            iqhip10LoggingInp1ClippingEmbCh10Clipping
                RollCallString,
            iqhip10LoggingInp1ClippingLogEmbCh11Clipping
                INTEGER,
            iqhip10LoggingInp1ClippingEmbCh11Clipping
                RollCallString,
            iqhip10LoggingInp1ClippingLogEmbCh12Clipping
                INTEGER,
            iqhip10LoggingInp1ClippingEmbCh12Clipping
                RollCallString,
            iqhip10LoggingInp1ClippingLogEmbCh13Clipping
                INTEGER,
            iqhip10LoggingInp1ClippingEmbCh13Clipping
                RollCallString,
            iqhip10LoggingInp1ClippingLogEmbCh14Clipping
                INTEGER,
            iqhip10LoggingInp1ClippingEmbCh14Clipping
                RollCallString,
            iqhip10LoggingInp1ClippingLogEmbCh15Clipping
                INTEGER,
            iqhip10LoggingInp1ClippingEmbCh15Clipping
                RollCallString,
            iqhip10LoggingInp1ClippingLogEmbCh16Clipping
                INTEGER,
            iqhip10LoggingInp1ClippingEmbCh16Clipping
                RollCallString,
            iqhip10LoggingInp1LikenessLogDetector1Chans
                INTEGER,
            iqhip10LoggingInp1LikenessDetector1Chans
                RollCallString,
            iqhip10LoggingInp1LikenessLogDetector1State
                INTEGER,
            iqhip10LoggingInp1LikenessDetector1State
                RollCallString,
            iqhip10LoggingInp1LikenessLogDetector2Chans
                INTEGER,
            iqhip10LoggingInp1LikenessDetector2Chans
                RollCallString,
            iqhip10LoggingInp1LikenessLogDetector2State
                INTEGER,
            iqhip10LoggingInp1LikenessDetector2State
                RollCallString,
            iqhip10LoggingInp1LikenessLogDetector3Chans
                INTEGER,
            iqhip10LoggingInp1LikenessDetector3Chans
                RollCallString,
            iqhip10LoggingInp1LikenessLogDetector3State
                INTEGER,
            iqhip10LoggingInp1LikenessDetector3State
                RollCallString,
            iqhip10LoggingInp1LikenessLogDetector4Chans
                INTEGER,
            iqhip10LoggingInp1LikenessDetector4Chans
                RollCallString,
            iqhip10LoggingInp1LikenessLogDetector4State
                INTEGER,
            iqhip10LoggingInp1LikenessDetector4State
                RollCallString,
            iqhip10LoggingOut1UMIDLogUMIDState
                INTEGER,
            iqhip10LoggingOut1UMIDUMIDState
                RollCallString,
            iqhip10LoggingOut1UMIDLogOutputUMID
                INTEGER,
            iqhip10LoggingOut1UMIDOutputUMID18
                RollCallString,
            iqhip10LoggingOut1UMIDOutputUMID916
                RollCallString,
            iqhip10LoggingOut1UMIDOutputUMID1724
                RollCallString,
            iqhip10LoggingOut1UMIDOutputUMID2532
                RollCallString,
            iqhip10LoggingInp1UMIDLogUMIDState
                INTEGER,
            iqhip10LoggingInp1UMIDUMIDState
                RollCallString,
            iqhip10LoggingInp1UMIDLogUMIDCurrent18
                INTEGER,
            iqhip10LoggingInp1UMIDUMIDCurrent18
                RollCallString,
            iqhip10LoggingInp1UMIDUMIDCurrent916
                RollCallString,
            iqhip10LoggingInp1UMIDUMIDCurrent1724
                RollCallString,
            iqhip10LoggingInp1UMIDUMIDCurrent2532
                RollCallString,
            iqhip10LoggingInp1UMIDLogUMIDPrevious18
                INTEGER,
            iqhip10LoggingInp1UMIDUMIDPrev18
                RollCallString,
            iqhip10LoggingInp1UMIDUMIDPrev916
                RollCallString,
            iqhip10LoggingInp1UMIDUMIDPrev1724
                RollCallString,
            iqhip10LoggingInp1UMIDUMIDPrev2532
                RollCallString,
            iqhip10LoggingInp1UMIDLogUMIDPreviousCount
                INTEGER,
            iqhip10LoggingInp1UMIDUMIDPrevCount
                RollCallString,
            iqhip10LoggingOut1PIDLogPIDState
                INTEGER,
            iqhip10LoggingOut1PIDPIDState
                RollCallString,
            iqhip10LoggingOut1PIDLogPIDHouseID
                INTEGER,
            iqhip10LoggingOut1PIDPIDHouseID
                RollCallString,
            iqhip10LoggingOut1PIDLogPIDTitle
                INTEGER,
            iqhip10LoggingOut1PIDPIDTitle
                RollCallString,
            iqhip10LoggingOut1PIDLogSegmentNumber
                INTEGER,
            iqhip10LoggingOut1PIDSegmentNumber
                RollCallString,
            iqhip10LoggingOut1PIDLogDuration
                INTEGER,
            iqhip10LoggingOut1PIDDuration
                RollCallString,
            iqhip10LoggingOut1PIDLogFrameRate
                INTEGER,
            iqhip10LoggingOut1PIDFrameRate
                RollCallString,
            iqhip10LoggingInp1PIDLogPIDState
                INTEGER,
            iqhip10LoggingInp1PIDPIDState
                RollCallString,
            iqhip10LoggingInp1PIDLogPIDHouseID
                INTEGER,
            iqhip10LoggingInp1PIDPIDHouseID
                RollCallString,
            iqhip10LoggingInp1PIDLogPIDTitle
                INTEGER,
            iqhip10LoggingInp1PIDPIDTitle
                RollCallString,
            iqhip10LoggingInp1PIDLogSegmentNumber
                INTEGER,
            iqhip10LoggingInp1PIDSegmentNumber
                RollCallString,
            iqhip10LoggingInp1PIDLogDuration
                INTEGER,
            iqhip10LoggingInp1PIDDuration
                RollCallString,
            iqhip10LoggingInp1PIDLogFrameRate
                INTEGER,
            iqhip10LoggingInp1PIDFrameRate
                RollCallString,
            iqhip10LoggingInp1PIDLogPreviousHouseID
                INTEGER,
            iqhip10LoggingInp1PIDPreviousHouseID
                RollCallString,
            iqhip10LoggingInp1PIDLogPreviousTitle
                INTEGER,
            iqhip10LoggingInp1PIDPreviousTitle
                RollCallString,
            iqhip10LoggingInp1PIDLogPreviousSegNum
                INTEGER,
            iqhip10LoggingInp1PIDPreviousSegNum
                RollCallString,
            iqhip10LoggingInp1PIDLogPreviousDuration
                INTEGER,
            iqhip10LoggingInp1PIDPreviousDuration
                RollCallString,
            iqhip10LoggingInp1PIDLogPreviousFrameRate
                INTEGER,
            iqhip10LoggingInp1PIDPreviousFrameRate
                RollCallString,
            iqhip10LoggingInp1PIDLogPreviousCount
                INTEGER,
            iqhip10LoggingInp1PIDPreviousCount
                RollCallString,
            iqhip10MemoriesRecallMemory
                INTEGER,
            iqhip10MemoriesSelMemory
                INTEGER,
            iqhip10MemoriesSaveMemory
                INTEGER,
            iqhip10MemoriesClearMemory
                INTEGER,
            iqhip10MemoriesMemoryNameChangeName
                RollCallString,
            iqhip10MemoriesMemoryNameLastUserMemory
                RollCallString,
            iqhip10MemoriesMemoryName1
                RollCallString,
            iqhip10MemoriesMemoryName2
                RollCallString,
            iqhip10MemoriesMemoryName3
                RollCallString,
            iqhip10MemoriesMemoryName4
                RollCallString,
            iqhip10MemoriesMemoryName5
                RollCallString,
            iqhip10MemoriesMemoryName6
                RollCallString,
            iqhip10MemoriesMemoryName7
                RollCallString,
            iqhip10MemoriesMemoryName8
                RollCallString,
            iqhip10MemoriesMemoryName9
                RollCallString,
            iqhip10MemoriesMemoryName10
                RollCallString,
            iqhip10MemoriesMemoryName11
                RollCallString,
            iqhip10MemoriesMemoryName12
                RollCallString,
            iqhip10MemoriesMemoryName13
                RollCallString,
            iqhip10MemoriesMemoryName14
                RollCallString,
            iqhip10MemoriesMemoryName15
                RollCallString,
            iqhip10MemoriesMemoryName16
                RollCallString,
            iqhip10SFPOutputTxAOFF
                INTEGER,
            iqhip10SFPOutputTxAOFFInpLoss
                INTEGER,
            iqhip10SFPOutputTxBOFF
                INTEGER,
            iqhip10SFPOutputTxBOFFInpLoss
                INTEGER,
            iqhip10SFPOutputTxAOutputState
                RollCallString,
            iqhip10SFPOutputTxBOutputState
                RollCallString,
            iqhip10SetupProduct
                RollCallString,
            iqhip10SetupProductRelease
                RollCallString,
            iqhip10SetupProductBuild
                RollCallString,
            iqhip10SetupProductSerial
                RollCallString,
            iqhip10SetupProductFirmware
                RollCallString,
            iqhip10SetupProductPCB
                RollCallString,
            iqhip10SetupProductFactoryDefault
                INTEGER,
            iqhip10SetupProductDefaultSettings
                INTEGER,
            iqhip10SetupProductRestartSoftHard
                INTEGER,
            iqhip10SetupProductInput1Name
                RollCallString,
            iqhip10SetupProductSFPARxName
                RollCallString,
            iqhip10SetupProductRearType
                RollCallString,
            iqhip10SetupUpgradeStart
                INTEGER,
            iqhip10SetupUpgradeEnd
                INTEGER,
            iqhip10SetupUpgradeCancel
                INTEGER,
            iqhip10SetupUpgradeAbort
                INTEGER,
            iqhip10SetupOutputStd
                INTEGER,
            iqhip10SFPSetupVendor
                RollCallString,
            iqhip10SFPSetupPartNumber
                RollCallString,
            iqhip10SFPSetupSerialNumber
                RollCallString,
            iqhip10SFPSetupIdentifier
                RollCallString,
            iqhip10SFPSetupType
                RollCallString,
            iqhip10SFPSetupConnector
                RollCallString,
            iqhip10SFPSetupStatus
                RollCallString,
            iqhip10SFPSetupConfigureSFPType
                INTEGER,
            iqhip10RollTrackDisableAll
                INTEGER,
            iqhip10RollTrackIndex
                INTEGER,
            iqhip10RollTrackSource
                INTEGER,
            iqhip10RollTrackAddress
                RollCallString,
            iqhip10RollTrackCommand
                RollCallString,
            iqhip10RollTrackStatus
                RollCallString,
            iqhip10RollTrackSending
                RollCallString,
            iqhip10DialoguePagecontrolsConfig1
                RollCallString,
            iqhip10DialoguePagecontrolsConfig2
                RollCallString,
            iqhip10DialoguePagecontrolsConfig3
                RollCallString,
            iqhip10DialoguePagecontrolsConfig4
                RollCallString,
            iqhip10PatternEnable
                INTEGER,
            iqhip10PatternEnableOnIPLoss
                INTEGER,
            iqhip10PatternScroll
                INTEGER,
            iqhip10PatternType
                INTEGER
        }

    iqhip10SlotIndex OBJECT-TYPE
        SYNTAX            Unsigned32
        MAX-ACCESS        not-accessible
        STATUS            current
        DESCRIPTION
                "The unique Index value for each slot.  Its value
                ranges between 1 and the value of slotNumber."
        ::= { iqhip10CmdEntry 99999 }


    iqhip10Input OBJECT-TYPE
        SYNTAX            INTEGER {
                            valIN1(0),
                            valSFPA(1)
                            }
        MAX-ACCESS        read-write
        STATUS            current
        DESCRIPTION
                "CMNT: - 
                 TYPE: - RadiobuttonList
                 PAGE: - Input
                    Input  cmdID= 4050
                    IN 1  value= 0
                    SFP A  value= 1  "
        ::= { iqhip10CmdEntry 4050 }


    iqhip10InputSERIALIO OBJECT-TYPE
        SYNTAX            INTEGER {
                            valOutput(0),
                            valInput(1)
                            }
        MAX-ACCESS        read-write
        STATUS            current
        DESCRIPTION
                "CMNT: - 
                 TYPE: - RadiobuttonList
                 PAGE: - Input
                    SERIAL IO  cmdID= 4051
                    Output  value= 0
                    Input  value= 1  "
        ::= { iqhip10CmdEntry 4051 }


    iqhip10InputMuteOutput1 OBJECT-TYPE
        SYNTAX            INTEGER { disable(0), enable(1)  }
        MAX-ACCESS        read-write
        STATUS            current
        DESCRIPTION
                "CMNT: - 
                 TYPE: - Checkbox
                 PAGE: - Input
                    Output 1  cmdID= 4020  "
        ::= { iqhip10CmdEntry 4020 }


    iqhip10InputMuteOutput2 OBJECT-TYPE
        SYNTAX            INTEGER { disable(0), enable(1)  }
        MAX-ACCESS        read-write
        STATUS            current
        DESCRIPTION
                "CMNT: - 
                 TYPE: - Checkbox
                 PAGE: - Input
                    Output 2  cmdID= 4021  "
        ::= { iqhip10CmdEntry 4021 }


    iqhip10InputMuteOutput3 OBJECT-TYPE
        SYNTAX            INTEGER { disable(0), enable(1)  }
        MAX-ACCESS        read-write
        STATUS            current
        DESCRIPTION
                "CMNT: - 
                 TYPE: - Checkbox
                 PAGE: - Input
                    Output 3  cmdID= 4022  "
        ::= { iqhip10CmdEntry 4022 }


    iqhip10InputMuteOutput4 OBJECT-TYPE
        SYNTAX            INTEGER { disable(0), enable(1)  }
        MAX-ACCESS        read-write
        STATUS            current
        DESCRIPTION
                "CMNT: - 
                 TYPE: - Checkbox
                 PAGE: - Input
                    Output 4  cmdID= 4023  "
        ::= { iqhip10CmdEntry 4023 }


    iqhip10InputMuteOnInputErrorOutput1 OBJECT-TYPE
        SYNTAX            INTEGER { disable(0), enable(1)  }
        MAX-ACCESS        read-write
        STATUS            current
        DESCRIPTION
                "CMNT: - 
                 TYPE: - Checkbox
                 PAGE: - Input
                    Output 1  cmdID= 4030  "
        ::= { iqhip10CmdEntry 4030 }


    iqhip10InputMuteOnInputErrorOutput2 OBJECT-TYPE
        SYNTAX            INTEGER { disable(0), enable(1)  }
        MAX-ACCESS        read-write
        STATUS            current
        DESCRIPTION
                "CMNT: - 
                 TYPE: - Checkbox
                 PAGE: - Input
                    Output 2  cmdID= 4031  "
        ::= { iqhip10CmdEntry 4031 }


    iqhip10InputMuteOnInputErrorOutput3 OBJECT-TYPE
        SYNTAX            INTEGER { disable(0), enable(1)  }
        MAX-ACCESS        read-write
        STATUS            current
        DESCRIPTION
                "CMNT: - 
                 TYPE: - Checkbox
                 PAGE: - Input
                    Output 3  cmdID= 4032  "
        ::= { iqhip10CmdEntry 4032 }


    iqhip10InputMuteOnInputErrorOutput4 OBJECT-TYPE
        SYNTAX            INTEGER { disable(0), enable(1)  }
        MAX-ACCESS        read-write
        STATUS            current
        DESCRIPTION
                "CMNT: - 
                 TYPE: - Checkbox
                 PAGE: - Input
                    Output 4  cmdID= 4033  "
        ::= { iqhip10CmdEntry 4033 }


    iqhip10HyperionRegionsRegionSelect OBJECT-TYPE
        SYNTAX            INTEGER {
                            valNone(-1),
                            valRegion1(0),
                            valRegion2(1)
                            }
        MAX-ACCESS        read-write
        STATUS            current
        DESCRIPTION
                "CMNT: - 
                 TYPE: - RadiobuttonList
                 PAGE: - Hyperion
                    Region Select  cmdID= 5700
                    None  value= -1
                    Region 1  value= 0
                    Region 2  value= 1  "
        ::= { iqhip10CmdEntry 5700 }

	iqhip10RegionsRegionEnables OBJECT-TYPE
		SYNTAX		INTEGER {
							valRegion1Disable(0),
							valRegion1Enable(1),
							valRegion2Disable(2),
							valRegion2Enable(3)
							}
		MAX-ACCESS		read-write
		STATUS			current
		DESCRIPTION
				"TYPE: - RadiobuttonList
				 PAGE: - Regions
					Region Enables  cmdID= 6010 
					Region 1 Disable   value= 0  
					Region 1 Enable   value= 1  
					Region 2 Disable   value= 2  
					Region 2 Enable   value= 3  "
		::= { iqhip10CmdEntry 6010 }


    iqhip10RegionDetectorsDetectorWindowWindowMode OBJECT-TYPE
        SYNTAX            INTEGER {
                            valInside(0),
                            valOutside(1)
                            }
        MAX-ACCESS        read-write
        STATUS            current
        DESCRIPTION
                "CMNT: - 
                 TYPE: - RadiobuttonList
                 PAGE: - Region Detectors
                    Window Mode  cmdID= 6016
                    Inside  value= 0
                    Outside  value= 1  "
        ::= { iqhip10CmdEntry 6016 }


    iqhip10RegionDetectorsDetectorWindowFullScreen OBJECT-TYPE
        SYNTAX            INTEGER { noAction(0),valFullScreen(1) }
        MAX-ACCESS        read-write
        STATUS            current
        DESCRIPTION
                "CMNT: - 
                 TYPE: - Button
                 PAGE: - Region Detectors
                    Full Screen  cmdID= 6017
                    value= 1  "
        ::= { iqhip10CmdEntry 6017 }


    iqhip10RegionDetectorsDetectorWindowXPosition OBJECT-TYPE
        SYNTAX            INTEGER
        MAX-ACCESS        read-write
        STATUS            current
        DESCRIPTION
                "CMNT: - 
                 TYPE: - Number
                 PAGE: - Region Detectors
                    X Position  cmdID= 6011
                    min= 0  max= 3000  step= 1  format= %0.0f  div_scale= 1  preset= 0
                    Min = 0  Max = 3000  Step = 1  Preset = 0  "
        ::= { iqhip10CmdEntry 6011 }


    iqhip10RegionDetectorsDetectorWindowWidth OBJECT-TYPE
        SYNTAX            INTEGER
        MAX-ACCESS        read-write
        STATUS            current
        DESCRIPTION
                "CMNT: - 
                 TYPE: - Number
                 PAGE: - Region Detectors
                    Width  cmdID= 6012
                    min= 0  max= 3000  step= 1  format= %0.0f  div_scale= 1  preset= 2880
                    Min = 0  Max = 3000  Step = 1  Preset = 2880  "
        ::= { iqhip10CmdEntry 6012 }


    iqhip10RegionDetectorsDetectorWindowYPosition OBJECT-TYPE
        SYNTAX            INTEGER
        MAX-ACCESS        read-write
        STATUS            current
        DESCRIPTION
                "CMNT: - 
                 TYPE: - Number
                 PAGE: - Region Detectors
                    Y Position  cmdID= 6013
                    min= 0  max= 25000  step= 1  format= %0.0f  div_scale= 1  preset= 0
                    Min = 0  Max = 25000  Step = 1  Preset = 0  "
        ::= { iqhip10CmdEntry 6013 }


    iqhip10RegionDetectorsDetectorWindowHeight OBJECT-TYPE
        SYNTAX            INTEGER
        MAX-ACCESS        read-write
        STATUS            current
        DESCRIPTION
                "CMNT: - 
                 TYPE: - Number
                 PAGE: - Region Detectors
                    Height  cmdID= 6014
                    min= 0  max= 25000  step= 1  format= %0.0f  div_scale= 1  preset= 24684
                    Min = 0  Max = 25000  Step = 1  Preset = 24684  "
        ::= { iqhip10CmdEntry 6014 }


    iqhip10RegionDetectorsBlackEnable OBJECT-TYPE
        SYNTAX            INTEGER { disable(0), enable(1)  }
        MAX-ACCESS        read-write
        STATUS            current
        DESCRIPTION
                "CMNT: - 
                 TYPE: - Checkbox
                 PAGE: - Region Detectors
                    Enable  cmdID= 6030  "
        ::= { iqhip10CmdEntry 6030 }


    iqhip10RegionDetectorsBlackAlarmcount OBJECT-TYPE
        SYNTAX            RollCallString
        MAX-ACCESS        read-only
        STATUS            current
        DESCRIPTION
                "CMNT: - 
                 TYPE: - Display
                 PAGE: - Region Detectors
                    Alarm count  cmdID= 6031  "
        ::= { iqhip10CmdEntry 6031 }


    iqhip10RegionDetectorsBlackReset OBJECT-TYPE
        SYNTAX            INTEGER { noAction(0),valReset(1) }
        MAX-ACCESS        read-write
        STATUS            current
        DESCRIPTION
                "CMNT: - 
                 TYPE: - Button
                 PAGE: - Region Detectors
                    Reset  cmdID= 6032
                    value= 1  "
        ::= { iqhip10CmdEntry 6032 }


    iqhip10RegionDetectorsBlackResetWhenOK OBJECT-TYPE
        SYNTAX            INTEGER { disable(0), enable(1)  }
        MAX-ACCESS        read-write
        STATUS            current
        DESCRIPTION
                "CMNT: - 
                 TYPE: - Checkbox
                 PAGE: - Region Detectors
                    Reset When OK  cmdID= 6033  "
        ::= { iqhip10CmdEntry 6033 }


    iqhip10RegionDetectorsBlackWarningCount OBJECT-TYPE
        SYNTAX            INTEGER
        MAX-ACCESS        read-write
        STATUS            current
        DESCRIPTION
                "CMNT: - 
                 TYPE: - Number
                 PAGE: - Region Detectors
                    Warning Count  cmdID= 1233
                    min= 0  max= 16000  step= 1  format= %0.0f  div_scale= 1  preset= 600
                    Min = 0  Max = 16000  Step = 1  Preset = 600  "
        ::= { iqhip10CmdEntry 1233 }


    iqhip10RegionDetectorsBlackFailCount OBJECT-TYPE
        SYNTAX            INTEGER
        MAX-ACCESS        read-write
        STATUS            current
        DESCRIPTION
                "CMNT: - 
                 TYPE: - Number
                 PAGE: - Region Detectors
                    Fail Count  cmdID= 1232
                    min= 0  max= 16000  step= 1  format= %0.0f  div_scale= 1  preset= 1800
                    Min = 0  Max = 16000  Step = 1  Preset = 1800  "
        ::= { iqhip10CmdEntry 1232 }


    iqhip10RegionDetectorsBlackFailHoldCount OBJECT-TYPE
        SYNTAX            INTEGER
        MAX-ACCESS        read-write
        STATUS            current
        DESCRIPTION
                "CMNT: - 
                 TYPE: - Number
                 PAGE: - Region Detectors
                    Fail Hold Count  cmdID= 1234
                    min= 1  max= 16000  step= 1  format= %0.0f  div_scale= 1  preset= 300
                    Min = 1  Max = 16000  Step = 1  Preset = 300  "
        ::= { iqhip10CmdEntry 1234 }


    iqhip10RegionDetectorsBlackishEnable OBJECT-TYPE
        SYNTAX            INTEGER { disable(0), enable(1)  }
        MAX-ACCESS        read-write
        STATUS            current
        DESCRIPTION
                "CMNT: - 
                 TYPE: - Checkbox
                 PAGE: - Region Detectors
                    Enable  cmdID= 6040  "
        ::= { iqhip10CmdEntry 6040 }


    iqhip10RegionDetectorsBlackishAlarmcount OBJECT-TYPE
        SYNTAX            RollCallString
        MAX-ACCESS        read-only
        STATUS            current
        DESCRIPTION
                "CMNT: - 
                 TYPE: - Display
                 PAGE: - Region Detectors
                    Alarm count  cmdID= 6041  "
        ::= { iqhip10CmdEntry 6041 }


    iqhip10RegionDetectorsBlackishReset OBJECT-TYPE
        SYNTAX            INTEGER { noAction(0),valReset(1) }
        MAX-ACCESS        read-write
        STATUS            current
        DESCRIPTION
                "CMNT: - 
                 TYPE: - Button
                 PAGE: - Region Detectors
                    Reset  cmdID= 6042
                    value= 1  "
        ::= { iqhip10CmdEntry 6042 }


    iqhip10RegionDetectorsBlackishResetWhenOK OBJECT-TYPE
        SYNTAX            INTEGER { disable(0), enable(1)  }
        MAX-ACCESS        read-write
        STATUS            current
        DESCRIPTION
                "CMNT: - 
                 TYPE: - Checkbox
                 PAGE: - Region Detectors
                    Reset When OK  cmdID= 6043  "
        ::= { iqhip10CmdEntry 6043 }


    iqhip10RegionDetectorsBlackishCurrentDetectedLevel OBJECT-TYPE
        SYNTAX            RollCallString
        MAX-ACCESS        read-only
        STATUS            current
        DESCRIPTION
                "CMNT: - 
                 TYPE: - Display
                 PAGE: - Region Detectors
                    Current Detected Level  cmdID= 6044  "
        ::= { iqhip10CmdEntry 6044 }


    iqhip10RegionDetectorsBlackishMaxLevelThreshold OBJECT-TYPE
        SYNTAX            INTEGER
        MAX-ACCESS        read-write
        STATUS            current
        DESCRIPTION
                "CMNT: - 
                 TYPE: - Number
                 PAGE: - Region Detectors
                    Max Level Threshold  cmdID= 6045
                    min= 0  max= 100  step= 1  format= %0.0f  div_scale= 1  preset= 10
                    Min = 0  Max = 100  Step = 1  Preset = 10  "
        ::= { iqhip10CmdEntry 6045 }


    iqhip10RegionDetectorsBlackishWarningCount OBJECT-TYPE
        SYNTAX            INTEGER
        MAX-ACCESS        read-write
        STATUS            current
        DESCRIPTION
                "CMNT: - 
                 TYPE: - Number
                 PAGE: - Region Detectors
                    Warning Count  cmdID= 1238
                    min= 0  max= 16000  step= 1  format= %0.0f  div_scale= 1  preset= 600
                    Min = 0  Max = 16000  Step = 1  Preset = 600  "
        ::= { iqhip10CmdEntry 1238 }


    iqhip10RegionDetectorsBlackishFailCount OBJECT-TYPE
        SYNTAX            INTEGER
        MAX-ACCESS        read-write
        STATUS            current
        DESCRIPTION
                "CMNT: - 
                 TYPE: - Number
                 PAGE: - Region Detectors
                    Fail Count  cmdID= 1237
                    min= 0  max= 16000  step= 1  format= %0.0f  div_scale= 1  preset= 1800
                    Min = 0  Max = 16000  Step = 1  Preset = 1800  "
        ::= { iqhip10CmdEntry 1237 }


    iqhip10RegionDetectorsBlackishFailHoldCount OBJECT-TYPE
        SYNTAX            INTEGER
        MAX-ACCESS        read-write
        STATUS            current
        DESCRIPTION
                "CMNT: - 
                 TYPE: - Number
                 PAGE: - Region Detectors
                    Fail Hold Count  cmdID= 1239
                    min= 1  max= 16000  step= 1  format= %0.0f  div_scale= 1  preset= 300
                    Min = 1  Max = 16000  Step = 1  Preset = 300  "
        ::= { iqhip10CmdEntry 1239 }


    iqhip10RegionDetectorsFreezeEnable OBJECT-TYPE
        SYNTAX            INTEGER { disable(0), enable(1)  }
        MAX-ACCESS        read-write
        STATUS            current
        DESCRIPTION
                "CMNT: - 
                 TYPE: - Checkbox
                 PAGE: - Region Detectors
                    Enable  cmdID= 6050  "
        ::= { iqhip10CmdEntry 6050 }


    iqhip10RegionDetectorsFreezeAlarmcount OBJECT-TYPE
        SYNTAX            RollCallString
        MAX-ACCESS        read-only
        STATUS            current
        DESCRIPTION
                "CMNT: - 
                 TYPE: - Display
                 PAGE: - Region Detectors
                    Alarm count  cmdID= 6051  "
        ::= { iqhip10CmdEntry 6051 }


    iqhip10RegionDetectorsFreezeReset OBJECT-TYPE
        SYNTAX            INTEGER { noAction(0),valReset(1) }
        MAX-ACCESS        read-write
        STATUS            current
        DESCRIPTION
                "CMNT: - 
                 TYPE: - Button
                 PAGE: - Region Detectors
                    Reset  cmdID= 6052
                    value= 1  "
        ::= { iqhip10CmdEntry 6052 }


    iqhip10RegionDetectorsFreezeResetWhenOK OBJECT-TYPE
        SYNTAX            INTEGER { disable(0), enable(1)  }
        MAX-ACCESS        read-write
        STATUS            current
        DESCRIPTION
                "CMNT: - 
                 TYPE: - Checkbox
                 PAGE: - Region Detectors
                    Reset When OK  cmdID= 6053  "
        ::= { iqhip10CmdEntry 6053 }


    iqhip10RegionsRegionDetectorsFreezeTolerance OBJECT-TYPE
        SYNTAX            INTEGER
        MAX-ACCESS        read-write
        STATUS            current
        DESCRIPTION
                "CMNT: - 
                 TYPE: - Number
                 PAGE: - Regions
                    Freeze Tolerance  cmdID= 6054
                    min= 0  max= 10  step= 1  format= %0.0f  div_scale= 1  preset= 0
                    Min = 0  Max = 10  Step = 1  Preset = 0  "
        ::= { iqhip10CmdEntry 6054 }


    iqhip10RegionDetectorsFreezeWarningCount OBJECT-TYPE
        SYNTAX            INTEGER
        MAX-ACCESS        read-write
        STATUS            current
        DESCRIPTION
                "CMNT: - 
                 TYPE: - Number
                 PAGE: - Region Detectors
                    Warning Count  cmdID= 1651
                    min= 0  max= 16000  step= 1  format= %0.0f  div_scale= 1  preset= 600
                    Min = 0  Max = 16000  Step = 1  Preset = 600  "
        ::= { iqhip10CmdEntry 1651 }


    iqhip10RegionDetectorsFreezeFailCount OBJECT-TYPE
        SYNTAX            INTEGER
        MAX-ACCESS        read-write
        STATUS            current
        DESCRIPTION
                "CMNT: - 
                 TYPE: - Number
                 PAGE: - Region Detectors
                    Fail Count  cmdID= 1650
                    min= 0  max= 16000  step= 1  format= %0.0f  div_scale= 1  preset= 1800
                    Min = 0  Max = 16000  Step = 1  Preset = 1800  "
        ::= { iqhip10CmdEntry 1650 }


    iqhip10RegionDetectorsFreezeFailHoldCount OBJECT-TYPE
        SYNTAX            INTEGER
        MAX-ACCESS        read-write
        STATUS            current
        DESCRIPTION
                "CMNT: - 
                 TYPE: - Number
                 PAGE: - Region Detectors
                    Fail Hold Count  cmdID= 1652
                    min= 1  max= 16000  step= 1  format= %0.0f  div_scale= 1  preset= 1
                    Min = 1  Max = 16000  Step = 1  Preset = 1  "
        ::= { iqhip10CmdEntry 1652 }


    iqhip10RegionDetectorsStillishEnable OBJECT-TYPE
        SYNTAX            INTEGER { disable(0), enable(1)  }
        MAX-ACCESS        read-write
        STATUS            current
        DESCRIPTION
                "CMNT: - 
                 TYPE: - Checkbox
                 PAGE: - Region Detectors
                    Enable  cmdID= 6060  "
        ::= { iqhip10CmdEntry 6060 }


    iqhip10RegionDetectorsStillishAlarmcount OBJECT-TYPE
        SYNTAX            RollCallString
        MAX-ACCESS        read-only
        STATUS            current
        DESCRIPTION
                "CMNT: - 
                 TYPE: - Display
                 PAGE: - Region Detectors
                    Alarm count  cmdID= 6061  "
        ::= { iqhip10CmdEntry 6061 }


    iqhip10RegionDetectorsStillishReset OBJECT-TYPE
        SYNTAX            INTEGER { noAction(0),valReset(1) }
        MAX-ACCESS        read-write
        STATUS            current
        DESCRIPTION
                "CMNT: - 
                 TYPE: - Button
                 PAGE: - Region Detectors
                    Reset  cmdID= 6062
                    value= 1  "
        ::= { iqhip10CmdEntry 6062 }


    iqhip10RegionDetectorsStillishResetWhenOK OBJECT-TYPE
        SYNTAX            INTEGER { disable(0), enable(1)  }
        MAX-ACCESS        read-write
        STATUS            current
        DESCRIPTION
                "CMNT: - 
                 TYPE: - Checkbox
                 PAGE: - Region Detectors
                    Reset When OK  cmdID= 6063  "
        ::= { iqhip10CmdEntry 6063 }


    iqhip10RegionDetectorsStillishCurrentDetectedLevel OBJECT-TYPE
        SYNTAX            RollCallString
        MAX-ACCESS        read-only
        STATUS            current
        DESCRIPTION
                "CMNT: - 
                 TYPE: - Display
                 PAGE: - Region Detectors
                    Current Detected Level  cmdID= 6064  "
        ::= { iqhip10CmdEntry 6064 }


    iqhip10RegionDetectorsStillishMaxLevelThreshold OBJECT-TYPE
        SYNTAX            INTEGER
        MAX-ACCESS        read-write
        STATUS            current
        DESCRIPTION
                "CMNT: - 
                 TYPE: - Number
                 PAGE: - Region Detectors
                    Max Level Threshold  cmdID= 6065
                    min= 0  max= 100  step= 1  format= %0.0f  div_scale= 1  preset= 90
                    Min = 0  Max = 100  Step = 1  Preset = 90  "
        ::= { iqhip10CmdEntry 6065 }


    iqhip10RegionDetectorsStillishWarningCount OBJECT-TYPE
        SYNTAX            INTEGER
        MAX-ACCESS        read-write
        STATUS            current
        DESCRIPTION
                "CMNT: - 
                 TYPE: - Number
                 PAGE: - Region Detectors
                    Warning Count  cmdID= 1216
                    min= 0  max= 16000  step= 1  format= %0.0f  div_scale= 1  preset= 600
                    Min = 0  Max = 16000  Step = 1  Preset = 600  "
        ::= { iqhip10CmdEntry 1216 }


    iqhip10RegionDetectorsStillishFailCount OBJECT-TYPE
        SYNTAX            INTEGER
        MAX-ACCESS        read-write
        STATUS            current
        DESCRIPTION
                "CMNT: - 
                 TYPE: - Number
                 PAGE: - Region Detectors
                    Fail Count  cmdID= 1215
                    min= 0  max= 16000  step= 1  format= %0.0f  div_scale= 1  preset= 1800
                    Min = 0  Max = 16000  Step = 1  Preset = 1800  "
        ::= { iqhip10CmdEntry 1215 }


    iqhip10RegionDetectorsStillishFailHoldCount OBJECT-TYPE
        SYNTAX            INTEGER
        MAX-ACCESS        read-write
        STATUS            current
        DESCRIPTION
                "CMNT: - 
                 TYPE: - Number
                 PAGE: - Region Detectors
                    Fail Hold Count  cmdID= 1217
                    min= 1  max= 16000  step= 1  format= %0.0f  div_scale= 1  preset= 300
                    Min = 1  Max = 16000  Step = 1  Preset = 300  "
        ::= { iqhip10CmdEntry 1217 }


    iqhip10VideoMonitorAveragePictureLvlEnableAlarm OBJECT-TYPE
        SYNTAX            INTEGER { disable(0), enable(1)  }
        MAX-ACCESS        read-write
        STATUS            current
        DESCRIPTION
                "CMNT: - 
                 TYPE: - Checkbox
                 PAGE: - Video Monitor
                    Enable Alarm  cmdID= 1326  "
        ::= { iqhip10CmdEntry 1326 }


    iqhip10HyperionVideoMonitorAveragePictureLvl OBJECT-TYPE
        SYNTAX            RollCallString
        MAX-ACCESS        read-only
        STATUS            current
        DESCRIPTION
                "CMNT: - 
                 TYPE: - Display
                 PAGE: - Hyperion
                    Average Picture Lvl  cmdID= 1320  "
        ::= { iqhip10CmdEntry 1320 }


    iqhip10VideoMonitorAveragePictureLvlMaxLoggingThres OBJECT-TYPE
        SYNTAX            INTEGER
        MAX-ACCESS        read-write
        STATUS            current
        DESCRIPTION
                "CMNT: - 
                 TYPE: - Number
                 PAGE: - Video Monitor
                    Max Logging Thres  cmdID= 1324
                    min= 0  max= 100  step= 1  format= %0.0f  div_scale= 1  preset= 95
                    Min = 0  Max = 100  Step = 1  Preset = 95  "
        ::= { iqhip10CmdEntry 1324 }


    iqhip10VideoMonitorAveragePictureLvlMinLoggingThres OBJECT-TYPE
        SYNTAX            INTEGER
        MAX-ACCESS        read-write
        STATUS            current
        DESCRIPTION
                "CMNT: - 
                 TYPE: - Number
                 PAGE: - Video Monitor
                    Min Logging Thres  cmdID= 1323
                    min= 0  max= 100  step= 1  format= %0.0f  div_scale= 1  preset= 5
                    Min = 0  Max = 100  Step = 1  Preset = 5  "
        ::= { iqhip10CmdEntry 1323 }


    iqhip10LumaVideoLevelOverloadStatus OBJECT-TYPE
        SYNTAX            RollCallString
        MAX-ACCESS        read-only
        STATUS            current
        DESCRIPTION
                "CMNT: - 
                 TYPE: - Display
                 PAGE: - Luma Video Level
                    Status  cmdID= 1343  "
        ::= { iqhip10CmdEntry 1343 }


    iqhip10LumaVideoLevelOverloadMaximumReading OBJECT-TYPE
        SYNTAX            RollCallString
        MAX-ACCESS        read-only
        STATUS            current
        DESCRIPTION
                "CMNT: - 
                 TYPE: - Display
                 PAGE: - Luma Video Level
                    Maximum Reading  cmdID= 1352  "
        ::= { iqhip10CmdEntry 1352 }


    iqhip10LumaVideoLevelOverloadEnableAlarm OBJECT-TYPE
        SYNTAX            INTEGER { disable(0), enable(1)  }
        MAX-ACCESS        read-write
        STATUS            current
        DESCRIPTION
                "CMNT: - 
                 TYPE: - Checkbox
                 PAGE: - Luma Video Level
                    Enable Alarm   cmdID= 1349  "
        ::= { iqhip10CmdEntry 1349 }


    iqhip10VideoMonitorLumaVideoLevelOverloadThreshold OBJECT-TYPE
        SYNTAX            INTEGER
        MAX-ACCESS        read-write
        STATUS            current
        DESCRIPTION
                "CMNT: - 
                 TYPE: - Number
                 PAGE: - Video Monitor
                    Overload Threshold  cmdID= 1341
                    min= 0  max= 1023  step= 1  format= %0.0f  div_scale= 1  preset= 940
                    Min = 0  Max = 1023  Step = 1  Preset = 940  "
        ::= { iqhip10CmdEntry 1341 }


    iqhip10LumaVideoLevelOverloadAvePicAboveThres OBJECT-TYPE
        SYNTAX            INTEGER
        MAX-ACCESS        read-write
        STATUS            current
        DESCRIPTION
                "CMNT: - 
                 TYPE: - Number
                 PAGE: - Luma Video Level
                    Ave Pic Above Thres  cmdID= 1356
                    min= 0  max= 99  step= 1  format= %0.0f  div_scale= 1  preset= 0
                    Min = 0  Max = 99  Step = 1  Preset = 0  "
        ::= { iqhip10CmdEntry 1356 }


    iqhip10LumaVideoLevelUnderloadStatus OBJECT-TYPE
        SYNTAX            RollCallString
        MAX-ACCESS        read-only
        STATUS            current
        DESCRIPTION
                "CMNT: - 
                 TYPE: - Display
                 PAGE: - Luma Video Level
                    Status  cmdID= 1347  "
        ::= { iqhip10CmdEntry 1347 }


    iqhip10LumaVideoLevelUnderloadMinimumReading OBJECT-TYPE
        SYNTAX            RollCallString
        MAX-ACCESS        read-only
        STATUS            current
        DESCRIPTION
                "CMNT: - 
                 TYPE: - Display
                 PAGE: - Luma Video Level
                    Minimum Reading  cmdID= 1353  "
        ::= { iqhip10CmdEntry 1353 }


    iqhip10LumaVideoLevelUnderloadEnableAlarm OBJECT-TYPE
        SYNTAX            INTEGER { disable(0), enable(1)  }
        MAX-ACCESS        read-write
        STATUS            current
        DESCRIPTION
                "CMNT: - 
                 TYPE: - Checkbox
                 PAGE: - Luma Video Level
                    Enable Alarm  cmdID= 1348  "
        ::= { iqhip10CmdEntry 1348 }


    iqhip10VideoMonitorLumaVideoLevelUnderloadThreshold OBJECT-TYPE
        SYNTAX            INTEGER
        MAX-ACCESS        read-write
        STATUS            current
        DESCRIPTION
                "CMNT: - 
                 TYPE: - Number
                 PAGE: - Video Monitor
                    Underload Threshold  cmdID= 1345
                    min= 0  max= 1023  step= 1  format= %0.0f  div_scale= 1  preset= 64
                    Min = 0  Max = 1023  Step = 1  Preset = 64  "
        ::= { iqhip10CmdEntry 1345 }


    iqhip10LumaVideoLevelUnderloadAvePicBelowThres OBJECT-TYPE
        SYNTAX            INTEGER
        MAX-ACCESS        read-write
        STATUS            current
        DESCRIPTION
                "CMNT: - 
                 TYPE: - Number
                 PAGE: - Luma Video Level
                    Ave Pic Below Thres  cmdID= 1357
                    min= 0  max= 99  step= 1  format= %0.0f  div_scale= 1  preset= 0
                    Min = 0  Max = 99  Step = 1  Preset = 0  "
        ::= { iqhip10CmdEntry 1357 }


    iqhip10ChromaVideoLevelOverloadStatus OBJECT-TYPE
        SYNTAX            RollCallString
        MAX-ACCESS        read-only
        STATUS            current
        DESCRIPTION
                "CMNT: - 
                 TYPE: - Display
                 PAGE: - Chroma Video Level
                    Status  cmdID= 1342  "
        ::= { iqhip10CmdEntry 1342 }


    iqhip10ChromaVideoLevelOverloadMaximumReading OBJECT-TYPE
        SYNTAX            RollCallString
        MAX-ACCESS        read-only
        STATUS            current
        DESCRIPTION
                "CMNT: - 
                 TYPE: - Display
                 PAGE: - Chroma Video Level
                    Maximum Reading  cmdID= 1354  "
        ::= { iqhip10CmdEntry 1354 }


    iqhip10ChromaVideoLevelOverloadEnableAlarm OBJECT-TYPE
        SYNTAX            INTEGER { disable(0), enable(1)  }
        MAX-ACCESS        read-write
        STATUS            current
        DESCRIPTION
                "CMNT: - 
                 TYPE: - Checkbox
                 PAGE: - Chroma Video Level
                    Enable Alarm  cmdID= 1351  "
        ::= { iqhip10CmdEntry 1351 }


    iqhip10VideoMonitorChromaVideoLevelOverloadThreshold OBJECT-TYPE
        SYNTAX            INTEGER
        MAX-ACCESS        read-write
        STATUS            current
        DESCRIPTION
                "CMNT: - 
                 TYPE: - Number
                 PAGE: - Video Monitor
                    Overload Threshold  cmdID= 1340
                    min= 0  max= 1023  step= 1  format= %0.0f  div_scale= 1  preset= 960
                    Min = 0  Max = 1023  Step = 1  Preset = 960  "
        ::= { iqhip10CmdEntry 1340 }


    iqhip10ChromaVideoLevelOverloadAvePicAboveThres OBJECT-TYPE
        SYNTAX            INTEGER
        MAX-ACCESS        read-write
        STATUS            current
        DESCRIPTION
                "CMNT: - 
                 TYPE: - Number
                 PAGE: - Chroma Video Level
                    Ave Pic Above Thres  cmdID= 1358
                    min= 0  max= 99  step= 1  format= %0.0f  div_scale= 1  preset= 0
                    Min = 0  Max = 99  Step = 1  Preset = 0  "
        ::= { iqhip10CmdEntry 1358 }


    iqhip10ChromaVideoLevelUnderloadStatus OBJECT-TYPE
        SYNTAX            RollCallString
        MAX-ACCESS        read-only
        STATUS            current
        DESCRIPTION
                "CMNT: - 
                 TYPE: - Display
                 PAGE: - Chroma Video Level
                    Status  cmdID= 1346  "
        ::= { iqhip10CmdEntry 1346 }


    iqhip10ChromaVideoLevelUnderloadMinimumReading OBJECT-TYPE
        SYNTAX            RollCallString
        MAX-ACCESS        read-only
        STATUS            current
        DESCRIPTION
                "CMNT: - 
                 TYPE: - Display
                 PAGE: - Chroma Video Level
                    Minimum Reading  cmdID= 1355  "
        ::= { iqhip10CmdEntry 1355 }


    iqhip10ChromaVideoLevelUnderloadEnableAlarm OBJECT-TYPE
        SYNTAX            INTEGER { disable(0), enable(1)  }
        MAX-ACCESS        read-write
        STATUS            current
        DESCRIPTION
                "CMNT: - 
                 TYPE: - Checkbox
                 PAGE: - Chroma Video Level
                    Enable Alarm  cmdID= 1350  "
        ::= { iqhip10CmdEntry 1350 }


    iqhip10VideoMonitorChromaVideoLevelUnderloadThreshold OBJECT-TYPE
        SYNTAX            INTEGER
        MAX-ACCESS        read-write
        STATUS            current
        DESCRIPTION
                "CMNT: - 
                 TYPE: - Number
                 PAGE: - Video Monitor
                    Underload Threshold  cmdID= 1344
                    min= 0  max= 1023  step= 1  format= %0.0f  div_scale= 1  preset= 64
                    Min = 0  Max = 1023  Step = 1  Preset = 64  "
        ::= { iqhip10CmdEntry 1344 }


    iqhip10ChromaVideoLevelUnderloadAvePicBelowThres OBJECT-TYPE
        SYNTAX            INTEGER
        MAX-ACCESS        read-write
        STATUS            current
        DESCRIPTION
                "CMNT: - 
                 TYPE: - Number
                 PAGE: - Chroma Video Level
                    Ave Pic Below Thres  cmdID= 1359
                    min= 0  max= 99  step= 1  format= %0.0f  div_scale= 1  preset= 0
                    Min = 0  Max = 99  Step = 1  Preset = 0  "
        ::= { iqhip10CmdEntry 1359 }


    iqhip10HyperionVideoMonitorChromaBitDepth OBJECT-TYPE
        SYNTAX            RollCallString
        MAX-ACCESS        read-only
        STATUS            current
        DESCRIPTION
                "CMNT: - 
                 TYPE: - Display
                 PAGE: - Hyperion
                    Chroma Bit Depth  cmdID= 1330  "
        ::= { iqhip10CmdEntry 1330 }


    iqhip10HyperionVideoMonitorLumaBitDepth OBJECT-TYPE
        SYNTAX            RollCallString
        MAX-ACCESS        read-only
        STATUS            current
        DESCRIPTION
                "CMNT: - 
                 TYPE: - Display
                 PAGE: - Hyperion
                    Luma Bit Depth  cmdID= 1331  "
        ::= { iqhip10CmdEntry 1331 }


    iqhip10HyperionVideoMonitorRGBLegalizerEnable OBJECT-TYPE
        SYNTAX            INTEGER { disable(0), enable(1)  }
        MAX-ACCESS        read-write
        STATUS            current
        DESCRIPTION
                "CMNT: - 
                 TYPE: - Checkbox
                 PAGE: - Hyperion
                    RGB Legalizer Enable  cmdID= 1360  "
        ::= { iqhip10CmdEntry 1360 }


    iqhip10HyperionVideoMonitorRGBLegalizerRange OBJECT-TYPE
        SYNTAX            INTEGER {
                            val700mV(0),
                            val721mV(1),
                            val735mV(2)
                            }
        MAX-ACCESS        read-write
        STATUS            current
        DESCRIPTION
                "CMNT: - 
                 TYPE: - RadiobuttonList
                 PAGE: - Hyperion
                    RGB Legalizer Range  cmdID= 1300
                    700 mV  value= 0
                    721 mV  value= 1
                    735 mV  value= 2  "
        ::= { iqhip10CmdEntry 1300 }


    iqhip10ClosedCaptionsCCCEA608BState OBJECT-TYPE
        SYNTAX            RollCallString
        MAX-ACCESS        read-only
        STATUS            current
        DESCRIPTION
                "CMNT: - 
                 TYPE: - Display
                 PAGE: - Closed Captions
                    State  cmdID= 1368  "
        ::= { iqhip10CmdEntry 1368 }


    iqhip10ClosedCaptionsCCCEA608BTitle1 OBJECT-TYPE
        SYNTAX            RollCallString
        MAX-ACCESS        read-only
        STATUS            current
        DESCRIPTION
                "CMNT: - 
                 TYPE: - Display
                 PAGE: - Closed Captions
                    Title 1  cmdID= 1371  "
        ::= { iqhip10CmdEntry 1371 }


    iqhip10ClosedCaptionsCCCEA608BTitle2 OBJECT-TYPE
        SYNTAX            RollCallString
        MAX-ACCESS        read-only
        STATUS            current
        DESCRIPTION
                "CMNT: - 
                 TYPE: - Display
                 PAGE: - Closed Captions
                    Title 2  cmdID= 1372  "
        ::= { iqhip10CmdEntry 1372 }


    iqhip10ClosedCaptionsCCCEA708BField1 OBJECT-TYPE
        SYNTAX            RollCallString
        MAX-ACCESS        read-only
        STATUS            current
        DESCRIPTION
                "CMNT: - 
                 TYPE: - Display
                 PAGE: - Closed Captions
                    Field 1  cmdID= 1366  "
        ::= { iqhip10CmdEntry 1366 }


    iqhip10ClosedCaptionsCCCEA708BField2 OBJECT-TYPE
        SYNTAX            RollCallString
        MAX-ACCESS        read-only
        STATUS            current
        DESCRIPTION
                "CMNT: - 
                 TYPE: - Display
                 PAGE: - Closed Captions
                    Field 2  cmdID= 1367  "
        ::= { iqhip10CmdEntry 1367 }


    iqhip10ClosedCaptionsTemporalControlEnableAlarm OBJECT-TYPE
        SYNTAX            INTEGER { disable(0), enable(1)  }
        MAX-ACCESS        read-write
        STATUS            current
        DESCRIPTION
                "CMNT: - 
                 TYPE: - Checkbox
                 PAGE: - Closed Captions
                    Enable Alarm  cmdID= 1370  "
        ::= { iqhip10CmdEntry 1370 }


    iqhip10ClosedCaptionsTemporalControlResetWhenOK OBJECT-TYPE
        SYNTAX            INTEGER { disable(0), enable(1)  }
        MAX-ACCESS        read-write
        STATUS            current
        DESCRIPTION
                "CMNT: - 
                 TYPE: - Checkbox
                 PAGE: - Closed Captions
                    Reset When OK  cmdID= 1373  "
        ::= { iqhip10CmdEntry 1373 }


    iqhip10ClosedCaptionsTemporalControlAlarm OBJECT-TYPE
        SYNTAX            RollCallString
        MAX-ACCESS        read-only
        STATUS            current
        DESCRIPTION
                "CMNT: - 
                 TYPE: - Display
                 PAGE: - Closed Captions
                    Alarm  cmdID= 1365  "
        ::= { iqhip10CmdEntry 1365 }


    iqhip10ClosedCaptionsTemporalControlFailCount OBJECT-TYPE
        SYNTAX            INTEGER
        MAX-ACCESS        read-write
        STATUS            current
        DESCRIPTION
                "CMNT: - 
                 TYPE: - Number
                 PAGE: - Closed Captions
                    Fail Count  cmdID= 1362
                    min= 0  max= 24000  step= 1  format= %0.0f  div_scale= 1  preset= 1800
                    Min = 0  Max = 24000  Step = 1  Preset = 1800  "
        ::= { iqhip10CmdEntry 1362 }


    iqhip10ClosedCaptionsTemporalControlWarningCount OBJECT-TYPE
        SYNTAX            INTEGER
        MAX-ACCESS        read-write
        STATUS            current
        DESCRIPTION
                "CMNT: - 
                 TYPE: - Number
                 PAGE: - Closed Captions
                    Warning Count  cmdID= 1363
                    min= 0  max= 24000  step= 1  format= %0.0f  div_scale= 1  preset= 600
                    Min = 0  Max = 24000  Step = 1  Preset = 600  "
        ::= { iqhip10CmdEntry 1363 }


    iqhip10ClosedCaptionsTemporalControlFailHoldCount OBJECT-TYPE
        SYNTAX            INTEGER
        MAX-ACCESS        read-write
        STATUS            current
        DESCRIPTION
                "CMNT: - 
                 TYPE: - Number
                 PAGE: - Closed Captions
                    Fail Hold Count  cmdID= 1364
                    min= 0  max= 16000  step= 1  format= %0.0f  div_scale= 1  preset= 300
                    Min = 0  Max = 16000  Step = 1  Preset = 300  "
        ::= { iqhip10CmdEntry 1364 }


    iqhip10ClosedCaptionsTemporalControlResetAlarm OBJECT-TYPE
        SYNTAX            INTEGER { noAction(0),valResetAlarm(1) }
        MAX-ACCESS        read-write
        STATUS            current
        DESCRIPTION
                "CMNT: - 
                 TYPE: - Button
                 PAGE: - Closed Captions
                    Reset Alarm  cmdID= 1369
                    value= 1  "
        ::= { iqhip10CmdEntry 1369 }


    iqhip10AncillaryDataContentAdvisoryEnableAlarm OBJECT-TYPE
        SYNTAX            INTEGER { disable(0), enable(1)  }
        MAX-ACCESS        read-write
        STATUS            current
        DESCRIPTION
                "CMNT: - 
                 TYPE: - Checkbox
                 PAGE: - Ancillary Data
                    Enable Alarm  cmdID= 1402  "
        ::= { iqhip10CmdEntry 1402 }


    iqhip10AncillaryDataContentAdvisorySystem OBJECT-TYPE
        SYNTAX            RollCallString
        MAX-ACCESS        read-only
        STATUS            current
        DESCRIPTION
                "CMNT: - 
                 TYPE: - Display
                 PAGE: - Ancillary Data
                    System  cmdID= 1400  "
        ::= { iqhip10CmdEntry 1400 }


    iqhip10AncillaryDataContentAdvisoryRating OBJECT-TYPE
        SYNTAX            RollCallString
        MAX-ACCESS        read-only
        STATUS            current
        DESCRIPTION
                "CMNT: - 
                 TYPE: - Display
                 PAGE: - Ancillary Data
                    Rating  cmdID= 1401  "
        ::= { iqhip10CmdEntry 1401 }


    iqhip10TimeCodeAncTimeCodeEnableAlarm OBJECT-TYPE
        SYNTAX            INTEGER { disable(0), enable(1)  }
        MAX-ACCESS        read-write
        STATUS            current
        DESCRIPTION
                "CMNT: - 
                 TYPE: - Checkbox
                 PAGE: - Time Code
                    Enable Alarm  cmdID= 1337  "
        ::= { iqhip10CmdEntry 1337 }


    iqhip10TimeCodeAncTimeCodeField1 OBJECT-TYPE
        SYNTAX            RollCallString
        MAX-ACCESS        read-only
        STATUS            current
        DESCRIPTION
                "CMNT: - 
                 TYPE: - Display
                 PAGE: - Time Code
                    Field 1  cmdID= 1333  "
        ::= { iqhip10CmdEntry 1333 }


    iqhip10TimeCodeAncTimeCodeField2 OBJECT-TYPE
        SYNTAX            RollCallString
        MAX-ACCESS        read-only
        STATUS            current
        DESCRIPTION
                "CMNT: - 
                 TYPE: - Display
                 PAGE: - Time Code
                    Field 2  cmdID= 1334  "
        ::= { iqhip10CmdEntry 1334 }


    iqhip10TimeCodeVITCEnableAlarm OBJECT-TYPE
        SYNTAX            INTEGER { disable(0), enable(1)  }
        MAX-ACCESS        read-write
        STATUS            current
        DESCRIPTION
                "CMNT: - 
                 TYPE: - Checkbox
                 PAGE: - Time Code
                    Enable Alarm  cmdID= 1802  "
        ::= { iqhip10CmdEntry 1802 }


    iqhip10TimeCodeVITCField1 OBJECT-TYPE
        SYNTAX            RollCallString
        MAX-ACCESS        read-only
        STATUS            current
        DESCRIPTION
                "CMNT: - 
                 TYPE: - Display
                 PAGE: - Time Code
                    Field 1  cmdID= 1800  "
        ::= { iqhip10CmdEntry 1800 }


    iqhip10TimeCodeVITCField2 OBJECT-TYPE
        SYNTAX            RollCallString
        MAX-ACCESS        read-only
        STATUS            current
        DESCRIPTION
                "CMNT: - 
                 TYPE: - Display
                 PAGE: - Time Code
                    Field 2  cmdID= 1801  "
        ::= { iqhip10CmdEntry 1801 }


    iqhip10AncillaryDataTimeCodeCurrentTimeCode OBJECT-TYPE
        SYNTAX            RollCallString
        MAX-ACCESS        read-only
        STATUS            current
        DESCRIPTION
                "CMNT: - 
                 TYPE: - Display
                 PAGE: - Ancillary Data
                    Current Time Code  cmdID= 1338  "
        ::= { iqhip10CmdEntry 1338 }


    iqhip10AncillaryDataTimeCodeSDTimeCodeSel OBJECT-TYPE
        SYNTAX            INTEGER {
                            valAuto(0),
                            valVITC(1),
                            valAnc(2)
                            }
        MAX-ACCESS        read-write
        STATUS            current
        DESCRIPTION
                "CMNT: - 
                 TYPE: - RadiobuttonList
                 PAGE: - Ancillary Data
                    SD Time Code Sel  cmdID= 1820
                    Auto  value= 0
                    VITC  value= 1
                    Anc  value= 2  "
        ::= { iqhip10CmdEntry 1820 }


    iqhip10AncillaryDataTimeCodeDisconEnableAlarm OBJECT-TYPE
        SYNTAX            INTEGER { disable(0), enable(1)  }
        MAX-ACCESS        read-write
        STATUS            current
        DESCRIPTION
                "CMNT: - 
                 TYPE: - Checkbox
                 PAGE: - Ancillary Data
                    Enable Alarm  cmdID= 3242  "
        ::= { iqhip10CmdEntry 3242 }


    iqhip10AncillaryDataTimeCodeDisconFail OBJECT-TYPE
        SYNTAX            INTEGER
        MAX-ACCESS        read-write
        STATUS            current
        DESCRIPTION
                "CMNT: - 
                 TYPE: - Number
                 PAGE: - Ancillary Data
                    Fail  cmdID= 3240
                    min= 1  max= 100  step= 1  format= %0.0f  div_scale= 1  preset= 30
                    Min = 1  Max = 100  Step = 1  Preset = 30  "
        ::= { iqhip10CmdEntry 3240 }


    iqhip10AncillaryDataTimeCodeDisconHold OBJECT-TYPE
        SYNTAX            INTEGER
        MAX-ACCESS        read-write
        STATUS            current
        DESCRIPTION
                "CMNT: - 
                 TYPE: - Number
                 PAGE: - Ancillary Data
                    Hold  cmdID= 3241
                    min= 1  max= 100  step= 1  format= %0.0f  div_scale= 1  preset= 5
                    Min = 1  Max = 100  Step = 1  Preset = 5  "
        ::= { iqhip10CmdEntry 3241 }


    iqhip10AncillaryDataTimeCodeDisconErrorAt OBJECT-TYPE
        SYNTAX            RollCallString
        MAX-ACCESS        read-only
        STATUS            current
        DESCRIPTION
                "CMNT: - 
                 TYPE: - Display
                 PAGE: - Ancillary Data
                    Error At  cmdID= 3243  "
        ::= { iqhip10CmdEntry 3243 }


    iqhip10AncillaryDataTimeCodeDisconOKAt OBJECT-TYPE
        SYNTAX            RollCallString
        MAX-ACCESS        read-only
        STATUS            current
        DESCRIPTION
                "CMNT: - 
                 TYPE: - Display
                 PAGE: - Ancillary Data
                    OK At  cmdID= 3244  "
        ::= { iqhip10CmdEntry 3244 }


    iqhip10AncillaryDataTimeCodeForceTCUpdates OBJECT-TYPE
        SYNTAX            INTEGER { disable(0), enable(1)  }
        MAX-ACCESS        read-write
        STATUS            current
        DESCRIPTION
                "CMNT: - 
                 TYPE: - Checkbox
                 PAGE: - Ancillary Data
                    Force TC Updates  cmdID= 1339  "
        ::= { iqhip10CmdEntry 1339 }


    iqhip10AncillaryDataUserAncDet1EnableAlarm OBJECT-TYPE
        SYNTAX            INTEGER { disable(0), enable(1)  }
        MAX-ACCESS        read-write
        STATUS            current
        DESCRIPTION
                "CMNT: - 
                 TYPE: - Checkbox
                 PAGE: - Ancillary Data
                    Enable Alarm  cmdID= 1390  "
        ::= { iqhip10CmdEntry 1390 }


    iqhip10AncillaryDataUserAncDet1DIDType OBJECT-TYPE
        SYNTAX            INTEGER {
                            valType1(1),
                            valType2(0)
                            }
        MAX-ACCESS        read-write
        STATUS            current
        DESCRIPTION
                "CMNT: - 
                 TYPE: - RadiobuttonList
                 PAGE: - Ancillary Data
                    DID Type  cmdID= 1382
                    Type 1  value= 1
                    Type 2  value= 0  "
        ::= { iqhip10CmdEntry 1382 }


    iqhip10AncillaryDataUserAncDet1DIDselect OBJECT-TYPE
        SYNTAX            INTEGER
        MAX-ACCESS        read-write
        STATUS            current
        DESCRIPTION
                "CMNT: - 
                 TYPE: - Number
                 PAGE: - Ancillary Data
                    DID select  cmdID= 1380
                    min= 0  max= 255  step= 1  format= %0.0f  div_scale= 1  preset= 0
                    Min = 0  Max = 255  Step = 1  Preset = 0  "
        ::= { iqhip10CmdEntry 1380 }


    iqhip10AncillaryDataUserAncDet1SDIDselect OBJECT-TYPE
        SYNTAX            INTEGER
        MAX-ACCESS        read-write
        STATUS            current
        DESCRIPTION
                "CMNT: - 
                 TYPE: - Number
                 PAGE: - Ancillary Data
                    SDID select  cmdID= 1381
                    min= 0  max= 255  step= 1  format= %0.0f  div_scale= 1  preset= 0
                    Min = 0  Max = 255  Step = 1  Preset = 0  "
        ::= { iqhip10CmdEntry 1381 }


    iqhip10AncillaryDataUserAncDet1Field1 OBJECT-TYPE
        SYNTAX            RollCallString
        MAX-ACCESS        read-only
        STATUS            current
        DESCRIPTION
                "CMNT: - 
                 TYPE: - Display
                 PAGE: - Ancillary Data
                    Field 1  cmdID= 1386  "
        ::= { iqhip10CmdEntry 1386 }


    iqhip10AncillaryDataUserAncDet1Field2 OBJECT-TYPE
        SYNTAX            RollCallString
        MAX-ACCESS        read-only
        STATUS            current
        DESCRIPTION
                "CMNT: - 
                 TYPE: - Display
                 PAGE: - Ancillary Data
                    Field 2  cmdID= 1387  "
        ::= { iqhip10CmdEntry 1387 }


    iqhip10AncillaryDataUserAncDet1Name OBJECT-TYPE
        SYNTAX            RollCallString
        MAX-ACCESS        read-write
        STATUS            current
        DESCRIPTION
                "CMNT: - 
                 TYPE: - Editstring
                 PAGE: - Ancillary Data
                    Name  cmdID= 1391
                    preset= User Anc 1"
        ::= { iqhip10CmdEntry 1391 }


    iqhip10AncillaryDataUserAncDet2EnableAlarm OBJECT-TYPE
        SYNTAX            INTEGER { disable(0), enable(1)  }
        MAX-ACCESS        read-write
        STATUS            current
        DESCRIPTION
                "CMNT: - 
                 TYPE: - Checkbox
                 PAGE: - Ancillary Data
                    Enable Alarm  cmdID= 1392  "
        ::= { iqhip10CmdEntry 1392 }


    iqhip10AncillaryDataUserAncDet2DIDType OBJECT-TYPE
        SYNTAX            INTEGER {
                            valType1(1),
                            valType2(0)
                            }
        MAX-ACCESS        read-write
        STATUS            current
        DESCRIPTION
                "CMNT: - 
                 TYPE: - RadiobuttonList
                 PAGE: - Ancillary Data
                    DID Type  cmdID= 1385
                    Type 1  value= 1
                    Type 2  value= 0  "
        ::= { iqhip10CmdEntry 1385 }


    iqhip10AncillaryDataUserAncDet2DIDselect OBJECT-TYPE
        SYNTAX            INTEGER
        MAX-ACCESS        read-write
        STATUS            current
        DESCRIPTION
                "CMNT: - 
                 TYPE: - Number
                 PAGE: - Ancillary Data
                    DID select  cmdID= 1383
                    min= 0  max= 255  step= 1  format= %0.0f  div_scale= 1  preset= 0
                    Min = 0  Max = 255  Step = 1  Preset = 0  "
        ::= { iqhip10CmdEntry 1383 }


    iqhip10AncillaryDataUserAncDet2SDIDselect OBJECT-TYPE
        SYNTAX            INTEGER
        MAX-ACCESS        read-write
        STATUS            current
        DESCRIPTION
                "CMNT: - 
                 TYPE: - Number
                 PAGE: - Ancillary Data
                    SDID select  cmdID= 1384
                    min= 0  max= 255  step= 1  format= %0.0f  div_scale= 1  preset= 0
                    Min = 0  Max = 255  Step = 1  Preset = 0  "
        ::= { iqhip10CmdEntry 1384 }


    iqhip10AncillaryDataUserAncDet2Field1 OBJECT-TYPE
        SYNTAX            RollCallString
        MAX-ACCESS        read-only
        STATUS            current
        DESCRIPTION
                "CMNT: - 
                 TYPE: - Display
                 PAGE: - Ancillary Data
                    Field 1  cmdID= 1388  "
        ::= { iqhip10CmdEntry 1388 }


    iqhip10AncillaryDataUserAncDet2Field2 OBJECT-TYPE
        SYNTAX            RollCallString
        MAX-ACCESS        read-only
        STATUS            current
        DESCRIPTION
                "CMNT: - 
                 TYPE: - Display
                 PAGE: - Ancillary Data
                    Field 2  cmdID= 1389  "
        ::= { iqhip10CmdEntry 1389 }


    iqhip10AncillaryDataUserAncDet2Name OBJECT-TYPE
        SYNTAX            RollCallString
        MAX-ACCESS        read-write
        STATUS            current
        DESCRIPTION
                "CMNT: - 
                 TYPE: - Editstring
                 PAGE: - Ancillary Data
                    Name  cmdID= 1393
                    preset= User Anc 2"
        ::= { iqhip10CmdEntry 1393 }


    iqhip10AncillaryDataWSSVIInputWSSPresence OBJECT-TYPE
        SYNTAX            RollCallString
        MAX-ACCESS        read-only
        STATUS            current
        DESCRIPTION
                "CMNT: - 
                 TYPE: - Display
                 PAGE: - Ancillary Data
                    WSS Presence   cmdID= 1420  "
        ::= { iqhip10CmdEntry 1420 }


    iqhip10AncillaryDataWSSVIInputWSSEnableAlarm OBJECT-TYPE
        SYNTAX            INTEGER { disable(0), enable(1)  }
        MAX-ACCESS        read-write
        STATUS            current
        DESCRIPTION
                "CMNT: - 
                 TYPE: - Checkbox
                 PAGE: - Ancillary Data
                    WSS Enable Alarm  cmdID= 1421  "
        ::= { iqhip10CmdEntry 1421 }


    iqhip10AncillaryDataWSSVIInputWSSData OBJECT-TYPE
        SYNTAX            RollCallString
        MAX-ACCESS        read-only
        STATUS            current
        DESCRIPTION
                "CMNT: - 
                 TYPE: - Display
                 PAGE: - Ancillary Data
                    WSS Data  cmdID= 1425  "
        ::= { iqhip10CmdEntry 1425 }


    iqhip10AncillaryDataWSSVIInputWSSScanSys OBJECT-TYPE
        SYNTAX            RollCallString
        MAX-ACCESS        read-only
        STATUS            current
        DESCRIPTION
                "CMNT: - 
                 TYPE: - Display
                 PAGE: - Ancillary Data
                    WSS Scan Sys  cmdID= 1426  "
        ::= { iqhip10CmdEntry 1426 }


    iqhip10AncillaryDataWSSVIInputETSIData OBJECT-TYPE
        SYNTAX            RollCallString
        MAX-ACCESS        read-only
        STATUS            current
        DESCRIPTION
                "CMNT: - 
                 TYPE: - Display
                 PAGE: - Ancillary Data
                    ETSI Data  cmdID= 1434  "
        ::= { iqhip10CmdEntry 1434 }


    iqhip10AncillaryDataWSSVIInputWSSType OBJECT-TYPE
        SYNTAX            INTEGER {
                            valETSI(1),
                            valAFD(2)
                            }
        MAX-ACCESS        read-write
        STATUS            current
        DESCRIPTION
                "CMNT: - 
                 TYPE: - RadiobuttonList
                 PAGE: - Ancillary Data
                    WSS Type  cmdID= 1424
                    ETSI  value= 1
                    AFD  value= 2  "
        ::= { iqhip10CmdEntry 1424 }


    iqhip10AncillaryDataWSSVIInputVIPresence OBJECT-TYPE
        SYNTAX            RollCallString
        MAX-ACCESS        read-only
        STATUS            current
        DESCRIPTION
                "CMNT: - 
                 TYPE: - Display
                 PAGE: - Ancillary Data
                    VI Presence   cmdID= 1422  "
        ::= { iqhip10CmdEntry 1422 }


    iqhip10AncillaryDataWSSVIInputVIEnableAlarm OBJECT-TYPE
        SYNTAX            INTEGER { disable(0), enable(1)  }
        MAX-ACCESS        read-write
        STATUS            current
        DESCRIPTION
                "CMNT: - 
                 TYPE: - Checkbox
                 PAGE: - Ancillary Data
                    VI Enable Alarm  cmdID= 1423  "
        ::= { iqhip10CmdEntry 1423 }


    iqhip10AncillaryDataWSSVIInputVIType OBJECT-TYPE
        SYNTAX            INTEGER {
                            valSMPTE(1),
                            valAFD(2),
                            valAFDn2008(3)
                            }
        MAX-ACCESS        read-write
        STATUS            current
        DESCRIPTION
                "CMNT: - 
                 TYPE: - RadiobuttonList
                 PAGE: - Ancillary Data
                    VI Type  cmdID= 1427
                    SMPTE  value= 1
                    AFD  value= 2
                    AFD-2008  value= 3  "
        ::= { iqhip10CmdEntry 1427 }


    iqhip10AncillaryDataWSSVIInputVIData OBJECT-TYPE
        SYNTAX            RollCallString
        MAX-ACCESS        read-only
        STATUS            current
        DESCRIPTION
                "CMNT: - 
                 TYPE: - Display
                 PAGE: - Ancillary Data
                    VI Data  cmdID= 1429  "
        ::= { iqhip10CmdEntry 1429 }


    iqhip10AncillaryDataWSSVIInputVIScanSys OBJECT-TYPE
        SYNTAX            RollCallString
        MAX-ACCESS        read-only
        STATUS            current
        DESCRIPTION
                "CMNT: - 
                 TYPE: - Display
                 PAGE: - Ancillary Data
                    VI Scan Sys  cmdID= 1428  "
        ::= { iqhip10CmdEntry 1428 }


    iqhip10AncillaryDataAFDSMPTE20162016Presence OBJECT-TYPE
        SYNTAX            RollCallString
        MAX-ACCESS        read-only
        STATUS            current
        DESCRIPTION
                "CMNT: - 
                 TYPE: - Display
                 PAGE: - Ancillary Data
                    2016 Presence   cmdID= 1430  "
        ::= { iqhip10CmdEntry 1430 }


    iqhip10AncillaryDataAFDSMPTE20162016EnableAlarm OBJECT-TYPE
        SYNTAX            INTEGER { disable(0), enable(1)  }
        MAX-ACCESS        read-write
        STATUS            current
        DESCRIPTION
                "CMNT: - 
                 TYPE: - Checkbox
                 PAGE: - Ancillary Data
                    2016 Enable Alarm  cmdID= 1431  "
        ::= { iqhip10CmdEntry 1431 }


    iqhip10AncillaryDataAFDSMPTE20162016Data OBJECT-TYPE
        SYNTAX            RollCallString
        MAX-ACCESS        read-only
        STATUS            current
        DESCRIPTION
                "CMNT: - 
                 TYPE: - Display
                 PAGE: - Ancillary Data
                    2016 Data  cmdID= 1432  "
        ::= { iqhip10CmdEntry 1432 }


    iqhip10AncillaryDataAFDSMPTE20162016ScanSys OBJECT-TYPE
        SYNTAX            RollCallString
        MAX-ACCESS        read-only
        STATUS            current
        DESCRIPTION
                "CMNT: - 
                 TYPE: - Display
                 PAGE: - Ancillary Data
                    2016 Scan Sys  cmdID= 1433  "
        ::= { iqhip10CmdEntry 1433 }


    iqhip10HyperionAudioDataActiveAudioCh OBJECT-TYPE
        SYNTAX            RollCallString
        MAX-ACCESS        read-only
        STATUS            current
        DESCRIPTION
                "CMNT: - 
                 TYPE: - Display
                 PAGE: - Hyperion
                    Active Audio Ch  cmdID= 1332  "
        ::= { iqhip10CmdEntry 1332 }


    iqhip10AudioDataGroup1EnableAlarmCh1 OBJECT-TYPE
        SYNTAX            INTEGER { disable(0), enable(1)  }
        MAX-ACCESS        read-write
        STATUS            current
        DESCRIPTION
                "CMNT: - 
                 TYPE: - Checkbox
                 PAGE: - Audio Data
                    Enable Alarm Ch 1  cmdID= 1520  "
        ::= { iqhip10CmdEntry 1520 }


    iqhip10AudioDataGroup1TypeCh1 OBJECT-TYPE
        SYNTAX            RollCallString
        MAX-ACCESS        read-only
        STATUS            current
        DESCRIPTION
                "CMNT: - 
                 TYPE: - Display
                 PAGE: - Audio Data
                    Type Ch 1  cmdID= 1500  "
        ::= { iqhip10CmdEntry 1500 }


    iqhip10AudioDataGroup1BitdepthCh1 OBJECT-TYPE
        SYNTAX            RollCallString
        MAX-ACCESS        read-only
        STATUS            current
        DESCRIPTION
                "CMNT: - 
                 TYPE: - Display
                 PAGE: - Audio Data
                    Bit depth Ch 1  cmdID= 1550  "
        ::= { iqhip10CmdEntry 1550 }


    iqhip10AudioDataGroup1EnableAlarmCh2 OBJECT-TYPE
        SYNTAX            INTEGER { disable(0), enable(1)  }
        MAX-ACCESS        read-write
        STATUS            current
        DESCRIPTION
                "CMNT: - 
                 TYPE: - Checkbox
                 PAGE: - Audio Data
                    Enable Alarm Ch 2  cmdID= 1521  "
        ::= { iqhip10CmdEntry 1521 }


    iqhip10AudioDataGroup1TypeCh2 OBJECT-TYPE
        SYNTAX            RollCallString
        MAX-ACCESS        read-only
        STATUS            current
        DESCRIPTION
                "CMNT: - 
                 TYPE: - Display
                 PAGE: - Audio Data
                    Type Ch 2  cmdID= 1501  "
        ::= { iqhip10CmdEntry 1501 }


    iqhip10AudioDataGroup1BitdepthCh2 OBJECT-TYPE
        SYNTAX            RollCallString
        MAX-ACCESS        read-only
        STATUS            current
        DESCRIPTION
                "CMNT: - 
                 TYPE: - Display
                 PAGE: - Audio Data
                    Bit depth Ch2  cmdID= 1551  "
        ::= { iqhip10CmdEntry 1551 }


    iqhip10AudioDataGroup1EnableAlarmCh3 OBJECT-TYPE
        SYNTAX            INTEGER { disable(0), enable(1)  }
        MAX-ACCESS        read-write
        STATUS            current
        DESCRIPTION
                "CMNT: - 
                 TYPE: - Checkbox
                 PAGE: - Audio Data
                    Enable Alarm Ch 3  cmdID= 1522  "
        ::= { iqhip10CmdEntry 1522 }


    iqhip10AudioDataGroup1TypeCh3 OBJECT-TYPE
        SYNTAX            RollCallString
        MAX-ACCESS        read-only
        STATUS            current
        DESCRIPTION
                "CMNT: - 
                 TYPE: - Display
                 PAGE: - Audio Data
                    Type Ch 3  cmdID= 1502  "
        ::= { iqhip10CmdEntry 1502 }


    iqhip10AudioDataGroup1BitdepthCh3 OBJECT-TYPE
        SYNTAX            RollCallString
        MAX-ACCESS        read-only
        STATUS            current
        DESCRIPTION
                "CMNT: - 
                 TYPE: - Display
                 PAGE: - Audio Data
                    Bit depth Ch3  cmdID= 1552  "
        ::= { iqhip10CmdEntry 1552 }


    iqhip10AudioDataGroup1EnableAlarmCh4 OBJECT-TYPE
        SYNTAX            INTEGER { disable(0), enable(1)  }
        MAX-ACCESS        read-write
        STATUS            current
        DESCRIPTION
                "CMNT: - 
                 TYPE: - Checkbox
                 PAGE: - Audio Data
                    Enable Alarm Ch 4  cmdID= 1523  "
        ::= { iqhip10CmdEntry 1523 }


    iqhip10AudioDataGroup1TypeCh4 OBJECT-TYPE
        SYNTAX            RollCallString
        MAX-ACCESS        read-only
        STATUS            current
        DESCRIPTION
                "CMNT: - 
                 TYPE: - Display
                 PAGE: - Audio Data
                    Type Ch 4  cmdID= 1503  "
        ::= { iqhip10CmdEntry 1503 }


    iqhip10AudioDataGroup1BitdepthCh4 OBJECT-TYPE
        SYNTAX            RollCallString
        MAX-ACCESS        read-only
        STATUS            current
        DESCRIPTION
                "CMNT: - 
                 TYPE: - Display
                 PAGE: - Audio Data
                    Bit depth Ch4  cmdID= 1553  "
        ::= { iqhip10CmdEntry 1553 }


    iqhip10AudioDataGroup2EnableAlarmCh5 OBJECT-TYPE
        SYNTAX            INTEGER { disable(0), enable(1)  }
        MAX-ACCESS        read-write
        STATUS            current
        DESCRIPTION
                "CMNT: - 
                 TYPE: - Checkbox
                 PAGE: - Audio Data
                    Enable Alarm Ch 5  cmdID= 1524  "
        ::= { iqhip10CmdEntry 1524 }


    iqhip10AudioDataGroup2TypeCh5 OBJECT-TYPE
        SYNTAX            RollCallString
        MAX-ACCESS        read-only
        STATUS            current
        DESCRIPTION
                "CMNT: - 
                 TYPE: - Display
                 PAGE: - Audio Data
                    Type Ch 5  cmdID= 1504  "
        ::= { iqhip10CmdEntry 1504 }


    iqhip10AudioDataGroup2BitdepthCh5 OBJECT-TYPE
        SYNTAX            RollCallString
        MAX-ACCESS        read-only
        STATUS            current
        DESCRIPTION
                "CMNT: - 
                 TYPE: - Display
                 PAGE: - Audio Data
                    Bit depth Ch 5  cmdID= 1554  "
        ::= { iqhip10CmdEntry 1554 }


    iqhip10AudioDataGroup2EnableAlarmCh6 OBJECT-TYPE
        SYNTAX            INTEGER { disable(0), enable(1)  }
        MAX-ACCESS        read-write
        STATUS            current
        DESCRIPTION
                "CMNT: - 
                 TYPE: - Checkbox
                 PAGE: - Audio Data
                    Enable Alarm Ch 6  cmdID= 1525  "
        ::= { iqhip10CmdEntry 1525 }


    iqhip10AudioDataGroup2TypeCh6 OBJECT-TYPE
        SYNTAX            RollCallString
        MAX-ACCESS        read-only
        STATUS            current
        DESCRIPTION
                "CMNT: - 
                 TYPE: - Display
                 PAGE: - Audio Data
                    Type Ch 6  cmdID= 1505  "
        ::= { iqhip10CmdEntry 1505 }


    iqhip10AudioDataGroup2BitdepthCh6 OBJECT-TYPE
        SYNTAX            RollCallString
        MAX-ACCESS        read-only
        STATUS            current
        DESCRIPTION
                "CMNT: - 
                 TYPE: - Display
                 PAGE: - Audio Data
                    Bit depth Ch 6  cmdID= 1555  "
        ::= { iqhip10CmdEntry 1555 }


    iqhip10AudioDataGroup2EnableAlarmCh7 OBJECT-TYPE
        SYNTAX            INTEGER { disable(0), enable(1)  }
        MAX-ACCESS        read-write
        STATUS            current
        DESCRIPTION
                "CMNT: - 
                 TYPE: - Checkbox
                 PAGE: - Audio Data
                    Enable Alarm Ch 7  cmdID= 1526  "
        ::= { iqhip10CmdEntry 1526 }


    iqhip10AudioDataGroup2TypeCh7 OBJECT-TYPE
        SYNTAX            RollCallString
        MAX-ACCESS        read-only
        STATUS            current
        DESCRIPTION
                "CMNT: - 
                 TYPE: - Display
                 PAGE: - Audio Data
                    Type Ch 7  cmdID= 1506  "
        ::= { iqhip10CmdEntry 1506 }


    iqhip10AudioDataGroup2BitdepthCh7 OBJECT-TYPE
        SYNTAX            RollCallString
        MAX-ACCESS        read-only
        STATUS            current
        DESCRIPTION
                "CMNT: - 
                 TYPE: - Display
                 PAGE: - Audio Data
                    Bit depth Ch 7  cmdID= 1556  "
        ::= { iqhip10CmdEntry 1556 }


    iqhip10AudioDataGroup2EnableAlarmCh8 OBJECT-TYPE
        SYNTAX            INTEGER { disable(0), enable(1)  }
        MAX-ACCESS        read-write
        STATUS            current
        DESCRIPTION
                "CMNT: - 
                 TYPE: - Checkbox
                 PAGE: - Audio Data
                    Enable Alarm Ch 8  cmdID= 1527  "
        ::= { iqhip10CmdEntry 1527 }


    iqhip10AudioDataGroup2TypeCh8 OBJECT-TYPE
        SYNTAX            RollCallString
        MAX-ACCESS        read-only
        STATUS            current
        DESCRIPTION
                "CMNT: - 
                 TYPE: - Display
                 PAGE: - Audio Data
                    Type Ch 8  cmdID= 1507  "
        ::= { iqhip10CmdEntry 1507 }


    iqhip10AudioDataGroup2BitdepthCh8 OBJECT-TYPE
        SYNTAX            RollCallString
        MAX-ACCESS        read-only
        STATUS            current
        DESCRIPTION
                "CMNT: - 
                 TYPE: - Display
                 PAGE: - Audio Data
                    Bit depth Ch 8  cmdID= 1557  "
        ::= { iqhip10CmdEntry 1557 }


    iqhip10AudioDataGroup3EnableAlarmCh9 OBJECT-TYPE
        SYNTAX            INTEGER { disable(0), enable(1)  }
        MAX-ACCESS        read-write
        STATUS            current
        DESCRIPTION
                "CMNT: - 
                 TYPE: - Checkbox
                 PAGE: - Audio Data
                    Enable Alarm Ch 9  cmdID= 1528  "
        ::= { iqhip10CmdEntry 1528 }


    iqhip10AudioDataGroup3TypeCh9 OBJECT-TYPE
        SYNTAX            RollCallString
        MAX-ACCESS        read-only
        STATUS            current
        DESCRIPTION
                "CMNT: - 
                 TYPE: - Display
                 PAGE: - Audio Data
                    Type Ch 9  cmdID= 1508  "
        ::= { iqhip10CmdEntry 1508 }


    iqhip10AudioDataGroup3BitdepthCh9 OBJECT-TYPE
        SYNTAX            RollCallString
        MAX-ACCESS        read-only
        STATUS            current
        DESCRIPTION
                "CMNT: - 
                 TYPE: - Display
                 PAGE: - Audio Data
                    Bit depth Ch 9  cmdID= 1558  "
        ::= { iqhip10CmdEntry 1558 }


    iqhip10AudioDataGroup3EnableAlarmCh10 OBJECT-TYPE
        SYNTAX            INTEGER { disable(0), enable(1)  }
        MAX-ACCESS        read-write
        STATUS            current
        DESCRIPTION
                "CMNT: - 
                 TYPE: - Checkbox
                 PAGE: - Audio Data
                    Enable Alarm Ch 10  cmdID= 1529  "
        ::= { iqhip10CmdEntry 1529 }


    iqhip10AudioDataGroup3TypeCh10 OBJECT-TYPE
        SYNTAX            RollCallString
        MAX-ACCESS        read-only
        STATUS            current
        DESCRIPTION
                "CMNT: - 
                 TYPE: - Display
                 PAGE: - Audio Data
                    Type Ch 10  cmdID= 1509  "
        ::= { iqhip10CmdEntry 1509 }


    iqhip10AudioDataGroup3BitdepthCh10 OBJECT-TYPE
        SYNTAX            RollCallString
        MAX-ACCESS        read-only
        STATUS            current
        DESCRIPTION
                "CMNT: - 
                 TYPE: - Display
                 PAGE: - Audio Data
                    Bit depth Ch 10  cmdID= 1559  "
        ::= { iqhip10CmdEntry 1559 }


    iqhip10AudioDataGroup3EnableAlarmCh11 OBJECT-TYPE
        SYNTAX            INTEGER { disable(0), enable(1)  }
        MAX-ACCESS        read-write
        STATUS            current
        DESCRIPTION
                "CMNT: - 
                 TYPE: - Checkbox
                 PAGE: - Audio Data
                    Enable Alarm Ch 11  cmdID= 1530  "
        ::= { iqhip10CmdEntry 1530 }


    iqhip10AudioDataGroup3TypeCh11 OBJECT-TYPE
        SYNTAX            RollCallString
        MAX-ACCESS        read-only
        STATUS            current
        DESCRIPTION
                "CMNT: - 
                 TYPE: - Display
                 PAGE: - Audio Data
                    Type Ch 11  cmdID= 1510  "
        ::= { iqhip10CmdEntry 1510 }


    iqhip10AudioDataGroup3BitdepthCh11 OBJECT-TYPE
        SYNTAX            RollCallString
        MAX-ACCESS        read-only
        STATUS            current
        DESCRIPTION
                "CMNT: - 
                 TYPE: - Display
                 PAGE: - Audio Data
                    Bit depth Ch 11  cmdID= 1560  "
        ::= { iqhip10CmdEntry 1560 }


    iqhip10AudioDataGroup3EnableAlarmCh12 OBJECT-TYPE
        SYNTAX            INTEGER { disable(0), enable(1)  }
        MAX-ACCESS        read-write
        STATUS            current
        DESCRIPTION
                "CMNT: - 
                 TYPE: - Checkbox
                 PAGE: - Audio Data
                    Enable Alarm Ch 12  cmdID= 1531  "
        ::= { iqhip10CmdEntry 1531 }


    iqhip10AudioDataGroup3TypeCh12 OBJECT-TYPE
        SYNTAX            RollCallString
        MAX-ACCESS        read-only
        STATUS            current
        DESCRIPTION
                "CMNT: - 
                 TYPE: - Display
                 PAGE: - Audio Data
                    Type Ch 12  cmdID= 1511  "
        ::= { iqhip10CmdEntry 1511 }


    iqhip10AudioDataGroup3BitdepthCh12 OBJECT-TYPE
        SYNTAX            RollCallString
        MAX-ACCESS        read-only
        STATUS            current
        DESCRIPTION
                "CMNT: - 
                 TYPE: - Display
                 PAGE: - Audio Data
                    Bit depth Ch 12  cmdID= 1561  "
        ::= { iqhip10CmdEntry 1561 }


    iqhip10AudioDataGroup4EnableAlarmCh13 OBJECT-TYPE
        SYNTAX            INTEGER { disable(0), enable(1)  }
        MAX-ACCESS        read-write
        STATUS            current
        DESCRIPTION
                "CMNT: - 
                 TYPE: - Checkbox
                 PAGE: - Audio Data
                    Enable Alarm Ch 13  cmdID= 1532  "
        ::= { iqhip10CmdEntry 1532 }


    iqhip10AudioDataGroup4TypeCh13 OBJECT-TYPE
        SYNTAX            RollCallString
        MAX-ACCESS        read-only
        STATUS            current
        DESCRIPTION
                "CMNT: - 
                 TYPE: - Display
                 PAGE: - Audio Data
                    Type Ch 13  cmdID= 1512  "
        ::= { iqhip10CmdEntry 1512 }


    iqhip10AudioDataGroup4BitdepthCh13 OBJECT-TYPE
        SYNTAX            RollCallString
        MAX-ACCESS        read-only
        STATUS            current
        DESCRIPTION
                "CMNT: - 
                 TYPE: - Display
                 PAGE: - Audio Data
                    Bit depth Ch 13  cmdID= 1562  "
        ::= { iqhip10CmdEntry 1562 }


    iqhip10AudioDataGroup4EnableAlarmCh14 OBJECT-TYPE
        SYNTAX            INTEGER { disable(0), enable(1)  }
        MAX-ACCESS        read-write
        STATUS            current
        DESCRIPTION
                "CMNT: - 
                 TYPE: - Checkbox
                 PAGE: - Audio Data
                    Enable Alarm Ch 14  cmdID= 1533  "
        ::= { iqhip10CmdEntry 1533 }


    iqhip10AudioDataGroup4TypeCh14 OBJECT-TYPE
        SYNTAX            RollCallString
        MAX-ACCESS        read-only
        STATUS            current
        DESCRIPTION
                "CMNT: - 
                 TYPE: - Display
                 PAGE: - Audio Data
                    Type Ch 14  cmdID= 1513  "
        ::= { iqhip10CmdEntry 1513 }


    iqhip10AudioDataGroup4BitdepthCh14 OBJECT-TYPE
        SYNTAX            RollCallString
        MAX-ACCESS        read-only
        STATUS            current
        DESCRIPTION
                "CMNT: - 
                 TYPE: - Display
                 PAGE: - Audio Data
                    Bit depth Ch 14  cmdID= 1563  "
        ::= { iqhip10CmdEntry 1563 }


    iqhip10AudioDataGroup4EnableAlarmCh15 OBJECT-TYPE
        SYNTAX            INTEGER { disable(0), enable(1)  }
        MAX-ACCESS        read-write
        STATUS            current
        DESCRIPTION
                "CMNT: - 
                 TYPE: - Checkbox
                 PAGE: - Audio Data
                    Enable Alarm Ch 15  cmdID= 1534  "
        ::= { iqhip10CmdEntry 1534 }


    iqhip10AudioDataGroup4TypeCh15 OBJECT-TYPE
        SYNTAX            RollCallString
        MAX-ACCESS        read-only
        STATUS            current
        DESCRIPTION
                "CMNT: - 
                 TYPE: - Display
                 PAGE: - Audio Data
                    Type Ch 15  cmdID= 1514  "
        ::= { iqhip10CmdEntry 1514 }


    iqhip10AudioDataGroup4BitdepthCh15 OBJECT-TYPE
        SYNTAX            RollCallString
        MAX-ACCESS        read-only
        STATUS            current
        DESCRIPTION
                "CMNT: - 
                 TYPE: - Display
                 PAGE: - Audio Data
                    Bit depth Ch 15  cmdID= 1564  "
        ::= { iqhip10CmdEntry 1564 }


    iqhip10AudioDataGroup4EnableAlarmCh16 OBJECT-TYPE
        SYNTAX            INTEGER { disable(0), enable(1)  }
        MAX-ACCESS        read-write
        STATUS            current
        DESCRIPTION
                "CMNT: - 
                 TYPE: - Checkbox
                 PAGE: - Audio Data
                    Enable Alarm Ch 16  cmdID= 1535  "
        ::= { iqhip10CmdEntry 1535 }


    iqhip10AudioDataGroup4TypeCh16 OBJECT-TYPE
        SYNTAX            RollCallString
        MAX-ACCESS        read-only
        STATUS            current
        DESCRIPTION
                "CMNT: - 
                 TYPE: - Display
                 PAGE: - Audio Data
                    Type Ch 16  cmdID= 1515  "
        ::= { iqhip10CmdEntry 1515 }


    iqhip10AudioDataGroup4BitdepthCh16 OBJECT-TYPE
        SYNTAX            RollCallString
        MAX-ACCESS        read-only
        STATUS            current
        DESCRIPTION
                "CMNT: - 
                 TYPE: - Display
                 PAGE: - Audio Data
                    Bit depth Ch 16  cmdID= 1565  "
        ::= { iqhip10CmdEntry 1565 }


    iqhip10AudioDataDolbyEStatusEnableAlarmPair1 OBJECT-TYPE
        SYNTAX            INTEGER { disable(0), enable(1)  }
        MAX-ACCESS        read-write
        STATUS            current
        DESCRIPTION
                "CMNT: - 
                 TYPE: - Checkbox
                 PAGE: - Audio Data
                    Enable Alarm Pair 1  cmdID= 1490  "
        ::= { iqhip10CmdEntry 1490 }


    iqhip10AudioDataDolbyEStatusStatusPair1 OBJECT-TYPE
        SYNTAX            RollCallString
        MAX-ACCESS        read-only
        STATUS            current
        DESCRIPTION
                "CMNT: - 
                 TYPE: - Display
                 PAGE: - Audio Data
                    Status Pair 1  cmdID= 1480  "
        ::= { iqhip10CmdEntry 1480 }


    iqhip10AudioDataDolbyEStatusEnableAlarmPair2 OBJECT-TYPE
        SYNTAX            INTEGER { disable(0), enable(1)  }
        MAX-ACCESS        read-write
        STATUS            current
        DESCRIPTION
                "CMNT: - 
                 TYPE: - Checkbox
                 PAGE: - Audio Data
                    Enable Alarm Pair 2  cmdID= 1491  "
        ::= { iqhip10CmdEntry 1491 }


    iqhip10AudioDataDolbyEStatusStatusPair2 OBJECT-TYPE
        SYNTAX            RollCallString
        MAX-ACCESS        read-only
        STATUS            current
        DESCRIPTION
                "CMNT: - 
                 TYPE: - Display
                 PAGE: - Audio Data
                    Status Pair 2  cmdID= 1481  "
        ::= { iqhip10CmdEntry 1481 }


    iqhip10AudioDataDolbyEStatusEnableAlarmPair3 OBJECT-TYPE
        SYNTAX            INTEGER { disable(0), enable(1)  }
        MAX-ACCESS        read-write
        STATUS            current
        DESCRIPTION
                "CMNT: - 
                 TYPE: - Checkbox
                 PAGE: - Audio Data
                    Enable Alarm Pair 3  cmdID= 1492  "
        ::= { iqhip10CmdEntry 1492 }


    iqhip10AudioDataDolbyEStatusStatusPair3 OBJECT-TYPE
        SYNTAX            RollCallString
        MAX-ACCESS        read-only
        STATUS            current
        DESCRIPTION
                "CMNT: - 
                 TYPE: - Display
                 PAGE: - Audio Data
                    Status Pair 3  cmdID= 1482  "
        ::= { iqhip10CmdEntry 1482 }


    iqhip10AudioDataDolbyEStatusEnableAlarmPair4 OBJECT-TYPE
        SYNTAX            INTEGER { disable(0), enable(1)  }
        MAX-ACCESS        read-write
        STATUS            current
        DESCRIPTION
                "CMNT: - 
                 TYPE: - Checkbox
                 PAGE: - Audio Data
                    Enable Alarm Pair 4  cmdID= 1493  "
        ::= { iqhip10CmdEntry 1493 }


    iqhip10AudioDataDolbyEStatusStatusPair4 OBJECT-TYPE
        SYNTAX            RollCallString
        MAX-ACCESS        read-only
        STATUS            current
        DESCRIPTION
                "CMNT: - 
                 TYPE: - Display
                 PAGE: - Audio Data
                    Status Pair 4  cmdID= 1483  "
        ::= { iqhip10CmdEntry 1483 }


    iqhip10AudioDataDolbyEStatusEnableAlarmPair5 OBJECT-TYPE
        SYNTAX            INTEGER { disable(0), enable(1)  }
        MAX-ACCESS        read-write
        STATUS            current
        DESCRIPTION
                "CMNT: - 
                 TYPE: - Checkbox
                 PAGE: - Audio Data
                    Enable Alarm Pair 5  cmdID= 1494  "
        ::= { iqhip10CmdEntry 1494 }


    iqhip10AudioDataDolbyEStatusStatusPair5 OBJECT-TYPE
        SYNTAX            RollCallString
        MAX-ACCESS        read-only
        STATUS            current
        DESCRIPTION
                "CMNT: - 
                 TYPE: - Display
                 PAGE: - Audio Data
                    Status Pair 5  cmdID= 1484  "
        ::= { iqhip10CmdEntry 1484 }


    iqhip10AudioDataDolbyEStatusEnableAlarmPair6 OBJECT-TYPE
        SYNTAX            INTEGER { disable(0), enable(1)  }
        MAX-ACCESS        read-write
        STATUS            current
        DESCRIPTION
                "CMNT: - 
                 TYPE: - Checkbox
                 PAGE: - Audio Data
                    Enable Alarm Pair 6  cmdID= 1495  "
        ::= { iqhip10CmdEntry 1495 }


    iqhip10AudioDataDolbyEStatusStatusPair6 OBJECT-TYPE
        SYNTAX            RollCallString
        MAX-ACCESS        read-only
        STATUS            current
        DESCRIPTION
                "CMNT: - 
                 TYPE: - Display
                 PAGE: - Audio Data
                    Status Pair 6  cmdID= 1485  "
        ::= { iqhip10CmdEntry 1485 }


    iqhip10AudioDataDolbyEStatusEnableAlarmPair7 OBJECT-TYPE
        SYNTAX            INTEGER { disable(0), enable(1)  }
        MAX-ACCESS        read-write
        STATUS            current
        DESCRIPTION
                "CMNT: - 
                 TYPE: - Checkbox
                 PAGE: - Audio Data
                    Enable Alarm Pair 7  cmdID= 1496  "
        ::= { iqhip10CmdEntry 1496 }


    iqhip10AudioDataDolbyEStatusStatusPair7 OBJECT-TYPE
        SYNTAX            RollCallString
        MAX-ACCESS        read-only
        STATUS            current
        DESCRIPTION
                "CMNT: - 
                 TYPE: - Display
                 PAGE: - Audio Data
                    Status Pair 7  cmdID= 1486  "
        ::= { iqhip10CmdEntry 1486 }


    iqhip10AudioDataDolbyEStatusEnableAlarmPair8 OBJECT-TYPE
        SYNTAX            INTEGER { disable(0), enable(1)  }
        MAX-ACCESS        read-write
        STATUS            current
        DESCRIPTION
                "CMNT: - 
                 TYPE: - Checkbox
                 PAGE: - Audio Data
                    Enable Alarm Pair 8  cmdID= 1497  "
        ::= { iqhip10CmdEntry 1497 }


    iqhip10AudioDataDolbyEStatusStatusPair8 OBJECT-TYPE
        SYNTAX            RollCallString
        MAX-ACCESS        read-only
        STATUS            current
        DESCRIPTION
                "CMNT: - 
                 TYPE: - Display
                 PAGE: - Audio Data
                    Status Pair 8  cmdID= 1487  "
        ::= { iqhip10CmdEntry 1487 }


    iqhip10HyperionAudioLevelDetChannelIndex OBJECT-TYPE
        SYNTAX            INTEGER
        MAX-ACCESS        read-write
        STATUS            current
        DESCRIPTION
                "CMNT: - 
                 TYPE: - Number
                 PAGE: - Hyperion
                    Channel Index  cmdID= 3001
                    min= 1  max= 16  step= 1  format= %0.0f  div_scale= 1  preset= 1
                    Min = 1  Max = 16  Step = 1  Preset = 1  "
        ::= { iqhip10CmdEntry 3001 }


    iqhip10HyperionAudioLevelDetAverageAudioLevel OBJECT-TYPE
        SYNTAX            RollCallString
        MAX-ACCESS        read-only
        STATUS            current
        DESCRIPTION
                "CMNT: - 
                 TYPE: - Display
                 PAGE: - Hyperion
                    Average Audio Level  cmdID= 3000  "
        ::= { iqhip10CmdEntry 3000 }


    iqhip10AudioLevelDetOverloadDetectorEnableAlarm OBJECT-TYPE
        SYNTAX            INTEGER { disable(0), enable(1)  }
        MAX-ACCESS        read-write
        STATUS            current
        DESCRIPTION
                "CMNT: - 
                 TYPE: - Checkbox
                 PAGE: - Audio Level Det
                    Enable Alarm  cmdID= 3006  "
        ::= { iqhip10CmdEntry 3006 }


    iqhip10AudioLevelDetOverloadDetectorAlarm OBJECT-TYPE
        SYNTAX            RollCallString
        MAX-ACCESS        read-only
        STATUS            current
        DESCRIPTION
                "CMNT: - 
                 TYPE: - Display
                 PAGE: - Audio Level Det
                    Alarm  cmdID= 3007  "
        ::= { iqhip10CmdEntry 3007 }


    iqhip10AudioLevelDetOverloadDetectorLeveldB OBJECT-TYPE
        SYNTAX            INTEGER
        MAX-ACCESS        read-write
        STATUS            current
        DESCRIPTION
                "CMNT: - 
                 TYPE: - Number
                 PAGE: - Audio Level Det
                    Level (dB)  cmdID= 3002
                    min= -15  max= 0  step= 1  format= %0.0f  div_scale= 1  preset= -5
                    Min = -15  Max = 0  Step = 1  Preset = -5  "
        ::= { iqhip10CmdEntry 3002 }


    iqhip10AudioLevelDetOverloadDetectorWarningsecs OBJECT-TYPE
        SYNTAX            INTEGER
        MAX-ACCESS        read-write
        STATUS            current
        DESCRIPTION
                "CMNT: - 
                 TYPE: - Number
                 PAGE: - Audio Level Det
                    Warning (secs)  cmdID= 3003
                    min= 1  max= 120  step= 1  format= %0.0f  div_scale= 1  preset= 30
                    Min = 1  Max = 120  Step = 1  Preset = 30  "
        ::= { iqhip10CmdEntry 3003 }


    iqhip10AudioLevelDetOverloadDetectorFailsecs OBJECT-TYPE
        SYNTAX            INTEGER
        MAX-ACCESS        read-write
        STATUS            current
        DESCRIPTION
                "CMNT: - 
                 TYPE: - Number
                 PAGE: - Audio Level Det
                    Fail (secs)  cmdID= 3004
                    min= 1  max= 120  step= 1  format= %0.0f  div_scale= 1  preset= 60
                    Min = 1  Max = 120  Step = 1  Preset = 60  "
        ::= { iqhip10CmdEntry 3004 }


    iqhip10AudioLevelDetOverloadDetectorFailHoldsecs OBJECT-TYPE
        SYNTAX            INTEGER
        MAX-ACCESS        read-write
        STATUS            current
        DESCRIPTION
                "CMNT: - 
                 TYPE: - Number
                 PAGE: - Audio Level Det
                    Fail Hold (secs)  cmdID= 3005
                    min= 1  max= 120  step= 1  format= %0.0f  div_scale= 1  preset= 20
                    Min = 1  Max = 120  Step = 1  Preset = 20  "
        ::= { iqhip10CmdEntry 3005 }


    iqhip10AudioLevelDetectorAlarmReset OBJECT-TYPE
        SYNTAX            INTEGER {
                                     valOLAlarmReset(1),
                                   valLoudAlarmReset(2),
                                  valQuietAlarmReset(3),
                                valSilenceAlarmReset(4)
                                  }
        MAX-ACCESS        read-write
        STATUS            current
        DESCRIPTION
                "CMNT: - 
                 TYPE: - Button
                 PAGE: - Audio Level Det
					OL Alarm Reset      cmdID= 3032  value= 1  
					Loud Alarm Reset    cmdID= 3032  value= 2  
					Quiet Alarm  Reset  cmdID= 3032  value= 3  
					Silence Alarm Reset cmdID= 3032  value= 4  "
        ::= { iqhip10CmdEntry 3032 }


    iqhip10AudioLevelDetLoudDetectorEnableAlarm OBJECT-TYPE
        SYNTAX            INTEGER { disable(0), enable(1)  }
        MAX-ACCESS        read-write
        STATUS            current
        DESCRIPTION
                "CMNT: - 
                 TYPE: - Checkbox
                 PAGE: - Audio Level Det
                    Enable Alarm  cmdID= 3012  "
        ::= { iqhip10CmdEntry 3012 }


    iqhip10AudioLevelDetLoudDetectorAlarm OBJECT-TYPE
        SYNTAX            RollCallString
        MAX-ACCESS        read-only
        STATUS            current
        DESCRIPTION
                "CMNT: - 
                 TYPE: - Display
                 PAGE: - Audio Level Det
                    Alarm  cmdID= 3013  "
        ::= { iqhip10CmdEntry 3013 }


    iqhip10AudioLevelDetLoudDetectorLeveldB OBJECT-TYPE
        SYNTAX            INTEGER
        MAX-ACCESS        read-write
        STATUS            current
        DESCRIPTION
                "CMNT: - 
                 TYPE: - Number
                 PAGE: - Audio Level Det
                    Level (dB)  cmdID= 3008
                    min= -25  max= 0  step= 1  format= %0.0f  div_scale= 1  preset= -10
                    Min = -25  Max = 0  Step = 1  Preset = -10  "
        ::= { iqhip10CmdEntry 3008 }


    iqhip10AudioLevelDetLoudDetectorWarningsecs OBJECT-TYPE
        SYNTAX            INTEGER
        MAX-ACCESS        read-write
        STATUS            current
        DESCRIPTION
                "CMNT: - 
                 TYPE: - Number
                 PAGE: - Audio Level Det
                    Warning (secs)  cmdID= 3009
                    min= 1  max= 120  step= 1  format= %0.0f  div_scale= 1  preset= 30
                    Min = 1  Max = 120  Step = 1  Preset = 30  "
        ::= { iqhip10CmdEntry 3009 }


    iqhip10AudioLevelDetLoudDetectorFailsecs OBJECT-TYPE
        SYNTAX            INTEGER
        MAX-ACCESS        read-write
        STATUS            current
        DESCRIPTION
                "CMNT: - 
                 TYPE: - Number
                 PAGE: - Audio Level Det
                    Fail (secs)  cmdID= 3010
                    min= 1  max= 120  step= 1  format= %0.0f  div_scale= 1  preset= 60
                    Min = 1  Max = 120  Step = 1  Preset = 60  "
        ::= { iqhip10CmdEntry 3010 }


    iqhip10AudioLevelDetLoudDetectorFailHoldsecs OBJECT-TYPE
        SYNTAX            INTEGER
        MAX-ACCESS        read-write
        STATUS            current
        DESCRIPTION
                "CMNT: - 
                 TYPE: - Number
                 PAGE: - Audio Level Det
                    Fail Hold (secs)  cmdID= 3011
                    min= 1  max= 120  step= 1  format= %0.0f  div_scale= 1  preset= 20
                    Min = 1  Max = 120  Step = 1  Preset = 20  "
        ::= { iqhip10CmdEntry 3011 }


    iqhip10AudioLevelDetQuietDetectorEnableAlarm OBJECT-TYPE
        SYNTAX            INTEGER { disable(0), enable(1)  }
        MAX-ACCESS        read-write
        STATUS            current
        DESCRIPTION
                "CMNT: - 
                 TYPE: - Checkbox
                 PAGE: - Audio Level Det
                    Enable Alarm  cmdID= 3018  "
        ::= { iqhip10CmdEntry 3018 }


    iqhip10AudioLevelDetQuietDetectorAlarm OBJECT-TYPE
        SYNTAX            RollCallString
        MAX-ACCESS        read-only
        STATUS            current
        DESCRIPTION
                "CMNT: - 
                 TYPE: - Display
                 PAGE: - Audio Level Det
                    Alarm  cmdID= 3019  "
        ::= { iqhip10CmdEntry 3019 }


    iqhip10AudioLevelDetQuietDetectorLeveldB OBJECT-TYPE
        SYNTAX            INTEGER
        MAX-ACCESS        read-write
        STATUS            current
        DESCRIPTION
                "CMNT: - 
                 TYPE: - Number
                 PAGE: - Audio Level Det
                    Level (dB)  cmdID= 3014
                    min= -50  max= -10  step= 1  format= %0.0f  div_scale= 1  preset= -40
                    Min = -50  Max = -10  Step = 1  Preset = -40  "
        ::= { iqhip10CmdEntry 3014 }


    iqhip10AudioLevelDetQuietDetectorWarningsecs OBJECT-TYPE
        SYNTAX            INTEGER
        MAX-ACCESS        read-write
        STATUS            current
        DESCRIPTION
                "CMNT: - 
                 TYPE: - Number
                 PAGE: - Audio Level Det
                    Warning (secs)  cmdID= 3015
                    min= 1  max= 120  step= 1  format= %0.0f  div_scale= 1  preset= 30
                    Min = 1  Max = 120  Step = 1  Preset = 30  "
        ::= { iqhip10CmdEntry 3015 }


    iqhip10AudioLevelDetQuietDetectorFailsecs OBJECT-TYPE
        SYNTAX            INTEGER
        MAX-ACCESS        read-write
        STATUS            current
        DESCRIPTION
                "CMNT: - 
                 TYPE: - Number
                 PAGE: - Audio Level Det
                    Fail (secs)  cmdID= 3016
                    min= 1  max= 120  step= 1  format= %0.0f  div_scale= 1  preset= 60
                    Min = 1  Max = 120  Step = 1  Preset = 60  "
        ::= { iqhip10CmdEntry 3016 }


    iqhip10AudioLevelDetQuietDetectorFailHoldsecs OBJECT-TYPE
        SYNTAX            INTEGER
        MAX-ACCESS        read-write
        STATUS            current
        DESCRIPTION
                "CMNT: - 
                 TYPE: - Number
                 PAGE: - Audio Level Det
                    Fail Hold (secs)  cmdID= 3017
                    min= 1  max= 120  step= 1  format= %0.0f  div_scale= 1  preset= 20
                    Min = 1  Max = 120  Step = 1  Preset = 20  "
        ::= { iqhip10CmdEntry 3017 }


    iqhip10AudioLevelDetSilenceDetectorEnableAlarm OBJECT-TYPE
        SYNTAX            INTEGER { disable(0), enable(1)  }
        MAX-ACCESS        read-write
        STATUS            current
        DESCRIPTION
                "CMNT: - 
                 TYPE: - Checkbox
                 PAGE: - Audio Level Det
                    Enable Alarm  cmdID= 3024  "
        ::= { iqhip10CmdEntry 3024 }


    iqhip10AudioLevelDetSilenceDetectorAlarm OBJECT-TYPE
        SYNTAX            RollCallString
        MAX-ACCESS        read-only
        STATUS            current
        DESCRIPTION
                "CMNT: - 
                 TYPE: - Display
                 PAGE: - Audio Level Det
                    Alarm  cmdID= 3025  "
        ::= { iqhip10CmdEntry 3025 }


    iqhip10AudioLevelDetSilenceDetectorLeveldB OBJECT-TYPE
        SYNTAX            INTEGER
        MAX-ACCESS        read-write
        STATUS            current
        DESCRIPTION
                "CMNT: - 
                 TYPE: - Number
                 PAGE: - Audio Level Det
                    Level (dB)  cmdID= 3020
                    min= -99  max= -60  step= 1  format= %0.0f  div_scale= 1  preset= -60
                    Min = -99  Max = -60  Step = 1  Preset = -60  "
        ::= { iqhip10CmdEntry 3020 }


    iqhip10AudioLevelDetSilenceDetectorWarningsecs OBJECT-TYPE
        SYNTAX            INTEGER
        MAX-ACCESS        read-write
        STATUS            current
        DESCRIPTION
                "CMNT: - 
                 TYPE: - Number
                 PAGE: - Audio Level Det
                    Warning (secs)  cmdID= 3021
                    min= 1  max= 120  step= 1  format= %0.0f  div_scale= 1  preset= 30
                    Min = 1  Max = 120  Step = 1  Preset = 30  "
        ::= { iqhip10CmdEntry 3021 }


    iqhip10AudioLevelDetSilenceDetectorFailsecs OBJECT-TYPE
        SYNTAX            INTEGER
        MAX-ACCESS        read-write
        STATUS            current
        DESCRIPTION
                "CMNT: - 
                 TYPE: - Number
                 PAGE: - Audio Level Det
                    Fail (secs)  cmdID= 3022
                    min= 1  max= 120  step= 1  format= %0.0f  div_scale= 1  preset= 60
                    Min = 1  Max = 120  Step = 1  Preset = 60  "
        ::= { iqhip10CmdEntry 3022 }


    iqhip10AudioLevelDetSilenceDetectorFailHoldsecs OBJECT-TYPE
        SYNTAX            INTEGER
        MAX-ACCESS        read-write
        STATUS            current
        DESCRIPTION
                "CMNT: - 
                 TYPE: - Number
                 PAGE: - Audio Level Det
                    Fail Hold (secs)  cmdID= 3023
                    min= 1  max= 120  step= 1  format= %0.0f  div_scale= 1  preset= 20
                    Min = 1  Max = 120  Step = 1  Preset = 20  "
        ::= { iqhip10CmdEntry 3023 }


    iqhip10AudioLevelDetDuplicateSettingsCopyFromChannel OBJECT-TYPE
        SYNTAX            INTEGER
        MAX-ACCESS        read-write
        STATUS            current
        DESCRIPTION
                "CMNT: - 
                 TYPE: - Number
                 PAGE: - Audio Level Det
                    Copy From Channel  cmdID= 3030
                    min= 1  max= 16  step= 1  format= %0.0f  div_scale= 1  preset= 1
                    Min = 1  Max = 16  Step = 1  Preset = 1  "
        ::= { iqhip10CmdEntry 3030 }


    iqhip10AudioLevelDetDuplicateSettingsCopySettings OBJECT-TYPE
        SYNTAX            INTEGER { noAction(0),valCopySettings(1) }
        MAX-ACCESS        read-write
        STATUS            current
        DESCRIPTION
                "CMNT: - 
                 TYPE: - Button
                 PAGE: - Audio Level Det
                    Copy Settings  cmdID= 3031
                    value= 1  "
        ::= { iqhip10CmdEntry 3031 }


    iqhip10AudioLevelDetAlarmChansEnableChanDet OBJECT-TYPE
        SYNTAX            INTEGER {
                                    valEnableAllChanDet(17),
                                   valDisableAllChanDet(16),
                                        valEnableChanDet(3),
                                       valDisableChanDet(2)
                                  }
        MAX-ACCESS        read-write
        STATUS            current
        DESCRIPTION
                "CMNT: - 
                 TYPE: - Button
                 PAGE: - Audio Level Det
					Enable All Chan Det  cmdID= 3040  value= 17  
					Disable All Chan Det cmdID= 3040  value= 16  
					Alarm Indexed Chan  cmdID= 3040 
					Enable Chan Det  value= 3  
					Disable Chan Det  value= 2  "
        ::= { iqhip10CmdEntry 3040 }


    iqhip10AudioLevelDetAlarmAllChansResetonOK OBJECT-TYPE
        SYNTAX            INTEGER { disable(0), enable(1)  }
        MAX-ACCESS        read-write
        STATUS            current
        DESCRIPTION
                "CMNT: - 
                 TYPE: - Checkbox
                 PAGE: - Audio Level Det
                    Reset on OK  cmdID= 3033  "
        ::= { iqhip10CmdEntry 3033 }


    iqhip10HyperionAudioLevelIndRollMapAudLvlEn OBJECT-TYPE
        SYNTAX            INTEGER { disable(0), enable(1)  }
        MAX-ACCESS        read-write
        STATUS            current
        DESCRIPTION
                "CMNT: - 
                 TYPE: - Checkbox
                 PAGE: - Hyperion
                    RollMap Aud Lvl En  cmdID= 38275  "
        ::= { iqhip10CmdEntry 38275 }


    iqhip10HyperionAudioLevelIndOSDMarker OBJECT-TYPE
        SYNTAX            INTEGER
        MAX-ACCESS        read-write
        STATUS            current
        DESCRIPTION
                "CMNT: - 
                 TYPE: - Number
                 PAGE: - Hyperion
                    OSD Marker  cmdID= 3150
                    min= -102  max= 0  step= 1  format= %0.0f  div_scale= 1  preset= -20
                    Min = -102  Max = 0  Step = 1  Preset = -20  "
        ::= { iqhip10CmdEntry 3150 }


    iqhip10HyperionAudioLevelIndRollMapAudLvl OBJECT-TYPE
        SYNTAX            RollCallString
        MAX-ACCESS        read-only
        STATUS            current
        DESCRIPTION
                "CMNT: - 
                 TYPE: - Display
                 PAGE: - Hyperion
                    RollMap Aud Lvl  cmdID= 38276  "
        ::= { iqhip10CmdEntry 38276 }


    iqhip10HyperionAudioLevelIndEnableChannel1 OBJECT-TYPE
        SYNTAX            INTEGER { disable(0), enable(1)  }
        MAX-ACCESS        read-write
        STATUS            current
        DESCRIPTION
                "CMNT: - 
                 TYPE: - Checkbox
                 PAGE: - Hyperion
                    Enable Channel 1  cmdID= 1582  "
        ::= { iqhip10CmdEntry 1582 }


    iqhip10HyperionAudioLevelIndChannel1 OBJECT-TYPE
        SYNTAX            RollCallString
        MAX-ACCESS        read-only
        STATUS            current
        DESCRIPTION
                "CMNT: - 
                 TYPE: - Display
                 PAGE: - Hyperion
                    Channel 1  cmdID= 1566  "
        ::= { iqhip10CmdEntry 1566 }


    iqhip10HyperionAudioLevelIndEnableChannel2 OBJECT-TYPE
        SYNTAX            INTEGER { disable(0), enable(1)  }
        MAX-ACCESS        read-write
        STATUS            current
        DESCRIPTION
                "CMNT: - 
                 TYPE: - Checkbox
                 PAGE: - Hyperion
                    Enable Channel 2  cmdID= 1583  "
        ::= { iqhip10CmdEntry 1583 }


    iqhip10HyperionAudioLevelIndChannel2 OBJECT-TYPE
        SYNTAX            RollCallString
        MAX-ACCESS        read-only
        STATUS            current
        DESCRIPTION
                "CMNT: - 
                 TYPE: - Display
                 PAGE: - Hyperion
                    Channel 2  cmdID= 1567  "
        ::= { iqhip10CmdEntry 1567 }


    iqhip10HyperionAudioLevelIndEnableChannel3 OBJECT-TYPE
        SYNTAX            INTEGER { disable(0), enable(1)  }
        MAX-ACCESS        read-write
        STATUS            current
        DESCRIPTION
                "CMNT: - 
                 TYPE: - Checkbox
                 PAGE: - Hyperion
                    Enable Channel 3  cmdID= 1584  "
        ::= { iqhip10CmdEntry 1584 }


    iqhip10HyperionAudioLevelIndChannel3 OBJECT-TYPE
        SYNTAX            RollCallString
        MAX-ACCESS        read-only
        STATUS            current
        DESCRIPTION
                "CMNT: - 
                 TYPE: - Display
                 PAGE: - Hyperion
                    Channel 3  cmdID= 1568  "
        ::= { iqhip10CmdEntry 1568 }


    iqhip10HyperionAudioLevelIndEnableChannel4 OBJECT-TYPE
        SYNTAX            INTEGER { disable(0), enable(1)  }
        MAX-ACCESS        read-write
        STATUS            current
        DESCRIPTION
                "CMNT: - 
                 TYPE: - Checkbox
                 PAGE: - Hyperion
                    Enable Channel 4  cmdID= 1585  "
        ::= { iqhip10CmdEntry 1585 }


    iqhip10HyperionAudioLevelIndChannel4 OBJECT-TYPE
        SYNTAX            RollCallString
        MAX-ACCESS        read-only
        STATUS            current
        DESCRIPTION
                "CMNT: - 
                 TYPE: - Display
                 PAGE: - Hyperion
                    Channel 4  cmdID= 1569  "
        ::= { iqhip10CmdEntry 1569 }


    iqhip10HyperionAudioLevelIndEnableChannel5 OBJECT-TYPE
        SYNTAX            INTEGER { disable(0), enable(1)  }
        MAX-ACCESS        read-write
        STATUS            current
        DESCRIPTION
                "CMNT: - 
                 TYPE: - Checkbox
                 PAGE: - Hyperion
                    Enable Channel 5  cmdID= 1586  "
        ::= { iqhip10CmdEntry 1586 }


    iqhip10HyperionAudioLevelIndChannel5 OBJECT-TYPE
        SYNTAX            RollCallString
        MAX-ACCESS        read-only
        STATUS            current
        DESCRIPTION
                "CMNT: - 
                 TYPE: - Display
                 PAGE: - Hyperion
                    Channel 5  cmdID= 1570  "
        ::= { iqhip10CmdEntry 1570 }


    iqhip10HyperionAudioLevelIndEnableChannel6 OBJECT-TYPE
        SYNTAX            INTEGER { disable(0), enable(1)  }
        MAX-ACCESS        read-write
        STATUS            current
        DESCRIPTION
                "CMNT: - 
                 TYPE: - Checkbox
                 PAGE: - Hyperion
                    Enable Channel 6  cmdID= 1587  "
        ::= { iqhip10CmdEntry 1587 }


    iqhip10HyperionAudioLevelIndChannel6 OBJECT-TYPE
        SYNTAX            RollCallString
        MAX-ACCESS        read-only
        STATUS            current
        DESCRIPTION
                "CMNT: - 
                 TYPE: - Display
                 PAGE: - Hyperion
                    Channel 6  cmdID= 1571  "
        ::= { iqhip10CmdEntry 1571 }


    iqhip10HyperionAudioLevelIndEnableChannel7 OBJECT-TYPE
        SYNTAX            INTEGER { disable(0), enable(1)  }
        MAX-ACCESS        read-write
        STATUS            current
        DESCRIPTION
                "CMNT: - 
                 TYPE: - Checkbox
                 PAGE: - Hyperion
                    Enable Channel 7  cmdID= 1588  "
        ::= { iqhip10CmdEntry 1588 }


    iqhip10HyperionAudioLevelIndChannel7 OBJECT-TYPE
        SYNTAX            RollCallString
        MAX-ACCESS        read-only
        STATUS            current
        DESCRIPTION
                "CMNT: - 
                 TYPE: - Display
                 PAGE: - Hyperion
                    Channel 7  cmdID= 1572  "
        ::= { iqhip10CmdEntry 1572 }


    iqhip10HyperionAudioLevelIndEnableChannel8 OBJECT-TYPE
        SYNTAX            INTEGER { disable(0), enable(1)  }
        MAX-ACCESS        read-write
        STATUS            current
        DESCRIPTION
                "CMNT: - 
                 TYPE: - Checkbox
                 PAGE: - Hyperion
                    Enable Channel 8  cmdID= 1589  "
        ::= { iqhip10CmdEntry 1589 }


    iqhip10HyperionAudioLevelIndChannel8 OBJECT-TYPE
        SYNTAX            RollCallString
        MAX-ACCESS        read-only
        STATUS            current
        DESCRIPTION
                "CMNT: - 
                 TYPE: - Display
                 PAGE: - Hyperion
                    Channel 8  cmdID= 1573  "
        ::= { iqhip10CmdEntry 1573 }


    iqhip10HyperionAudioLevelIndEnableChannel9 OBJECT-TYPE
        SYNTAX            INTEGER { disable(0), enable(1)  }
        MAX-ACCESS        read-write
        STATUS            current
        DESCRIPTION
                "CMNT: - 
                 TYPE: - Checkbox
                 PAGE: - Hyperion
                    Enable Channel 9  cmdID= 1590  "
        ::= { iqhip10CmdEntry 1590 }


    iqhip10HyperionAudioLevelIndChannel9 OBJECT-TYPE
        SYNTAX            RollCallString
        MAX-ACCESS        read-only
        STATUS            current
        DESCRIPTION
                "CMNT: - 
                 TYPE: - Display
                 PAGE: - Hyperion
                    Channel 9  cmdID= 1574  "
        ::= { iqhip10CmdEntry 1574 }


    iqhip10HyperionAudioLevelIndEnableChannel10 OBJECT-TYPE
        SYNTAX            INTEGER { disable(0), enable(1)  }
        MAX-ACCESS        read-write
        STATUS            current
        DESCRIPTION
                "CMNT: - 
                 TYPE: - Checkbox
                 PAGE: - Hyperion
                    Enable Channel 10  cmdID= 1591  "
        ::= { iqhip10CmdEntry 1591 }


    iqhip10HyperionAudioLevelIndChannel10 OBJECT-TYPE
        SYNTAX            RollCallString
        MAX-ACCESS        read-only
        STATUS            current
        DESCRIPTION
                "CMNT: - 
                 TYPE: - Display
                 PAGE: - Hyperion
                    Channel 10  cmdID= 1575  "
        ::= { iqhip10CmdEntry 1575 }


    iqhip10HyperionAudioLevelIndEnableChannel11 OBJECT-TYPE
        SYNTAX            INTEGER { disable(0), enable(1)  }
        MAX-ACCESS        read-write
        STATUS            current
        DESCRIPTION
                "CMNT: - 
                 TYPE: - Checkbox
                 PAGE: - Hyperion
                    Enable Channel 11  cmdID= 1592  "
        ::= { iqhip10CmdEntry 1592 }


    iqhip10HyperionAudioLevelIndChannel11 OBJECT-TYPE
        SYNTAX            RollCallString
        MAX-ACCESS        read-only
        STATUS            current
        DESCRIPTION
                "CMNT: - 
                 TYPE: - Display
                 PAGE: - Hyperion
                    Channel 11  cmdID= 1576  "
        ::= { iqhip10CmdEntry 1576 }


    iqhip10HyperionAudioLevelIndEnableChannel12 OBJECT-TYPE
        SYNTAX            INTEGER { disable(0), enable(1)  }
        MAX-ACCESS        read-write
        STATUS            current
        DESCRIPTION
                "CMNT: - 
                 TYPE: - Checkbox
                 PAGE: - Hyperion
                    Enable Channel 12  cmdID= 1593  "
        ::= { iqhip10CmdEntry 1593 }


    iqhip10HyperionAudioLevelIndChannel12 OBJECT-TYPE
        SYNTAX            RollCallString
        MAX-ACCESS        read-only
        STATUS            current
        DESCRIPTION
                "CMNT: - 
                 TYPE: - Display
                 PAGE: - Hyperion
                    Channel 12  cmdID= 1577  "
        ::= { iqhip10CmdEntry 1577 }


    iqhip10HyperionAudioLevelIndEnableChannel13 OBJECT-TYPE
        SYNTAX            INTEGER { disable(0), enable(1)  }
        MAX-ACCESS        read-write
        STATUS            current
        DESCRIPTION
                "CMNT: - 
                 TYPE: - Checkbox
                 PAGE: - Hyperion
                    Enable Channel 13  cmdID= 1594  "
        ::= { iqhip10CmdEntry 1594 }


    iqhip10HyperionAudioLevelIndChannel13 OBJECT-TYPE
        SYNTAX            RollCallString
        MAX-ACCESS        read-only
        STATUS            current
        DESCRIPTION
                "CMNT: - 
                 TYPE: - Display
                 PAGE: - Hyperion
                    Channel 13  cmdID= 1578  "
        ::= { iqhip10CmdEntry 1578 }


    iqhip10HyperionAudioLevelIndEnableChannel14 OBJECT-TYPE
        SYNTAX            INTEGER { disable(0), enable(1)  }
        MAX-ACCESS        read-write
        STATUS            current
        DESCRIPTION
                "CMNT: - 
                 TYPE: - Checkbox
                 PAGE: - Hyperion
                    Enable Channel 14  cmdID= 1595  "
        ::= { iqhip10CmdEntry 1595 }


    iqhip10HyperionAudioLevelIndChannel14 OBJECT-TYPE
        SYNTAX            RollCallString
        MAX-ACCESS        read-only
        STATUS            current
        DESCRIPTION
                "CMNT: - 
                 TYPE: - Display
                 PAGE: - Hyperion
                    Channel 14  cmdID= 1579  "
        ::= { iqhip10CmdEntry 1579 }


    iqhip10HyperionAudioLevelIndEnableChannel15 OBJECT-TYPE
        SYNTAX            INTEGER { disable(0), enable(1)  }
        MAX-ACCESS        read-write
        STATUS            current
        DESCRIPTION
                "CMNT: - 
                 TYPE: - Checkbox
                 PAGE: - Hyperion
                    Enable Channel 15  cmdID= 1596  "
        ::= { iqhip10CmdEntry 1596 }


    iqhip10HyperionAudioLevelIndChannel15 OBJECT-TYPE
        SYNTAX            RollCallString
        MAX-ACCESS        read-only
        STATUS            current
        DESCRIPTION
                "CMNT: - 
                 TYPE: - Display
                 PAGE: - Hyperion
                    Channel 15  cmdID= 1580  "
        ::= { iqhip10CmdEntry 1580 }


    iqhip10HyperionAudioLevelIndEnableChannel16 OBJECT-TYPE
        SYNTAX            INTEGER { disable(0), enable(1)  }
        MAX-ACCESS        read-write
        STATUS            current
        DESCRIPTION
                "CMNT: - 
                 TYPE: - Checkbox
                 PAGE: - Hyperion
                    Enable Channel 16  cmdID= 1597  "
        ::= { iqhip10CmdEntry 1597 }


    iqhip10HyperionAudioLevelIndChannel16 OBJECT-TYPE
        SYNTAX            RollCallString
        MAX-ACCESS        read-only
        STATUS            current
        DESCRIPTION
                "CMNT: - 
                 TYPE: - Display
                 PAGE: - Hyperion
                    Channel 16  cmdID= 1581  "
        ::= { iqhip10CmdEntry 1581 }


    iqhip10HyperionClippingDetectorThreshold OBJECT-TYPE
        SYNTAX            INTEGER
        MAX-ACCESS        read-write
        STATUS            current
        DESCRIPTION
                "CMNT: - 
                 TYPE: - Number
                 PAGE: - Hyperion
                    Threshold  cmdID= 3140
                    min= 0  max= 4  step= 1  format= %0.0f  div_scale= 1  preset= 1
                    Min = 0  Max = 4  Step = 1  Preset = 1  "
        ::= { iqhip10CmdEntry 3140 }


    iqhip10HyperionClippingDetectorSensitivity OBJECT-TYPE
        SYNTAX            INTEGER
        MAX-ACCESS        read-write
        STATUS            current
        DESCRIPTION
                "CMNT: - 
                 TYPE: - Number
                 PAGE: - Hyperion
                    Sensitivity  cmdID= 3141
                    min= 1  max= 100  step= 1  format= %0.0f  div_scale= 1  preset= 50
                    Min = 1  Max = 100  Step = 1  Preset = 50  "
        ::= { iqhip10CmdEntry 3141 }


    iqhip10HyperionClippingDetectorStatusCh1 OBJECT-TYPE
        SYNTAX            RollCallString
        MAX-ACCESS        read-only
        STATUS            current
        DESCRIPTION
                "CMNT: - 
                 TYPE: - Display
                 PAGE: - Hyperion
                    Status Ch 1  cmdID= 3180  "
        ::= { iqhip10CmdEntry 3180 }


    iqhip10HyperionClippingDetectorEnableAlarmCh1 OBJECT-TYPE
        SYNTAX            INTEGER { disable(0), enable(1)  }
        MAX-ACCESS        read-write
        STATUS            current
        DESCRIPTION
                "CMNT: - 
                 TYPE: - Checkbox
                 PAGE: - Hyperion
                    Enable Alarm Ch 1  cmdID= 3220  "
        ::= { iqhip10CmdEntry 3220 }


    iqhip10HyperionClippingDetectorStatusCh2 OBJECT-TYPE
        SYNTAX            RollCallString
        MAX-ACCESS        read-only
        STATUS            current
        DESCRIPTION
                "CMNT: - 
                 TYPE: - Display
                 PAGE: - Hyperion
                    Status Ch 2  cmdID= 3181  "
        ::= { iqhip10CmdEntry 3181 }


    iqhip10HyperionClippingDetectorEnableAlarmCh2 OBJECT-TYPE
        SYNTAX            INTEGER { disable(0), enable(1)  }
        MAX-ACCESS        read-write
        STATUS            current
        DESCRIPTION
                "CMNT: - 
                 TYPE: - Checkbox
                 PAGE: - Hyperion
                    Enable Alarm Ch 2  cmdID= 3221  "
        ::= { iqhip10CmdEntry 3221 }


    iqhip10HyperionClippingDetectorStatusCh3 OBJECT-TYPE
        SYNTAX            RollCallString
        MAX-ACCESS        read-only
        STATUS            current
        DESCRIPTION
                "CMNT: - 
                 TYPE: - Display
                 PAGE: - Hyperion
                    Status Ch 3  cmdID= 3182  "
        ::= { iqhip10CmdEntry 3182 }


    iqhip10HyperionClippingDetectorEnableAlarmCh3 OBJECT-TYPE
        SYNTAX            INTEGER { disable(0), enable(1)  }
        MAX-ACCESS        read-write
        STATUS            current
        DESCRIPTION
                "CMNT: - 
                 TYPE: - Checkbox
                 PAGE: - Hyperion
                    Enable Alarm Ch 3  cmdID= 3222  "
        ::= { iqhip10CmdEntry 3222 }


    iqhip10HyperionClippingDetectorStatusCh4 OBJECT-TYPE
        SYNTAX            RollCallString
        MAX-ACCESS        read-only
        STATUS            current
        DESCRIPTION
                "CMNT: - 
                 TYPE: - Display
                 PAGE: - Hyperion
                    Status Ch 4  cmdID= 3183  "
        ::= { iqhip10CmdEntry 3183 }


    iqhip10HyperionClippingDetectorEnableAlarmCh4 OBJECT-TYPE
        SYNTAX            INTEGER { disable(0), enable(1)  }
        MAX-ACCESS        read-write
        STATUS            current
        DESCRIPTION
                "CMNT: - 
                 TYPE: - Checkbox
                 PAGE: - Hyperion
                    Enable Alarm Ch 4  cmdID= 3223  "
        ::= { iqhip10CmdEntry 3223 }


    iqhip10HyperionClippingDetectorStatusCh5 OBJECT-TYPE
        SYNTAX            RollCallString
        MAX-ACCESS        read-only
        STATUS            current
        DESCRIPTION
                "CMNT: - 
                 TYPE: - Display
                 PAGE: - Hyperion
                    Status Ch 5  cmdID= 3184  "
        ::= { iqhip10CmdEntry 3184 }


    iqhip10HyperionClippingDetectorEnableAlarmCh5 OBJECT-TYPE
        SYNTAX            INTEGER { disable(0), enable(1)  }
        MAX-ACCESS        read-write
        STATUS            current
        DESCRIPTION
                "CMNT: - 
                 TYPE: - Checkbox
                 PAGE: - Hyperion
                    Enable Alarm Ch 5  cmdID= 3224  "
        ::= { iqhip10CmdEntry 3224 }


    iqhip10HyperionClippingDetectorStatusCh6 OBJECT-TYPE
        SYNTAX            RollCallString
        MAX-ACCESS        read-only
        STATUS            current
        DESCRIPTION
                "CMNT: - 
                 TYPE: - Display
                 PAGE: - Hyperion
                    Status Ch 6  cmdID= 3185  "
        ::= { iqhip10CmdEntry 3185 }


    iqhip10HyperionClippingDetectorEnableAlarmCh6 OBJECT-TYPE
        SYNTAX            INTEGER { disable(0), enable(1)  }
        MAX-ACCESS        read-write
        STATUS            current
        DESCRIPTION
                "CMNT: - 
                 TYPE: - Checkbox
                 PAGE: - Hyperion
                    Enable Alarm Ch 6  cmdID= 3225  "
        ::= { iqhip10CmdEntry 3225 }


    iqhip10HyperionClippingDetectorStatusCh7 OBJECT-TYPE
        SYNTAX            RollCallString
        MAX-ACCESS        read-only
        STATUS            current
        DESCRIPTION
                "CMNT: - 
                 TYPE: - Display
                 PAGE: - Hyperion
                    Status Ch 7  cmdID= 3186  "
        ::= { iqhip10CmdEntry 3186 }


    iqhip10HyperionClippingDetectorEnableAlarmCh7 OBJECT-TYPE
        SYNTAX            INTEGER { disable(0), enable(1)  }
        MAX-ACCESS        read-write
        STATUS            current
        DESCRIPTION
                "CMNT: - 
                 TYPE: - Checkbox
                 PAGE: - Hyperion
                    Enable Alarm Ch 7  cmdID= 3226  "
        ::= { iqhip10CmdEntry 3226 }


    iqhip10HyperionClippingDetectorStatusCh8 OBJECT-TYPE
        SYNTAX            RollCallString
        MAX-ACCESS        read-only
        STATUS            current
        DESCRIPTION
                "CMNT: - 
                 TYPE: - Display
                 PAGE: - Hyperion
                    Status Ch 8  cmdID= 3187  "
        ::= { iqhip10CmdEntry 3187 }


    iqhip10HyperionClippingDetectorEnableAlarmCh8 OBJECT-TYPE
        SYNTAX            INTEGER { disable(0), enable(1)  }
        MAX-ACCESS        read-write
        STATUS            current
        DESCRIPTION
                "CMNT: - 
                 TYPE: - Checkbox
                 PAGE: - Hyperion
                    Enable Alarm Ch 8  cmdID= 3227  "
        ::= { iqhip10CmdEntry 3227 }


    iqhip10HyperionClippingDetectorStatusCh9 OBJECT-TYPE
        SYNTAX            RollCallString
        MAX-ACCESS        read-only
        STATUS            current
        DESCRIPTION
                "CMNT: - 
                 TYPE: - Display
                 PAGE: - Hyperion
                    Status Ch 9  cmdID= 3188  "
        ::= { iqhip10CmdEntry 3188 }


    iqhip10HyperionClippingDetectorEnableAlarmCh9 OBJECT-TYPE
        SYNTAX            INTEGER { disable(0), enable(1)  }
        MAX-ACCESS        read-write
        STATUS            current
        DESCRIPTION
                "CMNT: - 
                 TYPE: - Checkbox
                 PAGE: - Hyperion
                    Enable Alarm Ch 9  cmdID= 3228  "
        ::= { iqhip10CmdEntry 3228 }


    iqhip10HyperionClippingDetectorStatusCh10 OBJECT-TYPE
        SYNTAX            RollCallString
        MAX-ACCESS        read-only
        STATUS            current
        DESCRIPTION
                "CMNT: - 
                 TYPE: - Display
                 PAGE: - Hyperion
                    Status Ch 10  cmdID= 3189  "
        ::= { iqhip10CmdEntry 3189 }


    iqhip10HyperionClippingDetectorEnableAlarmCh10 OBJECT-TYPE
        SYNTAX            INTEGER { disable(0), enable(1)  }
        MAX-ACCESS        read-write
        STATUS            current
        DESCRIPTION
                "CMNT: - 
                 TYPE: - Checkbox
                 PAGE: - Hyperion
                    Enable Alarm Ch 10  cmdID= 3229  "
        ::= { iqhip10CmdEntry 3229 }


    iqhip10HyperionClippingDetectorStatusCh11 OBJECT-TYPE
        SYNTAX            RollCallString
        MAX-ACCESS        read-only
        STATUS            current
        DESCRIPTION
                "CMNT: - 
                 TYPE: - Display
                 PAGE: - Hyperion
                    Status Ch 11  cmdID= 3190  "
        ::= { iqhip10CmdEntry 3190 }


    iqhip10HyperionClippingDetectorEnableAlarmCh11 OBJECT-TYPE
        SYNTAX            INTEGER { disable(0), enable(1)  }
        MAX-ACCESS        read-write
        STATUS            current
        DESCRIPTION
                "CMNT: - 
                 TYPE: - Checkbox
                 PAGE: - Hyperion
                    Enable Alarm Ch 11  cmdID= 3230  "
        ::= { iqhip10CmdEntry 3230 }


    iqhip10HyperionClippingDetectorStatusCh12 OBJECT-TYPE
        SYNTAX            RollCallString
        MAX-ACCESS        read-only
        STATUS            current
        DESCRIPTION
                "CMNT: - 
                 TYPE: - Display
                 PAGE: - Hyperion
                    Status Ch 12  cmdID= 3191  "
        ::= { iqhip10CmdEntry 3191 }


    iqhip10HyperionClippingDetectorEnableAlarmCh12 OBJECT-TYPE
        SYNTAX            INTEGER { disable(0), enable(1)  }
        MAX-ACCESS        read-write
        STATUS            current
        DESCRIPTION
                "CMNT: - 
                 TYPE: - Checkbox
                 PAGE: - Hyperion
                    Enable Alarm Ch 12  cmdID= 3231  "
        ::= { iqhip10CmdEntry 3231 }


    iqhip10HyperionClippingDetectorStatusCh13 OBJECT-TYPE
        SYNTAX            RollCallString
        MAX-ACCESS        read-only
        STATUS            current
        DESCRIPTION
                "CMNT: - 
                 TYPE: - Display
                 PAGE: - Hyperion
                    Status Ch 13  cmdID= 3192  "
        ::= { iqhip10CmdEntry 3192 }


    iqhip10HyperionClippingDetectorEnableAlarmCh13 OBJECT-TYPE
        SYNTAX            INTEGER { disable(0), enable(1)  }
        MAX-ACCESS        read-write
        STATUS            current
        DESCRIPTION
                "CMNT: - 
                 TYPE: - Checkbox
                 PAGE: - Hyperion
                    Enable Alarm Ch 13  cmdID= 3232  "
        ::= { iqhip10CmdEntry 3232 }


    iqhip10HyperionClippingDetectorStatusCh14 OBJECT-TYPE
        SYNTAX            RollCallString
        MAX-ACCESS        read-only
        STATUS            current
        DESCRIPTION
                "CMNT: - 
                 TYPE: - Display
                 PAGE: - Hyperion
                    Status Ch 14  cmdID= 3193  "
        ::= { iqhip10CmdEntry 3193 }


    iqhip10HyperionClippingDetectorEnableAlarmCh14 OBJECT-TYPE
        SYNTAX            INTEGER { disable(0), enable(1)  }
        MAX-ACCESS        read-write
        STATUS            current
        DESCRIPTION
                "CMNT: - 
                 TYPE: - Checkbox
                 PAGE: - Hyperion
                    Enable Alarm Ch 14  cmdID= 3233  "
        ::= { iqhip10CmdEntry 3233 }


    iqhip10HyperionClippingDetectorStatusCh15 OBJECT-TYPE
        SYNTAX            RollCallString
        MAX-ACCESS        read-only
        STATUS            current
        DESCRIPTION
                "CMNT: - 
                 TYPE: - Display
                 PAGE: - Hyperion
                    Status Ch 15  cmdID= 3194  "
        ::= { iqhip10CmdEntry 3194 }


    iqhip10HyperionClippingDetectorEnableAlarmCh15 OBJECT-TYPE
        SYNTAX            INTEGER { disable(0), enable(1)  }
        MAX-ACCESS        read-write
        STATUS            current
        DESCRIPTION
                "CMNT: - 
                 TYPE: - Checkbox
                 PAGE: - Hyperion
                    Enable Alarm Ch 15  cmdID= 3234  "
        ::= { iqhip10CmdEntry 3234 }


    iqhip10HyperionClippingDetectorStatusCh16 OBJECT-TYPE
        SYNTAX            RollCallString
        MAX-ACCESS        read-only
        STATUS            current
        DESCRIPTION
                "CMNT: - 
                 TYPE: - Display
                 PAGE: - Hyperion
                    Status Ch 16  cmdID= 3195  "
        ::= { iqhip10CmdEntry 3195 }


    iqhip10HyperionClippingDetectorEnableAlarmCh16 OBJECT-TYPE
        SYNTAX            INTEGER { disable(0), enable(1)  }
        MAX-ACCESS        read-write
        STATUS            current
        DESCRIPTION
                "CMNT: - 
                 TYPE: - Checkbox
                 PAGE: - Hyperion
                    Enable Alarm Ch 16  cmdID= 3235  "
        ::= { iqhip10CmdEntry 3235 }


    iqhip10AudioLikenessDetector1Likeness OBJECT-TYPE
        SYNTAX            RollCallString
        MAX-ACCESS        read-only
        STATUS            current
        DESCRIPTION
                "CMNT: - 
                 TYPE: - Display
                 PAGE: - Audio Likeness
                    Likeness  cmdID= 3120  "
        ::= { iqhip10CmdEntry 3120 }


    iqhip10AudioLikenessDetector1State OBJECT-TYPE
        SYNTAX            RollCallString
        MAX-ACCESS        read-only
        STATUS            current
        DESCRIPTION
                "CMNT: - 
                 TYPE: - Display
                 PAGE: - Audio Likeness
                    State  cmdID= 3130  "
        ::= { iqhip10CmdEntry 3130 }


    iqhip10AudioLikenessDetector1SelectChannelA OBJECT-TYPE
        SYNTAX            INTEGER
        MAX-ACCESS        read-write
        STATUS            current
        DESCRIPTION
                "CMNT: - 
                 TYPE: - Number
                 PAGE: - Audio Likeness
                    Select Channel A  cmdID= 3100
                    min= 1  max= 16  step= 1  format= %0.0f  div_scale= 1  preset= 1
                    Min = 1  Max = 16  Step = 1  Preset = 1  "
        ::= { iqhip10CmdEntry 3100 }


    iqhip10AudioLikenessDetector1SelectChannelB OBJECT-TYPE
        SYNTAX            INTEGER
        MAX-ACCESS        read-write
        STATUS            current
        DESCRIPTION
                "CMNT: - 
                 TYPE: - Number
                 PAGE: - Audio Likeness
                    Select Channel B  cmdID= 3101
                    min= 1  max= 16  step= 1  format= %0.0f  div_scale= 1  preset= 2
                    Min = 1  Max = 16  Step = 1  Preset = 2  "
        ::= { iqhip10CmdEntry 3101 }


    iqhip10AudioLikenessDetector1EnableAlarm OBJECT-TYPE
        SYNTAX            INTEGER { disable(0), enable(1)  }
        MAX-ACCESS        read-write
        STATUS            current
        DESCRIPTION
                "CMNT: - 
                 TYPE: - Checkbox
                 PAGE: - Audio Likeness
                    Enable Alarm  cmdID= 3108  "
        ::= { iqhip10CmdEntry 3108 }


    iqhip10AudioLikenessDetector2Likeness OBJECT-TYPE
        SYNTAX            RollCallString
        MAX-ACCESS        read-only
        STATUS            current
        DESCRIPTION
                "CMNT: - 
                 TYPE: - Display
                 PAGE: - Audio Likeness
                    Likeness  cmdID= 3121  "
        ::= { iqhip10CmdEntry 3121 }


    iqhip10AudioLikenessDetector2State OBJECT-TYPE
        SYNTAX            RollCallString
        MAX-ACCESS        read-only
        STATUS            current
        DESCRIPTION
                "CMNT: - 
                 TYPE: - Display
                 PAGE: - Audio Likeness
                    State  cmdID= 3131  "
        ::= { iqhip10CmdEntry 3131 }


    iqhip10AudioLikenessDetector2SelectChannelA OBJECT-TYPE
        SYNTAX            INTEGER
        MAX-ACCESS        read-write
        STATUS            current
        DESCRIPTION
                "CMNT: - 
                 TYPE: - Number
                 PAGE: - Audio Likeness
                    Select Channel A  cmdID= 3102
                    min= 1  max= 16  step= 1  format= %0.0f  div_scale= 1  preset= 3
                    Min = 1  Max = 16  Step = 1  Preset = 3  "
        ::= { iqhip10CmdEntry 3102 }


    iqhip10AudioLikenessDetector2SelectChannelB OBJECT-TYPE
        SYNTAX            INTEGER
        MAX-ACCESS        read-write
        STATUS            current
        DESCRIPTION
                "CMNT: - 
                 TYPE: - Number
                 PAGE: - Audio Likeness
                    Select Channel B  cmdID= 3103
                    min= 1  max= 16  step= 1  format= %0.0f  div_scale= 1  preset= 4
                    Min = 1  Max = 16  Step = 1  Preset = 4  "
        ::= { iqhip10CmdEntry 3103 }


    iqhip10AudioLikenessDetector2AlarmEnable OBJECT-TYPE
        SYNTAX            INTEGER { disable(0), enable(1)  }
        MAX-ACCESS        read-write
        STATUS            current
        DESCRIPTION
                "CMNT: - 
                 TYPE: - Checkbox
                 PAGE: - Audio Likeness
                    Alarm Enable  cmdID= 3109  "
        ::= { iqhip10CmdEntry 3109 }


    iqhip10AudioLikenessDetector3Likeness OBJECT-TYPE
        SYNTAX            RollCallString
        MAX-ACCESS        read-only
        STATUS            current
        DESCRIPTION
                "CMNT: - 
                 TYPE: - Display
                 PAGE: - Audio Likeness
                    Likeness  cmdID= 3122  "
        ::= { iqhip10CmdEntry 3122 }


    iqhip10AudioLikenessDetector3State OBJECT-TYPE
        SYNTAX            RollCallString
        MAX-ACCESS        read-only
        STATUS            current
        DESCRIPTION
                "CMNT: - 
                 TYPE: - Display
                 PAGE: - Audio Likeness
                    State  cmdID= 3132  "
        ::= { iqhip10CmdEntry 3132 }


    iqhip10AudioLikenessDetector3SelectChannelA OBJECT-TYPE
        SYNTAX            INTEGER
        MAX-ACCESS        read-write
        STATUS            current
        DESCRIPTION
                "CMNT: - 
                 TYPE: - Number
                 PAGE: - Audio Likeness
                    Select Channel A  cmdID= 3104
                    min= 1  max= 16  step= 1  format= %0.0f  div_scale= 1  preset= 5
                    Min = 1  Max = 16  Step = 1  Preset = 5  "
        ::= { iqhip10CmdEntry 3104 }


    iqhip10AudioLikenessDetector3SelectChannelB OBJECT-TYPE
        SYNTAX            INTEGER
        MAX-ACCESS        read-write
        STATUS            current
        DESCRIPTION
                "CMNT: - 
                 TYPE: - Number
                 PAGE: - Audio Likeness
                    Select Channel B  cmdID= 3105
                    min= 1  max= 16  step= 1  format= %0.0f  div_scale= 1  preset= 6
                    Min = 1  Max = 16  Step = 1  Preset = 6  "
        ::= { iqhip10CmdEntry 3105 }


    iqhip10AudioLikenessDetector3AlarmEnable OBJECT-TYPE
        SYNTAX            INTEGER { disable(0), enable(1)  }
        MAX-ACCESS        read-write
        STATUS            current
        DESCRIPTION
                "CMNT: - 
                 TYPE: - Checkbox
                 PAGE: - Audio Likeness
                    Alarm Enable  cmdID= 3110  "
        ::= { iqhip10CmdEntry 3110 }


    iqhip10AudioLikenessDetector4Likeness OBJECT-TYPE
        SYNTAX            RollCallString
        MAX-ACCESS        read-only
        STATUS            current
        DESCRIPTION
                "CMNT: - 
                 TYPE: - Display
                 PAGE: - Audio Likeness
                    Likeness  cmdID= 3123  "
        ::= { iqhip10CmdEntry 3123 }


    iqhip10AudioLikenessDetector4State OBJECT-TYPE
        SYNTAX            RollCallString
        MAX-ACCESS        read-only
        STATUS            current
        DESCRIPTION
                "CMNT: - 
                 TYPE: - Display
                 PAGE: - Audio Likeness
                    State  cmdID= 3133  "
        ::= { iqhip10CmdEntry 3133 }


    iqhip10AudioLikenessDetector4SelectChannelA OBJECT-TYPE
        SYNTAX            INTEGER
        MAX-ACCESS        read-write
        STATUS            current
        DESCRIPTION
                "CMNT: - 
                 TYPE: - Number
                 PAGE: - Audio Likeness
                    Select Channel A  cmdID= 3106
                    min= 1  max= 16  step= 1  format= %0.0f  div_scale= 1  preset= 7
                    Min = 1  Max = 16  Step = 1  Preset = 7  "
        ::= { iqhip10CmdEntry 3106 }


    iqhip10AudioLikenessDetector4SelectChannelB OBJECT-TYPE
        SYNTAX            INTEGER
        MAX-ACCESS        read-write
        STATUS            current
        DESCRIPTION
                "CMNT: - 
                 TYPE: - Number
                 PAGE: - Audio Likeness
                    Select Channel B  cmdID= 3107
                    min= 1  max= 16  step= 1  format= %0.0f  div_scale= 1  preset= 8
                    Min = 1  Max = 16  Step = 1  Preset = 8  "
        ::= { iqhip10CmdEntry 3107 }


    iqhip10AudioLikenessDetector4AlarmEnable OBJECT-TYPE
        SYNTAX            INTEGER { disable(0), enable(1)  }
        MAX-ACCESS        read-write
        STATUS            current
        DESCRIPTION
                "CMNT: - 
                 TYPE: - Checkbox
                 PAGE: - Audio Likeness
                    Alarm Enable  cmdID= 3111  "
        ::= { iqhip10CmdEntry 3111 }


    iqhip10UMIDReaderDetectonYOnly OBJECT-TYPE
        SYNTAX            INTEGER { disable(0), enable(1)  }
        MAX-ACCESS        read-write
        STATUS            current
        DESCRIPTION
                "CMNT: - 
                 TYPE: - Checkbox
                 PAGE: - UMID
                    Detect on Y Only  cmdID= 1742  "
        ::= { iqhip10CmdEntry 1742 }


    iqhip10UMIDReaderUMIDPresence OBJECT-TYPE
        SYNTAX            RollCallString
        MAX-ACCESS        read-only
        STATUS            current
        DESCRIPTION
                "CMNT: - 
                 TYPE: - Display
                 PAGE: - UMID
                    UMID Presence  cmdID= 1730  "
        ::= { iqhip10CmdEntry 1730 }


    iqhip10UMIDReaderFoundOnLine OBJECT-TYPE
        SYNTAX            RollCallString
        MAX-ACCESS        read-only
        STATUS            current
        DESCRIPTION
                "CMNT: - 
                 TYPE: - Display
                 PAGE: - UMID
                    Found On Line:  cmdID= 1731  "
        ::= { iqhip10CmdEntry 1731 }


    iqhip10ReaderUniversalLabelVersionNumber OBJECT-TYPE
        SYNTAX            RollCallString
        MAX-ACCESS        read-only
        STATUS            current
        DESCRIPTION
                "CMNT: - 
                 TYPE: - Display
                 PAGE: - Reader
                    Version Number  cmdID= 1732  "
        ::= { iqhip10CmdEntry 1732 }


    iqhip10ReaderUniversalLabelMaterialType OBJECT-TYPE
        SYNTAX            RollCallString
        MAX-ACCESS        read-only
        STATUS            current
        DESCRIPTION
                "CMNT: - 
                 TYPE: - Display
                 PAGE: - Reader
                    Material Type  cmdID= 1733  "
        ::= { iqhip10CmdEntry 1733 }


    iqhip10ReaderUniversalLabelIdentMatNumGen OBJECT-TYPE
        SYNTAX            RollCallString
        MAX-ACCESS        read-only
        STATUS            current
        DESCRIPTION
                "CMNT: - 
                 TYPE: - Display
                 PAGE: - Reader
                    Ident Mat Num Gen  cmdID= 1734  "
        ::= { iqhip10CmdEntry 1734 }


    iqhip10ReaderUniversalLabelIdentInstNumGen OBJECT-TYPE
        SYNTAX            RollCallString
        MAX-ACCESS        read-only
        STATUS            current
        DESCRIPTION
                "CMNT: - 
                 TYPE: - Display
                 PAGE: - Reader
                    Ident Inst Num Gen  cmdID= 1735  "
        ::= { iqhip10CmdEntry 1735 }


    iqhip10UMIDReaderInstanceNumber OBJECT-TYPE
        SYNTAX            RollCallString
        MAX-ACCESS        read-only
        STATUS            current
        DESCRIPTION
                "CMNT: - 
                 TYPE: - Display
                 PAGE: - UMID
                    Instance Number  cmdID= 1736  "
        ::= { iqhip10CmdEntry 1736 }


    iqhip10ReaderMaterialNumberMaterialNum14 OBJECT-TYPE
        SYNTAX            RollCallString
        MAX-ACCESS        read-only
        STATUS            current
        DESCRIPTION
                "CMNT: - 
                 TYPE: - Display
                 PAGE: - Reader
                    Material Num 1-4  cmdID= 1737  "
        ::= { iqhip10CmdEntry 1737 }


    iqhip10ReaderMaterialNumberMaterialNum58 OBJECT-TYPE
        SYNTAX            RollCallString
        MAX-ACCESS        read-only
        STATUS            current
        DESCRIPTION
                "CMNT: - 
                 TYPE: - Display
                 PAGE: - Reader
                    Material Num 5-8  cmdID= 1738  "
        ::= { iqhip10CmdEntry 1738 }


    iqhip10ReaderMaterialNumberMaterialNum912 OBJECT-TYPE
        SYNTAX            RollCallString
        MAX-ACCESS        read-only
        STATUS            current
        DESCRIPTION
                "CMNT: - 
                 TYPE: - Display
                 PAGE: - Reader
                    Material Num 9-12  cmdID= 1739  "
        ::= { iqhip10CmdEntry 1739 }


    iqhip10ReaderMaterialNumberMaterialNum1316 OBJECT-TYPE
        SYNTAX            RollCallString
        MAX-ACCESS        read-only
        STATUS            current
        DESCRIPTION
                "CMNT: - 
                 TYPE: - Display
                 PAGE: - Reader
                    Material Num 13-16  cmdID= 1740  "
        ::= { iqhip10CmdEntry 1740 }


    iqhip10UMIDReaderCount OBJECT-TYPE
        SYNTAX            RollCallString
        MAX-ACCESS        read-only
        STATUS            current
        DESCRIPTION
                "CMNT: - 
                 TYPE: - Display
                 PAGE: - UMID
                    Count  cmdID= 1741  "
        ::= { iqhip10CmdEntry 1741 }


    iqhip10HyperionUMIDDelete OBJECT-TYPE
        SYNTAX            INTEGER { disable(0), enable(1)  }
        MAX-ACCESS        read-write
        STATUS            current
        DESCRIPTION
                "CMNT: - 
                 TYPE: - Checkbox
                 PAGE: - Hyperion
                    UMID Delete  cmdID= 1720  "
        ::= { iqhip10CmdEntry 1720 }


    iqhip10UMIDGeneratorEnable OBJECT-TYPE
        SYNTAX            INTEGER { disable(0), enable(1)  }
        MAX-ACCESS        read-write
        STATUS            current
        DESCRIPTION
                "CMNT: - 
                 TYPE: - Checkbox
                 PAGE: - UMID
                    Enable  cmdID= 1700  "
        ::= { iqhip10CmdEntry 1700 }


    iqhip10HyperionUMIDGeneratorStatus OBJECT-TYPE
        SYNTAX            RollCallString
        MAX-ACCESS        read-only
        STATUS            current
        DESCRIPTION
                "CMNT: - 
                 TYPE: - Display
                 PAGE: - Hyperion
                    Generator Status  cmdID= 1713  "
        ::= { iqhip10CmdEntry 1713 }


    iqhip10UMIDGeneratorGenerateonYOnly OBJECT-TYPE
        SYNTAX            INTEGER { disable(0), enable(1)  }
        MAX-ACCESS        read-write
        STATUS            current
        DESCRIPTION
                "CMNT: - 
                 TYPE: - Checkbox
                 PAGE: - UMID
                    Generate on Y Only  cmdID= 1712  "
        ::= { iqhip10CmdEntry 1712 }


    iqhip10UMIDGeneratorTake OBJECT-TYPE
        SYNTAX            INTEGER { noAction(0),valTake(1) }
        MAX-ACCESS        read-write
        STATUS            current
        DESCRIPTION
                "CMNT: - 
                 TYPE: - Button
                 PAGE: - UMID
                    Take  cmdID= 1711
                    value= 1  "
        ::= { iqhip10CmdEntry 1711 }


    iqhip10UMIDGeneratorLineNumber OBJECT-TYPE
        SYNTAX            INTEGER {
                            valLine8(8),
                            valLine9(9),
                            valLine10(10),
                            valLine11(11),
                            valLine12(12),
                            valLine13(13),
                            valLine14(14),
                            valLine15(15),
                            valLine16(16),
                            valLine17(17),
                            valLine18(18),
                            valLine19(19),
                            valLine20(20)
                            }
        MAX-ACCESS        read-write
        STATUS            current
        DESCRIPTION
                "CMNT: - 
                 TYPE: - RadiobuttonList
                 PAGE: - UMID
                    Line Number  cmdID= 1701
                    Line 8  value= 8
                    Line 9  value= 9
                    Line 10  value= 10
                    Line 11  value= 11
                    Line 12  value= 12
                    Line 13  value= 13
                    Line 14  value= 14
                    Line 15  value= 15
                    Line 16  value= 16
                    Line 17  value= 17
                    Line 18  value= 18
                    Line 19  value= 19
                    Line 20  value= 20  "
        ::= { iqhip10CmdEntry 1701 }


    iqhip10GeneratorUniversalLabelVersionNumber OBJECT-TYPE
        SYNTAX            INTEGER
        MAX-ACCESS        read-write
        STATUS            current
        DESCRIPTION
                "CMNT: - 
                 TYPE: - Number
                 PAGE: - Generator
                    Version Number  cmdID= 1703
                    min= 0  max= 255  step= 1  format= %0.0f  div_scale= 1  preset= 0
                    Min = 0  Max = 255  Step = 1  Preset = 0  "
        ::= { iqhip10CmdEntry 1703 }


    iqhip10GeneratorUniversalLabelMaterialType OBJECT-TYPE
        SYNTAX            INTEGER
        MAX-ACCESS        read-write
        STATUS            current
        DESCRIPTION
                "CMNT: - 
                 TYPE: - Number
                 PAGE: - Generator
                    Material Type  cmdID= 1704
                    min= 1  max= 15  step= 1  format= %0.0f  div_scale= 1  preset= 1
                    Min = 1  Max = 15  Step = 1  Preset = 1  "
        ::= { iqhip10CmdEntry 1704 }


    iqhip10GeneratorUniversalLabelIdentofMaterial OBJECT-TYPE
        SYNTAX            INTEGER
        MAX-ACCESS        read-write
        STATUS            current
        DESCRIPTION
                "CMNT: - 
                 TYPE: - Number
                 PAGE: - Generator
                    Ident of Material  cmdID= 1705
                    min= 0  max= 7  step= 1  format= %0.0f  div_scale= 1  preset= 0
                    Min = 0  Max = 7  Step = 1  Preset = 0  "
        ::= { iqhip10CmdEntry 1705 }


    iqhip10GeneratorUniversalLabelIdentofInstance OBJECT-TYPE
        SYNTAX            INTEGER
        MAX-ACCESS        read-write
        STATUS            current
        DESCRIPTION
                "CMNT: - 
                 TYPE: - Number
                 PAGE: - Generator
                    Ident of Instance  cmdID= 1706
                    min= 0  max= 15  step= 1  format= %0.0f  div_scale= 1  preset= 0
                    Min = 0  Max = 15  Step = 1  Preset = 0  "
        ::= { iqhip10CmdEntry 1706 }


    iqhip10UMIDGeneratorInstanceNum OBJECT-TYPE
        SYNTAX            RollCallString
        MAX-ACCESS        read-write
        STATUS            current
        DESCRIPTION
                "CMNT: - 
                 TYPE: - Editstring
                 PAGE: - UMID
                    Instance Num  cmdID= 1702
                    preset= 00 00 00"
        ::= { iqhip10CmdEntry 1702 }


    iqhip10UMIDGeneratorMaterialNum14 OBJECT-TYPE
        SYNTAX            RollCallString
        MAX-ACCESS        read-write
        STATUS            current
        DESCRIPTION
                "CMNT: - 
                 TYPE: - Editstring
                 PAGE: - UMID
                    Material Num 1-4  cmdID= 1707
                    preset= 00 00 00 00"
        ::= { iqhip10CmdEntry 1707 }


    iqhip10UMIDGeneratorMaterialNum58 OBJECT-TYPE
        SYNTAX            RollCallString
        MAX-ACCESS        read-write
        STATUS            current
        DESCRIPTION
                "CMNT: - 
                 TYPE: - Editstring
                 PAGE: - UMID
                    Material Num 5-8  cmdID= 1708
                    preset= 00 00 00 00"
        ::= { iqhip10CmdEntry 1708 }


    iqhip10UMIDGeneratorMaterialNum912 OBJECT-TYPE
        SYNTAX            RollCallString
        MAX-ACCESS        read-write
        STATUS            current
        DESCRIPTION
                "CMNT: - 
                 TYPE: - Editstring
                 PAGE: - UMID
                    Material Num 9-12  cmdID= 1709
                    preset= 00 00 00 00"
        ::= { iqhip10CmdEntry 1709 }


    iqhip10UMIDGeneratorMaterialNum1316 OBJECT-TYPE
        SYNTAX            RollCallString
        MAX-ACCESS        read-write
        STATUS            current
        DESCRIPTION
                "CMNT: - 
                 TYPE: - Editstring
                 PAGE: - UMID
                    Material Num 13-16  cmdID= 1710
                    preset= 00 00 00 00"
        ::= { iqhip10CmdEntry 1710 }


    iqhip10HyperionUMIDAlarmEnable OBJECT-TYPE
        SYNTAX            INTEGER { disable(0), enable(1)  }
        MAX-ACCESS        read-write
        STATUS            current
        DESCRIPTION
                "CMNT: - 
                 TYPE: - Checkbox
                 PAGE: - Hyperion
                    UMID Alarm Enable  cmdID= 1744  "
        ::= { iqhip10CmdEntry 1744 }


    iqhip10PIDReaderPIDPresence OBJECT-TYPE
        SYNTAX            RollCallString
        MAX-ACCESS        read-only
        STATUS            current
        DESCRIPTION
                "CMNT: - 
                 TYPE: - Display
                 PAGE: - PID
                    PID Presence  cmdID= 1930  "
        ::= { iqhip10CmdEntry 1930 }


    iqhip10PIDReaderFoundOnLine OBJECT-TYPE
        SYNTAX            RollCallString
        MAX-ACCESS        read-only
        STATUS            current
        DESCRIPTION
                "CMNT: - 
                 TYPE: - Display
                 PAGE: - PID
                    Found On Line:  cmdID= 1932  "
        ::= { iqhip10CmdEntry 1932 }


    iqhip10PIDReaderHouseID OBJECT-TYPE
        SYNTAX            RollCallString
        MAX-ACCESS        read-only
        STATUS            current
        DESCRIPTION
                "CMNT: - 
                 TYPE: - Display
                 PAGE: - PID
                    House ID  cmdID= 1931  "
        ::= { iqhip10CmdEntry 1931 }


    iqhip10PIDReaderProgramTitle OBJECT-TYPE
        SYNTAX            RollCallString
        MAX-ACCESS        read-only
        STATUS            current
        DESCRIPTION
                "CMNT: - 
                 TYPE: - Display
                 PAGE: - PID
                    Program Title  cmdID= 1933  "
        ::= { iqhip10CmdEntry 1933 }


    iqhip10PIDReaderSegmentNumber OBJECT-TYPE
        SYNTAX            RollCallString
        MAX-ACCESS        read-only
        STATUS            current
        DESCRIPTION
                "CMNT: - 
                 TYPE: - Display
                 PAGE: - PID
                    Segment Number  cmdID= 1934  "
        ::= { iqhip10CmdEntry 1934 }


    iqhip10PIDReaderDuration OBJECT-TYPE
        SYNTAX            RollCallString
        MAX-ACCESS        read-only
        STATUS            current
        DESCRIPTION
                "CMNT: - 
                 TYPE: - Display
                 PAGE: - PID
                    Duration  cmdID= 1935  "
        ::= { iqhip10CmdEntry 1935 }


    iqhip10PIDReaderFrameRate OBJECT-TYPE
        SYNTAX            RollCallString
        MAX-ACCESS        read-only
        STATUS            current
        DESCRIPTION
                "CMNT: - 
                 TYPE: - Display
                 PAGE: - PID
                    Frame Rate  cmdID= 1936  "
        ::= { iqhip10CmdEntry 1936 }


    iqhip10PIDReaderCount OBJECT-TYPE
        SYNTAX            RollCallString
        MAX-ACCESS        read-only
        STATUS            current
        DESCRIPTION
                "CMNT: - 
                 TYPE: - Display
                 PAGE: - PID
                    Count  cmdID= 1937  "
        ::= { iqhip10CmdEntry 1937 }


    iqhip10HyperionPIDDelete OBJECT-TYPE
        SYNTAX            INTEGER { disable(0), enable(1)  }
        MAX-ACCESS        read-write
        STATUS            current
        DESCRIPTION
                "CMNT: - 
                 TYPE: - Checkbox
                 PAGE: - Hyperion
                    PID Delete  cmdID= 1920  "
        ::= { iqhip10CmdEntry 1920 }


    iqhip10PIDGeneratorEnable OBJECT-TYPE
        SYNTAX            INTEGER { disable(0), enable(1)  }
        MAX-ACCESS        read-write
        STATUS            current
        DESCRIPTION
                "CMNT: - 
                 TYPE: - Checkbox
                 PAGE: - PID
                    Enable  cmdID= 1900  "
        ::= { iqhip10CmdEntry 1900 }


    iqhip10HyperionPIDGeneratorStatus OBJECT-TYPE
        SYNTAX            RollCallString
        MAX-ACCESS        read-only
        STATUS            current
        DESCRIPTION
                "CMNT: - 
                 TYPE: - Display
                 PAGE: - Hyperion
                    Generator Status  cmdID= 1912  "
        ::= { iqhip10CmdEntry 1912 }


    iqhip10PIDGeneratorTake OBJECT-TYPE
        SYNTAX            INTEGER { noAction(0),valTake(1) }
        MAX-ACCESS        read-write
        STATUS            current
        DESCRIPTION
                "CMNT: - 
                 TYPE: - Button
                 PAGE: - PID
                    Take  cmdID= 1911
                    value= 1  "
        ::= { iqhip10CmdEntry 1911 }


    iqhip10PIDGeneratorLineNumber OBJECT-TYPE
        SYNTAX            INTEGER {
                            valLine8(8),
                            valLine9(9),
                            valLine10(10),
                            valLine11(11),
                            valLine12(12),
                            valLine13(13),
                            valLine14(14),
                            valLine15(15),
                            valLine16(16),
                            valLine17(17),
                            valLine18(18),
                            valLine19(19),
                            valLine20(20)
                            }
        MAX-ACCESS        read-write
        STATUS            current
        DESCRIPTION
                "CMNT: - 
                 TYPE: - RadiobuttonList
                 PAGE: - PID
                    Line Number  cmdID= 1901
                    Line 8  value= 8
                    Line 9  value= 9
                    Line 10  value= 10
                    Line 11  value= 11
                    Line 12  value= 12
                    Line 13  value= 13
                    Line 14  value= 14
                    Line 15  value= 15
                    Line 16  value= 16
                    Line 17  value= 17
                    Line 18  value= 18
                    Line 19  value= 19
                    Line 20  value= 20  "
        ::= { iqhip10CmdEntry 1901 }


    iqhip10PIDGeneratorHouseID OBJECT-TYPE
        SYNTAX            RollCallString
        MAX-ACCESS        read-write
        STATUS            current
        DESCRIPTION
                "CMNT: - 
                 TYPE: - Editstring
                 PAGE: - PID
                    House ID  cmdID= 1902
                    preset= House ID"
        ::= { iqhip10CmdEntry 1902 }


    iqhip10PIDGeneratorProgramTitle OBJECT-TYPE
        SYNTAX            RollCallString
        MAX-ACCESS        read-write
        STATUS            current
        DESCRIPTION
                "CMNT: - 
                 TYPE: - Editstring
                 PAGE: - PID
                    Program Title  cmdID= 1903
                    preset= Title"
        ::= { iqhip10CmdEntry 1903 }


    iqhip10PIDGeneratorProgramTitleEn OBJECT-TYPE
        SYNTAX            INTEGER { disable(0), enable(1)  }
        MAX-ACCESS        read-write
        STATUS            current
        DESCRIPTION
                "CMNT: - 
                 TYPE: - Checkbox
                 PAGE: - PID
                    Program Title En  cmdID= 1907  "
        ::= { iqhip10CmdEntry 1907 }


    iqhip10PIDGeneratorSegmentNumber OBJECT-TYPE
        SYNTAX            RollCallString
        MAX-ACCESS        read-write
        STATUS            current
        DESCRIPTION
                "CMNT: - 
                 TYPE: - Editstring
                 PAGE: - PID
                    Segment Number  cmdID= 1904
                    preset= 0"
        ::= { iqhip10CmdEntry 1904 }


    iqhip10PIDGeneratorSegmentNumberEn OBJECT-TYPE
        SYNTAX            INTEGER { disable(0), enable(1)  }
        MAX-ACCESS        read-write
        STATUS            current
        DESCRIPTION
                "CMNT: - 
                 TYPE: - Checkbox
                 PAGE: - PID
                    Segment Number En  cmdID= 1908  "
        ::= { iqhip10CmdEntry 1908 }


    iqhip10PIDGeneratorDuration OBJECT-TYPE
        SYNTAX            RollCallString
        MAX-ACCESS        read-write
        STATUS            current
        DESCRIPTION
                "CMNT: - 
                 TYPE: - Editstring
                 PAGE: - PID
                    Duration  cmdID= 1905
                    preset= 0"
        ::= { iqhip10CmdEntry 1905 }


    iqhip10PIDGeneratorDurationEn OBJECT-TYPE
        SYNTAX            INTEGER { disable(0), enable(1)  }
        MAX-ACCESS        read-write
        STATUS            current
        DESCRIPTION
                "CMNT: - 
                 TYPE: - Checkbox
                 PAGE: - PID
                    Duration En  cmdID= 1909  "
        ::= { iqhip10CmdEntry 1909 }


    iqhip10PIDGeneratorFrameRateEn OBJECT-TYPE
        SYNTAX            INTEGER { disable(0), enable(1)  }
        MAX-ACCESS        read-write
        STATUS            current
        DESCRIPTION
                "CMNT: - 
                 TYPE: - Checkbox
                 PAGE: - PID
                    Frame Rate En  cmdID= 1910  "
        ::= { iqhip10CmdEntry 1910 }


    iqhip10PIDGeneratorFrameRate OBJECT-TYPE
        SYNTAX            INTEGER {
                            valFollowInput(0),
                            val23976(1),
                            val24000(2),
                            val25000(3),
                            val29970(4),
                            val30000(5),
                            val50000(6),
                            val59940(7),
                            val60000(8)
                            }
        MAX-ACCESS        read-write
        STATUS            current
        DESCRIPTION
                "CMNT: - 
                 TYPE: - RadiobuttonList
                 PAGE: - PID
                    Frame Rate  cmdID= 1906
                    Follow Input  value= 0
                    23.976  value= 1
                    24.000  value= 2
                    25.000  value= 3
                    29.970  value= 4
                    30.000  value= 5
                    50.000  value= 6
                    59.940  value= 7
                    60.000  value= 8  "
        ::= { iqhip10CmdEntry 1906 }


    iqhip10HyperionPIDAlarmEnable OBJECT-TYPE
        SYNTAX            INTEGER { disable(0), enable(1)  }
        MAX-ACCESS        read-write
        STATUS            current
        DESCRIPTION
                "CMNT: - 
                 TYPE: - Checkbox
                 PAGE: - Hyperion
                    PID Alarm Enable  cmdID= 1938  "
        ::= { iqhip10CmdEntry 1938 }


    iqhip10HyperionOSDPassword OBJECT-TYPE
        SYNTAX            RollCallString
        MAX-ACCESS        read-write
        STATUS            current
        DESCRIPTION
                "CMNT: - 
                 TYPE: - Editstring
                 PAGE: - Hyperion
                    OSD Password: !!!  cmdID= 5001
                    preset= 0"
        ::= { iqhip10CmdEntry 5001 }


    iqhip10HyperionOSDEnable OBJECT-TYPE
        SYNTAX            INTEGER { disable(0), enable(1)  }
        MAX-ACCESS        read-write
        STATUS            current
        DESCRIPTION
                "CMNT: - 
                 TYPE: - Checkbox
                 PAGE: - Hyperion
                    OSD Enable  cmdID= 5000  "
        ::= { iqhip10CmdEntry 5000 }


    iqhip10HyperionOSDHold OBJECT-TYPE
        SYNTAX            INTEGER { disable(0), enable(1)  }
        MAX-ACCESS        read-write
        STATUS            current
        DESCRIPTION
                "CMNT: - 
                 TYPE: - Checkbox
                 PAGE: - Hyperion
                    OSD Hold  cmdID= 5040  "
        ::= { iqhip10CmdEntry 5040 }


    iqhip10OSDOnScreenDispEnIndicators OBJECT-TYPE
        SYNTAX            INTEGER { disable(0), enable(1)  }
        MAX-ACCESS        read-write
        STATUS            current
        DESCRIPTION
                "CMNT: - 
                 TYPE: - Checkbox
                 PAGE: - OSD
                    Indicators   cmdID= 5002  "
        ::= { iqhip10CmdEntry 5002 }


    iqhip10OSDOnScreenDispEnAudioLevelInds OBJECT-TYPE
        SYNTAX            INTEGER { disable(0), enable(1)  }
        MAX-ACCESS        read-write
        STATUS            current
        DESCRIPTION
                "CMNT: - 
                 TYPE: - Checkbox
                 PAGE: - OSD
                    Audio Level Inds  cmdID= 5004  "
        ::= { iqhip10CmdEntry 5004 }


    iqhip10OSDOnScreenDispEnTimecode OBJECT-TYPE
        SYNTAX            INTEGER { disable(0), enable(1)  }
        MAX-ACCESS        read-write
        STATUS            current
        DESCRIPTION
                "CMNT: - 
                 TYPE: - Checkbox
                 PAGE: - OSD
                    Timecode  cmdID= 5007  "
        ::= { iqhip10CmdEntry 5007 }


    iqhip10OSDOnScreenDispEnGreyBackground OBJECT-TYPE
        SYNTAX            INTEGER { disable(0), enable(1)  }
        MAX-ACCESS        read-write
        STATUS            current
        DESCRIPTION
                "CMNT: - 
                 TYPE: - Checkbox
                 PAGE: - OSD
                    Grey Background  cmdID= 5015  "
        ::= { iqhip10CmdEntry 5015 }


    iqhip10OSDOnScreenDispEnInputModeEn OBJECT-TYPE
        SYNTAX            INTEGER { disable(0), enable(1)  }
        MAX-ACCESS        read-write
        STATUS            current
        DESCRIPTION
                "CMNT: - 
                 TYPE: - Checkbox
                 PAGE: - OSD
                    Input Mode En  cmdID= 5027  "
        ::= { iqhip10CmdEntry 5027 }


    iqhip10OSDOnScreenDispEnInput1NameEn OBJECT-TYPE
        SYNTAX            INTEGER { disable(0), enable(1)  }
        MAX-ACCESS        read-write
        STATUS            current
        DESCRIPTION
                "CMNT: - 
                 TYPE: - Checkbox
                 PAGE: - OSD
                    Input 1 Name En  cmdID= 5010  "
        ::= { iqhip10CmdEntry 5010 }


    iqhip10OSDOnScreenDispEnSFPRxANameEn OBJECT-TYPE
        SYNTAX            INTEGER { disable(0), enable(1)  }
        MAX-ACCESS        read-write
        STATUS            current
        DESCRIPTION
                "CMNT: - 
                 TYPE: - Checkbox
                 PAGE: - OSD
                    SFP Rx A Name En  cmdID= 5024  "
        ::= { iqhip10CmdEntry 5024 }


    iqhip10OSDOnScreenDispEnCaption1Edit OBJECT-TYPE
        SYNTAX            RollCallString
        MAX-ACCESS        read-write
        STATUS            current
        DESCRIPTION
                "CMNT: - 
                 TYPE: - Editstring
                 PAGE: - OSD
                    Caption 1 Edit  cmdID= 5012
                    preset= Caption 1          "
        ::= { iqhip10CmdEntry 5012 }


    iqhip10OSDOnScreenDispEnCaption1Enable OBJECT-TYPE
        SYNTAX            INTEGER { disable(0), enable(1)  }
        MAX-ACCESS        read-write
        STATUS            current
        DESCRIPTION
                "CMNT: - 
                 TYPE: - Checkbox
                 PAGE: - OSD
                    Caption 1 Enable  cmdID= 5011  "
        ::= { iqhip10CmdEntry 5011 }


    iqhip10OSDOnScreenDispEnCaption2Edit OBJECT-TYPE
        SYNTAX            RollCallString
        MAX-ACCESS        read-write
        STATUS            current
        DESCRIPTION
                "CMNT: - 
                 TYPE: - Editstring
                 PAGE: - OSD
                    Caption 2 Edit  cmdID= 5014
                    preset= Caption 2          "
        ::= { iqhip10CmdEntry 5014 }


    iqhip10OSDOnScreenDispEnCaption2Enable OBJECT-TYPE
        SYNTAX            INTEGER { disable(0), enable(1)  }
        MAX-ACCESS        read-write
        STATUS            current
        DESCRIPTION
                "CMNT: - 
                 TYPE: - Checkbox
                 PAGE: - OSD
                    Caption 2 Enable  cmdID= 5013  "
        ::= { iqhip10CmdEntry 5013 }


    iqhip10OSDOnScreenDispEnContentAdvisory OBJECT-TYPE
        SYNTAX            INTEGER { disable(0), enable(1)  }
        MAX-ACCESS        read-write
        STATUS            current
        DESCRIPTION
                "CMNT: - 
                 TYPE: - Checkbox
                 PAGE: - OSD
                    Content Advisory  cmdID= 5016  "
        ::= { iqhip10CmdEntry 5016 }


    iqhip10OSDOnScreenDispEnIncomingPID OBJECT-TYPE
        SYNTAX            INTEGER { disable(0), enable(1)  }
        MAX-ACCESS        read-write
        STATUS            current
        DESCRIPTION
                "CMNT: - 
                 TYPE: - Checkbox
                 PAGE: - OSD
                    Incoming PID  cmdID= 5017  "
        ::= { iqhip10CmdEntry 5017 }


    iqhip10OSDOnScreenDispEnOutgoingPID OBJECT-TYPE
        SYNTAX            INTEGER { disable(0), enable(1)  }
        MAX-ACCESS        read-write
        STATUS            current
        DESCRIPTION
                "CMNT: - 
                 TYPE: - Checkbox
                 PAGE: - OSD
                    Outgoing PID  cmdID= 5018  "
        ::= { iqhip10CmdEntry 5018 }


    iqhip10OSDOnScreenDispEnAudioLvlIndZoom OBJECT-TYPE
        SYNTAX            INTEGER { disable(0), enable(1)  }
        MAX-ACCESS        read-write
        STATUS            current
        DESCRIPTION
                "CMNT: - 
                 TYPE: - Checkbox
                 PAGE: - OSD
                    Audio Lvl Ind Zoom  cmdID= 5003  "
        ::= { iqhip10CmdEntry 5003 }


    iqhip10OSDOnScreenDispEnRegion1DetWindow OBJECT-TYPE
        SYNTAX            INTEGER { disable(0), enable(1)  }
        MAX-ACCESS        read-write
        STATUS            current
        DESCRIPTION
                "CMNT: - 
                 TYPE: - Checkbox
                 PAGE: - OSD
                    Region 1 Det Window  cmdID= 5025  "
        ::= { iqhip10CmdEntry 5025 }


    iqhip10OSDOnScreenDispEnRegion2DetWindow OBJECT-TYPE
        SYNTAX            INTEGER { disable(0), enable(1)  }
        MAX-ACCESS        read-write
        STATUS            current
        DESCRIPTION
                "CMNT: - 
                 TYPE: - Checkbox
                 PAGE: - OSD
                    Region 2 Det Window  cmdID= 5026  "
        ::= { iqhip10CmdEntry 5026 }


    iqhip10OSDOutputEnablesOutput1 OBJECT-TYPE
        SYNTAX            INTEGER { disable(0), enable(1)  }
        MAX-ACCESS        read-write
        STATUS            current
        DESCRIPTION
                "CMNT: - 
                 TYPE: - Checkbox
                 PAGE: - OSD
                    Output 1  cmdID= 5020  "
        ::= { iqhip10CmdEntry 5020 }


    iqhip10OSDOutputEnablesOutput2 OBJECT-TYPE
        SYNTAX            INTEGER { disable(0), enable(1)  }
        MAX-ACCESS        read-write
        STATUS            current
        DESCRIPTION
                "CMNT: - 
                 TYPE: - Checkbox
                 PAGE: - OSD
                    Output 2  cmdID= 5021  "
        ::= { iqhip10CmdEntry 5021 }


    iqhip10OSDOutputEnablesOutput3 OBJECT-TYPE
        SYNTAX            INTEGER { disable(0), enable(1)  }
        MAX-ACCESS        read-write
        STATUS            current
        DESCRIPTION
                "CMNT: - 
                 TYPE: - Checkbox
                 PAGE: - OSD
                    Output 3  cmdID= 5022  "
        ::= { iqhip10CmdEntry 5022 }


    iqhip10OSDOutputEnablesOutput4 OBJECT-TYPE
        SYNTAX            INTEGER { disable(0), enable(1)  }
        MAX-ACCESS        read-write
        STATUS            current
        DESCRIPTION
                "CMNT: - 
                 TYPE: - Checkbox
                 PAGE: - OSD
                    Output 4  cmdID= 5023  "
        ::= { iqhip10CmdEntry 5023 }


    iqhip10HyperionEnableDisables OBJECT-TYPE
        SYNTAX            INTEGER {
                                    valEnableAll(1),
                                   valDisableAll(0),
                                   valEnRegions(11),
                                  valDisRegions(10),
                              valEnVideoMonitor(31),
                             valDisVideoMonitor(30),
                                   valEnANCData(41),
                                  valDisANCData(40),
                             valEnAudioLikeness(51),
                            valDisAudioLikeness(50),
                                 valEnAudioData(61),
                                valDisAudioData(60),
                             valEnAudioClipping(71),
                            valDisAudioClipping(70),
                               valEnDolbyEState(81),
                              valDisDolbyEState(80)
                                  }
        MAX-ACCESS        read-write
        STATUS            current
        DESCRIPTION
                "CMNT: - 
                 TYPE: - Button
                 PAGE: - Hyperion
					Enable All         cmdID= 5600  value=  1  
					Disable All        cmdID= 5600  value=  0  
					En Regions         cmdID= 5600  value= 11  
					Dis Regions        cmdID= 5600  value= 10  
					En  Video Monitor  cmdID= 5600  value= 31  
					Dis Video Monitor  cmdID= 5600  value= 30  
					En  ANC Data       cmdID= 5600  value= 41  
					Dis ANC Data       cmdID= 5600  value= 40  
					En  Audio Likeness cmdID= 5600  value= 51  
					Dis Audio Likeness cmdID= 5600  value= 50  
					En  Audio Data     cmdID= 5600  value= 61  
					Dis Audio Data     cmdID= 5600  value= 60  
					En  Audio Clipping cmdID= 5600  value= 71  
					Dis Audio Clipping cmdID= 5600  value= 70  
					En  Dolby E State  cmdID= 5600  value= 81  
					Dis Dolby E State  cmdID= 5600  value= 80  "
        ::= { iqhip10CmdEntry 5600 }


    iqhip10HyperionDisplayStatusHyperionDispEn OBJECT-TYPE
        SYNTAX            INTEGER {
                            valRegion(1)
                            }
        MAX-ACCESS        read-write
        STATUS            current
        DESCRIPTION
                "CMNT: - 
                 TYPE: - RadiobuttonList
                 PAGE: - Hyperion
                    Hyperion Disp En  cmdID= 1221
                    Region  value= 1  "
        ::= { iqhip10CmdEntry 1221 }


    iqhip10HyperionDisplayStatusDisplayTimeout OBJECT-TYPE
        SYNTAX            RollCallString
        MAX-ACCESS        read-only
        STATUS            current
        DESCRIPTION
                "CMNT: - 
                 TYPE: - Display
                 PAGE: - Hyperion
                    Display Timeout  cmdID= 1290  "
        ::= { iqhip10CmdEntry 1290 }


    iqhip10HyperionDisplayStatusHyperionDetStatus OBJECT-TYPE
        SYNTAX            INTEGER {
                            valAPLLimits(0),
                            valLumaOver(1),
                            valLumaUnder(2),
                            valChromaOver(3),
                            valChromaunder(4),
                            valClosedCap(5),
                            valContentAdv(6),
                            valVITC(7),
                            valANCTIME(8),
                            valTCDiscon(9),
                            valUserDID1(10),
                            valUserDID2(11),
                            valUMID(12),
                            valPID(13),
                            valWSS(14),
                            valVI(15),
                            valAudioLikeness(16),
                            valAudioData(17),
                            valAudioLevel(18),
                            valAudioClipping(19),
                            valDolbyEState(20),
                            valAFD(21),
                            valR1Blackish(22),
                            valR1Black(23),
                            valR1Stillish(24),
                            valR1Freeze(25),
                            valR2Blackish(26),
                            valR2Black(27),
                            valR2Stillish(28),
                            valR2Freeze(29)
                            }
        MAX-ACCESS        read-write
        STATUS            current
        DESCRIPTION
                "CMNT: - 
                 TYPE: - RadiobuttonList
                 PAGE: - Hyperion
                    Hyperion Det Status  cmdID= 5050
                    APL Limits  value= 0
                    Luma Over  value= 1
                    Luma Under  value= 2
                    Chroma Over  value= 3
                    Chroma under  value= 4
                    Closed Cap.  value= 5
                    Content Adv.  value= 6
                    VITC  value= 7
                    ANC TIME  value= 8
                    TC Discon  value= 9
                    User DID 1  value= 10
                    User DID 2  value= 11
                    UMID  value= 12
                    PID  value= 13
                    WSS  value= 14
                    VI  value= 15
                    Audio Likeness  value= 16
                    Audio Data  value= 17
                    Audio Level  value= 18
                    Audio Clipping  value= 19
                    Dolby E State  value= 20
                    AFD  value= 21
                    R1 Blackish  value= 22
                    R1 Black  value= 23
                    R1 Stillish  value= 24
                    R1 Freeze  value= 25
                    R2 Blackish  value= 26
                    R2 Black  value= 27
                    R2 Stillish  value= 28
                    R2 Freeze  value= 29  "
        ::= { iqhip10CmdEntry 5050 }


    iqhip10LoggingMiscTimecodelogEn OBJECT-TYPE
        SYNTAX            INTEGER { disable(0), enable(1)  }
        MAX-ACCESS        read-write
        STATUS            current
        DESCRIPTION
                "CMNT: - 
                 TYPE: - Checkbox
                 PAGE: - Logging
                    Timecode log En  cmdID= 35999  "
        ::= { iqhip10CmdEntry 35999 }


    iqhip10LoggingMiscLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging
                    Log Serial No.  cmdID= 1000  "
        ::= { iqhip10CmdEntry 1000 }


    iqhip10LoggingMiscSerialNo OBJECT-TYPE
        SYNTAX            RollCallString
        MAX-ACCESS        read-only
        STATUS            current
        DESCRIPTION
                "CMNT: - Logging state for Serial No.
                 TYPE: - Display
                 PAGE: - Logging
                    Serial No.=  cmdID= 2000  "
        ::= { iqhip10CmdEntry 2000 }


    iqhip10LoggingMiscLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging
                    Log OS Version  cmdID= 1001  "
        ::= { iqhip10CmdEntry 1001 }


    iqhip10LoggingMiscOSVersion OBJECT-TYPE
        SYNTAX            RollCallString
        MAX-ACCESS        read-only
        STATUS            current
        DESCRIPTION
                "CMNT: - 
                 TYPE: - Display
                 PAGE: - Logging
                    OS Version=  cmdID= 2001  "
        ::= { iqhip10CmdEntry 2001 }


    iqhip10LoggingMiscLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging
                    Log Build No.  cmdID= 1002  "
        ::= { iqhip10CmdEntry 1002 }


    iqhip10LoggingMiscBuildNo OBJECT-TYPE
        SYNTAX            RollCallString
        MAX-ACCESS        read-only
        STATUS            current
        DESCRIPTION
                "CMNT: - Logging state for Build No.
                 TYPE: - Display
                 PAGE: - Logging
                    Build No.=  cmdID= 2002  "
        ::= { iqhip10CmdEntry 2002 }


    iqhip10LoggingMiscLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging
                    Log Hardware Ver.  cmdID= 1003  "
        ::= { iqhip10CmdEntry 1003 }


    iqhip10LoggingMiscHardwareVer OBJECT-TYPE
        SYNTAX            RollCallString
        MAX-ACCESS        read-only
        STATUS            current
        DESCRIPTION
                "CMNT: - Logging state for Hardware Ver.
                 TYPE: - Display
                 PAGE: - Logging
                    Hardware Ver.=  cmdID= 2003  "
        ::= { iqhip10CmdEntry 2003 }


    iqhip10LoggingMiscLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging
                    Log Firmware Ver.  cmdID= 1004  "
        ::= { iqhip10CmdEntry 1004 }


    iqhip10LoggingMiscFirmwareVer OBJECT-TYPE
        SYNTAX            RollCallString
        MAX-ACCESS        read-only
        STATUS            current
        DESCRIPTION
                "CMNT: - Logging state for Firmware Ver.
                 TYPE: - Display
                 PAGE: - Logging
                    Firmware Ver.=  cmdID= 2004  "
        ::= { iqhip10CmdEntry 2004 }


    iqhip10LoggingMiscLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging
                    Log Up Time  cmdID= 1005  "
        ::= { iqhip10CmdEntry 1005 }


    iqhip10LoggingMiscUpTime OBJECT-TYPE
        SYNTAX            RollCallString
        MAX-ACCESS        read-only
        STATUS            current
        DESCRIPTION
                "CMNT: - Logging state for Up Time
                 TYPE: - Display
                 PAGE: - Logging
                    Up Time=  cmdID= 2005  "
        ::= { iqhip10CmdEntry 2005 }


    iqhip10LoggingMiscLogRollTracks OBJECT-TYPE
        SYNTAX            INTEGER { disable(0), enable(1)  }
        MAX-ACCESS        read-write
        STATUS            current
        DESCRIPTION
                "CMNT: - 
                 TYPE: - Checkbox
                 PAGE: - Logging
                    Log RollTracks  cmdID= 35000  "
        ::= { iqhip10CmdEntry 35000 }


    iqhip10LoggingMiscRollTracks OBJECT-TYPE
        SYNTAX            RollCallString
        MAX-ACCESS        read-only
        STATUS            current
        DESCRIPTION
                "CMNT: - 
                 TYPE: - Display
                 PAGE: - Logging
                    RollTracks=  cmdID= 36000  "
        ::= { iqhip10CmdEntry 36000 }


    iqhip10LoggingMiscLogOSDStatus OBJECT-TYPE
        SYNTAX            INTEGER { disable(0), enable(1)  }
        MAX-ACCESS        read-write
        STATUS            current
        DESCRIPTION
                "CMNT: - 
                 TYPE: - Checkbox
                 PAGE: - Logging
                    Log OSD Status  cmdID= 1159  "
        ::= { iqhip10CmdEntry 1159 }


    iqhip10LoggingMiscOSDStatus OBJECT-TYPE
        SYNTAX            RollCallString
        MAX-ACCESS        read-only
        STATUS            current
        DESCRIPTION
                "CMNT: - 
                 TYPE: - Display
                 PAGE: - Logging
                    OSD Status=  cmdID= 2159  "
        ::= { iqhip10CmdEntry 2159 }


    iqhip10LoggingMiscLogCaption1 OBJECT-TYPE
        SYNTAX            INTEGER { disable(0), enable(1)  }
        MAX-ACCESS        read-write
        STATUS            current
        DESCRIPTION
                "CMNT: - 
                 TYPE: - Checkbox
                 PAGE: - Logging
                    Log Caption 1  cmdID= 1194  "
        ::= { iqhip10CmdEntry 1194 }


    iqhip10LoggingMiscInput1Caption1 OBJECT-TYPE
        SYNTAX            RollCallString
        MAX-ACCESS        read-only
        STATUS            current
        DESCRIPTION
                "CMNT: - 
                 TYPE: - Display
                 PAGE: - Logging
                    Input 1 Caption 1=  cmdID= 4178  "
        ::= { iqhip10CmdEntry 4178 }


    iqhip10LoggingMiscLogCaption2 OBJECT-TYPE
        SYNTAX            INTEGER { disable(0), enable(1)  }
        MAX-ACCESS        read-write
        STATUS            current
        DESCRIPTION
                "CMNT: - 
                 TYPE: - Checkbox
                 PAGE: - Logging
                    Log Caption 2  cmdID= 1195  "
        ::= { iqhip10CmdEntry 1195 }


    iqhip10LoggingMiscInput1Caption2 OBJECT-TYPE
        SYNTAX            RollCallString
        MAX-ACCESS        read-only
        STATUS            current
        DESCRIPTION
                "CMNT: - 
                 TYPE: - Display
                 PAGE: - Logging
                    Input 1 Caption 2=  cmdID= 4179  "
        ::= { iqhip10CmdEntry 4179 }


    iqhip10LoggingMiscLogLastRecallMem OBJECT-TYPE
        SYNTAX            INTEGER { disable(0), enable(1)  }
        MAX-ACCESS        read-write
        STATUS            current
        DESCRIPTION
                "CMNT: - 
                 TYPE: - Checkbox
                 PAGE: - Logging
                    Log Last Recall Mem  cmdID= 1166  "
        ::= { iqhip10CmdEntry 1166 }


    iqhip10LoggingMiscLastRecallMem OBJECT-TYPE
        SYNTAX            RollCallString
        MAX-ACCESS        read-only
        STATUS            current
        DESCRIPTION
                "CMNT: - 
                 TYPE: - Display
                 PAGE: - Logging
                    Last Recall Mem=  cmdID= 2166  "
        ::= { iqhip10CmdEntry 2166 }


    iqhip10LoggingMiscLogRearID OBJECT-TYPE
        SYNTAX            INTEGER { disable(0), enable(1)  }
        MAX-ACCESS        read-write
        STATUS            current
        DESCRIPTION
                "CMNT: - Enable/Disable logging for Rear ID
                 TYPE: - Checkbox
                 PAGE: - Logging
                    Log Rear ID  cmdID= 35997  "
        ::= { iqhip10CmdEntry 35997 }


    iqhip10LoggingMiscRearID OBJECT-TYPE
        SYNTAX            RollCallString
        MAX-ACCESS        read-only
        STATUS            current
        DESCRIPTION
                "CMNT: - Logging Rear ID
                 TYPE: - Display
                 PAGE: - Logging
                    Rear ID  cmdID= 36997  "
        ::= { iqhip10CmdEntry 36997 }


    iqhip10LoggingMiscLogSlotWidth OBJECT-TYPE
        SYNTAX            INTEGER { disable(0), enable(1)  }
        MAX-ACCESS        read-write
        STATUS            current
        DESCRIPTION
                "CMNT: - Enable/Disable logging for Display Slot Width
                 TYPE: - Checkbox
                 PAGE: - Logging
                    Log Slot Width  cmdID= 35998  "
        ::= { iqhip10CmdEntry 35998 }


    iqhip10LoggingMiscSlotWidth OBJECT-TYPE
        SYNTAX            RollCallString
        MAX-ACCESS        read-only
        STATUS            current
        DESCRIPTION
                "CMNT: - Logging Slot width
                 TYPE: - Display
                 PAGE: - Logging
                    SlotWidth=  cmdID= 36998  "
        ::= { iqhip10CmdEntry 36998 }


    iqhip10LoggingMiscLogSlotStart OBJECT-TYPE
        SYNTAX            INTEGER { disable(0), enable(1)  }
        MAX-ACCESS        read-write
        STATUS            current
        DESCRIPTION
                "CMNT: - Enable/Disable logging for Display Slot Start
                 TYPE: - Checkbox
                 PAGE: - Logging
                    Log Slot Start  cmdID= 35995  "
        ::= { iqhip10CmdEntry 35995 }


    iqhip10LoggingMiscSlotStart OBJECT-TYPE
        SYNTAX            RollCallString
        MAX-ACCESS        read-only
        STATUS            current
        DESCRIPTION
                "CMNT: - Logging Slot start
                 TYPE: - Display
                 PAGE: - Logging
                    SlotStart=  cmdID= 36999  "
        ::= { iqhip10CmdEntry 36999 }


    iqhip10LoggingMiscLogRearStatus OBJECT-TYPE
        SYNTAX            INTEGER { disable(0), enable(1)  }
        MAX-ACCESS        read-write
        STATUS            current
        DESCRIPTION
                "CMNT: - Enable/Disable logging for Display Rear Status
                 TYPE: - Checkbox
                 PAGE: - Logging
                    Log RearStatus  cmdID= 35996  "
        ::= { iqhip10CmdEntry 35996 }


    iqhip10LoggingMiscRearSTATUS OBJECT-TYPE
        SYNTAX            RollCallString
        MAX-ACCESS        read-only
        STATUS            current
        DESCRIPTION
                "CMNT: - Logging Rear Status
                 TYPE: - Display
                 PAGE: - Logging
                    RearSTATUS=  cmdID= 36996  "
        ::= { iqhip10CmdEntry 36996 }


    iqhip10LoggingMiscLogPowerUsage OBJECT-TYPE
        SYNTAX            INTEGER { disable(0), enable(1)  }
        MAX-ACCESS        read-write
        STATUS            current
        DESCRIPTION
                "CMNT: - Enable/Disable logging for Power Status
                 TYPE: - Checkbox
                 PAGE: - Logging
                    Log Power Usage  cmdID= 35003  "
        ::= { iqhip10CmdEntry 35003 }


    iqhip10LoggingMiscPowerUsage OBJECT-TYPE
        SYNTAX            RollCallString
        MAX-ACCESS        read-only
        STATUS            current
        DESCRIPTION
                "CMNT: - Logging Power usage
                 TYPE: - Display
                 PAGE: - Logging
                    Power Usage=  cmdID= 36003  "
        ::= { iqhip10CmdEntry 36003 }


    iqhip10LoggingMiscLogLicensedOpt OBJECT-TYPE
        SYNTAX            INTEGER { disable(0), enable(1)  }
        MAX-ACCESS        read-write
        STATUS            current
        DESCRIPTION
                "CMNT: - Enable/Disable logging for Display Licensed Options
                 TYPE: - Checkbox
                 PAGE: - Logging
                    Log Licensed Opt.  cmdID= 35994  "
        ::= { iqhip10CmdEntry 35994 }


    iqhip10LoggingMiscLicensedOptions OBJECT-TYPE
        SYNTAX            RollCallString
        MAX-ACCESS        read-only
        STATUS            current
        DESCRIPTION
                "CMNT: - Logging Licened Options
                 TYPE: - Display
                 PAGE: - Logging
                    Licensed Options   cmdID= 36994  "
        ::= { iqhip10CmdEntry 36994 }


    iqhip10LoggingInput1LogInputIdent OBJECT-TYPE
        SYNTAX            INTEGER { disable(0), enable(1)  }
        MAX-ACCESS        read-write
        STATUS            current
        DESCRIPTION
                "CMNT: - 
                 TYPE: - Checkbox
                 PAGE: - Logging
                    Log Input Ident  cmdID= 1130  "
        ::= { iqhip10CmdEntry 1130 }


    iqhip10LoggingInput1InputIdent OBJECT-TYPE
        SYNTAX            RollCallString
        MAX-ACCESS        read-only
        STATUS            current
        DESCRIPTION
                "CMNT: - 
                 TYPE: - Display
                 PAGE: - Logging
                    Input Ident=  cmdID= 2130  "
        ::= { iqhip10CmdEntry 2130 }


    iqhip10LoggingInput1LogInputName OBJECT-TYPE
        SYNTAX            INTEGER { disable(0), enable(1)  }
        MAX-ACCESS        read-write
        STATUS            current
        DESCRIPTION
                "CMNT: - 
                 TYPE: - Checkbox
                 PAGE: - Logging
                    Log Input Name  cmdID= 1095  "
        ::= { iqhip10CmdEntry 1095 }


    iqhip10LoggingInput1InputName OBJECT-TYPE
        SYNTAX            RollCallString
        MAX-ACCESS        read-only
        STATUS            current
        DESCRIPTION
                "CMNT: - 
                 TYPE: - Display
                 PAGE: - Logging
                    Input Name=  cmdID= 2095  "
        ::= { iqhip10CmdEntry 2095 }


    iqhip10LoggingInput1LogInputType OBJECT-TYPE
        SYNTAX            INTEGER { disable(0), enable(1)  }
        MAX-ACCESS        read-write
        STATUS            current
        DESCRIPTION
                "CMNT: - 
                 TYPE: - Checkbox
                 PAGE: - Logging
                    Log Input Type  cmdID= 1096  "
        ::= { iqhip10CmdEntry 1096 }


    iqhip10LoggingInput1InputType OBJECT-TYPE
        SYNTAX            RollCallString
        MAX-ACCESS        read-only
        STATUS            current
        DESCRIPTION
                "CMNT: - 
                 TYPE: - Display
                 PAGE: - Logging
                    Input Type=  cmdID= 2096  "
        ::= { iqhip10CmdEntry 2096 }


    iqhip10LoggingInput1LogInputState OBJECT-TYPE
        SYNTAX            INTEGER { disable(0), enable(1)  }
        MAX-ACCESS        read-write
        STATUS            current
        DESCRIPTION
                "CMNT: - Enable/Disable logging for Input 1 status
                 TYPE: - Checkbox
                 PAGE: - Logging
                    Log Input State  cmdID= 1006  "
        ::= { iqhip10CmdEntry 1006 }


    iqhip10LoggingInput1InputState OBJECT-TYPE
        SYNTAX            RollCallString
        MAX-ACCESS        read-only
        STATUS            current
        DESCRIPTION
                "CMNT: - Logging state for Input
                 TYPE: - Display
                 PAGE: - Logging
                    Input State=  cmdID= 2006  "
        ::= { iqhip10CmdEntry 2006 }


    iqhip10LoggingInput1LogInputStandard OBJECT-TYPE
        SYNTAX            INTEGER { disable(0), enable(1)  }
        MAX-ACCESS        read-write
        STATUS            current
        DESCRIPTION
                "CMNT: - Enable/Disable logging for Input 1 Standard
                 TYPE: - Checkbox
                 PAGE: - Logging
                    Log Input Standard  cmdID= 1007  "
        ::= { iqhip10CmdEntry 1007 }


    iqhip10LoggingInput1InputStandard OBJECT-TYPE
        SYNTAX            RollCallString
        MAX-ACCESS        read-only
        STATUS            current
        DESCRIPTION
                "CMNT: - Logging state for Input Standard
                 TYPE: - Display
                 PAGE: - Logging
                    Input Standard=  cmdID= 2007  "
        ::= { iqhip10CmdEntry 2007 }


    iqhip10LoggingInput1LogEDH OBJECT-TYPE
        SYNTAX            INTEGER { disable(0), enable(1)  }
        MAX-ACCESS        read-write
        STATUS            current
        DESCRIPTION
                "CMNT: - 
                 TYPE: - Checkbox
                 PAGE: - Logging
                    Log EDH  cmdID= 1093  "
        ::= { iqhip10CmdEntry 1093 }


    iqhip10LoggingInput1EDH OBJECT-TYPE
        SYNTAX            RollCallString
        MAX-ACCESS        read-only
        STATUS            current
        DESCRIPTION
                "CMNT: - 
                 TYPE: - Display
                 PAGE: - Logging
                    EDH=  cmdID= 2093  "
        ::= { iqhip10CmdEntry 2093 }


    iqhip10LoggingInput1LogCRC OBJECT-TYPE
        SYNTAX            INTEGER { disable(0), enable(1)  }
        MAX-ACCESS        read-write
        STATUS            current
        DESCRIPTION
                "CMNT: - 
                 TYPE: - Checkbox
                 PAGE: - Logging
                    Log CRC  cmdID= 1094  "
        ::= { iqhip10CmdEntry 1094 }


    iqhip10LoggingInput1CRC OBJECT-TYPE
        SYNTAX            RollCallString
        MAX-ACCESS        read-only
        STATUS            current
        DESCRIPTION
                "CMNT: - 
                 TYPE: - Display
                 PAGE: - Logging
                    CRC=  cmdID= 2094  "
        ::= { iqhip10CmdEntry 2094 }


    iqhip10LoggingSFPLogType OBJECT-TYPE
        SYNTAX            INTEGER { disable(0), enable(1)  }
        MAX-ACCESS        read-write
        STATUS            current
        DESCRIPTION
                "CMNT: - Enable/Disable logging for SFP Type
                 TYPE: - Checkbox
                 PAGE: - Logging
                    Log Type  cmdID= 35050  "
        ::= { iqhip10CmdEntry 35050 }


    iqhip10LoggingSFP1Type OBJECT-TYPE
        SYNTAX            RollCallString
        MAX-ACCESS        read-only
        STATUS            current
        DESCRIPTION
                "CMNT: - Logging state for SFP Type
                 TYPE: - Display
                 PAGE: - Logging
                    SFP 1 Type=  cmdID= 36050  "
        ::= { iqhip10CmdEntry 36050 }


    iqhip10LoggingSFPLogStatus OBJECT-TYPE
        SYNTAX            INTEGER { disable(0), enable(1)  }
        MAX-ACCESS        read-write
        STATUS            current
        DESCRIPTION
                "CMNT: - Enable/Disable logging for SFP Status
                 TYPE: - Checkbox
                 PAGE: - Logging
                    Log Status  cmdID= 35054  "
        ::= { iqhip10CmdEntry 35054 }


    iqhip10LoggingSFPStatus OBJECT-TYPE
        SYNTAX            RollCallString
        MAX-ACCESS        read-only
        STATUS            current
        DESCRIPTION
                "CMNT: - Logging state for SFP Status
                 TYPE: - Display
                 PAGE: - Logging
                    SFP Status=  cmdID= 36054  "
        ::= { iqhip10CmdEntry 36054 }


    iqhip10LoggingSFPLogConnector OBJECT-TYPE
        SYNTAX            INTEGER { disable(0), enable(1)  }
        MAX-ACCESS        read-write
        STATUS            current
        DESCRIPTION
                "CMNT: - Enable/Disable logging for SFP Type
                 TYPE: - Checkbox
                 PAGE: - Logging
                    Log Connector  cmdID= 35051  "
        ::= { iqhip10CmdEntry 35051 }


    iqhip10LoggingSFPConnector OBJECT-TYPE
        SYNTAX            RollCallString
        MAX-ACCESS        read-only
        STATUS            current
        DESCRIPTION
                "CMNT: - Logging state for SFP Type
                 TYPE: - Display
                 PAGE: - Logging
                    SFP Connector  cmdID= 36051  "
        ::= { iqhip10CmdEntry 36051 }


    iqhip10LoggingSFPARxLogRxIdent OBJECT-TYPE
        SYNTAX            INTEGER { disable(0), enable(1)  }
        MAX-ACCESS        read-write
        STATUS            current
        DESCRIPTION
                "CMNT: - Enable/Disable logging for SFP A Rx Ident
                 TYPE: - Checkbox
                 PAGE: - Logging
                    Log Rx Ident  cmdID= 35062  "
        ::= { iqhip10CmdEntry 35062 }


    iqhip10LoggingSFPARxRxIdent OBJECT-TYPE
        SYNTAX            RollCallString
        MAX-ACCESS        read-only
        STATUS            current
        DESCRIPTION
                "CMNT: - Logging state for SFP 2 Rx Ident
                 TYPE: - Display
                 PAGE: - Logging
                    Rx Ident=  cmdID= 36062  "
        ::= { iqhip10CmdEntry 36062 }


    iqhip10LoggingSFPARxLogRxName OBJECT-TYPE
        SYNTAX            INTEGER { disable(0), enable(1)  }
        MAX-ACCESS        read-write
        STATUS            current
        DESCRIPTION
                "CMNT: - Enable/Disable logging for SFP 2 Rx Name
                 TYPE: - Checkbox
                 PAGE: - Logging
                    Log Rx Name  cmdID= 35082  "
        ::= { iqhip10CmdEntry 35082 }


    iqhip10LoggingSFPARxRxName OBJECT-TYPE
        SYNTAX            RollCallString
        MAX-ACCESS        read-only
        STATUS            current
        DESCRIPTION
                "CMNT: - Logging state for SFP 2 Rx Name
                 TYPE: - Display
                 PAGE: - Logging
                    Rx Name=  cmdID= 36082  "
        ::= { iqhip10CmdEntry 36082 }


    iqhip10LoggingSFPARxLogRxPowerState OBJECT-TYPE
        SYNTAX            INTEGER { disable(0), enable(1)  }
        MAX-ACCESS        read-write
        STATUS            current
        DESCRIPTION
                "CMNT: - Enable/Disable logging for Input 2 Rx Power State
                 TYPE: - Checkbox
                 PAGE: - Logging
                    Log Rx Power State  cmdID= 35094  "
        ::= { iqhip10CmdEntry 35094 }


    iqhip10LoggingSFPARxRxPowerState OBJECT-TYPE
        SYNTAX            RollCallString
        MAX-ACCESS        read-only
        STATUS            current
        DESCRIPTION
                "CMNT: - Logging state for SFP 2 Rx Power State
                 TYPE: - Display
                 PAGE: - Logging
                    Rx Power State=  cmdID= 36094  "
        ::= { iqhip10CmdEntry 36094 }


    iqhip10LoggingSFPARxLogRxPower OBJECT-TYPE
        SYNTAX            INTEGER { disable(0), enable(1)  }
        MAX-ACCESS        read-write
        STATUS            current
        DESCRIPTION
                "CMNT: - Enable/Disable logging for SFP 2 Rx Power
                 TYPE: - Checkbox
                 PAGE: - Logging
                    Log Rx Power  cmdID= 35096  "
        ::= { iqhip10CmdEntry 35096 }


    iqhip10LoggingSFPARxRxPower OBJECT-TYPE
        SYNTAX            RollCallString
        MAX-ACCESS        read-only
        STATUS            current
        DESCRIPTION
                "CMNT: - Logging state for SFP 2 Rx Power
                 TYPE: - Display
                 PAGE: - Logging
                    Rx Power=  cmdID= 36096  "
        ::= { iqhip10CmdEntry 36096 }


    iqhip10LoggingSFPATxLogTxPowerState OBJECT-TYPE
        SYNTAX            INTEGER { disable(0), enable(1)  }
        MAX-ACCESS        read-write
        STATUS            current
        DESCRIPTION
                "CMNT: - Enable/Disable logging for Output 2 Tx Power State
                 TYPE: - Checkbox
                 PAGE: - Logging
                    Log Tx Power State  cmdID= 35089  "
        ::= { iqhip10CmdEntry 35089 }


    iqhip10LoggingSFPATxTxPowerState OBJECT-TYPE
        SYNTAX            RollCallString
        MAX-ACCESS        read-only
        STATUS            current
        DESCRIPTION
                "CMNT: - Logging state for Output 2 Tx Power State
                 TYPE: - Display
                 PAGE: - Logging
                    Tx Power State=  cmdID= 36089  "
        ::= { iqhip10CmdEntry 36089 }


    iqhip10LoggingSFPATxLogTxPower OBJECT-TYPE
        SYNTAX            INTEGER { disable(0), enable(1)  }
        MAX-ACCESS        read-write
        STATUS            current
        DESCRIPTION
                "CMNT: - Enable/Disable logging for Output 2 Tx Power
                 TYPE: - Checkbox
                 PAGE: - Logging
                    Log Tx Power  cmdID= 35093  "
        ::= { iqhip10CmdEntry 35093 }


    iqhip10LoggingSFPATxTxPower OBJECT-TYPE
        SYNTAX            RollCallString
        MAX-ACCESS        read-only
        STATUS            current
        DESCRIPTION
                "CMNT: - Logging state for Output 2 Tx Power
                 TYPE: - Display
                 PAGE: - Logging
                    Tx Power=  cmdID= 36093  "
        ::= { iqhip10CmdEntry 36093 }


    iqhip10LoggingSFPATxLogWavelength OBJECT-TYPE
        SYNTAX            INTEGER { disable(0), enable(1)  }
        MAX-ACCESS        read-write
        STATUS            current
        DESCRIPTION
                "CMNT: - Enable/Disable logging for Output 2 Wavelength
                 TYPE: - Checkbox
                 PAGE: - Logging
                    Log Wavelength  cmdID= 35085  "
        ::= { iqhip10CmdEntry 35085 }


    iqhip10LoggingSFPATxWavelength OBJECT-TYPE
        SYNTAX            RollCallString
        MAX-ACCESS        read-only
        STATUS            current
        DESCRIPTION
                "CMNT: - Logging state for Output 1 Wavelength
                 TYPE: - Display
                 PAGE: - Logging
                    Wavelength=  cmdID= 36085  "
        ::= { iqhip10CmdEntry 36085 }


    iqhip10LoggingSFPATxLogLaserBias OBJECT-TYPE
        SYNTAX            INTEGER { disable(0), enable(1)  }
        MAX-ACCESS        read-write
        STATUS            current
        DESCRIPTION
                "CMNT: - Enable/Disable logging for Output 2 Laser Bias
                 TYPE: - Checkbox
                 PAGE: - Logging
                    Log Laser Bias  cmdID= 35091  "
        ::= { iqhip10CmdEntry 35091 }


    iqhip10LoggingSFPATxLaserBias OBJECT-TYPE
        SYNTAX            RollCallString
        MAX-ACCESS        read-only
        STATUS            current
        DESCRIPTION
                "CMNT: - Logging state for Output 2 Laser Bias
                 TYPE: - Display
                 PAGE: - Logging
                    Laser Bias=  cmdID= 36091  "
        ::= { iqhip10CmdEntry 36091 }


    iqhip10LoggingSFPATxLogLaserBiasState OBJECT-TYPE
        SYNTAX            INTEGER { disable(0), enable(1)  }
        MAX-ACCESS        read-write
        STATUS            current
        DESCRIPTION
                "CMNT: - Enable/Disable logging for Output 2 Laser Bias State
                 TYPE: - Checkbox
                 PAGE: - Logging
                    Log Laser Bias State  cmdID= 35087  "
        ::= { iqhip10CmdEntry 35087 }


    iqhip10LoggingSFPATxLaserBiasState OBJECT-TYPE
        SYNTAX            RollCallString
        MAX-ACCESS        read-only
        STATUS            current
        DESCRIPTION
                "CMNT: - Logging state for Output 2 Laser Bias State
                 TYPE: - Display
                 PAGE: - Logging
                    Laser Bias State=  cmdID= 36087  "
        ::= { iqhip10CmdEntry 36087 }


    iqhip10LoggingSFPBTxLogTxPowerState OBJECT-TYPE
        SYNTAX            INTEGER { disable(0), enable(1)  }
        MAX-ACCESS        read-write
        STATUS            current
        DESCRIPTION
                "CMNT: - Enable/Disable logging for Output 1 Tx Power State
                 TYPE: - Checkbox
                 PAGE: - Logging
                    Log Tx Power State  cmdID= 35088  "
        ::= { iqhip10CmdEntry 35088 }


    iqhip10LoggingSFPBTxTxPowerState OBJECT-TYPE
        SYNTAX            RollCallString
        MAX-ACCESS        read-only
        STATUS            current
        DESCRIPTION
                "CMNT: - Logging state for Output 1 Tx Power State
                 TYPE: - Display
                 PAGE: - Logging
                    Tx Power State=  cmdID= 36088  "
        ::= { iqhip10CmdEntry 36088 }


    iqhip10LoggingSFPBTxLogTxPower OBJECT-TYPE
        SYNTAX            INTEGER { disable(0), enable(1)  }
        MAX-ACCESS        read-write
        STATUS            current
        DESCRIPTION
                "CMNT: - Enable/Disable logging for Output 1Tx Power
                 TYPE: - Checkbox
                 PAGE: - Logging
                    Log Tx Power  cmdID= 35092  "
        ::= { iqhip10CmdEntry 35092 }


    iqhip10LoggingSFPBTxTxPower OBJECT-TYPE
        SYNTAX            RollCallString
        MAX-ACCESS        read-only
        STATUS            current
        DESCRIPTION
                "CMNT: - Logging state for Output 1 Tx Power
                 TYPE: - Display
                 PAGE: - Logging
                    Tx Power=  cmdID= 36092  "
        ::= { iqhip10CmdEntry 36092 }


    iqhip10LoggingSFPBTxLogWavelength OBJECT-TYPE
        SYNTAX            INTEGER { disable(0), enable(1)  }
        MAX-ACCESS        read-write
        STATUS            current
        DESCRIPTION
                "CMNT: - Enable/Disable logging for Output 1 Wavelength
                 TYPE: - Checkbox
                 PAGE: - Logging
                    Log Wavelength  cmdID= 35084  "
        ::= { iqhip10CmdEntry 35084 }


    iqhip10LoggingSFPBTxWavelength OBJECT-TYPE
        SYNTAX            RollCallString
        MAX-ACCESS        read-only
        STATUS            current
        DESCRIPTION
                "CMNT: - Logging state for Output 1 Wavelength
                 TYPE: - Display
                 PAGE: - Logging
                    Wavelength=  cmdID= 36084  "
        ::= { iqhip10CmdEntry 36084 }


    iqhip10LoggingSFPBTxLogLaserBias OBJECT-TYPE
        SYNTAX            INTEGER { disable(0), enable(1)  }
        MAX-ACCESS        read-write
        STATUS            current
        DESCRIPTION
                "CMNT: - Enable/Disable logging for Output 1 Laser Bias
                 TYPE: - Checkbox
                 PAGE: - Logging
                    Log Laser Bias  cmdID= 35090  "
        ::= { iqhip10CmdEntry 35090 }


    iqhip10LoggingSFPBTxLaserBias OBJECT-TYPE
        SYNTAX            RollCallString
        MAX-ACCESS        read-only
        STATUS            current
        DESCRIPTION
                "CMNT: - Logging state for Output 1 Laser Bias
                 TYPE: - Display
                 PAGE: - Logging
                    Laser Bias=  cmdID= 36090  "
        ::= { iqhip10CmdEntry 36090 }


    iqhip10LoggingSFPBTxLogLaserBiasState OBJECT-TYPE
        SYNTAX            INTEGER { disable(0), enable(1)  }
        MAX-ACCESS        read-write
        STATUS            current
        DESCRIPTION
                "CMNT: - Enable/Disable logging for Output 1 Laser Bias State
                 TYPE: - Checkbox
                 PAGE: - Logging
                    Log Laser Bias State  cmdID= 35086  "
        ::= { iqhip10CmdEntry 35086 }


    iqhip10LoggingSFPBTxLaserBiasState OBJECT-TYPE
        SYNTAX            RollCallString
        MAX-ACCESS        read-only
        STATUS            current
        DESCRIPTION
                "CMNT: - Logging state for Output 1 Laser Bias State
                 TYPE: - Display
                 PAGE: - Logging
                    Laser Bias State=  cmdID= 36086  "
        ::= { iqhip10CmdEntry 36086 }


    iqhip10LoggingMonitorLogHyperionSummary OBJECT-TYPE
        SYNTAX            INTEGER { disable(0), enable(1)  }
        MAX-ACCESS        read-write
        STATUS            current
        DESCRIPTION
                "CMNT: - 
                 TYPE: - Checkbox
                 PAGE: - Logging
                    Log Hyperion Summary  cmdID= 1129  "
        ::= { iqhip10CmdEntry 1129 }


    iqhip10LoggingMonitorHyperionSummary OBJECT-TYPE
        SYNTAX            RollCallString
        MAX-ACCESS        read-only
        STATUS            current
        DESCRIPTION
                "CMNT: - 
                 TYPE: - Display
                 PAGE: - Logging
                    Hyperion Summary =  cmdID= 2129  "
        ::= { iqhip10CmdEntry 2129 }


    iqhip10MonitorRegion1LogReg1Black OBJECT-TYPE
        SYNTAX            INTEGER { disable(0), enable(1)  }
        MAX-ACCESS        read-write
        STATUS            current
        DESCRIPTION
                "CMNT: - 
                 TYPE: - Checkbox
                 PAGE: - Monitor
                    Log Reg 1 Black  cmdID= 1180  "
        ::= { iqhip10CmdEntry 1180 }


    iqhip10MonitorRegion1Reg1Black OBJECT-TYPE
        SYNTAX            RollCallString
        MAX-ACCESS        read-only
        STATUS            current
        DESCRIPTION
                "CMNT: - 
                 TYPE: - Display
                 PAGE: - Monitor
                    Reg 1 Black =   cmdID= 4170  "
        ::= { iqhip10CmdEntry 4170 }


    iqhip10MonitorRegion1Reg1BlackLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 1 Black Log Opt  cmdID= 3310
                    Timecode At Start  value= 0
                    Timecode At Fail  value= 1  "
        ::= { iqhip10CmdEntry 3310 }


    iqhip10MonitorRegion1LogReg1Blackish OBJECT-TYPE
        SYNTAX            INTEGER { disable(0), enable(1)  }
        MAX-ACCESS        read-write
        STATUS            current
        DESCRIPTION
                "CMNT: - 
                 TYPE: - Checkbox
                 PAGE: - Monitor
                    Log Reg 1 Blackish  cmdID= 1181  "
        ::= { iqhip10CmdEntry 1181 }


    iqhip10MonitorRegion1Reg1Blackish OBJECT-TYPE
        SYNTAX            RollCallString
        MAX-ACCESS        read-only
        STATUS            current
        DESCRIPTION
                "CMNT: - 
                 TYPE: - Display
                 PAGE: - Monitor
                    Reg 1 Blackish =   cmdID= 4171  "
        ::= { iqhip10CmdEntry 4171 }


    iqhip10MonitorRegion1Reg1BlackishLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 1 Blackish Log Opt  cmdID= 3311
                    Timecode At Start  value= 0
                    Timecode At Fail  value= 1  "
        ::= { iqhip10CmdEntry 3311 }


    iqhip10MonitorRegion1LogReg1Stillish OBJECT-TYPE
        SYNTAX            INTEGER { disable(0), enable(1)  }
        MAX-ACCESS        read-write
        STATUS            current
        DESCRIPTION
                "CMNT: - 
                 TYPE: - Checkbox
                 PAGE: - Monitor
                    Log Reg 1 Stillish  cmdID= 1182  "
        ::= { iqhip10CmdEntry 1182 }


    iqhip10MonitorRegion1Reg1Stillish OBJECT-TYPE
        SYNTAX            RollCallString
        MAX-ACCESS        read-only
        STATUS            current
        DESCRIPTION
                "CMNT: - 
                 TYPE: - Display
                 PAGE: - Monitor
                    Reg 1 Stillish =   cmdID= 4172  "
        ::= { iqhip10CmdEntry 4172 }


    iqhip10MonitorRegion1Reg1StillishLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 1 Stillish Log Opt  cmdID= 3312
                    Timecode At Start  value= 0
                    Timecode At Fail  value= 1  "
        ::= { iqhip10CmdEntry 3312 }


    iqhip10MonitorRegion1LogReg1Freeze OBJECT-TYPE
        SYNTAX            INTEGER { disable(0), enable(1)  }
        MAX-ACCESS        read-write
        STATUS            current
        DESCRIPTION
                "CMNT: - 
                 TYPE: - Checkbox
                 PAGE: - Monitor
                    Log Reg 1 Freeze  cmdID= 1183  "
        ::= { iqhip10CmdEntry 1183 }


    iqhip10MonitorRegion1Reg1Freeze OBJECT-TYPE
        SYNTAX            RollCallString
        MAX-ACCESS        read-only
        STATUS            current
        DESCRIPTION
                "CMNT: - 
                 TYPE: - Display
                 PAGE: - Monitor
                    Reg 1 Freeze =   cmdID= 4173  "
        ::= { iqhip10CmdEntry 4173 }


    iqhip10MonitorRegion1Reg1FreezeLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 1 Freeze Log Opt  cmdID= 3313
                    Timecode At Start  value= 0
                    Timecode At Fail  value= 1  "
        ::= { iqhip10CmdEntry 3313 }


    iqhip10MonitorRegion2LogReg2Black OBJECT-TYPE
        SYNTAX            INTEGER { disable(0), enable(1)  }
        MAX-ACCESS        read-write
        STATUS            current
        DESCRIPTION
                "CMNT: - 
                 TYPE: - Checkbox
                 PAGE: - Monitor
                    Log Reg 2 Black  cmdID= 1190  "
        ::= { iqhip10CmdEntry 1190 }


    iqhip10MonitorRegion2Reg1Black OBJECT-TYPE
        SYNTAX            RollCallString
        MAX-ACCESS        read-only
        STATUS            current
        DESCRIPTION
                "CMNT: - 
                 TYPE: - Display
                 PAGE: - Monitor
                    Reg 1 Black =   cmdID= 4174  "
        ::= { iqhip10CmdEntry 4174 }


    iqhip10MonitorRegion2Reg2BlackLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 2 Black Log Opt  cmdID= 3314
                    Timecode At Start  value= 0
                    Timecode At Fail  value= 1  "
        ::= { iqhip10CmdEntry 3314 }


    iqhip10MonitorRegion2LogReg2Blackish OBJECT-TYPE
        SYNTAX            INTEGER { disable(0), enable(1)  }
        MAX-ACCESS        read-write
        STATUS            current
        DESCRIPTION
                "CMNT: - 
                 TYPE: - Checkbox
                 PAGE: - Monitor
                    Log Reg 2 Blackish  cmdID= 1191  "
        ::= { iqhip10CmdEntry 1191 }


    iqhip10MonitorRegion2Reg2Blackish OBJECT-TYPE
        SYNTAX            RollCallString
        MAX-ACCESS        read-only
        STATUS            current
        DESCRIPTION
                "CMNT: - 
                 TYPE: - Display
                 PAGE: - Monitor
                    Reg 2 Blackish =   cmdID= 4175  "
        ::= { iqhip10CmdEntry 4175 }


    iqhip10MonitorRegion2Reg2BlackishLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 2 Blackish Log Opt  cmdID= 3315
                    Timecode At Start  value= 0
                    Timecode At Fail  value= 1  "
        ::= { iqhip10CmdEntry 3315 }


    iqhip10MonitorRegion2LogReg2Stillish OBJECT-TYPE
        SYNTAX            INTEGER { disable(0), enable(1)  }
        MAX-ACCESS        read-write
        STATUS            current
        DESCRIPTION
                "CMNT: - 
                 TYPE: - Checkbox
                 PAGE: - Monitor
                    Log Reg 2 Stillish  cmdID= 1192  "
        ::= { iqhip10CmdEntry 1192 }


    iqhip10MonitorRegion2Reg2Stillish OBJECT-TYPE
        SYNTAX            RollCallString
        MAX-ACCESS        read-only
        STATUS            current
        DESCRIPTION
                "CMNT: - 
                 TYPE: - Display
                 PAGE: - Monitor
                    Reg 2 Stillish =   cmdID= 4176  "
        ::= { iqhip10CmdEntry 4176 }


    iqhip10MonitorRegion2Reg2StillishLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 2 Stillish Log Opt  cmdID= 3316
                    Timecode At Start  value= 0
                    Timecode At Fail  value= 1  "
        ::= { iqhip10CmdEntry 3316 }


    iqhip10MonitorRegion2LogReg2Freeze OBJECT-TYPE
        SYNTAX            INTEGER { disable(0), enable(1)  }
        MAX-ACCESS        read-write
        STATUS            current
        DESCRIPTION
                "CMNT: - 
                 TYPE: - Checkbox
                 PAGE: - Monitor
                    Log Reg 2 Freeze  cmdID= 1193  "
        ::= { iqhip10CmdEntry 1193 }


    iqhip10MonitorRegion2Reg2Freeze OBJECT-TYPE
        SYNTAX            RollCallString
        MAX-ACCESS        read-only
        STATUS            current
        DESCRIPTION
                "CMNT: - 
                 TYPE: - Display
                 PAGE: - Monitor
                    Reg 2 Freeze =   cmdID= 4177  "
        ::= { iqhip10CmdEntry 4177 }


    iqhip10MonitorRegion2Reg2FreezeLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Monitor
                    Reg 2 Freeze Log Opt  cmdID= 3317
                    Timecode At Start  value= 0
                    Timecode At Fail  value= 1  "
        ::= { iqhip10CmdEntry 3317 }


    iqhip10LoggingMonitorLogCldCapState OBJECT-TYPE
        SYNTAX            INTEGER { disable(0), enable(1)  }
        MAX-ACCESS        read-write
        STATUS            current
        DESCRIPTION
                "CMNT: - 
                 TYPE: - Checkbox
                 PAGE: - Logging
                    Log Cld. Cap.State  cmdID= 1011  "
        ::= { iqhip10CmdEntry 1011 }


    iqhip10LoggingMonitorClosedCapState OBJECT-TYPE
        SYNTAX            RollCallString
        MAX-ACCESS        read-only
        STATUS            current
        DESCRIPTION
                "CMNT: - 
                 TYPE: - Display
                 PAGE: - Logging
                    Closed Cap. State =   cmdID= 2011  "
        ::= { iqhip10CmdEntry 2011 }


    iqhip10LoggingMonitorClosedCapLogOpt OBJECT-TYPE
        SYNTAX            INTEGER {
                            valTimecodeAtStart(0),
                            valTimecodeAtFail(1)
                            }
        MAX-ACCESS        read-write
        STATUS            current
        DESCRIPTION
                "CMNT: - 
                 TYPE: - RadiobuttonList
                 PAGE: - Logging
                    Closed Cap Log Opt  cmdID= 3304
                    Timecode At Start  value= 0
                    Timecode At Fail  value= 1  "
        ::= { iqhip10CmdEntry 3304 }


    iqhip10LoggingMonitorLogCldCapType OBJECT-TYPE
        SYNTAX            INTEGER { disable(0), enable(1)  }
        MAX-ACCESS        read-write
        STATUS            current
        DESCRIPTION
                "CMNT: - 
                 TYPE: - Checkbox
                 PAGE: - Logging
                    Log Cld. Cap.Type  cmdID= 1012  "
        ::= { iqhip10CmdEntry 1012 }


    iqhip10LoggingMonitorClosedCapType OBJECT-TYPE
        SYNTAX            RollCallString
        MAX-ACCESS        read-only
        STATUS            current
        DESCRIPTION
                "CMNT: - 
                 TYPE: - Display
                 PAGE: - Logging
                    Closed Cap.Type=  cmdID= 2012  "
        ::= { iqhip10CmdEntry 2012 }


    iqhip10LoggingMonitorLogCldCapTitle OBJECT-TYPE
        SYNTAX            INTEGER { disable(0), enable(1)  }
        MAX-ACCESS        read-write
        STATUS            current
        DESCRIPTION
                "CMNT: - 
                 TYPE: - Checkbox
                 PAGE: - Logging
                    Log Cld. Cap.Title  cmdID= 1164  "
        ::= { iqhip10CmdEntry 1164 }


    iqhip10LoggingMonitorClosedCapTitle OBJECT-TYPE
        SYNTAX            RollCallString
        MAX-ACCESS        read-only
        STATUS            current
        DESCRIPTION
                "CMNT: - 
                 TYPE: - Display
                 PAGE: - Logging
                    Closed Cap.Title=  cmdID= 2164  "
        ::= { iqhip10CmdEntry 2164 }


    iqhip10LoggingMonitorLogYBitDepth OBJECT-TYPE
        SYNTAX            INTEGER { disable(0), enable(1)  }
        MAX-ACCESS        read-write
        STATUS            current
        DESCRIPTION
                "CMNT: - 
                 TYPE: - Checkbox
                 PAGE: - Logging
                    Log Y Bit Depth  cmdID= 1017  "
        ::= { iqhip10CmdEntry 1017 }


    iqhip10LoggingMonitorYBitDepth OBJECT-TYPE
        SYNTAX            RollCallString
        MAX-ACCESS        read-only
        STATUS            current
        DESCRIPTION
                "CMNT: - 
                 TYPE: - Display
                 PAGE: - Logging
                    Y Bit Depth=  cmdID= 2017  "
        ::= { iqhip10CmdEntry 2017 }


    iqhip10LoggingMonitorLogCBitDepth OBJECT-TYPE
        SYNTAX            INTEGER { disable(0), enable(1)  }
        MAX-ACCESS        read-write
        STATUS            current
        DESCRIPTION
                "CMNT: - 
                 TYPE: - Checkbox
                 PAGE: - Logging
                    Log C Bit Depth  cmdID= 1018  "
        ::= { iqhip10CmdEntry 1018 }


    iqhip10LoggingMonitorCBitDepth OBJECT-TYPE
        SYNTAX            RollCallString
        MAX-ACCESS        read-only
        STATUS            current
        DESCRIPTION
                "CMNT: - 
                 TYPE: - Display
                 PAGE: - Logging
                    C Bit Depth=  cmdID= 2018  "
        ::= { iqhip10CmdEntry 2018 }


    iqhip10LoggingMonitorLogVideoYLvlHigh OBJECT-TYPE
        SYNTAX            INTEGER { disable(0), enable(1)  }
        MAX-ACCESS        read-write
        STATUS            current
        DESCRIPTION
                "CMNT: - 
                 TYPE: - Checkbox
                 PAGE: - Logging
                    Log Video Y Lvl. High  cmdID= 1019  "
        ::= { iqhip10CmdEntry 1019 }


    iqhip10LoggingMonitorVideoYLevelHigh OBJECT-TYPE
        SYNTAX            RollCallString
        MAX-ACCESS        read-only
        STATUS            current
        DESCRIPTION
                "CMNT: - 
                 TYPE: - Display
                 PAGE: - Logging
                    Video Y Level High=  cmdID= 2019  "
        ::= { iqhip10CmdEntry 2019 }


    iqhip10LoggingMonitorLogVideoCLvlHigh OBJECT-TYPE
        SYNTAX            INTEGER { disable(0), enable(1)  }
        MAX-ACCESS        read-write
        STATUS            current
        DESCRIPTION
                "CMNT: - 
                 TYPE: - Checkbox
                 PAGE: - Logging
                    Log Video C Lvl. High  cmdID= 1020  "
        ::= { iqhip10CmdEntry 1020 }


    iqhip10LoggingMonitorVideoCLevelHigh OBJECT-TYPE
        SYNTAX            RollCallString
        MAX-ACCESS        read-only
        STATUS            current
        DESCRIPTION
                "CMNT: - 
                 TYPE: - Display
                 PAGE: - Logging
                    Video C Level High=  cmdID= 2020  "
        ::= { iqhip10CmdEntry 2020 }


    iqhip10LoggingMonitorLogVideoYLvlLow OBJECT-TYPE
        SYNTAX            INTEGER { disable(0), enable(1)  }
        MAX-ACCESS        read-write
        STATUS            current
        DESCRIPTION
                "CMNT: - 
                 TYPE: - Checkbox
                 PAGE: - Logging
                    Log Video Y Lvl. Low  cmdID= 1021  "
        ::= { iqhip10CmdEntry 1021 }


    iqhip10LoggingMonitorVideoYLevelLow OBJECT-TYPE
        SYNTAX            RollCallString
        MAX-ACCESS        read-only
        STATUS            current
        DESCRIPTION
                "CMNT: - 
                 TYPE: - Display
                 PAGE: - Logging
                    Video Y Level Low=  cmdID= 2021  "
        ::= { iqhip10CmdEntry 2021 }


    iqhip10LoggingMonitorLogVideoCLvlLow OBJECT-TYPE
        SYNTAX            INTEGER { disable(0), enable(1)  }
        MAX-ACCESS        read-write
        STATUS            current
        DESCRIPTION
                "CMNT: - 
                 TYPE: - Checkbox
                 PAGE: - Logging
                    Log Video C Lvl. Low  cmdID= 1022  "
        ::= { iqhip10CmdEntry 1022 }


    iqhip10LoggingMonitorVideoCLevelLow OBJECT-TYPE
        SYNTAX            RollCallString
        MAX-ACCESS        read-only
        STATUS            current
        DESCRIPTION
                "CMNT: - 
                 TYPE: - Display
                 PAGE: - Logging
                    Video C Level Low=  cmdID= 2022  "
        ::= { iqhip10CmdEntry 2022 }


    iqhip10LoggingMonitorLogAPL OBJECT-TYPE
        SYNTAX            INTEGER { disable(0), enable(1)  }
        MAX-ACCESS        read-write
        STATUS            current
        DESCRIPTION
                "CMNT: - 
                 TYPE: - Checkbox
                 PAGE: - Logging
                    Log APL  cmdID= 1023  "
        ::= { iqhip10CmdEntry 1023 }


    iqhip10LoggingMonitorAPL OBJECT-TYPE
        SYNTAX            RollCallString
        MAX-ACCESS        read-only
        STATUS            current
        DESCRIPTION
                "CMNT: - 
                 TYPE: - Display
                 PAGE: - Logging
                    APL=  cmdID= 2023  "
        ::= { iqhip10CmdEntry 2023 }


    iqhip10LoggingMonitorLogVITCState OBJECT-TYPE
        SYNTAX            INTEGER { disable(0), enable(1)  }
        MAX-ACCESS        read-write
        STATUS            current
        DESCRIPTION
                "CMNT: - 
                 TYPE: - Checkbox
                 PAGE: - Logging
                    Log VITC State  cmdID= 1024  "
        ::= { iqhip10CmdEntry 1024 }


    iqhip10LoggingMonitorVITCState OBJECT-TYPE
        SYNTAX            RollCallString
        MAX-ACCESS        read-only
        STATUS            current
        DESCRIPTION
                "CMNT: - 
                 TYPE: - Display
                 PAGE: - Logging
                    VITC State=  cmdID= 2024  "
        ::= { iqhip10CmdEntry 2024 }


    iqhip10LoggingMonitorLogCAState OBJECT-TYPE
        SYNTAX            INTEGER { disable(0), enable(1)  }
        MAX-ACCESS        read-write
        STATUS            current
        DESCRIPTION
                "CMNT: - 
                 TYPE: - Checkbox
                 PAGE: - Logging
                    Log CA State  cmdID= 1025  "
        ::= { iqhip10CmdEntry 1025 }


    iqhip10LoggingMonitorCAState OBJECT-TYPE
        SYNTAX            RollCallString
        MAX-ACCESS        read-only
        STATUS            current
        DESCRIPTION
                "CMNT: - 
                 TYPE: - Display
                 PAGE: - Logging
                    CA State=  cmdID= 2025  "
        ::= { iqhip10CmdEntry 2025 }


    iqhip10LoggingMonitorLogCASystem OBJECT-TYPE
        SYNTAX            INTEGER { disable(0), enable(1)  }
        MAX-ACCESS        read-write
        STATUS            current
        DESCRIPTION
                "CMNT: - 
                 TYPE: - Checkbox
                 PAGE: - Logging
                    Log CA System  cmdID= 1026  "
        ::= { iqhip10CmdEntry 1026 }


    iqhip10LoggingMonitorCASystem OBJECT-TYPE
        SYNTAX            RollCallString
        MAX-ACCESS        read-only
        STATUS            current
        DESCRIPTION
                "CMNT: - 
                 TYPE: - Display
                 PAGE: - Logging
                    CA System=  cmdID= 2026  "
        ::= { iqhip10CmdEntry 2026 }


    iqhip10LoggingMonitorLogCAAgeRating OBJECT-TYPE
        SYNTAX            INTEGER { disable(0), enable(1)  }
        MAX-ACCESS        read-write
        STATUS            current
        DESCRIPTION
                "CMNT: - 
                 TYPE: - Checkbox
                 PAGE: - Logging
                    Log CA Age Rating  cmdID= 1027  "
        ::= { iqhip10CmdEntry 1027 }


    iqhip10LoggingMonitorCAAgeRating OBJECT-TYPE
        SYNTAX            RollCallString
        MAX-ACCESS        read-only
        STATUS            current
        DESCRIPTION
                "CMNT: - 
                 TYPE: - Display
                 PAGE: - Logging
                    CA Age Rating=  cmdID= 2027  "
        ::= { iqhip10CmdEntry 2027 }


    iqhip10LoggingMonitorLogANCTCState OBJECT-TYPE
        SYNTAX            INTEGER { disable(0), enable(1)  }
        MAX-ACCESS        read-write
        STATUS            current
        DESCRIPTION
                "CMNT: - 
                 TYPE: - Checkbox
                 PAGE: - Logging
                    Log ANC TC State  cmdID= 1092  "
        ::= { iqhip10CmdEntry 1092 }


    iqhip10LoggingMonitorANCTimecodeState OBJECT-TYPE
        SYNTAX            RollCallString
        MAX-ACCESS        read-only
        STATUS            current
        DESCRIPTION
                "CMNT: - 
                 TYPE: - Display
                 PAGE: - Logging
                    ANC Timecode State=  cmdID= 2092  "
        ::= { iqhip10CmdEntry 2092 }


    iqhip10LoggingMonitorLogTimecodeDiscon OBJECT-TYPE
        SYNTAX            INTEGER { disable(0), enable(1)  }
        MAX-ACCESS        read-write
        STATUS            current
        DESCRIPTION
                "CMNT: - 
                 TYPE: - Checkbox
                 PAGE: - Logging
                    Log Timecode Discon  cmdID= 1165  "
        ::= { iqhip10CmdEntry 1165 }


    iqhip10LoggingMonitorTimecodeDiscon OBJECT-TYPE
        SYNTAX            RollCallString
        MAX-ACCESS        read-only
        STATUS            current
        DESCRIPTION
                "CMNT: - 
                 TYPE: - Display
                 PAGE: - Logging
                    Timecode Discon=  cmdID= 2165  "
        ::= { iqhip10CmdEntry 2165 }


    iqhip10LoggingMonitorLogUser1DIDName OBJECT-TYPE
        SYNTAX            INTEGER { disable(0), enable(1)  }
        MAX-ACCESS        read-write
        STATUS            current
        DESCRIPTION
                "CMNT: - 
                 TYPE: - Checkbox
                 PAGE: - Logging
                    Log User 1 DID Name  cmdID= 1097  "
        ::= { iqhip10CmdEntry 1097 }


    iqhip10LoggingMonitorUser1DIDName OBJECT-TYPE
        SYNTAX            RollCallString
        MAX-ACCESS        read-only
        STATUS            current
        DESCRIPTION
                "CMNT: - 
                 TYPE: - Display
                 PAGE: - Logging
                    User 1 DID Name=  cmdID= 2097  "
        ::= { iqhip10CmdEntry 2097 }


    iqhip10LoggingMonitorLogUser1DIDState OBJECT-TYPE
        SYNTAX            INTEGER { disable(0), enable(1)  }
        MAX-ACCESS        read-write
        STATUS            current
        DESCRIPTION
                "CMNT: - 
                 TYPE: - Checkbox
                 PAGE: - Logging
                    Log User 1 DID State  cmdID= 1098  "
        ::= { iqhip10CmdEntry 1098 }


    iqhip10LoggingMonitorUser1DIDState OBJECT-TYPE
        SYNTAX            RollCallString
        MAX-ACCESS        read-only
        STATUS            current
        DESCRIPTION
                "CMNT: - 
                 TYPE: - Display
                 PAGE: - Logging
                    User 1 DID State=  cmdID= 2098  "
        ::= { iqhip10CmdEntry 2098 }


    iqhip10LoggingMonitorLogUser2DIDName OBJECT-TYPE
        SYNTAX            INTEGER { disable(0), enable(1)  }
        MAX-ACCESS        read-write
        STATUS            current
        DESCRIPTION
                "CMNT: - 
                 TYPE: - Checkbox
                 PAGE: - Logging
                    Log User 2 DID Name  cmdID= 1099  "
        ::= { iqhip10CmdEntry 1099 }


    iqhip10LoggingMonitorUser2DIDName OBJECT-TYPE
        SYNTAX            RollCallString
        MAX-ACCESS        read-only
        STATUS            current
        DESCRIPTION
                "CMNT: - 
                 TYPE: - Display
                 PAGE: - Logging
                    User 2 DID Name=  cmdID= 2099  "
        ::= { iqhip10CmdEntry 2099 }


    iqhip10LoggingMonitorLogUser2DIDState OBJECT-TYPE
        SYNTAX            INTEGER { disable(0), enable(1)  }
        MAX-ACCESS        read-write
        STATUS            current
        DESCRIPTION
                "CMNT: - 
                 TYPE: - Checkbox
                 PAGE: - Logging
                    Log User 2 DID State  cmdID= 1100  "
        ::= { iqhip10CmdEntry 1100 }


    iqhip10LoggingMonitorUser2DIDState OBJECT-TYPE
        SYNTAX            RollCallString
        MAX-ACCESS        read-only
        STATUS            current
        DESCRIPTION
                "CMNT: - 
                 TYPE: - Display
                 PAGE: - Logging
                    User 2 DID State=  cmdID= 2100  "
        ::= { iqhip10CmdEntry 2100 }


    iqhip10MonitorInp1WideScreenLogVIState OBJECT-TYPE
        SYNTAX            INTEGER { disable(0), enable(1)  }
        MAX-ACCESS        read-write
        STATUS            current
        DESCRIPTION
                "CMNT: - 
                 TYPE: - Checkbox
                 PAGE: - Monitor
                    Log VI State  cmdID= 1133  "
        ::= { iqhip10CmdEntry 1133 }


    iqhip10MonitorInp1WideScreenVIState OBJECT-TYPE
        SYNTAX            RollCallString
        MAX-ACCESS        read-only
        STATUS            current
        DESCRIPTION
                "CMNT: - 
                 TYPE: - Display
                 PAGE: - Monitor
                    VI State=  cmdID= 2133  "
        ::= { iqhip10CmdEntry 2133 }


    iqhip10MonitorInp1WideScreenLogVIAspect OBJECT-TYPE
        SYNTAX            INTEGER { disable(0), enable(1)  }
        MAX-ACCESS        read-write
        STATUS            current
        DESCRIPTION
                "CMNT: - 
                 TYPE: - Checkbox
                 PAGE: - Monitor
                    Log VI Aspect  cmdID= 1163  "
        ::= { iqhip10CmdEntry 1163 }


    iqhip10MonitorInp1WideScreenVIAspect OBJECT-TYPE
        SYNTAX            RollCallString
        MAX-ACCESS        read-only
        STATUS            current
        DESCRIPTION
                "CMNT: - 
                 TYPE: - Display
                 PAGE: - Monitor
                    VI Aspect=  cmdID= 2163  "
        ::= { iqhip10CmdEntry 2163 }


    iqhip10MonitorInp1WideScreenLogVI OBJECT-TYPE
        SYNTAX            INTEGER { disable(0), enable(1)  }
        MAX-ACCESS        read-write
        STATUS            current
        DESCRIPTION
                "CMNT: - 
                 TYPE: - Checkbox
                 PAGE: - Monitor
                    Log VI  cmdID= 1161  "
        ::= { iqhip10CmdEntry 1161 }


    iqhip10MonitorInp1WideScreenVI OBJECT-TYPE
        SYNTAX            RollCallString
        MAX-ACCESS        read-only
        STATUS            current
        DESCRIPTION
                "CMNT: - 
                 TYPE: - Display
                 PAGE: - Monitor
                    VI=  cmdID= 2161  "
        ::= { iqhip10CmdEntry 2161 }


    iqhip10MonitorInp1WideScreenLogWSSState OBJECT-TYPE
        SYNTAX            INTEGER { disable(0), enable(1)  }
        MAX-ACCESS        read-write
        STATUS            current
        DESCRIPTION
                "CMNT: - 
                 TYPE: - Checkbox
                 PAGE: - Monitor
                    Log WSS State  cmdID= 1132  "
        ::= { iqhip10CmdEntry 1132 }


    iqhip10MonitorInp1WideScreenWSSState OBJECT-TYPE
        SYNTAX            RollCallString
        MAX-ACCESS        read-only
        STATUS            current
        DESCRIPTION
                "CMNT: - 
                 TYPE: - Display
                 PAGE: - Monitor
                    WSS State=  cmdID= 2132  "
        ::= { iqhip10CmdEntry 2132 }


    iqhip10MonitorInp1WideScreenLogWSSAspect OBJECT-TYPE
        SYNTAX            INTEGER { disable(0), enable(1)  }
        MAX-ACCESS        read-write
        STATUS            current
        DESCRIPTION
                "CMNT: - 
                 TYPE: - Checkbox
                 PAGE: - Monitor
                    Log WSS Aspect  cmdID= 1162  "
        ::= { iqhip10CmdEntry 1162 }


    iqhip10MonitorInp1WideScreenWSSAspect OBJECT-TYPE
        SYNTAX            RollCallString
        MAX-ACCESS        read-only
        STATUS            current
        DESCRIPTION
                "CMNT: - 
                 TYPE: - Display
                 PAGE: - Monitor
                    WSS Aspect=  cmdID= 2162  "
        ::= { iqhip10CmdEntry 2162 }


    iqhip10MonitorInp1WideScreenLogWSS OBJECT-TYPE
        SYNTAX            INTEGER { disable(0), enable(1)  }
        MAX-ACCESS        read-write
        STATUS            current
        DESCRIPTION
                "CMNT: - 
                 TYPE: - Checkbox
                 PAGE: - Monitor
                    Log WSS  cmdID= 1160  "
        ::= { iqhip10CmdEntry 1160 }


    iqhip10MonitorInp1WideScreenWSS OBJECT-TYPE
        SYNTAX            RollCallString
        MAX-ACCESS        read-only
        STATUS            current
        DESCRIPTION
                "CMNT: - 
                 TYPE: - Display
                 PAGE: - Monitor
                    WSS=  cmdID= 2160  "
        ::= { iqhip10CmdEntry 2160 }


    iqhip10MonitorInp1WideScreenLogETSIData OBJECT-TYPE
        SYNTAX            INTEGER { disable(0), enable(1)  }
        MAX-ACCESS        read-write
        STATUS            current
        DESCRIPTION
                "CMNT: - 
                 TYPE: - Checkbox
                 PAGE: - Monitor
                    Log ETSI Data  cmdID= 1170  "
        ::= { iqhip10CmdEntry 1170 }


    iqhip10MonitorInp1WideScreenETSIData OBJECT-TYPE
        SYNTAX            RollCallString
        MAX-ACCESS        read-only
        STATUS            current
        DESCRIPTION
                "CMNT: - 
                 TYPE: - Display
                 PAGE: - Monitor
                    ETSI Data =  cmdID= 2170  "
        ::= { iqhip10CmdEntry 2170 }


    iqhip10MonitorInp1WideScreenLogAFD2016State OBJECT-TYPE
        SYNTAX            INTEGER { disable(0), enable(1)  }
        MAX-ACCESS        read-write
        STATUS            current
        DESCRIPTION
                "CMNT: - 
                 TYPE: - Checkbox
                 PAGE: - Monitor
                    Log AFD 2016 State  cmdID= 1167  "
        ::= { iqhip10CmdEntry 1167 }


    iqhip10MonitorInp1WideScreenAFD2016State OBJECT-TYPE
        SYNTAX            RollCallString
        MAX-ACCESS        read-only
        STATUS            current
        DESCRIPTION
                "CMNT: - 
                 TYPE: - Display
                 PAGE: - Monitor
                    AFD 2016 State=  cmdID= 2167  "
        ::= { iqhip10CmdEntry 2167 }


    iqhip10MonitorInp1WideScreenLogAFD2016Aspect OBJECT-TYPE
        SYNTAX            INTEGER { disable(0), enable(1)  }
        MAX-ACCESS        read-write
        STATUS            current
        DESCRIPTION
                "CMNT: - 
                 TYPE: - Checkbox
                 PAGE: - Monitor
                    Log AFD 2016 Aspect  cmdID= 1168  "
        ::= { iqhip10CmdEntry 1168 }


    iqhip10MonitorInp1WideScreenAFD2016Aspect OBJECT-TYPE
        SYNTAX            RollCallString
        MAX-ACCESS        read-only
        STATUS            current
        DESCRIPTION
                "CMNT: - 
                 TYPE: - Display
                 PAGE: - Monitor
                    AFD 2016 Aspect=  cmdID= 2168  "
        ::= { iqhip10CmdEntry 2168 }


    iqhip10MonitorInp1WideScreenLogAFD2016 OBJECT-TYPE
        SYNTAX            INTEGER { disable(0), enable(1)  }
        MAX-ACCESS        read-write
        STATUS            current
        DESCRIPTION
                "CMNT: - 
                 TYPE: - Checkbox
                 PAGE: - Monitor
                    Log AFD 2016  cmdID= 1169  "
        ::= { iqhip10CmdEntry 1169 }


    iqhip10MonitorInp1WideScreenAFD2016 OBJECT-TYPE
        SYNTAX            RollCallString
        MAX-ACCESS        read-only
        STATUS            current
        DESCRIPTION
                "CMNT: - 
                 TYPE: - Display
                 PAGE: - Monitor
                    AFD 2016=  cmdID= 2169  "
        ::= { iqhip10CmdEntry 2169 }


    iqhip10LoggingInp1AudStateLogEmbCh1State OBJECT-TYPE
        SYNTAX            INTEGER { disable(0), enable(1)  }
        MAX-ACCESS        read-write
        STATUS            current
        DESCRIPTION
                "CMNT: - 
                 TYPE: - Checkbox
                 PAGE: - Logging
                    Log Emb Ch 1 State  cmdID= 1028  "
        ::= { iqhip10CmdEntry 1028 }


    iqhip10LoggingInp1AudStateEmbCh1State OBJECT-TYPE
        SYNTAX            RollCallString
        MAX-ACCESS        read-only
        STATUS            current
        DESCRIPTION
                "CMNT: - 
                 TYPE: - Display
                 PAGE: - Logging
                    Emb Ch 1 State=  cmdID= 2028  "
        ::= { iqhip10CmdEntry 2028 }


    iqhip10LoggingInp1AudStateLogEmbCh2State OBJECT-TYPE
        SYNTAX            INTEGER { disable(0), enable(1)  }
        MAX-ACCESS        read-write
        STATUS            current
        DESCRIPTION
                "CMNT: - 
                 TYPE: - Checkbox
                 PAGE: - Logging
                    Log Emb Ch 2 State  cmdID= 1029  "
        ::= { iqhip10CmdEntry 1029 }


    iqhip10LoggingInp1AudStateEmbCh2State OBJECT-TYPE
        SYNTAX            RollCallString
        MAX-ACCESS        read-only
        STATUS            current
        DESCRIPTION
                "CMNT: - 
                 TYPE: - Display
                 PAGE: - Logging
                    Emb Ch 2 State=  cmdID= 2029  "
        ::= { iqhip10CmdEntry 2029 }


    iqhip10LoggingInp1AudStateLogEmbCh3State OBJECT-TYPE
        SYNTAX            INTEGER { disable(0), enable(1)  }
        MAX-ACCESS        read-write
        STATUS            current
        DESCRIPTION
                "CMNT: - 
                 TYPE: - Checkbox
                 PAGE: - Logging
                    Log Emb Ch 3 State  cmdID= 1030  "
        ::= { iqhip10CmdEntry 1030 }


    iqhip10LoggingInp1AudStateEmbCh3State OBJECT-TYPE
        SYNTAX            RollCallString
        MAX-ACCESS        read-only
        STATUS            current
        DESCRIPTION
                "CMNT: - 
                 TYPE: - Display
                 PAGE: - Logging
                    Emb Ch 3 State=  cmdID= 2030  "
        ::= { iqhip10CmdEntry 2030 }


    iqhip10LoggingInp1AudStateLogEmbCh4State OBJECT-TYPE
        SYNTAX            INTEGER { disable(0), enable(1)  }
        MAX-ACCESS        read-write
        STATUS            current
        DESCRIPTION
                "CMNT: - 
                 TYPE: - Checkbox
                 PAGE: - Logging
                    Log Emb Ch 4 State  cmdID= 1031  "
        ::= { iqhip10CmdEntry 1031 }


    iqhip10LoggingInp1AudStateEmbCh4State OBJECT-TYPE
        SYNTAX            RollCallString
        MAX-ACCESS        read-only
        STATUS            current
        DESCRIPTION
                "CMNT: - 
                 TYPE: - Display
                 PAGE: - Logging
                    Emb Ch 4 State=  cmdID= 2031  "
        ::= { iqhip10CmdEntry 2031 }


    iqhip10LoggingInp1AudStateLogEmbCh5State OBJECT-TYPE
        SYNTAX            INTEGER { disable(0), enable(1)  }
        MAX-ACCESS        read-write
        STATUS            current
        DESCRIPTION
                "CMNT: - 
                 TYPE: - Checkbox
                 PAGE: - Logging
                    Log Emb Ch 5 State  cmdID= 1032  "
        ::= { iqhip10CmdEntry 1032 }


    iqhip10LoggingInp1AudStateEmbCh5State OBJECT-TYPE
        SYNTAX            RollCallString
        MAX-ACCESS        read-only
        STATUS            current
        DESCRIPTION
                "CMNT: - 
                 TYPE: - Display
                 PAGE: - Logging
                    Emb Ch 5 State=  cmdID= 2032  "
        ::= { iqhip10CmdEntry 2032 }


    iqhip10LoggingInp1AudStateLogEmbCh6State OBJECT-TYPE
        SYNTAX            INTEGER { disable(0), enable(1)  }
        MAX-ACCESS        read-write
        STATUS            current
        DESCRIPTION
                "CMNT: - 
                 TYPE: - Checkbox
                 PAGE: - Logging
                    Log Emb Ch 6 State  cmdID= 1033  "
        ::= { iqhip10CmdEntry 1033 }


    iqhip10LoggingInp1AudStateEmbCh6State OBJECT-TYPE
        SYNTAX            RollCallString
        MAX-ACCESS        read-only
        STATUS            current
        DESCRIPTION
                "CMNT: - 
                 TYPE: - Display
                 PAGE: - Logging
                    Emb Ch 6 State=  cmdID= 2033  "
        ::= { iqhip10CmdEntry 2033 }


    iqhip10LoggingInp1AudStateLogEmbCh7State OBJECT-TYPE
        SYNTAX            INTEGER { disable(0), enable(1)  }
        MAX-ACCESS        read-write
        STATUS            current
        DESCRIPTION
                "CMNT: - 
                 TYPE: - Checkbox
                 PAGE: - Logging
                    Log Emb Ch 7 State  cmdID= 1034  "
        ::= { iqhip10CmdEntry 1034 }


    iqhip10LoggingInp1AudStateEmbCh7State OBJECT-TYPE
        SYNTAX            RollCallString
        MAX-ACCESS        read-only
        STATUS            current
        DESCRIPTION
                "CMNT: - 
                 TYPE: - Display
                 PAGE: - Logging
                    Emb Ch 7 State=  cmdID= 2034  "
        ::= { iqhip10CmdEntry 2034 }


    iqhip10LoggingInp1AudStateLogEmbCh8State OBJECT-TYPE
        SYNTAX            INTEGER { disable(0), enable(1)  }
        MAX-ACCESS        read-write
        STATUS            current
        DESCRIPTION
                "CMNT: - 
                 TYPE: - Checkbox
                 PAGE: - Logging
                    Log Emb Ch 8 State  cmdID= 1035  "
        ::= { iqhip10CmdEntry 1035 }


    iqhip10LoggingInp1AudStateEmbCh8State OBJECT-TYPE
        SYNTAX            RollCallString
        MAX-ACCESS        read-only
        STATUS            current
        DESCRIPTION
                "CMNT: - 
                 TYPE: - Display
                 PAGE: - Logging
                    Emb Ch 8 State=  cmdID= 2035  "
        ::= { iqhip10CmdEntry 2035 }


    iqhip10LoggingInp1AudStateLogEmbCh9State OBJECT-TYPE
        SYNTAX            INTEGER { disable(0), enable(1)  }
        MAX-ACCESS        read-write
        STATUS            current
        DESCRIPTION
                "CMNT: - 
                 TYPE: - Checkbox
                 PAGE: - Logging
                    Log Emb Ch 9 State  cmdID= 1036  "
        ::= { iqhip10CmdEntry 1036 }


    iqhip10LoggingInp1AudStateEmbCh9State OBJECT-TYPE
        SYNTAX            RollCallString
        MAX-ACCESS        read-only
        STATUS            current
        DESCRIPTION
                "CMNT: - 
                 TYPE: - Display
                 PAGE: - Logging
                    Emb Ch 9 State=  cmdID= 2036  "
        ::= { iqhip10CmdEntry 2036 }


    iqhip10LoggingInp1AudStateLogEmbCh10State OBJECT-TYPE
        SYNTAX            INTEGER { disable(0), enable(1)  }
        MAX-ACCESS        read-write
        STATUS            current
        DESCRIPTION
                "CMNT: - 
                 TYPE: - Checkbox
                 PAGE: - Logging
                    Log Emb Ch 10 State  cmdID= 1037  "
        ::= { iqhip10CmdEntry 1037 }


    iqhip10LoggingInp1AudStateEmbCh10State OBJECT-TYPE
        SYNTAX            RollCallString
        MAX-ACCESS        read-only
        STATUS            current
        DESCRIPTION
                "CMNT: - 
                 TYPE: - Display
                 PAGE: - Logging
                    Emb Ch 10 State=  cmdID= 2037  "
        ::= { iqhip10CmdEntry 2037 }


    iqhip10LoggingInp1AudStateLogEmbCh11State OBJECT-TYPE
        SYNTAX            INTEGER { disable(0), enable(1)  }
        MAX-ACCESS        read-write
        STATUS            current
        DESCRIPTION
                "CMNT: - 
                 TYPE: - Checkbox
                 PAGE: - Logging
                    Log Emb Ch 11 State  cmdID= 1038  "
        ::= { iqhip10CmdEntry 1038 }


    iqhip10LoggingInp1AudStateEmbCh11State OBJECT-TYPE
        SYNTAX            RollCallString
        MAX-ACCESS        read-only
        STATUS            current
        DESCRIPTION
                "CMNT: - 
                 TYPE: - Display
                 PAGE: - Logging
                    Emb Ch 11 State=  cmdID= 2038  "
        ::= { iqhip10CmdEntry 2038 }


    iqhip10LoggingInp1AudStateLogEmbCh12State OBJECT-TYPE
        SYNTAX            INTEGER { disable(0), enable(1)  }
        MAX-ACCESS        read-write
        STATUS            current
        DESCRIPTION
                "CMNT: - 
                 TYPE: - Checkbox
                 PAGE: - Logging
                    Log Emb Ch 12 State  cmdID= 1039  "
        ::= { iqhip10CmdEntry 1039 }


    iqhip10LoggingInp1AudStateEmbCh12State OBJECT-TYPE
        SYNTAX            RollCallString
        MAX-ACCESS        read-only
        STATUS            current
        DESCRIPTION
                "CMNT: - 
                 TYPE: - Display
                 PAGE: - Logging
                    Emb Ch 12 State=  cmdID= 2039  "
        ::= { iqhip10CmdEntry 2039 }


    iqhip10LoggingInp1AudStateLogEmbCh13State OBJECT-TYPE
        SYNTAX            INTEGER { disable(0), enable(1)  }
        MAX-ACCESS        read-write
        STATUS            current
        DESCRIPTION
                "CMNT: - 
                 TYPE: - Checkbox
                 PAGE: - Logging
                    Log Emb Ch 13 State  cmdID= 1040  "
        ::= { iqhip10CmdEntry 1040 }


    iqhip10LoggingInp1AudStateEmbCh13State OBJECT-TYPE
        SYNTAX            RollCallString
        MAX-ACCESS        read-only
        STATUS            current
        DESCRIPTION
                "CMNT: - 
                 TYPE: - Display
                 PAGE: - Logging
                    Emb Ch 13 State=  cmdID= 2040  "
        ::= { iqhip10CmdEntry 2040 }


    iqhip10LoggingInp1AudStateLogEmbCh14State OBJECT-TYPE
        SYNTAX            INTEGER { disable(0), enable(1)  }
        MAX-ACCESS        read-write
        STATUS            current
        DESCRIPTION
                "CMNT: - 
                 TYPE: - Checkbox
                 PAGE: - Logging
                    Log Emb Ch 14 State  cmdID= 1041  "
        ::= { iqhip10CmdEntry 1041 }


    iqhip10LoggingInp1AudStateEmbCh14State OBJECT-TYPE
        SYNTAX            RollCallString
        MAX-ACCESS        read-only
        STATUS            current
        DESCRIPTION
                "CMNT: - 
                 TYPE: - Display
                 PAGE: - Logging
                    Emb Ch 14 State=  cmdID= 2041  "
        ::= { iqhip10CmdEntry 2041 }


    iqhip10LoggingInp1AudStateLogEmbCh15State OBJECT-TYPE
        SYNTAX            INTEGER { disable(0), enable(1)  }
        MAX-ACCESS        read-write
        STATUS            current
        DESCRIPTION
                "CMNT: - 
                 TYPE: - Checkbox
                 PAGE: - Logging
                    Log Emb Ch 15 State  cmdID= 1042  "
        ::= { iqhip10CmdEntry 1042 }


    iqhip10LoggingInp1AudStateEmbCh15State OBJECT-TYPE
        SYNTAX            RollCallString
        MAX-ACCESS        read-only
        STATUS            current
        DESCRIPTION
                "CMNT: - 
                 TYPE: - Display
                 PAGE: - Logging
                    Emb Ch 15 State=  cmdID= 2042  "
        ::= { iqhip10CmdEntry 2042 }


    iqhip10LoggingInp1AudStateLogEmbCh16State OBJECT-TYPE
        SYNTAX            INTEGER { disable(0), enable(1)  }
        MAX-ACCESS        read-write
        STATUS            current
        DESCRIPTION
                "CMNT: - 
                 TYPE: - Checkbox
                 PAGE: - Logging
                    Log Emb Ch 16 State  cmdID= 1043  "
        ::= { iqhip10CmdEntry 1043 }


    iqhip10LoggingInp1AudStateEmbCh16State OBJECT-TYPE
        SYNTAX            RollCallString
        MAX-ACCESS        read-only
        STATUS            current
        DESCRIPTION
                "CMNT: - 
                 TYPE: - Display
                 PAGE: - Logging
                    Emb Ch 16 State=  cmdID= 2043  "
        ::= { iqhip10CmdEntry 2043 }


    iqhip10LoggingInp1AudTypeLogEmbCh1Type OBJECT-TYPE
        SYNTAX            INTEGER { disable(0), enable(1)  }
        MAX-ACCESS        read-write
        STATUS            current
        DESCRIPTION
                "CMNT: - 
                 TYPE: - Checkbox
                 PAGE: - Logging
                    Log Emb Ch 1 Type  cmdID= 1044  "
        ::= { iqhip10CmdEntry 1044 }


    iqhip10LoggingInp1AudTypeEmbCh1Type OBJECT-TYPE
        SYNTAX            RollCallString
        MAX-ACCESS        read-only
        STATUS            current
        DESCRIPTION
                "CMNT: - 
                 TYPE: - Display
                 PAGE: - Logging
                    Emb Ch 1 Type=  cmdID= 2044  "
        ::= { iqhip10CmdEntry 2044 }


    iqhip10LoggingInp1AudTypeLogEmbCh2Type OBJECT-TYPE
        SYNTAX            INTEGER { disable(0), enable(1)  }
        MAX-ACCESS        read-write
        STATUS            current
        DESCRIPTION
                "CMNT: - 
                 TYPE: - Checkbox
                 PAGE: - Logging
                    Log Emb Ch 2 Type  cmdID= 1045  "
        ::= { iqhip10CmdEntry 1045 }


    iqhip10LoggingInp1AudTypeEmbCh2Type OBJECT-TYPE
        SYNTAX            RollCallString
        MAX-ACCESS        read-only
        STATUS            current
        DESCRIPTION
                "CMNT: - 
                 TYPE: - Display
                 PAGE: - Logging
                    Emb Ch 2 Type=  cmdID= 2045  "
        ::= { iqhip10CmdEntry 2045 }


    iqhip10LoggingInp1AudTypeLogEmbCh3Type OBJECT-TYPE
        SYNTAX            INTEGER { disable(0), enable(1)  }
        MAX-ACCESS        read-write
        STATUS            current
        DESCRIPTION
                "CMNT: - 
                 TYPE: - Checkbox
                 PAGE: - Logging
                    Log Emb Ch 3 Type  cmdID= 1046  "
        ::= { iqhip10CmdEntry 1046 }


    iqhip10LoggingInp1AudTypeEmbCh3Type OBJECT-TYPE
        SYNTAX            RollCallString
        MAX-ACCESS        read-only
        STATUS            current
        DESCRIPTION
                "CMNT: - 
                 TYPE: - Display
                 PAGE: - Logging
                    Emb Ch 3 Type=  cmdID= 2046  "
        ::= { iqhip10CmdEntry 2046 }


    iqhip10LoggingInp1AudTypeLogEmbCh4Type OBJECT-TYPE
        SYNTAX            INTEGER { disable(0), enable(1)  }
        MAX-ACCESS        read-write
        STATUS            current
        DESCRIPTION
                "CMNT: - 
                 TYPE: - Checkbox
                 PAGE: - Logging
                    Log Emb Ch 4 Type  cmdID= 1047  "
        ::= { iqhip10CmdEntry 1047 }


    iqhip10LoggingInp1AudTypeEmbCh4Type OBJECT-TYPE
        SYNTAX            RollCallString
        MAX-ACCESS        read-only
        STATUS            current
        DESCRIPTION
                "CMNT: - 
                 TYPE: - Display
                 PAGE: - Logging
                    Emb Ch 4 Type=  cmdID= 2047  "
        ::= { iqhip10CmdEntry 2047 }


    iqhip10LoggingInp1AudTypeLogEmbCh5Type OBJECT-TYPE
        SYNTAX            INTEGER { disable(0), enable(1)  }
        MAX-ACCESS        read-write
        STATUS            current
        DESCRIPTION
                "CMNT: - 
                 TYPE: - Checkbox
                 PAGE: - Logging
                    Log Emb Ch 5 Type  cmdID= 1048  "
        ::= { iqhip10CmdEntry 1048 }


    iqhip10LoggingInp1AudTypeEmbCh5Type OBJECT-TYPE
        SYNTAX            RollCallString
        MAX-ACCESS        read-only
        STATUS            current
        DESCRIPTION
                "CMNT: - 
                 TYPE: - Display
                 PAGE: - Logging
                    Emb Ch 5 Type=  cmdID= 2048  "
        ::= { iqhip10CmdEntry 2048 }


    iqhip10LoggingInp1AudTypeLogEmbCh6Type OBJECT-TYPE
        SYNTAX            INTEGER { disable(0), enable(1)  }
        MAX-ACCESS        read-write
        STATUS            current
        DESCRIPTION
                "CMNT: - 
                 TYPE: - Checkbox
                 PAGE: - Logging
                    Log Emb Ch 6 Type  cmdID= 1049  "
        ::= { iqhip10CmdEntry 1049 }


    iqhip10LoggingInp1AudTypeEmbCh6Type OBJECT-TYPE
        SYNTAX            RollCallString
        MAX-ACCESS        read-only
        STATUS            current
        DESCRIPTION
                "CMNT: - 
                 TYPE: - Display
                 PAGE: - Logging
                    Emb Ch 6 Type=  cmdID= 2049  "
        ::= { iqhip10CmdEntry 2049 }


    iqhip10LoggingInp1AudTypeLogEmbCh7Type OBJECT-TYPE
        SYNTAX            INTEGER { disable(0), enable(1)  }
        MAX-ACCESS        read-write
        STATUS            current
        DESCRIPTION
                "CMNT: - 
                 TYPE: - Checkbox
                 PAGE: - Logging
                    Log Emb Ch 7 Type  cmdID= 1050  "
        ::= { iqhip10CmdEntry 1050 }


    iqhip10LoggingInp1AudTypeEmbCh7Type OBJECT-TYPE
        SYNTAX            RollCallString
        MAX-ACCESS        read-only
        STATUS            current
        DESCRIPTION
                "CMNT: - 
                 TYPE: - Display
                 PAGE: - Logging
                    Emb Ch 7 Type=  cmdID= 2050  "
        ::= { iqhip10CmdEntry 2050 }


    iqhip10LoggingInp1AudTypeLogEmbCh8Type OBJECT-TYPE
        SYNTAX            INTEGER { disable(0), enable(1)  }
        MAX-ACCESS        read-write
        STATUS            current
        DESCRIPTION
                "CMNT: - 
                 TYPE: - Checkbox
                 PAGE: - Logging
                    Log Emb Ch 8 Type  cmdID= 1051  "
        ::= { iqhip10CmdEntry 1051 }


    iqhip10LoggingInp1AudTypeEmbCh8Type OBJECT-TYPE
        SYNTAX            RollCallString
        MAX-ACCESS        read-only
        STATUS            current
        DESCRIPTION
                "CMNT: - 
                 TYPE: - Display
                 PAGE: - Logging
                    Emb Ch 8 Type=  cmdID= 2051  "
        ::= { iqhip10CmdEntry 2051 }


    iqhip10LoggingInp1AudTypeLogEmbCh9Type OBJECT-TYPE
        SYNTAX            INTEGER { disable(0), enable(1)  }
        MAX-ACCESS        read-write
        STATUS            current
        DESCRIPTION
                "CMNT: - 
                 TYPE: - Checkbox
                 PAGE: - Logging
                    Log Emb Ch 9 Type  cmdID= 1052  "
        ::= { iqhip10CmdEntry 1052 }


    iqhip10LoggingInp1AudTypeEmbCh9Type OBJECT-TYPE
        SYNTAX            RollCallString
        MAX-ACCESS        read-only
        STATUS            current
        DESCRIPTION
                "CMNT: - 
                 TYPE: - Display
                 PAGE: - Logging
                    Emb Ch 9 Type=  cmdID= 2052  "
        ::= { iqhip10CmdEntry 2052 }


    iqhip10LoggingInp1AudTypeLogEmbCh10Type OBJECT-TYPE
        SYNTAX            INTEGER { disable(0), enable(1)  }
        MAX-ACCESS        read-write
        STATUS            current
        DESCRIPTION
                "CMNT: - 
                 TYPE: - Checkbox
                 PAGE: - Logging
                    Log Emb Ch 10 Type  cmdID= 1053  "
        ::= { iqhip10CmdEntry 1053 }


    iqhip10LoggingInp1AudTypeEmbCh10Type OBJECT-TYPE
        SYNTAX            RollCallString
        MAX-ACCESS        read-only
        STATUS            current
        DESCRIPTION
                "CMNT: - 
                 TYPE: - Display
                 PAGE: - Logging
                    Emb Ch 10 Type=  cmdID= 2053  "
        ::= { iqhip10CmdEntry 2053 }


    iqhip10LoggingInp1AudTypeLogEmbCh11Type OBJECT-TYPE
        SYNTAX            INTEGER { disable(0), enable(1)  }
        MAX-ACCESS        read-write
        STATUS            current
        DESCRIPTION
                "CMNT: - 
                 TYPE: - Checkbox
                 PAGE: - Logging
                    Log Emb Ch 11 Type  cmdID= 1054  "
        ::= { iqhip10CmdEntry 1054 }


    iqhip10LoggingInp1AudTypeEmbCh11Type OBJECT-TYPE
        SYNTAX            RollCallString
        MAX-ACCESS        read-only
        STATUS            current
        DESCRIPTION
                "CMNT: - 
                 TYPE: - Display
                 PAGE: - Logging
                    Emb Ch 11 Type=  cmdID= 2054  "
        ::= { iqhip10CmdEntry 2054 }


    iqhip10LoggingInp1AudTypeLogEmbCh12Type OBJECT-TYPE
        SYNTAX            INTEGER { disable(0), enable(1)  }
        MAX-ACCESS        read-write
        STATUS            current
        DESCRIPTION
                "CMNT: - 
                 TYPE: - Checkbox
                 PAGE: - Logging
                    Log Emb Ch 12 Type  cmdID= 1055  "
        ::= { iqhip10CmdEntry 1055 }


    iqhip10LoggingInp1AudTypeEmbCh12Type OBJECT-TYPE
        SYNTAX            RollCallString
        MAX-ACCESS        read-only
        STATUS            current
        DESCRIPTION
                "CMNT: - 
                 TYPE: - Display
                 PAGE: - Logging
                    Emb Ch 12 Type=  cmdID= 2055  "
        ::= { iqhip10CmdEntry 2055 }


    iqhip10LoggingInp1AudTypeLogEmbCh13Type OBJECT-TYPE
        SYNTAX            INTEGER { disable(0), enable(1)  }
        MAX-ACCESS        read-write
        STATUS            current
        DESCRIPTION
                "CMNT: - 
                 TYPE: - Checkbox
                 PAGE: - Logging
                    Log Emb Ch 13 Type  cmdID= 1056  "
        ::= { iqhip10CmdEntry 1056 }


    iqhip10LoggingInp1AudTypeEmbCh13Type OBJECT-TYPE
        SYNTAX            RollCallString
        MAX-ACCESS        read-only
        STATUS            current
        DESCRIPTION
                "CMNT: - 
                 TYPE: - Display
                 PAGE: - Logging
                    Emb Ch 13 Type=  cmdID= 2056  "
        ::= { iqhip10CmdEntry 2056 }


    iqhip10LoggingInp1AudTypeLogEmbCh14Type OBJECT-TYPE
        SYNTAX            INTEGER { disable(0), enable(1)  }
        MAX-ACCESS        read-write
        STATUS            current
        DESCRIPTION
                "CMNT: - 
                 TYPE: - Checkbox
                 PAGE: - Logging
                    Log Emb Ch 14 Type  cmdID= 1057  "
        ::= { iqhip10CmdEntry 1057 }


    iqhip10LoggingInp1AudTypeEmbCh14Type OBJECT-TYPE
        SYNTAX            RollCallString
        MAX-ACCESS        read-only
        STATUS            current
        DESCRIPTION
                "CMNT: - 
                 TYPE: - Display
                 PAGE: - Logging
                    Emb Ch 14 Type=  cmdID= 2057  "
        ::= { iqhip10CmdEntry 2057 }


    iqhip10LoggingInp1AudTypeLogEmbCh15Type OBJECT-TYPE
        SYNTAX            INTEGER { disable(0), enable(1)  }
        MAX-ACCESS        read-write
        STATUS            current
        DESCRIPTION
                "CMNT: - 
                 TYPE: - Checkbox
                 PAGE: - Logging
                    Log Emb Ch 15 Type  cmdID= 1058  "
        ::= { iqhip10CmdEntry 1058 }


    iqhip10LoggingInp1AudTypeEmbCh15Type OBJECT-TYPE
        SYNTAX            RollCallString
        MAX-ACCESS        read-only
        STATUS            current
        DESCRIPTION
                "CMNT: - 
                 TYPE: - Display
                 PAGE: - Logging
                    Emb Ch 15 Type=  cmdID= 2058  "
        ::= { iqhip10CmdEntry 2058 }


    iqhip10LoggingInp1AudTypeLogEmbCh16Type OBJECT-TYPE
        SYNTAX            INTEGER { disable(0), enable(1)  }
        MAX-ACCESS        read-write
        STATUS            current
        DESCRIPTION
                "CMNT: - 
                 TYPE: - Checkbox
                 PAGE: - Logging
                    Log Emb Ch 16 Type  cmdID= 1059  "
        ::= { iqhip10CmdEntry 1059 }


    iqhip10LoggingInp1AudTypeEmbCh16Type OBJECT-TYPE
        SYNTAX            RollCallString
        MAX-ACCESS        read-only
        STATUS            current
        DESCRIPTION
                "CMNT: - 
                 TYPE: - Display
                 PAGE: - Logging
                    Emb Ch 16 Type=  cmdID= 2059  "
        ::= { iqhip10CmdEntry 2059 }


    iqhip10LoggingInp1DolbyEStateLogPair1 OBJECT-TYPE
        SYNTAX            INTEGER { disable(0), enable(1)  }
        MAX-ACCESS        read-write
        STATUS            current
        DESCRIPTION
                "CMNT: - 
                 TYPE: - Checkbox
                 PAGE: - Logging
                    Log Pair 1  cmdID= 1150  "
        ::= { iqhip10CmdEntry 1150 }


    iqhip10LoggingInp1DolbyEStatePair1State OBJECT-TYPE
        SYNTAX            RollCallString
        MAX-ACCESS        read-only
        STATUS            current
        DESCRIPTION
                "CMNT: - 
                 TYPE: - Display
                 PAGE: - Logging
                    Pair 1 State=  cmdID= 2150  "
        ::= { iqhip10CmdEntry 2150 }


    iqhip10LoggingInp1DolbyEStateLogPair2 OBJECT-TYPE
        SYNTAX            INTEGER { disable(0), enable(1)  }
        MAX-ACCESS        read-write
        STATUS            current
        DESCRIPTION
                "CMNT: - 
                 TYPE: - Checkbox
                 PAGE: - Logging
                    Log Pair 2  cmdID= 1151  "
        ::= { iqhip10CmdEntry 1151 }


    iqhip10LoggingInp1DolbyEStatePair2State OBJECT-TYPE
        SYNTAX            RollCallString
        MAX-ACCESS        read-only
        STATUS            current
        DESCRIPTION
                "CMNT: - 
                 TYPE: - Display
                 PAGE: - Logging
                    Pair 2 State=  cmdID= 2151  "
        ::= { iqhip10CmdEntry 2151 }


    iqhip10LoggingInp1DolbyEStateLogPair3 OBJECT-TYPE
        SYNTAX            INTEGER { disable(0), enable(1)  }
        MAX-ACCESS        read-write
        STATUS            current
        DESCRIPTION
                "CMNT: - 
                 TYPE: - Checkbox
                 PAGE: - Logging
                    Log Pair 3  cmdID= 1152  "
        ::= { iqhip10CmdEntry 1152 }


    iqhip10LoggingInp1DolbyEStatePair3State OBJECT-TYPE
        SYNTAX            RollCallString
        MAX-ACCESS        read-only
        STATUS            current
        DESCRIPTION
                "CMNT: - 
                 TYPE: - Display
                 PAGE: - Logging
                    Pair 3 State=  cmdID= 2152  "
        ::= { iqhip10CmdEntry 2152 }


    iqhip10LoggingInp1DolbyEStateLogPair4 OBJECT-TYPE
        SYNTAX            INTEGER { disable(0), enable(1)  }
        MAX-ACCESS        read-write
        STATUS            current
        DESCRIPTION
                "CMNT: - 
                 TYPE: - Checkbox
                 PAGE: - Logging
                    Log Pair 4  cmdID= 1153  "
        ::= { iqhip10CmdEntry 1153 }


    iqhip10LoggingInp1DolbyEStatePair4State OBJECT-TYPE
        SYNTAX            RollCallString
        MAX-ACCESS        read-only
        STATUS            current
        DESCRIPTION
                "CMNT: - 
                 TYPE: - Display
                 PAGE: - Logging
                    Pair 4 State=  cmdID= 2153  "
        ::= { iqhip10CmdEntry 2153 }


    iqhip10LoggingInp1DolbyEStateLogPair5 OBJECT-TYPE
        SYNTAX            INTEGER { disable(0), enable(1)  }
        MAX-ACCESS        read-write
        STATUS            current
        DESCRIPTION
                "CMNT: - 
                 TYPE: - Checkbox
                 PAGE: - Logging
                    Log Pair 5  cmdID= 1154  "
        ::= { iqhip10CmdEntry 1154 }


    iqhip10LoggingInp1DolbyEStatePair5State OBJECT-TYPE
        SYNTAX            RollCallString
        MAX-ACCESS        read-only
        STATUS            current
        DESCRIPTION
                "CMNT: - 
                 TYPE: - Display
                 PAGE: - Logging
                    Pair 5 State=  cmdID= 2154  "
        ::= { iqhip10CmdEntry 2154 }


    iqhip10LoggingInp1DolbyEStateLogPair6 OBJECT-TYPE
        SYNTAX            INTEGER { disable(0), enable(1)  }
        MAX-ACCESS        read-write
        STATUS            current
        DESCRIPTION
                "CMNT: - 
                 TYPE: - Checkbox
                 PAGE: - Logging
                    Log Pair 6  cmdID= 1155  "
        ::= { iqhip10CmdEntry 1155 }


    iqhip10LoggingInp1DolbyEStatePair6State OBJECT-TYPE
        SYNTAX            RollCallString
        MAX-ACCESS        read-only
        STATUS            current
        DESCRIPTION
                "CMNT: - 
                 TYPE: - Display
                 PAGE: - Logging
                    Pair 6 State=  cmdID= 2155  "
        ::= { iqhip10CmdEntry 2155 }


    iqhip10LoggingInp1DolbyEStateLogPair7 OBJECT-TYPE
        SYNTAX            INTEGER { disable(0), enable(1)  }
        MAX-ACCESS        read-write
        STATUS            current
        DESCRIPTION
                "CMNT: - 
                 TYPE: - Checkbox
                 PAGE: - Logging
                    Log Pair 7  cmdID= 1156  "
        ::= { iqhip10CmdEntry 1156 }


    iqhip10LoggingInp1DolbyEStatePair7State OBJECT-TYPE
        SYNTAX            RollCallString
        MAX-ACCESS        read-only
        STATUS            current
        DESCRIPTION
                "CMNT: - 
                 TYPE: - Display
                 PAGE: - Logging
                    Pair 7 State=  cmdID= 2156  "
        ::= { iqhip10CmdEntry 2156 }


    iqhip10LoggingInp1DolbyEStateLogPair8 OBJECT-TYPE
        SYNTAX            INTEGER { disable(0), enable(1)  }
        MAX-ACCESS        read-write
        STATUS            current
        DESCRIPTION
                "CMNT: - 
                 TYPE: - Checkbox
                 PAGE: - Logging
                    Log Pair 8  cmdID= 1157  "
        ::= { iqhip10CmdEntry 1157 }


    iqhip10LoggingInp1DolbyEStatePair8State OBJECT-TYPE
        SYNTAX            RollCallString
        MAX-ACCESS        read-only
        STATUS            current
        DESCRIPTION
                "CMNT: - 
                 TYPE: - Display
                 PAGE: - Logging
                    Pair 8 State=  cmdID= 2157  "
        ::= { iqhip10CmdEntry 2157 }


    iqhip10LoggingInp1BitDepthLogEmbCh1BitDepth OBJECT-TYPE
        SYNTAX            INTEGER { disable(0), enable(1)  }
        MAX-ACCESS        read-write
        STATUS            current
        DESCRIPTION
                "CMNT: - 
                 TYPE: - Checkbox
                 PAGE: - Logging
                    Log Emb Ch 1 Bit Depth  cmdID= 1060  "
        ::= { iqhip10CmdEntry 1060 }


    iqhip10LoggingInp1BitDepthEmbCh1BitDepth OBJECT-TYPE
        SYNTAX            RollCallString
        MAX-ACCESS        read-only
        STATUS            current
        DESCRIPTION
                "CMNT: - 
                 TYPE: - Display
                 PAGE: - Logging
                    Emb Ch 1 Bit Depth=  cmdID= 2060  "
        ::= { iqhip10CmdEntry 2060 }


    iqhip10LoggingInp1BitDepthLogEmbCh2BitDepth OBJECT-TYPE
        SYNTAX            INTEGER { disable(0), enable(1)  }
        MAX-ACCESS        read-write
        STATUS            current
        DESCRIPTION
                "CMNT: - 
                 TYPE: - Checkbox
                 PAGE: - Logging
                    Log Emb Ch 2 Bit Depth  cmdID= 1061  "
        ::= { iqhip10CmdEntry 1061 }


    iqhip10LoggingInp1BitDepthEmbCh2BitDepth OBJECT-TYPE
        SYNTAX            RollCallString
        MAX-ACCESS        read-only
        STATUS            current
        DESCRIPTION
                "CMNT: - 
                 TYPE: - Display
                 PAGE: - Logging
                    Emb Ch 2 Bit Depth=  cmdID= 2061  "
        ::= { iqhip10CmdEntry 2061 }


    iqhip10LoggingInp1BitDepthLogEmbCh3BitDepth OBJECT-TYPE
        SYNTAX            INTEGER { disable(0), enable(1)  }
        MAX-ACCESS        read-write
        STATUS            current
        DESCRIPTION
                "CMNT: - 
                 TYPE: - Checkbox
                 PAGE: - Logging
                    Log Emb Ch 3 Bit Depth  cmdID= 1062  "
        ::= { iqhip10CmdEntry 1062 }


    iqhip10LoggingInp1BitDepthEmbCh3BitDepth OBJECT-TYPE
        SYNTAX            RollCallString
        MAX-ACCESS        read-only
        STATUS            current
        DESCRIPTION
                "CMNT: - 
                 TYPE: - Display
                 PAGE: - Logging
                    Emb Ch 3 Bit Depth=  cmdID= 2062  "
        ::= { iqhip10CmdEntry 2062 }


    iqhip10LoggingInp1BitDepthLogEmbCh4BitDepth OBJECT-TYPE
        SYNTAX            INTEGER { disable(0), enable(1)  }
        MAX-ACCESS        read-write
        STATUS            current
        DESCRIPTION
                "CMNT: - 
                 TYPE: - Checkbox
                 PAGE: - Logging
                    Log Emb Ch 4 Bit Depth  cmdID= 1063  "
        ::= { iqhip10CmdEntry 1063 }


    iqhip10LoggingInp1BitDepthEmbCh4BitDepth OBJECT-TYPE
        SYNTAX            RollCallString
        MAX-ACCESS        read-only
        STATUS            current
        DESCRIPTION
                "CMNT: - 
                 TYPE: - Display
                 PAGE: - Logging
                    Emb Ch 4 Bit Depth=  cmdID= 2063  "
        ::= { iqhip10CmdEntry 2063 }


    iqhip10LoggingInp1BitDepthLogEmbCh5BitDepth OBJECT-TYPE
        SYNTAX            INTEGER { disable(0), enable(1)  }
        MAX-ACCESS        read-write
        STATUS            current
        DESCRIPTION
                "CMNT: - 
                 TYPE: - Checkbox
                 PAGE: - Logging
                    Log Emb Ch 5 Bit Depth  cmdID= 1064  "
        ::= { iqhip10CmdEntry 1064 }


    iqhip10LoggingInp1BitDepthEmbCh5BitDepth OBJECT-TYPE
        SYNTAX            RollCallString
        MAX-ACCESS        read-only
        STATUS            current
        DESCRIPTION
                "CMNT: - 
                 TYPE: - Display
                 PAGE: - Logging
                    Emb Ch 5 Bit Depth=  cmdID= 2064  "
        ::= { iqhip10CmdEntry 2064 }


    iqhip10LoggingInp1BitDepthLogEmbCh6BitDepth OBJECT-TYPE
        SYNTAX            INTEGER { disable(0), enable(1)  }
        MAX-ACCESS        read-write
        STATUS            current
        DESCRIPTION
                "CMNT: - 
                 TYPE: - Checkbox
                 PAGE: - Logging
                    Log Emb Ch 6 Bit Depth  cmdID= 1065  "
        ::= { iqhip10CmdEntry 1065 }


    iqhip10LoggingInp1BitDepthEmbCh6BitDepth OBJECT-TYPE
        SYNTAX            RollCallString
        MAX-ACCESS        read-only
        STATUS            current
        DESCRIPTION
                "CMNT: - 
                 TYPE: - Display
                 PAGE: - Logging
                    Emb Ch 6 Bit Depth=  cmdID= 2065  "
        ::= { iqhip10CmdEntry 2065 }


    iqhip10LoggingInp1BitDepthLogEmbCh7BitDepth OBJECT-TYPE
        SYNTAX            INTEGER { disable(0), enable(1)  }
        MAX-ACCESS        read-write
        STATUS            current
        DESCRIPTION
                "CMNT: - 
                 TYPE: - Checkbox
                 PAGE: - Logging
                    Log Emb Ch 7 Bit Depth  cmdID= 1066  "
        ::= { iqhip10CmdEntry 1066 }


    iqhip10LoggingInp1BitDepthEmbCh7BitDepth OBJECT-TYPE
        SYNTAX            RollCallString
        MAX-ACCESS        read-only
        STATUS            current
        DESCRIPTION
                "CMNT: - 
                 TYPE: - Display
                 PAGE: - Logging
                    Emb Ch 7 Bit Depth=  cmdID= 2066  "
        ::= { iqhip10CmdEntry 2066 }


    iqhip10LoggingInp1BitDepthLogEmbCh8BitDepth OBJECT-TYPE
        SYNTAX            INTEGER { disable(0), enable(1)  }
        MAX-ACCESS        read-write
        STATUS            current
        DESCRIPTION
                "CMNT: - 
                 TYPE: - Checkbox
                 PAGE: - Logging
                    Log Emb Ch 8 Bit Depth  cmdID= 1067  "
        ::= { iqhip10CmdEntry 1067 }


    iqhip10LoggingInp1BitDepthEmbCh8BitDepth OBJECT-TYPE
        SYNTAX            RollCallString
        MAX-ACCESS        read-only
        STATUS            current
        DESCRIPTION
                "CMNT: - 
                 TYPE: - Display
                 PAGE: - Logging
                    Emb Ch 8 Bit Depth=  cmdID= 2067  "
        ::= { iqhip10CmdEntry 2067 }


    iqhip10LoggingInp1BitDepthLogEmbCh9BitDepth OBJECT-TYPE
        SYNTAX            INTEGER { disable(0), enable(1)  }
        MAX-ACCESS        read-write
        STATUS            current
        DESCRIPTION
                "CMNT: - 
                 TYPE: - Checkbox
                 PAGE: - Logging
                    Log Emb Ch 9 Bit Depth  cmdID= 1068  "
        ::= { iqhip10CmdEntry 1068 }


    iqhip10LoggingInp1BitDepthEmbCh9BitDepth OBJECT-TYPE
        SYNTAX            RollCallString
        MAX-ACCESS        read-only
        STATUS            current
        DESCRIPTION
                "CMNT: - 
                 TYPE: - Display
                 PAGE: - Logging
                    Emb Ch 9 Bit Depth=  cmdID= 2068  "
        ::= { iqhip10CmdEntry 2068 }


    iqhip10LoggingInp1BitDepthLogEmbCh10BitDepth OBJECT-TYPE
        SYNTAX            INTEGER { disable(0), enable(1)  }
        MAX-ACCESS        read-write
        STATUS            current
        DESCRIPTION
                "CMNT: - 
                 TYPE: - Checkbox
                 PAGE: - Logging
                    Log Emb Ch 10 Bit Depth  cmdID= 1069  "
        ::= { iqhip10CmdEntry 1069 }


    iqhip10LoggingInp1BitDepthEmbCh10BitDep OBJECT-TYPE
        SYNTAX            RollCallString
        MAX-ACCESS        read-only
        STATUS            current
        DESCRIPTION
                "CMNT: - 
                 TYPE: - Display
                 PAGE: - Logging
                    Emb Ch 10 Bit Dep=  cmdID= 2069  "
        ::= { iqhip10CmdEntry 2069 }


    iqhip10LoggingInp1BitDepthLogEmbCh11BitDepth OBJECT-TYPE
        SYNTAX            INTEGER { disable(0), enable(1)  }
        MAX-ACCESS        read-write
        STATUS            current
        DESCRIPTION
                "CMNT: - 
                 TYPE: - Checkbox
                 PAGE: - Logging
                    Log Emb Ch 11 Bit Depth  cmdID= 1070  "
        ::= { iqhip10CmdEntry 1070 }


    iqhip10LoggingInp1BitDepthEmbCh11BitDep OBJECT-TYPE
        SYNTAX            RollCallString
        MAX-ACCESS        read-only
        STATUS            current
        DESCRIPTION
                "CMNT: - 
                 TYPE: - Display
                 PAGE: - Logging
                    Emb Ch 11 Bit Dep=  cmdID= 2070  "
        ::= { iqhip10CmdEntry 2070 }


    iqhip10LoggingInp1BitDepthLogEmbCh12BitDepth OBJECT-TYPE
        SYNTAX            INTEGER { disable(0), enable(1)  }
        MAX-ACCESS        read-write
        STATUS            current
        DESCRIPTION
                "CMNT: - 
                 TYPE: - Checkbox
                 PAGE: - Logging
                    Log Emb Ch 12 Bit Depth  cmdID= 1071  "
        ::= { iqhip10CmdEntry 1071 }


    iqhip10LoggingInp1BitDepthEmbCh12BitDep OBJECT-TYPE
        SYNTAX            RollCallString
        MAX-ACCESS        read-only
        STATUS            current
        DESCRIPTION
                "CMNT: - 
                 TYPE: - Display
                 PAGE: - Logging
                    Emb Ch 12 Bit Dep=  cmdID= 2071  "
        ::= { iqhip10CmdEntry 2071 }


    iqhip10LoggingInp1BitDepthLogEmbCh13BitDepth OBJECT-TYPE
        SYNTAX            INTEGER { disable(0), enable(1)  }
        MAX-ACCESS        read-write
        STATUS            current
        DESCRIPTION
                "CMNT: - 
                 TYPE: - Checkbox
                 PAGE: - Logging
                    Log Emb Ch 13 Bit Depth  cmdID= 1072  "
        ::= { iqhip10CmdEntry 1072 }


    iqhip10LoggingInp1BitDepthEmbCh13BitDep OBJECT-TYPE
        SYNTAX            RollCallString
        MAX-ACCESS        read-only
        STATUS            current
        DESCRIPTION
                "CMNT: - 
                 TYPE: - Display
                 PAGE: - Logging
                    Emb Ch 13 Bit Dep=  cmdID= 2072  "
        ::= { iqhip10CmdEntry 2072 }


    iqhip10LoggingInp1BitDepthLogEmbCh14BitDepth OBJECT-TYPE
        SYNTAX            INTEGER { disable(0), enable(1)  }
        MAX-ACCESS        read-write
        STATUS            current
        DESCRIPTION
                "CMNT: - 
                 TYPE: - Checkbox
                 PAGE: - Logging
                    Log Emb Ch 14 Bit Depth  cmdID= 1073  "
        ::= { iqhip10CmdEntry 1073 }


    iqhip10LoggingInp1BitDepthEmbCh14BitDep OBJECT-TYPE
        SYNTAX            RollCallString
        MAX-ACCESS        read-only
        STATUS            current
        DESCRIPTION
                "CMNT: - 
                 TYPE: - Display
                 PAGE: - Logging
                    Emb Ch 14 Bit Dep=  cmdID= 2073  "
        ::= { iqhip10CmdEntry 2073 }


    iqhip10LoggingInp1BitDepthLogEmbCh15BitDepth OBJECT-TYPE
        SYNTAX            INTEGER { disable(0), enable(1)  }
        MAX-ACCESS        read-write
        STATUS            current
        DESCRIPTION
                "CMNT: - 
                 TYPE: - Checkbox
                 PAGE: - Logging
                    Log Emb Ch 15 Bit Depth  cmdID= 1074  "
        ::= { iqhip10CmdEntry 1074 }


    iqhip10LoggingInp1BitDepthEmbCh15BitDep OBJECT-TYPE
        SYNTAX            RollCallString
        MAX-ACCESS        read-only
        STATUS            current
        DESCRIPTION
                "CMNT: - 
                 TYPE: - Display
                 PAGE: - Logging
                    Emb Ch 15 Bit Dep=  cmdID= 2074  "
        ::= { iqhip10CmdEntry 2074 }


    iqhip10LoggingInp1BitDepthLogEmbCh16BitDepth OBJECT-TYPE
        SYNTAX            INTEGER { disable(0), enable(1)  }
        MAX-ACCESS        read-write
        STATUS            current
        DESCRIPTION
                "CMNT: - 
                 TYPE: - Checkbox
                 PAGE: - Logging
                    Log Emb Ch 16 Bit Depth  cmdID= 1075  "
        ::= { iqhip10CmdEntry 1075 }


    iqhip10LoggingInp1BitDepthEmbCh16BitDep OBJECT-TYPE
        SYNTAX            RollCallString
        MAX-ACCESS        read-only
        STATUS            current
        DESCRIPTION
                "CMNT: - 
                 TYPE: - Display
                 PAGE: - Logging
                    Emb Ch 16 Bit Dep=  cmdID= 2075  "
        ::= { iqhip10CmdEntry 2075 }


    iqhip10LoggingInp1LevelLogEmbCh1Level OBJECT-TYPE
        SYNTAX            INTEGER { disable(0), enable(1)  }
        MAX-ACCESS        read-write
        STATUS            current
        DESCRIPTION
                "CMNT: - 
                 TYPE: - Checkbox
                 PAGE: - Logging
                    Log Emb Ch 1 Level  cmdID= 1076  "
        ::= { iqhip10CmdEntry 1076 }


    iqhip10LoggingInp1LevelEmbCh1Level OBJECT-TYPE
        SYNTAX            RollCallString
        MAX-ACCESS        read-only
        STATUS            current
        DESCRIPTION
                "CMNT: - 
                 TYPE: - Display
                 PAGE: - Logging
                    Emb Ch 1 Level=  cmdID= 2076  "
        ::= { iqhip10CmdEntry 2076 }


    iqhip10LoggingInp1LevelLogEmbCh2Level OBJECT-TYPE
        SYNTAX            INTEGER { disable(0), enable(1)  }
        MAX-ACCESS        read-write
        STATUS            current
        DESCRIPTION
                "CMNT: - 
                 TYPE: - Checkbox
                 PAGE: - Logging
                    Log Emb Ch 2 Level  cmdID= 1077  "
        ::= { iqhip10CmdEntry 1077 }


    iqhip10LoggingInp1LevelEmbCh2Level OBJECT-TYPE
        SYNTAX            RollCallString
        MAX-ACCESS        read-only
        STATUS            current
        DESCRIPTION
                "CMNT: - 
                 TYPE: - Display
                 PAGE: - Logging
                    Emb Ch 2 Level=  cmdID= 2077  "
        ::= { iqhip10CmdEntry 2077 }


    iqhip10LoggingInp1LevelLogEmbCh3Level OBJECT-TYPE
        SYNTAX            INTEGER { disable(0), enable(1)  }
        MAX-ACCESS        read-write
        STATUS            current
        DESCRIPTION
                "CMNT: - 
                 TYPE: - Checkbox
                 PAGE: - Logging
                    Log Emb Ch 3 Level  cmdID= 1078  "
        ::= { iqhip10CmdEntry 1078 }


    iqhip10LoggingInp1LevelEmbCh3Level OBJECT-TYPE
        SYNTAX            RollCallString
        MAX-ACCESS        read-only
        STATUS            current
        DESCRIPTION
                "CMNT: - 
                 TYPE: - Display
                 PAGE: - Logging
                    Emb Ch 3 Level=  cmdID= 2078  "
        ::= { iqhip10CmdEntry 2078 }


    iqhip10LoggingInp1LevelLogEmbCh4Level OBJECT-TYPE
        SYNTAX            INTEGER { disable(0), enable(1)  }
        MAX-ACCESS        read-write
        STATUS            current
        DESCRIPTION
                "CMNT: - 
                 TYPE: - Checkbox
                 PAGE: - Logging
                    Log Emb Ch 4 Level  cmdID= 1079  "
        ::= { iqhip10CmdEntry 1079 }


    iqhip10LoggingInp1LevelEmbCh4Level OBJECT-TYPE
        SYNTAX            RollCallString
        MAX-ACCESS        read-only
        STATUS            current
        DESCRIPTION
                "CMNT: - 
                 TYPE: - Display
                 PAGE: - Logging
                    Emb Ch 4 Level=  cmdID= 2079  "
        ::= { iqhip10CmdEntry 2079 }


    iqhip10LoggingInp1LevelLogEmbCh5Level OBJECT-TYPE
        SYNTAX            INTEGER { disable(0), enable(1)  }
        MAX-ACCESS        read-write
        STATUS            current
        DESCRIPTION
                "CMNT: - 
                 TYPE: - Checkbox
                 PAGE: - Logging
                    Log Emb Ch 5 Level  cmdID= 1080  "
        ::= { iqhip10CmdEntry 1080 }


    iqhip10LoggingInp1LevelEmbCh5Level OBJECT-TYPE
        SYNTAX            RollCallString
        MAX-ACCESS        read-only
        STATUS            current
        DESCRIPTION
                "CMNT: - 
                 TYPE: - Display
                 PAGE: - Logging
                    Emb Ch 5 Level=  cmdID= 2080  "
        ::= { iqhip10CmdEntry 2080 }


    iqhip10LoggingInp1LevelLogEmbCh6Level OBJECT-TYPE
        SYNTAX            INTEGER { disable(0), enable(1)  }
        MAX-ACCESS        read-write
        STATUS            current
        DESCRIPTION
                "CMNT: - 
                 TYPE: - Checkbox
                 PAGE: - Logging
                    Log Emb Ch 6 Level  cmdID= 1081  "
        ::= { iqhip10CmdEntry 1081 }


    iqhip10LoggingInp1LevelEmbCh6Level OBJECT-TYPE
        SYNTAX            RollCallString
        MAX-ACCESS        read-only
        STATUS            current
        DESCRIPTION
                "CMNT: - 
                 TYPE: - Display
                 PAGE: - Logging
                    Emb Ch 6 Level=  cmdID= 2081  "
        ::= { iqhip10CmdEntry 2081 }


    iqhip10LoggingInp1LevelLogEmbCh7Level OBJECT-TYPE
        SYNTAX            INTEGER { disable(0), enable(1)  }
        MAX-ACCESS        read-write
        STATUS            current
        DESCRIPTION
                "CMNT: - 
                 TYPE: - Checkbox
                 PAGE: - Logging
                    Log Emb Ch 7 Level  cmdID= 1082  "
        ::= { iqhip10CmdEntry 1082 }


    iqhip10LoggingInp1LevelEmbCh7Level OBJECT-TYPE
        SYNTAX            RollCallString
        MAX-ACCESS        read-only
        STATUS            current
        DESCRIPTION
                "CMNT: - 
                 TYPE: - Display
                 PAGE: - Logging
                    Emb Ch 7 Level=  cmdID= 2082  "
        ::= { iqhip10CmdEntry 2082 }


    iqhip10LoggingInp1LevelLogEmbCh8Level OBJECT-TYPE
        SYNTAX            INTEGER { disable(0), enable(1)  }
        MAX-ACCESS        read-write
        STATUS            current
        DESCRIPTION
                "CMNT: - 
                 TYPE: - Checkbox
                 PAGE: - Logging
                    Log Emb Ch 8 Level  cmdID= 1083  "
        ::= { iqhip10CmdEntry 1083 }


    iqhip10LoggingInp1LevelEmbCh8Level OBJECT-TYPE
        SYNTAX            RollCallString
        MAX-ACCESS        read-only
        STATUS            current
        DESCRIPTION
                "CMNT: - 
                 TYPE: - Display
                 PAGE: - Logging
                    Emb Ch 8 Level=  cmdID= 2083  "
        ::= { iqhip10CmdEntry 2083 }


    iqhip10LoggingInp1LevelLogEmbCh9Level OBJECT-TYPE
        SYNTAX            INTEGER { disable(0), enable(1)  }
        MAX-ACCESS        read-write
        STATUS            current
        DESCRIPTION
                "CMNT: - 
                 TYPE: - Checkbox
                 PAGE: - Logging
                    Log Emb Ch 9 Level  cmdID= 1084  "
        ::= { iqhip10CmdEntry 1084 }


    iqhip10LoggingInp1LevelEmbCh9Level OBJECT-TYPE
        SYNTAX            RollCallString
        MAX-ACCESS        read-only
        STATUS            current
        DESCRIPTION
                "CMNT: - 
                 TYPE: - Display
                 PAGE: - Logging
                    Emb Ch 9 Level=  cmdID= 2084  "
        ::= { iqhip10CmdEntry 2084 }


    iqhip10LoggingInp1LevelLogEmbCh10Level OBJECT-TYPE
        SYNTAX            INTEGER { disable(0), enable(1)  }
        MAX-ACCESS        read-write
        STATUS            current
        DESCRIPTION
                "CMNT: - 
                 TYPE: - Checkbox
                 PAGE: - Logging
                    Log Emb Ch 10 Level  cmdID= 1085  "
        ::= { iqhip10CmdEntry 1085 }


    iqhip10LoggingInp1LevelEmbCh10Level OBJECT-TYPE
        SYNTAX            RollCallString
        MAX-ACCESS        read-only
        STATUS            current
        DESCRIPTION
                "CMNT: - 
                 TYPE: - Display
                 PAGE: - Logging
                    Emb Ch 10 Level=  cmdID= 2085  "
        ::= { iqhip10CmdEntry 2085 }


    iqhip10LoggingInp1LevelLogEmbCh11Level OBJECT-TYPE
        SYNTAX            INTEGER { disable(0), enable(1)  }
        MAX-ACCESS        read-write
        STATUS            current
        DESCRIPTION
                "CMNT: - 
                 TYPE: - Checkbox
                 PAGE: - Logging
                    Log Emb Ch 11 Level  cmdID= 1086  "
        ::= { iqhip10CmdEntry 1086 }


    iqhip10LoggingInp1LevelEmbCh11Level OBJECT-TYPE
        SYNTAX            RollCallString
        MAX-ACCESS        read-only
        STATUS            current
        DESCRIPTION
                "CMNT: - 
                 TYPE: - Display
                 PAGE: - Logging
                    Emb Ch 11 Level=  cmdID= 2086  "
        ::= { iqhip10CmdEntry 2086 }


    iqhip10LoggingInp1LevelLogEmbCh12Level OBJECT-TYPE
        SYNTAX            INTEGER { disable(0), enable(1)  }
        MAX-ACCESS        read-write
        STATUS            current
        DESCRIPTION
                "CMNT: - 
                 TYPE: - Checkbox
                 PAGE: - Logging
                    Log Emb Ch 12 Level  cmdID= 1087  "
        ::= { iqhip10CmdEntry 1087 }


    iqhip10LoggingInp1LevelEmbCh12Level OBJECT-TYPE
        SYNTAX            RollCallString
        MAX-ACCESS        read-only
        STATUS            current
        DESCRIPTION
                "CMNT: - 
                 TYPE: - Display
                 PAGE: - Logging
                    Emb Ch 12 Level=  cmdID= 2087  "
        ::= { iqhip10CmdEntry 2087 }


    iqhip10LoggingInp1LevelLogEmbCh13Level OBJECT-TYPE
        SYNTAX            INTEGER { disable(0), enable(1)  }
        MAX-ACCESS        read-write
        STATUS            current
        DESCRIPTION
                "CMNT: - 
                 TYPE: - Checkbox
                 PAGE: - Logging
                    Log Emb Ch 13 Level  cmdID= 1088  "
        ::= { iqhip10CmdEntry 1088 }


    iqhip10LoggingInp1LevelEmbCh13Level OBJECT-TYPE
        SYNTAX            RollCallString
        MAX-ACCESS        read-only
        STATUS            current
        DESCRIPTION
                "CMNT: - 
                 TYPE: - Display
                 PAGE: - Logging
                    Emb Ch 13 Level=  cmdID= 2088  "
        ::= { iqhip10CmdEntry 2088 }


    iqhip10LoggingInp1LevelLogEmbCh14Level OBJECT-TYPE
        SYNTAX            INTEGER { disable(0), enable(1)  }
        MAX-ACCESS        read-write
        STATUS            current
        DESCRIPTION
                "CMNT: - 
                 TYPE: - Checkbox
                 PAGE: - Logging
                    Log Emb Ch 14 Level  cmdID= 1089  "
        ::= { iqhip10CmdEntry 1089 }


    iqhip10LoggingInp1LevelEmbCh14Level OBJECT-TYPE
        SYNTAX            RollCallString
        MAX-ACCESS        read-only
        STATUS            current
        DESCRIPTION
                "CMNT: - 
                 TYPE: - Display
                 PAGE: - Logging
                    Emb Ch 14 Level=  cmdID= 2089  "
        ::= { iqhip10CmdEntry 2089 }


    iqhip10LoggingInp1LevelLogEmbCh15Level OBJECT-TYPE
        SYNTAX            INTEGER { disable(0), enable(1)  }
        MAX-ACCESS        read-write
        STATUS            current
        DESCRIPTION
                "CMNT: - 
                 TYPE: - Checkbox
                 PAGE: - Logging
                    Log Emb Ch 15 Level  cmdID= 1090  "
        ::= { iqhip10CmdEntry 1090 }


    iqhip10LoggingInp1LevelEmbCh15Level OBJECT-TYPE
        SYNTAX            RollCallString
        MAX-ACCESS        read-only
        STATUS            current
        DESCRIPTION
                "CMNT: - 
                 TYPE: - Display
                 PAGE: - Logging
                    Emb Ch 15 Level=  cmdID= 2090  "
        ::= { iqhip10CmdEntry 2090 }


    iqhip10LoggingInp1LevelLogEmbCh16Level OBJECT-TYPE
        SYNTAX            INTEGER { disable(0), enable(1)  }
        MAX-ACCESS        read-write
        STATUS            current
        DESCRIPTION
                "CMNT: - 
                 TYPE: - Checkbox
                 PAGE: - Logging
                    Log Emb Ch 16 Level  cmdID= 1091  "
        ::= { iqhip10CmdEntry 1091 }


    iqhip10LoggingInp1LevelEmbCh16Level OBJECT-TYPE
        SYNTAX            RollCallString
        MAX-ACCESS        read-only
        STATUS            current
        DESCRIPTION
                "CMNT: - 
                 TYPE: - Display
                 PAGE: - Logging
                    Emb Ch 16 Level=  cmdID= 2091  "
        ::= { iqhip10CmdEntry 2091 }


    iqhip10LoggingInp1ClippingLogEmbCh1Clipping OBJECT-TYPE
        SYNTAX            INTEGER { disable(0), enable(1)  }
        MAX-ACCESS        read-write
        STATUS            current
        DESCRIPTION
                "CMNT: - 
                 TYPE: - Checkbox
                 PAGE: - Logging
                    Log Emb Ch 1 Clipping  cmdID= 1134  "
        ::= { iqhip10CmdEntry 1134 }


    iqhip10LoggingInp1ClippingEmbCh1Clipping OBJECT-TYPE
        SYNTAX            RollCallString
        MAX-ACCESS        read-only
        STATUS            current
        DESCRIPTION
                "CMNT: - 
                 TYPE: - Display
                 PAGE: - Logging
                    Emb Ch 1 Clipping=  cmdID= 2134  "
        ::= { iqhip10CmdEntry 2134 }


    iqhip10LoggingInp1ClippingLogEmbCh2Clipping OBJECT-TYPE
        SYNTAX            INTEGER { disable(0), enable(1)  }
        MAX-ACCESS        read-write
        STATUS            current
        DESCRIPTION
                "CMNT: - 
                 TYPE: - Checkbox
                 PAGE: - Logging
                    Log Emb Ch 2 Clipping  cmdID= 1135  "
        ::= { iqhip10CmdEntry 1135 }


    iqhip10LoggingInp1ClippingEmbCh2Clipping OBJECT-TYPE
        SYNTAX            RollCallString
        MAX-ACCESS        read-only
        STATUS            current
        DESCRIPTION
                "CMNT: - 
                 TYPE: - Display
                 PAGE: - Logging
                    Emb Ch 2 Clipping=  cmdID= 2135  "
        ::= { iqhip10CmdEntry 2135 }


    iqhip10LoggingInp1ClippingLogEmbCh3Clipping OBJECT-TYPE
        SYNTAX            INTEGER { disable(0), enable(1)  }
        MAX-ACCESS        read-write
        STATUS            current
        DESCRIPTION
                "CMNT: - 
                 TYPE: - Checkbox
                 PAGE: - Logging
                    Log Emb Ch 3 Clipping  cmdID= 1136  "
        ::= { iqhip10CmdEntry 1136 }


    iqhip10LoggingInp1ClippingEmbCh3Clipping OBJECT-TYPE
        SYNTAX            RollCallString
        MAX-ACCESS        read-only
        STATUS            current
        DESCRIPTION
                "CMNT: - 
                 TYPE: - Display
                 PAGE: - Logging
                    Emb Ch 3 Clipping=  cmdID= 2136  "
        ::= { iqhip10CmdEntry 2136 }


    iqhip10LoggingInp1ClippingLogEmbCh4Clipping OBJECT-TYPE
        SYNTAX            INTEGER { disable(0), enable(1)  }
        MAX-ACCESS        read-write
        STATUS            current
        DESCRIPTION
                "CMNT: - 
                 TYPE: - Checkbox
                 PAGE: - Logging
                    Log Emb Ch 4 Clipping  cmdID= 1137  "
        ::= { iqhip10CmdEntry 1137 }


    iqhip10LoggingInp1ClippingEmbCh4Clipping OBJECT-TYPE
        SYNTAX            RollCallString
        MAX-ACCESS        read-only
        STATUS            current
        DESCRIPTION
                "CMNT: - 
                 TYPE: - Display
                 PAGE: - Logging
                    Emb Ch 4 Clipping=  cmdID= 2137  "
        ::= { iqhip10CmdEntry 2137 }


    iqhip10LoggingInp1ClippingLogEmbCh5Clipping OBJECT-TYPE
        SYNTAX            INTEGER { disable(0), enable(1)  }
        MAX-ACCESS        read-write
        STATUS            current
        DESCRIPTION
                "CMNT: - 
                 TYPE: - Checkbox
                 PAGE: - Logging
                    Log Emb Ch 5 Clipping  cmdID= 1138  "
        ::= { iqhip10CmdEntry 1138 }


    iqhip10LoggingInp1ClippingEmbCh5Clipping OBJECT-TYPE
        SYNTAX            RollCallString
        MAX-ACCESS        read-only
        STATUS            current
        DESCRIPTION
                "CMNT: - 
                 TYPE: - Display
                 PAGE: - Logging
                    Emb Ch 5 Clipping=  cmdID= 2138  "
        ::= { iqhip10CmdEntry 2138 }


    iqhip10LoggingInp1ClippingLogEmbCh6Clipping OBJECT-TYPE
        SYNTAX            INTEGER { disable(0), enable(1)  }
        MAX-ACCESS        read-write
        STATUS            current
        DESCRIPTION
                "CMNT: - 
                 TYPE: - Checkbox
                 PAGE: - Logging
                    Log Emb Ch 6 Clipping  cmdID= 1139  "
        ::= { iqhip10CmdEntry 1139 }


    iqhip10LoggingInp1ClippingEmbCh6Clipping OBJECT-TYPE
        SYNTAX            RollCallString
        MAX-ACCESS        read-only
        STATUS            current
        DESCRIPTION
                "CMNT: - 
                 TYPE: - Display
                 PAGE: - Logging
                    Emb Ch 6 Clipping=  cmdID= 2139  "
        ::= { iqhip10CmdEntry 2139 }


    iqhip10LoggingInp1ClippingLogEmbCh7Clipping OBJECT-TYPE
        SYNTAX            INTEGER { disable(0), enable(1)  }
        MAX-ACCESS        read-write
        STATUS            current
        DESCRIPTION
                "CMNT: - 
                 TYPE: - Checkbox
                 PAGE: - Logging
                    Log Emb Ch 7 Clipping  cmdID= 1140  "
        ::= { iqhip10CmdEntry 1140 }


    iqhip10LoggingInp1ClippingEmbCh7Clipping OBJECT-TYPE
        SYNTAX            RollCallString
        MAX-ACCESS        read-only
        STATUS            current
        DESCRIPTION
                "CMNT: - 
                 TYPE: - Display
                 PAGE: - Logging
                    Emb Ch 7 Clipping=  cmdID= 2140  "
        ::= { iqhip10CmdEntry 2140 }


    iqhip10LoggingInp1ClippingLogEmbCh8Clipping OBJECT-TYPE
        SYNTAX            INTEGER { disable(0), enable(1)  }
        MAX-ACCESS        read-write
        STATUS            current
        DESCRIPTION
                "CMNT: - 
                 TYPE: - Checkbox
                 PAGE: - Logging
                    Log Emb Ch 8 Clipping  cmdID= 1141  "
        ::= { iqhip10CmdEntry 1141 }


    iqhip10LoggingInp1ClippingEmbCh8Clipping OBJECT-TYPE
        SYNTAX            RollCallString
        MAX-ACCESS        read-only
        STATUS            current
        DESCRIPTION
                "CMNT: - 
                 TYPE: - Display
                 PAGE: - Logging
                    Emb Ch 8 Clipping=  cmdID= 2141  "
        ::= { iqhip10CmdEntry 2141 }


    iqhip10LoggingInp1ClippingLogEmbCh9Clipping OBJECT-TYPE
        SYNTAX            INTEGER { disable(0), enable(1)  }
        MAX-ACCESS        read-write
        STATUS            current
        DESCRIPTION
                "CMNT: - 
                 TYPE: - Checkbox
                 PAGE: - Logging
                    Log Emb Ch 9 Clipping  cmdID= 1142  "
        ::= { iqhip10CmdEntry 1142 }


    iqhip10LoggingInp1ClippingEmbCh9Clipping OBJECT-TYPE
        SYNTAX            RollCallString
        MAX-ACCESS        read-only
        STATUS            current
        DESCRIPTION
                "CMNT: - 
                 TYPE: - Display
                 PAGE: - Logging
                    Emb Ch 9 Clipping=  cmdID= 2142  "
        ::= { iqhip10CmdEntry 2142 }


    iqhip10LoggingInp1ClippingLogEmbCh10Clipping OBJECT-TYPE
        SYNTAX            INTEGER { disable(0), enable(1)  }
        MAX-ACCESS        read-write
        STATUS            current
        DESCRIPTION
                "CMNT: - 
                 TYPE: - Checkbox
                 PAGE: - Logging
                    Log Emb Ch 10 Clipping  cmdID= 1143  "
        ::= { iqhip10CmdEntry 1143 }


    iqhip10LoggingInp1ClippingEmbCh10Clipping OBJECT-TYPE
        SYNTAX            RollCallString
        MAX-ACCESS        read-only
        STATUS            current
        DESCRIPTION
                "CMNT: - 
                 TYPE: - Display
                 PAGE: - Logging
                    Emb Ch 10 Clipping=  cmdID= 2143  "
        ::= { iqhip10CmdEntry 2143 }


    iqhip10LoggingInp1ClippingLogEmbCh11Clipping OBJECT-TYPE
        SYNTAX            INTEGER { disable(0), enable(1)  }
        MAX-ACCESS        read-write
        STATUS            current
        DESCRIPTION
                "CMNT: - 
                 TYPE: - Checkbox
                 PAGE: - Logging
                    Log Emb Ch 11 Clipping  cmdID= 1144  "
        ::= { iqhip10CmdEntry 1144 }


    iqhip10LoggingInp1ClippingEmbCh11Clipping OBJECT-TYPE
        SYNTAX            RollCallString
        MAX-ACCESS        read-only
        STATUS            current
        DESCRIPTION
                "CMNT: - 
                 TYPE: - Display
                 PAGE: - Logging
                    Emb Ch 11 Clipping=  cmdID= 2144  "
        ::= { iqhip10CmdEntry 2144 }


    iqhip10LoggingInp1ClippingLogEmbCh12Clipping OBJECT-TYPE
        SYNTAX            INTEGER { disable(0), enable(1)  }
        MAX-ACCESS        read-write
        STATUS            current
        DESCRIPTION
                "CMNT: - 
                 TYPE: - Checkbox
                 PAGE: - Logging
                    Log Emb Ch 12 Clipping  cmdID= 1145  "
        ::= { iqhip10CmdEntry 1145 }


    iqhip10LoggingInp1ClippingEmbCh12Clipping OBJECT-TYPE
        SYNTAX            RollCallString
        MAX-ACCESS        read-only
        STATUS            current
        DESCRIPTION
                "CMNT: - 
                 TYPE: - Display
                 PAGE: - Logging
                    Emb Ch 12 Clipping=  cmdID= 2145  "
        ::= { iqhip10CmdEntry 2145 }


    iqhip10LoggingInp1ClippingLogEmbCh13Clipping OBJECT-TYPE
        SYNTAX            INTEGER { disable(0), enable(1)  }
        MAX-ACCESS        read-write
        STATUS            current
        DESCRIPTION
                "CMNT: - 
                 TYPE: - Checkbox
                 PAGE: - Logging
                    Log Emb Ch 13 Clipping  cmdID= 1146  "
        ::= { iqhip10CmdEntry 1146 }


    iqhip10LoggingInp1ClippingEmbCh13Clipping OBJECT-TYPE
        SYNTAX            RollCallString
        MAX-ACCESS        read-only
        STATUS            current
        DESCRIPTION
                "CMNT: - 
                 TYPE: - Display
                 PAGE: - Logging
                    Emb Ch 13 Clipping=  cmdID= 2146  "
        ::= { iqhip10CmdEntry 2146 }


    iqhip10LoggingInp1ClippingLogEmbCh14Clipping OBJECT-TYPE
        SYNTAX            INTEGER { disable(0), enable(1)  }
        MAX-ACCESS        read-write
        STATUS            current
        DESCRIPTION
                "CMNT: - 
                 TYPE: - Checkbox
                 PAGE: - Logging
                    Log Emb Ch 14 Clipping  cmdID= 1147  "
        ::= { iqhip10CmdEntry 1147 }


    iqhip10LoggingInp1ClippingEmbCh14Clipping OBJECT-TYPE
        SYNTAX            RollCallString
        MAX-ACCESS        read-only
        STATUS            current
        DESCRIPTION
                "CMNT: - 
                 TYPE: - Display
                 PAGE: - Logging
                    Emb Ch 14 Clipping=  cmdID= 2147  "
        ::= { iqhip10CmdEntry 2147 }


    iqhip10LoggingInp1ClippingLogEmbCh15Clipping OBJECT-TYPE
        SYNTAX            INTEGER { disable(0), enable(1)  }
        MAX-ACCESS        read-write
        STATUS            current
        DESCRIPTION
                "CMNT: - 
                 TYPE: - Checkbox
                 PAGE: - Logging
                    Log Emb Ch 15 Clipping  cmdID= 1148  "
        ::= { iqhip10CmdEntry 1148 }


    iqhip10LoggingInp1ClippingEmbCh15Clipping OBJECT-TYPE
        SYNTAX            RollCallString
        MAX-ACCESS        read-only
        STATUS            current
        DESCRIPTION
                "CMNT: - 
                 TYPE: - Display
                 PAGE: - Logging
                    Emb Ch 15 Clipping=  cmdID= 2148  "
        ::= { iqhip10CmdEntry 2148 }


    iqhip10LoggingInp1ClippingLogEmbCh16Clipping OBJECT-TYPE
        SYNTAX            INTEGER { disable(0), enable(1)  }
        MAX-ACCESS        read-write
        STATUS            current
        DESCRIPTION
                "CMNT: - 
                 TYPE: - Checkbox
                 PAGE: - Logging
                    Log Emb Ch 16 Clipping  cmdID= 1149  "
        ::= { iqhip10CmdEntry 1149 }


    iqhip10LoggingInp1ClippingEmbCh16Clipping OBJECT-TYPE
        SYNTAX            RollCallString
        MAX-ACCESS        read-only
        STATUS            current
        DESCRIPTION
                "CMNT: - 
                 TYPE: - Display
                 PAGE: - Logging
                    Emb Ch 16 Clipping=  cmdID= 2149  "
        ::= { iqhip10CmdEntry 2149 }


    iqhip10LoggingInp1LikenessLogDetector1Chans OBJECT-TYPE
        SYNTAX            INTEGER { disable(0), enable(1)  }
        MAX-ACCESS        read-write
        STATUS            current
        DESCRIPTION
                "CMNT: - 
                 TYPE: - Checkbox
                 PAGE: - Logging
                    Log Detector 1 Chans  cmdID= 1101  "
        ::= { iqhip10CmdEntry 1101 }


    iqhip10LoggingInp1LikenessDetector1Chans OBJECT-TYPE
        SYNTAX            RollCallString
        MAX-ACCESS        read-only
        STATUS            current
        DESCRIPTION
                "CMNT: - 
                 TYPE: - Display
                 PAGE: - Logging
                    Detector 1 Chans=  cmdID= 2101  "
        ::= { iqhip10CmdEntry 2101 }


    iqhip10LoggingInp1LikenessLogDetector1State OBJECT-TYPE
        SYNTAX            INTEGER { disable(0), enable(1)  }
        MAX-ACCESS        read-write
        STATUS            current
        DESCRIPTION
                "CMNT: - 
                 TYPE: - Checkbox
                 PAGE: - Logging
                    Log Detector 1 State  cmdID= 1105  "
        ::= { iqhip10CmdEntry 1105 }


    iqhip10LoggingInp1LikenessDetector1State OBJECT-TYPE
        SYNTAX            RollCallString
        MAX-ACCESS        read-only
        STATUS            current
        DESCRIPTION
                "CMNT: - 
                 TYPE: - Display
                 PAGE: - Logging
                    Detector 1 State=  cmdID= 2105  "
        ::= { iqhip10CmdEntry 2105 }


    iqhip10LoggingInp1LikenessLogDetector2Chans OBJECT-TYPE
        SYNTAX            INTEGER { disable(0), enable(1)  }
        MAX-ACCESS        read-write
        STATUS            current
        DESCRIPTION
                "CMNT: - 
                 TYPE: - Checkbox
                 PAGE: - Logging
                    Log Detector 2 Chans  cmdID= 1102  "
        ::= { iqhip10CmdEntry 1102 }


    iqhip10LoggingInp1LikenessDetector2Chans OBJECT-TYPE
        SYNTAX            RollCallString
        MAX-ACCESS        read-only
        STATUS            current
        DESCRIPTION
                "CMNT: - 
                 TYPE: - Display
                 PAGE: - Logging
                    Detector 2 Chans=  cmdID= 2102  "
        ::= { iqhip10CmdEntry 2102 }


    iqhip10LoggingInp1LikenessLogDetector2State OBJECT-TYPE
        SYNTAX            INTEGER { disable(0), enable(1)  }
        MAX-ACCESS        read-write
        STATUS            current
        DESCRIPTION
                "CMNT: - 
                 TYPE: - Checkbox
                 PAGE: - Logging
                    Log Detector 2 State  cmdID= 1106  "
        ::= { iqhip10CmdEntry 1106 }


    iqhip10LoggingInp1LikenessDetector2State OBJECT-TYPE
        SYNTAX            RollCallString
        MAX-ACCESS        read-only
        STATUS            current
        DESCRIPTION
                "CMNT: - 
                 TYPE: - Display
                 PAGE: - Logging
                    Detector 2 State=  cmdID= 2106  "
        ::= { iqhip10CmdEntry 2106 }


    iqhip10LoggingInp1LikenessLogDetector3Chans OBJECT-TYPE
        SYNTAX            INTEGER { disable(0), enable(1)  }
        MAX-ACCESS        read-write
        STATUS            current
        DESCRIPTION
                "CMNT: - 
                 TYPE: - Checkbox
                 PAGE: - Logging
                    Log Detector 3 Chans  cmdID= 1103  "
        ::= { iqhip10CmdEntry 1103 }


    iqhip10LoggingInp1LikenessDetector3Chans OBJECT-TYPE
        SYNTAX            RollCallString
        MAX-ACCESS        read-only
        STATUS            current
        DESCRIPTION
                "CMNT: - 
                 TYPE: - Display
                 PAGE: - Logging
                    Detector 3 Chans=  cmdID= 2103  "
        ::= { iqhip10CmdEntry 2103 }


    iqhip10LoggingInp1LikenessLogDetector3State OBJECT-TYPE
        SYNTAX            INTEGER { disable(0), enable(1)  }
        MAX-ACCESS        read-write
        STATUS            current
        DESCRIPTION
                "CMNT: - 
                 TYPE: - Checkbox
                 PAGE: - Logging
                    Log Detector 3 State  cmdID= 1107  "
        ::= { iqhip10CmdEntry 1107 }


    iqhip10LoggingInp1LikenessDetector3State OBJECT-TYPE
        SYNTAX            RollCallString
        MAX-ACCESS        read-only
        STATUS            current
        DESCRIPTION
                "CMNT: - 
                 TYPE: - Display
                 PAGE: - Logging
                    Detector 3 State=  cmdID= 2107  "
        ::= { iqhip10CmdEntry 2107 }


    iqhip10LoggingInp1LikenessLogDetector4Chans OBJECT-TYPE
        SYNTAX            INTEGER { disable(0), enable(1)  }
        MAX-ACCESS        read-write
        STATUS            current
        DESCRIPTION
                "CMNT: - 
                 TYPE: - Checkbox
                 PAGE: - Logging
                    Log Detector 4 Chans  cmdID= 1104  "
        ::= { iqhip10CmdEntry 1104 }


    iqhip10LoggingInp1LikenessDetector4Chans OBJECT-TYPE
        SYNTAX            RollCallString
        MAX-ACCESS        read-only
        STATUS            current
        DESCRIPTION
                "CMNT: - 
                 TYPE: - Display
                 PAGE: - Logging
                    Detector 4 Chans=  cmdID= 2104  "
        ::= { iqhip10CmdEntry 2104 }


    iqhip10LoggingInp1LikenessLogDetector4State OBJECT-TYPE
        SYNTAX            INTEGER { disable(0), enable(1)  }
        MAX-ACCESS        read-write
        STATUS            current
        DESCRIPTION
                "CMNT: - 
                 TYPE: - Checkbox
                 PAGE: - Logging
                    Log Detector 4 State  cmdID= 1108  "
        ::= { iqhip10CmdEntry 1108 }


    iqhip10LoggingInp1LikenessDetector4State OBJECT-TYPE
        SYNTAX            RollCallString
        MAX-ACCESS        read-only
        STATUS            current
        DESCRIPTION
                "CMNT: - 
                 TYPE: - Display
                 PAGE: - Logging
                    Detector 4 State=  cmdID= 2108  "
        ::= { iqhip10CmdEntry 2108 }


    iqhip10LoggingOut1UMIDLogUMIDState OBJECT-TYPE
        SYNTAX            INTEGER { disable(0), enable(1)  }
        MAX-ACCESS        read-write
        STATUS            current
        DESCRIPTION
                "CMNT: - 
                 TYPE: - Checkbox
                 PAGE: - Logging
                    Log UMID State  cmdID= 1121  "
        ::= { iqhip10CmdEntry 1121 }


    iqhip10LoggingOut1UMIDUMIDState OBJECT-TYPE
        SYNTAX            RollCallString
        MAX-ACCESS        read-only
        STATUS            current
        DESCRIPTION
                "CMNT: - 
                 TYPE: - Display
                 PAGE: - Logging
                    UMID State=  cmdID= 2121  "
        ::= { iqhip10CmdEntry 2121 }


    iqhip10LoggingOut1UMIDLogOutputUMID OBJECT-TYPE
        SYNTAX            INTEGER { disable(0), enable(1)  }
        MAX-ACCESS        read-write
        STATUS            current
        DESCRIPTION
                "CMNT: - 
                 TYPE: - Checkbox
                 PAGE: - Logging
                    Log Output UMID  cmdID= 1122  "
        ::= { iqhip10CmdEntry 1122 }


    iqhip10LoggingOut1UMIDOutputUMID18 OBJECT-TYPE
        SYNTAX            RollCallString
        MAX-ACCESS        read-only
        STATUS            current
        DESCRIPTION
                "CMNT: - 
                 TYPE: - Display
                 PAGE: - Logging
                    Output UMID 1-8=  cmdID= 2122  "
        ::= { iqhip10CmdEntry 2122 }


    iqhip10LoggingOut1UMIDOutputUMID916 OBJECT-TYPE
        SYNTAX            RollCallString
        MAX-ACCESS        read-only
        STATUS            current
        DESCRIPTION
                "CMNT: - 
                 TYPE: - Display
                 PAGE: - Logging
                    Output UMID 9-16=  cmdID= 4101  "
        ::= { iqhip10CmdEntry 4101 }


    iqhip10LoggingOut1UMIDOutputUMID1724 OBJECT-TYPE
        SYNTAX            RollCallString
        MAX-ACCESS        read-only
        STATUS            current
        DESCRIPTION
                "CMNT: - 
                 TYPE: - Display
                 PAGE: - Logging
                    Output UMID 17-24=  cmdID= 4102  "
        ::= { iqhip10CmdEntry 4102 }


    iqhip10LoggingOut1UMIDOutputUMID2532 OBJECT-TYPE
        SYNTAX            RollCallString
        MAX-ACCESS        read-only
        STATUS            current
        DESCRIPTION
                "CMNT: - 
                 TYPE: - Display
                 PAGE: - Logging
                    Output UMID 25-32=  cmdID= 4103  "
        ::= { iqhip10CmdEntry 4103 }


    iqhip10LoggingInp1UMIDLogUMIDState OBJECT-TYPE
        SYNTAX            INTEGER { disable(0), enable(1)  }
        MAX-ACCESS        read-write
        STATUS            current
        DESCRIPTION
                "CMNT: - 
                 TYPE: - Checkbox
                 PAGE: - Logging
                    Log UMID State  cmdID= 1013  "
        ::= { iqhip10CmdEntry 1013 }


    iqhip10LoggingInp1UMIDUMIDState OBJECT-TYPE
        SYNTAX            RollCallString
        MAX-ACCESS        read-only
        STATUS            current
        DESCRIPTION
                "CMNT: - 
                 TYPE: - Display
                 PAGE: - Logging
                    UMID State=  cmdID= 2013  "
        ::= { iqhip10CmdEntry 2013 }


    iqhip10LoggingInp1UMIDLogUMIDCurrent18 OBJECT-TYPE
        SYNTAX            INTEGER { disable(0), enable(1)  }
        MAX-ACCESS        read-write
        STATUS            current
        DESCRIPTION
                "CMNT: - 
                 TYPE: - Checkbox
                 PAGE: - Logging
                    Log UMID Current 1-8  cmdID= 1014  "
        ::= { iqhip10CmdEntry 1014 }


    iqhip10LoggingInp1UMIDUMIDCurrent18 OBJECT-TYPE
        SYNTAX            RollCallString
        MAX-ACCESS        read-only
        STATUS            current
        DESCRIPTION
                "CMNT: - 
                 TYPE: - Display
                 PAGE: - Logging
                    UMID Current 1-8=  cmdID= 2014  "
        ::= { iqhip10CmdEntry 2014 }


    iqhip10LoggingInp1UMIDUMIDCurrent916 OBJECT-TYPE
        SYNTAX            RollCallString
        MAX-ACCESS        read-only
        STATUS            current
        DESCRIPTION
                "CMNT: - 
                 TYPE: - Display
                 PAGE: - Logging
                    UMID Current 9-16=  cmdID= 4104  "
        ::= { iqhip10CmdEntry 4104 }


    iqhip10LoggingInp1UMIDUMIDCurrent1724 OBJECT-TYPE
        SYNTAX            RollCallString
        MAX-ACCESS        read-only
        STATUS            current
        DESCRIPTION
                "CMNT: - 
                 TYPE: - Display
                 PAGE: - Logging
                    UMID Current 17-24=  cmdID= 4105  "
        ::= { iqhip10CmdEntry 4105 }


    iqhip10LoggingInp1UMIDUMIDCurrent2532 OBJECT-TYPE
        SYNTAX            RollCallString
        MAX-ACCESS        read-only
        STATUS            current
        DESCRIPTION
                "CMNT: - 
                 TYPE: - Display
                 PAGE: - Logging
                    UMID Current 25-32=  cmdID= 4106  "
        ::= { iqhip10CmdEntry 4106 }


    iqhip10LoggingInp1UMIDLogUMIDPrevious18 OBJECT-TYPE
        SYNTAX            INTEGER { disable(0), enable(1)  }
        MAX-ACCESS        read-write
        STATUS            current
        DESCRIPTION
                "CMNT: - 
                 TYPE: - Checkbox
                 PAGE: - Logging
                    Log UMID Previous 1-8  cmdID= 1015  "
        ::= { iqhip10CmdEntry 1015 }


    iqhip10LoggingInp1UMIDUMIDPrev18 OBJECT-TYPE
        SYNTAX            RollCallString
        MAX-ACCESS        read-only
        STATUS            current
        DESCRIPTION
                "CMNT: - 
                 TYPE: - Display
                 PAGE: - Logging
                    UMID Prev 1-8=  cmdID= 2015  "
        ::= { iqhip10CmdEntry 2015 }


    iqhip10LoggingInp1UMIDUMIDPrev916 OBJECT-TYPE
        SYNTAX            RollCallString
        MAX-ACCESS        read-only
        STATUS            current
        DESCRIPTION
                "CMNT: - 
                 TYPE: - Display
                 PAGE: - Logging
                    UMID Prev 9-16=  cmdID= 4107  "
        ::= { iqhip10CmdEntry 4107 }


    iqhip10LoggingInp1UMIDUMIDPrev1724 OBJECT-TYPE
        SYNTAX            RollCallString
        MAX-ACCESS        read-only
        STATUS            current
        DESCRIPTION
                "CMNT: - 
                 TYPE: - Display
                 PAGE: - Logging
                    UMID Prev 17-24=  cmdID= 4108  "
        ::= { iqhip10CmdEntry 4108 }


    iqhip10LoggingInp1UMIDUMIDPrev2532 OBJECT-TYPE
        SYNTAX            RollCallString
        MAX-ACCESS        read-only
        STATUS            current
        DESCRIPTION
                "CMNT: - 
                 TYPE: - Display
                 PAGE: - Logging
                    UMID Prev 25-32=  cmdID= 4109  "
        ::= { iqhip10CmdEntry 4109 }


    iqhip10LoggingInp1UMIDLogUMIDPreviousCount OBJECT-TYPE
        SYNTAX            INTEGER { disable(0), enable(1)  }
        MAX-ACCESS        read-write
        STATUS            current
        DESCRIPTION
                "CMNT: - 
                 TYPE: - Checkbox
                 PAGE: - Logging
                    Log UMID Previous Count  cmdID= 1016  "
        ::= { iqhip10CmdEntry 1016 }


    iqhip10LoggingInp1UMIDUMIDPrevCount OBJECT-TYPE
        SYNTAX            RollCallString
        MAX-ACCESS        read-only
        STATUS            current
        DESCRIPTION
                "CMNT: - 
                 TYPE: - Display
                 PAGE: - Logging
                    UMID Prev Count=  cmdID= 2016  "
        ::= { iqhip10CmdEntry 2016 }


    iqhip10LoggingOut1PIDLogPIDState OBJECT-TYPE
        SYNTAX            INTEGER { disable(0), enable(1)  }
        MAX-ACCESS        read-write
        STATUS            current
        DESCRIPTION
                "CMNT: - 
                 TYPE: - Checkbox
                 PAGE: - Logging
                    Log PID State  cmdID= 1123  "
        ::= { iqhip10CmdEntry 1123 }


    iqhip10LoggingOut1PIDPIDState OBJECT-TYPE
        SYNTAX            RollCallString
        MAX-ACCESS        read-only
        STATUS            current
        DESCRIPTION
                "CMNT: - 
                 TYPE: - Display
                 PAGE: - Logging
                    PID State=  cmdID= 2123  "
        ::= { iqhip10CmdEntry 2123 }


    iqhip10LoggingOut1PIDLogPIDHouseID OBJECT-TYPE
        SYNTAX            INTEGER { disable(0), enable(1)  }
        MAX-ACCESS        read-write
        STATUS            current
        DESCRIPTION
                "CMNT: - 
                 TYPE: - Checkbox
                 PAGE: - Logging
                    Log PID House ID  cmdID= 1124  "
        ::= { iqhip10CmdEntry 1124 }


    iqhip10LoggingOut1PIDPIDHouseID OBJECT-TYPE
        SYNTAX            RollCallString
        MAX-ACCESS        read-only
        STATUS            current
        DESCRIPTION
                "CMNT: - 
                 TYPE: - Display
                 PAGE: - Logging
                    PID House ID=  cmdID= 2124  "
        ::= { iqhip10CmdEntry 2124 }


    iqhip10LoggingOut1PIDLogPIDTitle OBJECT-TYPE
        SYNTAX            INTEGER { disable(0), enable(1)  }
        MAX-ACCESS        read-write
        STATUS            current
        DESCRIPTION
                "CMNT: - 
                 TYPE: - Checkbox
                 PAGE: - Logging
                    Log PID Title  cmdID= 1125  "
        ::= { iqhip10CmdEntry 1125 }


    iqhip10LoggingOut1PIDPIDTitle OBJECT-TYPE
        SYNTAX            RollCallString
        MAX-ACCESS        read-only
        STATUS            current
        DESCRIPTION
                "CMNT: - 
                 TYPE: - Display
                 PAGE: - Logging
                    PID Title=  cmdID= 2125  "
        ::= { iqhip10CmdEntry 2125 }


    iqhip10LoggingOut1PIDLogSegmentNumber OBJECT-TYPE
        SYNTAX            INTEGER { disable(0), enable(1)  }
        MAX-ACCESS        read-write
        STATUS            current
        DESCRIPTION
                "CMNT: - 
                 TYPE: - Checkbox
                 PAGE: - Logging
                    Log Segment Number  cmdID= 1126  "
        ::= { iqhip10CmdEntry 1126 }


    iqhip10LoggingOut1PIDSegmentNumber OBJECT-TYPE
        SYNTAX            RollCallString
        MAX-ACCESS        read-only
        STATUS            current
        DESCRIPTION
                "CMNT: - 
                 TYPE: - Display
                 PAGE: - Logging
                    Segment Number=  cmdID= 2126  "
        ::= { iqhip10CmdEntry 2126 }


    iqhip10LoggingOut1PIDLogDuration OBJECT-TYPE
        SYNTAX            INTEGER { disable(0), enable(1)  }
        MAX-ACCESS        read-write
        STATUS            current
        DESCRIPTION
                "CMNT: - 
                 TYPE: - Checkbox
                 PAGE: - Logging
                    Log Duration  cmdID= 1127  "
        ::= { iqhip10CmdEntry 1127 }


    iqhip10LoggingOut1PIDDuration OBJECT-TYPE
        SYNTAX            RollCallString
        MAX-ACCESS        read-only
        STATUS            current
        DESCRIPTION
                "CMNT: - 
                 TYPE: - Display
                 PAGE: - Logging
                    Duration=  cmdID= 2127  "
        ::= { iqhip10CmdEntry 2127 }


    iqhip10LoggingOut1PIDLogFrameRate OBJECT-TYPE
        SYNTAX            INTEGER { disable(0), enable(1)  }
        MAX-ACCESS        read-write
        STATUS            current
        DESCRIPTION
                "CMNT: - 
                 TYPE: - Checkbox
                 PAGE: - Logging
                    Log Frame Rate  cmdID= 1128  "
        ::= { iqhip10CmdEntry 1128 }


    iqhip10LoggingOut1PIDFrameRate OBJECT-TYPE
        SYNTAX            RollCallString
        MAX-ACCESS        read-only
        STATUS            current
        DESCRIPTION
                "CMNT: - 
                 TYPE: - Display
                 PAGE: - Logging
                    Frame Rate=  cmdID= 2128  "
        ::= { iqhip10CmdEntry 2128 }


    iqhip10LoggingInp1PIDLogPIDState OBJECT-TYPE
        SYNTAX            INTEGER { disable(0), enable(1)  }
        MAX-ACCESS        read-write
        STATUS            current
        DESCRIPTION
                "CMNT: - 
                 TYPE: - Checkbox
                 PAGE: - Logging
                    Log PID State  cmdID= 1109  "
        ::= { iqhip10CmdEntry 1109 }


    iqhip10LoggingInp1PIDPIDState OBJECT-TYPE
        SYNTAX            RollCallString
        MAX-ACCESS        read-only
        STATUS            current
        DESCRIPTION
                "CMNT: - 
                 TYPE: - Display
                 PAGE: - Logging
                    PID State=  cmdID= 2109  "
        ::= { iqhip10CmdEntry 2109 }


    iqhip10LoggingInp1PIDLogPIDHouseID OBJECT-TYPE
        SYNTAX            INTEGER { disable(0), enable(1)  }
        MAX-ACCESS        read-write
        STATUS            current
        DESCRIPTION
                "CMNT: - 
                 TYPE: - Checkbox
                 PAGE: - Logging
                    Log PID House ID  cmdID= 1110  "
        ::= { iqhip10CmdEntry 1110 }


    iqhip10LoggingInp1PIDPIDHouseID OBJECT-TYPE
        SYNTAX            RollCallString
        MAX-ACCESS        read-only
        STATUS            current
        DESCRIPTION
                "CMNT: - 
                 TYPE: - Display
                 PAGE: - Logging
                    PID House ID=  cmdID= 2110  "
        ::= { iqhip10CmdEntry 2110 }


    iqhip10LoggingInp1PIDLogPIDTitle OBJECT-TYPE
        SYNTAX            INTEGER { disable(0), enable(1)  }
        MAX-ACCESS        read-write
        STATUS            current
        DESCRIPTION
                "CMNT: - 
                 TYPE: - Checkbox
                 PAGE: - Logging
                    Log PID Title  cmdID= 1111  "
        ::= { iqhip10CmdEntry 1111 }


    iqhip10LoggingInp1PIDPIDTitle OBJECT-TYPE
        SYNTAX            RollCallString
        MAX-ACCESS        read-only
        STATUS            current
        DESCRIPTION
                "CMNT: - 
                 TYPE: - Display
                 PAGE: - Logging
                    PID Title=  cmdID= 2111  "
        ::= { iqhip10CmdEntry 2111 }


    iqhip10LoggingInp1PIDLogSegmentNumber OBJECT-TYPE
        SYNTAX            INTEGER { disable(0), enable(1)  }
        MAX-ACCESS        read-write
        STATUS            current
        DESCRIPTION
                "CMNT: - 
                 TYPE: - Checkbox
                 PAGE: - Logging
                    Log Segment Number  cmdID= 1112  "
        ::= { iqhip10CmdEntry 1112 }


    iqhip10LoggingInp1PIDSegmentNumber OBJECT-TYPE
        SYNTAX            RollCallString
        MAX-ACCESS        read-only
        STATUS            current
        DESCRIPTION
                "CMNT: - 
                 TYPE: - Display
                 PAGE: - Logging
                    Segment Number=  cmdID= 2112  "
        ::= { iqhip10CmdEntry 2112 }


    iqhip10LoggingInp1PIDLogDuration OBJECT-TYPE
        SYNTAX            INTEGER { disable(0), enable(1)  }
        MAX-ACCESS        read-write
        STATUS            current
        DESCRIPTION
                "CMNT: - 
                 TYPE: - Checkbox
                 PAGE: - Logging
                    Log Duration  cmdID= 1113  "
        ::= { iqhip10CmdEntry 1113 }


    iqhip10LoggingInp1PIDDuration OBJECT-TYPE
        SYNTAX            RollCallString
        MAX-ACCESS        read-only
        STATUS            current
        DESCRIPTION
                "CMNT: - 
                 TYPE: - Display
                 PAGE: - Logging
                    Duration=  cmdID= 2113  "
        ::= { iqhip10CmdEntry 2113 }


    iqhip10LoggingInp1PIDLogFrameRate OBJECT-TYPE
        SYNTAX            INTEGER { disable(0), enable(1)  }
        MAX-ACCESS        read-write
        STATUS            current
        DESCRIPTION
                "CMNT: - 
                 TYPE: - Checkbox
                 PAGE: - Logging
                    Log Frame Rate  cmdID= 1114  "
        ::= { iqhip10CmdEntry 1114 }


    iqhip10LoggingInp1PIDFrameRate OBJECT-TYPE
        SYNTAX            RollCallString
        MAX-ACCESS        read-only
        STATUS            current
        DESCRIPTION
                "CMNT: - 
                 TYPE: - Display
                 PAGE: - Logging
                    Frame Rate=  cmdID= 2114  "
        ::= { iqhip10CmdEntry 2114 }


    iqhip10LoggingInp1PIDLogPreviousHouseID OBJECT-TYPE
        SYNTAX            INTEGER { disable(0), enable(1)  }
        MAX-ACCESS        read-write
        STATUS            current
        DESCRIPTION
                "CMNT: - 
                 TYPE: - Checkbox
                 PAGE: - Logging
                    Log Previous House ID  cmdID= 1115  "
        ::= { iqhip10CmdEntry 1115 }


    iqhip10LoggingInp1PIDPreviousHouseID OBJECT-TYPE
        SYNTAX            RollCallString
        MAX-ACCESS        read-only
        STATUS            current
        DESCRIPTION
                "CMNT: - 
                 TYPE: - Display
                 PAGE: - Logging
                    Previous House ID=  cmdID= 2115  "
        ::= { iqhip10CmdEntry 2115 }


    iqhip10LoggingInp1PIDLogPreviousTitle OBJECT-TYPE
        SYNTAX            INTEGER { disable(0), enable(1)  }
        MAX-ACCESS        read-write
        STATUS            current
        DESCRIPTION
                "CMNT: - 
                 TYPE: - Checkbox
                 PAGE: - Logging
                    Log Previous Title  cmdID= 1116  "
        ::= { iqhip10CmdEntry 1116 }


    iqhip10LoggingInp1PIDPreviousTitle OBJECT-TYPE
        SYNTAX            RollCallString
        MAX-ACCESS        read-only
        STATUS            current
        DESCRIPTION
                "CMNT: - 
                 TYPE: - Display
                 PAGE: - Logging
                    Previous Title=  cmdID= 2116  "
        ::= { iqhip10CmdEntry 2116 }


    iqhip10LoggingInp1PIDLogPreviousSegNum OBJECT-TYPE
        SYNTAX            INTEGER { disable(0), enable(1)  }
        MAX-ACCESS        read-write
        STATUS            current
        DESCRIPTION
                "CMNT: - 
                 TYPE: - Checkbox
                 PAGE: - Logging
                    Log Previous Seg Num  cmdID= 1117  "
        ::= { iqhip10CmdEntry 1117 }


    iqhip10LoggingInp1PIDPreviousSegNum OBJECT-TYPE
        SYNTAX            RollCallString
        MAX-ACCESS        read-only
        STATUS            current
        DESCRIPTION
                "CMNT: - 
                 TYPE: - Display
                 PAGE: - Logging
                    Previous Seg Num=  cmdID= 2117  "
        ::= { iqhip10CmdEntry 2117 }


    iqhip10LoggingInp1PIDLogPreviousDuration OBJECT-TYPE
        SYNTAX            INTEGER { disable(0), enable(1)  }
        MAX-ACCESS        read-write
        STATUS            current
        DESCRIPTION
                "CMNT: - 
                 TYPE: - Checkbox
                 PAGE: - Logging
                    Log Previous Duration  cmdID= 1118  "
        ::= { iqhip10CmdEntry 1118 }


    iqhip10LoggingInp1PIDPreviousDuration OBJECT-TYPE
        SYNTAX            RollCallString
        MAX-ACCESS        read-only
        STATUS            current
        DESCRIPTION
                "CMNT: - 
                 TYPE: - Display
                 PAGE: - Logging
                    Previous Duration=  cmdID= 2118  "
        ::= { iqhip10CmdEntry 2118 }


    iqhip10LoggingInp1PIDLogPreviousFrameRate OBJECT-TYPE
        SYNTAX            INTEGER { disable(0), enable(1)  }
        MAX-ACCESS        read-write
        STATUS            current
        DESCRIPTION
                "CMNT: - 
                 TYPE: - Checkbox
                 PAGE: - Logging
                    Log Previous FrameRate  cmdID= 1119  "
        ::= { iqhip10CmdEntry 1119 }


    iqhip10LoggingInp1PIDPreviousFrameRate OBJECT-TYPE
        SYNTAX            RollCallString
        MAX-ACCESS        read-only
        STATUS            current
        DESCRIPTION
                "CMNT: - 
                 TYPE: - Display
                 PAGE: - Logging
                    Previous FrameRate=  cmdID= 2119  "
        ::= { iqhip10CmdEntry 2119 }


    iqhip10LoggingInp1PIDLogPreviousCount OBJECT-TYPE
        SYNTAX            INTEGER { disable(0), enable(1)  }
        MAX-ACCESS        read-write
        STATUS            current
        DESCRIPTION
                "CMNT: - 
                 TYPE: - Checkbox
                 PAGE: - Logging
                    Log Previous Count  cmdID= 1120  "
        ::= { iqhip10CmdEntry 1120 }


    iqhip10LoggingInp1PIDPreviousCount OBJECT-TYPE
        SYNTAX            RollCallString
        MAX-ACCESS        read-only
        STATUS            current
        DESCRIPTION
                "CMNT: - 
                 TYPE: - Display
                 PAGE: - Logging
                    Previous Count=  cmdID= 2120  "
        ::= { iqhip10CmdEntry 2120 }


    iqhip10MemoriesRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Recall Memory  cmdID= 1601
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqhip10CmdEntry 1601 }


    iqhip10MemoriesSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqhip10CmdEntry 37101 }


    iqhip10MemoriesSaveMemory OBJECT-TYPE
        SYNTAX            INTEGER { noAction(0),valSaveMemory(1) }
        MAX-ACCESS        read-write
        STATUS            current
        DESCRIPTION
                "CMNT: - 
                 TYPE: - Button
                 PAGE: - Memories
                    Save Memory  cmdID= 37102
                    value= 1  "
        ::= { iqhip10CmdEntry 37102 }


    iqhip10MemoriesClearMemory OBJECT-TYPE
        SYNTAX            INTEGER { noAction(0),valClearMemory(1) }
        MAX-ACCESS        read-write
        STATUS            current
        DESCRIPTION
                "CMNT: - Delete User Memory
                 TYPE: - Button
                 PAGE: - Memories
                    Clear Memory  cmdID= 37105
                    value= 1  "
        ::= { iqhip10CmdEntry 37105 }


    iqhip10MemoriesMemoryNameChangeName OBJECT-TYPE
        SYNTAX            RollCallString
        MAX-ACCESS        read-write
        STATUS            current
        DESCRIPTION
                "CMNT: - 
                 TYPE: - Editstring
                 PAGE: - Memories
                    Change Name  cmdID= 37103
                    preset= Display Memory"
        ::= { iqhip10CmdEntry 37103 }


    iqhip10MemoriesMemoryNameLastUserMemory OBJECT-TYPE
        SYNTAX            RollCallString
        MAX-ACCESS        read-only
        STATUS            current
        DESCRIPTION
                "CMNT: - 
                 TYPE: - Display
                 PAGE: - Memories
                    Last User Memory  cmdID= 37104  "
        ::= { iqhip10CmdEntry 37104 }


    iqhip10MemoriesMemoryName1 OBJECT-TYPE
        SYNTAX            RollCallString
        MAX-ACCESS        read-only
        STATUS            current
        DESCRIPTION
                "CMNT: - 
                 TYPE: - Display
                 PAGE: - Memories
                    Memory Name1  cmdID= 37106  "
        ::= { iqhip10CmdEntry 37106 }


    iqhip10MemoriesMemoryName2 OBJECT-TYPE
        SYNTAX            RollCallString
        MAX-ACCESS        read-only
        STATUS            current
        DESCRIPTION
                "CMNT: - 
                 TYPE: - Display
                 PAGE: - Memories
                    Memory Name2  cmdID= 37107  "
        ::= { iqhip10CmdEntry 37107 }


    iqhip10MemoriesMemoryName3 OBJECT-TYPE
        SYNTAX            RollCallString
        MAX-ACCESS        read-only
        STATUS            current
        DESCRIPTION
                "CMNT: - 
                 TYPE: - Display
                 PAGE: - Memories
                    Memory Name3  cmdID= 37108  "
        ::= { iqhip10CmdEntry 37108 }


    iqhip10MemoriesMemoryName4 OBJECT-TYPE
        SYNTAX            RollCallString
        MAX-ACCESS        read-only
        STATUS            current
        DESCRIPTION
                "CMNT: - 
                 TYPE: - Display
                 PAGE: - Memories
                    Memory Name4  cmdID= 37109  "
        ::= { iqhip10CmdEntry 37109 }


    iqhip10MemoriesMemoryName5 OBJECT-TYPE
        SYNTAX            RollCallString
        MAX-ACCESS        read-only
        STATUS            current
        DESCRIPTION
                "CMNT: - 
                 TYPE: - Display
                 PAGE: - Memories
                    Memory Name5  cmdID= 37110  "
        ::= { iqhip10CmdEntry 37110 }


    iqhip10MemoriesMemoryName6 OBJECT-TYPE
        SYNTAX            RollCallString
        MAX-ACCESS        read-only
        STATUS            current
        DESCRIPTION
                "CMNT: - 
                 TYPE: - Display
                 PAGE: - Memories
                    Memory Name6  cmdID= 37111  "
        ::= { iqhip10CmdEntry 37111 }


    iqhip10MemoriesMemoryName7 OBJECT-TYPE
        SYNTAX            RollCallString
        MAX-ACCESS        read-only
        STATUS            current
        DESCRIPTION
                "CMNT: - 
                 TYPE: - Display
                 PAGE: - Memories
                    Memory Name7  cmdID= 37112  "
        ::= { iqhip10CmdEntry 37112 }


    iqhip10MemoriesMemoryName8 OBJECT-TYPE
        SYNTAX            RollCallString
        MAX-ACCESS        read-only
        STATUS            current
        DESCRIPTION
                "CMNT: - 
                 TYPE: - Display
                 PAGE: - Memories
                    Memory Name8  cmdID= 37113  "
        ::= { iqhip10CmdEntry 37113 }


    iqhip10MemoriesMemoryName9 OBJECT-TYPE
        SYNTAX            RollCallString
        MAX-ACCESS        read-only
        STATUS            current
        DESCRIPTION
                "CMNT: - 
                 TYPE: - Display
                 PAGE: - Memories
                    Memory Name9  cmdID= 37114  "
        ::= { iqhip10CmdEntry 37114 }


    iqhip10MemoriesMemoryName10 OBJECT-TYPE
        SYNTAX            RollCallString
        MAX-ACCESS        read-only
        STATUS            current
        DESCRIPTION
                "CMNT: - 
                 TYPE: - Display
                 PAGE: - Memories
                    Memory Name10  cmdID= 37115  "
        ::= { iqhip10CmdEntry 37115 }


    iqhip10MemoriesMemoryName11 OBJECT-TYPE
        SYNTAX            RollCallString
        MAX-ACCESS        read-only
        STATUS            current
        DESCRIPTION
                "CMNT: - 
                 TYPE: - Display
                 PAGE: - Memories
                    Memory Name11  cmdID= 37116  "
        ::= { iqhip10CmdEntry 37116 }


    iqhip10MemoriesMemoryName12 OBJECT-TYPE
        SYNTAX            RollCallString
        MAX-ACCESS        read-only
        STATUS            current
        DESCRIPTION
                "CMNT: - 
                 TYPE: - Display
                 PAGE: - Memories
                    Memory Name12  cmdID= 37117  "
        ::= { iqhip10CmdEntry 37117 }


    iqhip10MemoriesMemoryName13 OBJECT-TYPE
        SYNTAX            RollCallString
        MAX-ACCESS        read-only
        STATUS            current
        DESCRIPTION
                "CMNT: - 
                 TYPE: - Display
                 PAGE: - Memories
                    Memory Name13  cmdID= 37118  "
        ::= { iqhip10CmdEntry 37118 }


    iqhip10MemoriesMemoryName14 OBJECT-TYPE
        SYNTAX            RollCallString
        MAX-ACCESS        read-only
        STATUS            current
        DESCRIPTION
                "CMNT: - 
                 TYPE: - Display
                 PAGE: - Memories
                    Memory Name14  cmdID= 37119  "
        ::= { iqhip10CmdEntry 37119 }


    iqhip10MemoriesMemoryName15 OBJECT-TYPE
        SYNTAX            RollCallString
        MAX-ACCESS        read-only
        STATUS            current
        DESCRIPTION
                "CMNT: - 
                 TYPE: - Display
                 PAGE: - Memories
                    Memory Name15  cmdID= 37120  "
        ::= { iqhip10CmdEntry 37120 }


    iqhip10MemoriesMemoryName16 OBJECT-TYPE
        SYNTAX            RollCallString
        MAX-ACCESS        read-only
        STATUS            current
        DESCRIPTION
                "CMNT: - 
                 TYPE: - Display
                 PAGE: - Memories
                    Memory Name16  cmdID= 37121  "
        ::= { iqhip10CmdEntry 37121 }


    iqhip10SFPOutputTxAOFF OBJECT-TYPE
        SYNTAX            INTEGER { disable(0), enable(1)  }
        MAX-ACCESS        read-write
        STATUS            current
        DESCRIPTION
                "CMNT: - SFP A Tx  Output OFF
                 TYPE: - Checkbox
                 PAGE: - SFP Output
                    Tx A OFF  cmdID= 4061  "
        ::= { iqhip10CmdEntry 4061 }


    iqhip10SFPOutputTxAOFFInpLoss OBJECT-TYPE
        SYNTAX            INTEGER { disable(0), enable(1)  }
        MAX-ACCESS        read-write
        STATUS            current
        DESCRIPTION
                "CMNT: - Tx 2 Output OFF On Inp loss
                 TYPE: - Checkbox
                 PAGE: - SFP Output
                    Tx A OFF Inp Loss  cmdID= 4063  "
        ::= { iqhip10CmdEntry 4063 }


    iqhip10SFPOutputTxBOFF OBJECT-TYPE
        SYNTAX            INTEGER { disable(0), enable(1)  }
        MAX-ACCESS        read-write
        STATUS            current
        DESCRIPTION
                "CMNT: - Tx 1 Output OFF
                 TYPE: - Checkbox
                 PAGE: - SFP Output
                    Tx B OFF  cmdID= 4060  "
        ::= { iqhip10CmdEntry 4060 }


    iqhip10SFPOutputTxBOFFInpLoss OBJECT-TYPE
        SYNTAX            INTEGER { disable(0), enable(1)  }
        MAX-ACCESS        read-write
        STATUS            current
        DESCRIPTION
                "CMNT: - Tx 1 Output OFF On Inp loss
                 TYPE: - Checkbox
                 PAGE: - SFP Output
                    Tx B OFF Inp Loss  cmdID= 4062  "
        ::= { iqhip10CmdEntry 4062 }


    iqhip10SFPOutputTxAOutputState OBJECT-TYPE
        SYNTAX            RollCallString
        MAX-ACCESS        read-only
        STATUS            current
        DESCRIPTION
                "CMNT: - Display the SFP 1 TX A output state
                 TYPE: - Display
                 PAGE: - SFP Output
                    Tx A Output State  cmdID= 9010  "
        ::= { iqhip10CmdEntry 9010 }


    iqhip10SFPOutputTxBOutputState OBJECT-TYPE
        SYNTAX            RollCallString
        MAX-ACCESS        read-only
        STATUS            current
        DESCRIPTION
                "CMNT: - Not Used in HIP10
                 TYPE: - Display
                 PAGE: - SFP Output
                    Tx B Output State  cmdID= 9011  "
        ::= { iqhip10CmdEntry 9011 }


    iqhip10SetupProduct OBJECT-TYPE
        SYNTAX            RollCallString
        MAX-ACCESS        read-only
        STATUS            current
        DESCRIPTION
                "CMNT: - 
                 TYPE: - Display
                 PAGE: - Setup
                    Product  cmdID= 32771  "
        ::= { iqhip10CmdEntry 32771 }


    iqhip10SetupProductRelease OBJECT-TYPE
        SYNTAX            RollCallString
        MAX-ACCESS        read-only
        STATUS            current
        DESCRIPTION
                "CMNT: - 
                 TYPE: - Display
                 PAGE: - Setup
                    Release  cmdID= 2  "
        ::= { iqhip10CmdEntry 2 }


    iqhip10SetupProductBuild OBJECT-TYPE
        SYNTAX            RollCallString
        MAX-ACCESS        read-only
        STATUS            current
        DESCRIPTION
                "CMNT: - 
                 TYPE: - Display
                 PAGE: - Setup
                    Build  cmdID= 5  "
        ::= { iqhip10CmdEntry 5 }


    iqhip10SetupProductSerial OBJECT-TYPE
        SYNTAX            RollCallString
        MAX-ACCESS        read-only
        STATUS            current
        DESCRIPTION
                "CMNT: - 
                 TYPE: - Display
                 PAGE: - Setup
                    Serial  cmdID= 1  "
        ::= { iqhip10CmdEntry 1 }


    iqhip10SetupProductFirmware OBJECT-TYPE
        SYNTAX            RollCallString
        MAX-ACCESS        read-only
        STATUS            current
        DESCRIPTION
                "CMNT: - 
                 TYPE: - Display
                 PAGE: - Setup
                    Firmware  cmdID= 5100  "
        ::= { iqhip10CmdEntry 5100 }


    iqhip10SetupProductPCB OBJECT-TYPE
        SYNTAX            RollCallString
        MAX-ACCESS        read-only
        STATUS            current
        DESCRIPTION
                "CMNT: - 
                 TYPE: - Display
                 PAGE: - Setup
                    PCB  cmdID= 5101  "
        ::= { iqhip10CmdEntry 5101 }


    iqhip10SetupProductFactoryDefault OBJECT-TYPE
        SYNTAX            INTEGER { noAction(0),valFactoryDefault(1) }
        MAX-ACCESS        read-write
        STATUS            current
        DESCRIPTION
                "CMNT: - 
                 TYPE: - Button
                 PAGE: - Setup
                    Factory Default  cmdID= 5520
                    value= 1  "
        ::= { iqhip10CmdEntry 5520 }


    iqhip10SetupProductDefaultSettings OBJECT-TYPE
        SYNTAX            INTEGER { noAction(0),valDefaultSettings(1) }
        MAX-ACCESS        read-write
        STATUS            current
        DESCRIPTION
                "CMNT: - 
                 TYPE: - Button
                 PAGE: - Setup
                    Default Settings  cmdID= 5521
                    value= 1  "
        ::= { iqhip10CmdEntry 5521 }


    iqhip10SetupProductRestartSoftHard OBJECT-TYPE
        SYNTAX            INTEGER { noAction(0),valRestartSoftHard(1) }
        MAX-ACCESS        read-write
        STATUS            current
        DESCRIPTION
                "CMNT: - 
                 TYPE: - Button
                 PAGE: - Setup
                    Restart Soft/Hard.  cmdID= 4
                    value= 1  "
        ::= { iqhip10CmdEntry 4 }


    iqhip10SetupProductInput1Name OBJECT-TYPE
        SYNTAX            RollCallString
        MAX-ACCESS        read-write
        STATUS            current
        DESCRIPTION
                "CMNT: - 
                 TYPE: - Editstring
                 PAGE: - Setup
                    Input 1 Name  cmdID= 1336
                    preset= INPUT 1 SERIAL IN  "
        ::= { iqhip10CmdEntry 1336 }


    iqhip10SetupProductSFPARxName OBJECT-TYPE
        SYNTAX            RollCallString
        MAX-ACCESS        read-write
        STATUS            current
        DESCRIPTION
                "CMNT: - 
                 TYPE: - Editstring
                 PAGE: - Setup
                    SFP A Rx Name  cmdID= 9002
                    preset= INPUT SFP A"
        ::= { iqhip10CmdEntry 9002 }


    iqhip10SetupProductRearType OBJECT-TYPE
        SYNTAX            RollCallString
        MAX-ACCESS        read-only
        STATUS            current
        DESCRIPTION
                "CMNT: - 
                 TYPE: - Display
                 PAGE: - Setup
                    Rear Type  cmdID= 32780  "
        ::= { iqhip10CmdEntry 32780 }


    iqhip10SetupUpgradeStart OBJECT-TYPE
        SYNTAX            INTEGER { noAction(0),valUpgradeStart(1) }
        MAX-ACCESS        read-write
        STATUS            current
        DESCRIPTION
                "CMNT: - 
                 TYPE: - Button
                 PAGE: - Setup
                    UpgradeStart  cmdID= 10
                    value= 1  "
        ::= { iqhip10CmdEntry 10 }


    iqhip10SetupUpgradeEnd OBJECT-TYPE
        SYNTAX            INTEGER { noAction(0),valUpgradeEnd(1) }
        MAX-ACCESS        read-write
        STATUS            current
        DESCRIPTION
                "CMNT: - 
                 TYPE: - Button
                 PAGE: - Setup
                    UpgradeEnd  cmdID= 11
                    value= 1  "
        ::= { iqhip10CmdEntry 11 }


    iqhip10SetupUpgradeCancel OBJECT-TYPE
        SYNTAX            INTEGER { noAction(0),valUpgradeCancel(1) }
        MAX-ACCESS        read-write
        STATUS            current
        DESCRIPTION
                "CMNT: - 
                 TYPE: - Button
                 PAGE: - Setup
                    UpgradeCancel  cmdID= 12
                    value= 1  "
        ::= { iqhip10CmdEntry 12 }


    iqhip10SetupUpgradeAbort OBJECT-TYPE
        SYNTAX            INTEGER { noAction(0),valUpgradeAbort(1) }
        MAX-ACCESS        read-write
        STATUS            current
        DESCRIPTION
                "CMNT: - 
                 TYPE: - Button
                 PAGE: - Setup
                    UpgradeAbort  cmdID= 13
                    value= 1  "
        ::= { iqhip10CmdEntry 13 }


    iqhip10SetupOutputStd OBJECT-TYPE
        SYNTAX            INTEGER
        MAX-ACCESS        read-write
        STATUS            current
        DESCRIPTION
                "CMNT: - 
                 TYPE: - Number
                 PAGE: - Setup
                    OutputStd  cmdID= 4070
                    min= 0  max= 42  step= 1  format= %0.0f  div_scale= 1  preset= 0
                    Min = 0  Max = 42  Step = 1  Preset = 0  "
        ::= { iqhip10CmdEntry 4070 }


    iqhip10SFPSetupVendor OBJECT-TYPE
        SYNTAX            RollCallString
        MAX-ACCESS        read-only
        STATUS            current
        DESCRIPTION
                "CMNT: - Display the SFP 1 vendor
                 TYPE: - Display
                 PAGE: - SFP Setup
                    Vendor  cmdID= 6000  "
        ::= { iqhip10CmdEntry 6000 }


    iqhip10SFPSetupPartNumber OBJECT-TYPE
        SYNTAX            RollCallString
        MAX-ACCESS        read-only
        STATUS            current
        DESCRIPTION
                "CMNT: - Display the SFP 1 Part number
                 TYPE: - Display
                 PAGE: - SFP Setup
                    Part Number  cmdID= 6002  "
        ::= { iqhip10CmdEntry 6002 }


    iqhip10SFPSetupSerialNumber OBJECT-TYPE
        SYNTAX            RollCallString
        MAX-ACCESS        read-only
        STATUS            current
        DESCRIPTION
                "CMNT: - Display the SFP 1 Serial number
                 TYPE: - Display
                 PAGE: - SFP Setup
                    Serial Number  cmdID= 6001  "
        ::= { iqhip10CmdEntry 6001 }


    iqhip10SFPSetupIdentifier OBJECT-TYPE
        SYNTAX            RollCallString
        MAX-ACCESS        read-only
        STATUS            current
        DESCRIPTION
                "CMNT: - Display the SFP 1 Identifier
                 TYPE: - Display
                 PAGE: - SFP Setup
                    Identifier  cmdID= 6003  "
        ::= { iqhip10CmdEntry 6003 }


    iqhip10SFPSetupType OBJECT-TYPE
        SYNTAX            RollCallString
        MAX-ACCESS        read-only
        STATUS            current
        DESCRIPTION
                "CMNT: - Display the SFP 1 Identifier
                 TYPE: - Display
                 PAGE: - SFP Setup
                    Type  cmdID= 6004  "
        ::= { iqhip10CmdEntry 6004 }


    iqhip10SFPSetupConnector OBJECT-TYPE
        SYNTAX            RollCallString
        MAX-ACCESS        read-only
        STATUS            current
        DESCRIPTION
                "CMNT: - Display the SFP 1 Connector type
                 TYPE: - Display
                 PAGE: - SFP Setup
                    Connector  cmdID= 6006  "
        ::= { iqhip10CmdEntry 6006 }


    iqhip10SFPSetupStatus OBJECT-TYPE
        SYNTAX            RollCallString
        MAX-ACCESS        read-only
        STATUS            current
        DESCRIPTION
                "CMNT: - Display the SFP 1 Identifier
                 TYPE: - Display
                 PAGE: - SFP Setup
                    Status  cmdID= 6005  "
        ::= { iqhip10CmdEntry 6005 }


    iqhip10SFPSetupConfigureSFPType OBJECT-TYPE
        SYNTAX            INTEGER {
                            valAuto(0),
                            valTxnTx(1),
                            valRxnRx(2),
                            valTxnn(3),
                            valRxnn(4),
                            valTxnRx(5),
                            valHDMI(6)
                            }
        MAX-ACCESS        read-write
        STATUS            current
        DESCRIPTION
                "CMNT: - 
                 TYPE: - RadiobuttonList
                 PAGE: - SFP Setup
                    Configure SFP Type  cmdID= 6100
                    Auto  value= 0
                    Tx-Tx  value= 1
                    Rx-Rx  value= 2
                    Tx--  value= 3
                    Rx--  value= 4
                    Tx-Rx  value= 5
                    HDMI  value= 6  "
        ::= { iqhip10CmdEntry 6100 }


    iqhip10RollTrackDisableAll OBJECT-TYPE
        SYNTAX            INTEGER { disable(0), enable(1)  }
        MAX-ACCESS        read-write
        STATUS            current
        DESCRIPTION
                "CMNT: - 
                 TYPE: - Checkbox
                 PAGE: - RollTrack
                    Disable All  cmdID= 1413  "
        ::= { iqhip10CmdEntry 1413 }


    iqhip10RollTrackIndex OBJECT-TYPE
        SYNTAX            INTEGER
        MAX-ACCESS        read-write
        STATUS            current
        DESCRIPTION
                "CMNT: - 
                 TYPE: - BarGraph
                 PAGE: - RollTrack
                    Index  cmdID= 1415
                    min= 1  max= 16  step= 1  format= %0.0f  div_scale= 1  preset= 1
                    Min = 1  Max = 16  Step = 1  Preset = 1  "
        ::= { iqhip10CmdEntry 1415 }


    iqhip10RollTrackSource OBJECT-TYPE
        SYNTAX            INTEGER {
                            valUnused(-1),
                            valInputOK(0),
                            valInputNone(1),
                            valIP11125103530I(2),
                            valIP11125103529I(3),
                            valIP11125108060p(41),
                            valIP11125108059p(42),
                            valIP11125108050p(43),
                            valIP11125108030I(4),
                            valIP11125108029I(5),
                            valIP11125108025I(6),
                            valIP11125108030P(7),
                            valIP11125108029P(8),
                            valIP11125108025P(9),
                            valIP11125108024P(10),
                            valIP11125108023P(11),
                            valIP175072060P(12),
                            valIP175072059P(13),
                            valIP152548029I(14),
                            valIP162557625I(15),
                            valIP11125108024sF(16),
                            valIP11125108023sF(17),
                            valIP175072050P(18),
                            valIP175072030P(19),
                            valIP175072029P(20),
                            valIP175072025P(21),
                            valHyperionOK(22),
                            valHyperionWARN(23),
                            valHyperionFAIL(24),
                            valAudioLevelOK(26),
                            valAudioLevelWARN(27),
                            valAudioLevelFAIL(28),
                            valReg1BlackOK(44),
                            valReg1BlackWARN(45),
                            valReg1BlackFAIL(46),
                            valReg1BlackishOK(47),
                            valReg1BlackishWARN(48),
                            valReg1BlackishFAIL(49),
                            valReg1StillishOK(50),
                            valReg1StillishWARN(51),
                            valReg1StillishFAIL(52),
                            valReg1FreezeOK(53),
                            valReg1FreezeWARN(54),
                            valReg1FreezeFAIL(55),
                            valReg2BlackOK(56),
                            valReg2BlackWARN(57),
                            valReg2BlackFAIL(58),
                            valReg2BlackishOK(59),
                            valReg2BlackishWARN(60),
                            valReg2BlackishFAIL(61),
                            valReg2StillishOK(62),
                            valReg2StillishWARN(63),
                            valReg2StillishFAIL(64),
                            valReg2FreezeOK(65),
                            valReg2FreezeWARN(66),
                            valReg2FreezeFAIL(67),
                            valRXAPowerOK(29),
                            valRXAPowerHigh(30),
                            valRXAPowerLow(31),
                            valTXBBiasOK(35),
                            valTXBBiasHigh(36),
                            valTXBBiasLow(37),
                            valTXABiasOK(38),
                            valTXABiasHigh(39),
                            valTXABiasLow(40)
                            }
        MAX-ACCESS        read-write
        STATUS            current
        DESCRIPTION
                "CMNT: - 
                 TYPE: - RadiobuttonList
                 PAGE: - RollTrack
                    Source  cmdID= 1416
                    Unused  value= -1
                    Input OK  value= 0
                    Input None  value= 1
                    IP1 1125(1035)/30I  value= 2
                    IP1 1125(1035)/29I  value= 3
                    IP1 1125(1080)/60p  value= 41
                    IP1 1125(1080)/59p  value= 42
                    IP1 1125(1080)/50p  value= 43
                    IP1 1125(1080)/30I  value= 4
                    IP1 1125(1080)/29I  value= 5
                    IP1 1125(1080)/25I  value= 6
                    IP1 1125(1080)/30P  value= 7
                    IP1 1125(1080)/29P  value= 8
                    IP1 1125(1080)/25P  value= 9
                    IP1 1125(1080)/24P  value= 10
                    IP1 1125(1080)/23P  value= 11
                    IP1 750(720)/60P  value= 12
                    IP1 750(720)/59P  value= 13
                    IP1 525(480)/29I  value= 14
                    IP1 625(576)/25I  value= 15
                    IP1 1125(1080)/24sF  value= 16
                    IP1 1125(1080)/23sF  value= 17
                    IP1 750(720)/50P  value= 18
                    IP1 750(720)/30P  value= 19
                    IP1 750(720)/29P  value= 20
                    IP1 750(720)/25P  value= 21
                    Hyperion OK  value= 22
                    Hyperion WARN  value= 23
                    Hyperion FAIL  value= 24
                    Audio Level OK  value= 26
                    Audio Level WARN  value= 27
                    Audio Level FAIL  value= 28
                    Reg 1 Black OK  value= 44
                    Reg 1 Black WARN  value= 45
                    Reg 1 Black FAIL  value= 46
                    Reg 1 Blackish OK  value= 47
                    Reg 1 Blackish WARN  value= 48
                    Reg 1 Blackish FAIL  value= 49
                    Reg 1 Stillish OK  value= 50
                    Reg 1 Stillish WARN  value= 51
                    Reg 1 Stillish FAIL  value= 52
                    Reg 1 Freeze OK  value= 53
                    Reg 1 Freeze WARN  value= 54
                    Reg 1 Freeze FAIL  value= 55
                    Reg 2 Black OK  value= 56
                    Reg 2 Black WARN  value= 57
                    Reg 2 Black FAIL  value= 58
                    Reg 2 Blackish OK  value= 59
                    Reg 2 Blackish WARN  value= 60
                    Reg 2 Blackish FAIL  value= 61
                    Reg 2 Stillish OK  value= 62
                    Reg 2 Stillish WARN  value= 63
                    Reg 2 Stillish FAIL  value= 64
                    Reg 2 Freeze OK  value= 65
                    Reg 2 Freeze WARN  value= 66
                    Reg 2 Freeze FAIL  value= 67
                    RX A Power OK  value= 29
                    RX A Power High  value= 30
                    RX A Power Low  value= 31
                    TX B Bias OK  value= 35
                    TX B Bias High  value= 36
                    TX B Bias Low  value= 37
                    TX A Bias OK  value= 38
                    TX A Bias High  value= 39
                    TX A Bias Low  value= 40  "
        ::= { iqhip10CmdEntry 1416 }


    iqhip10RollTrackAddress OBJECT-TYPE
        SYNTAX            RollCallString
        MAX-ACCESS        read-write
        STATUS            current
        DESCRIPTION
                "CMNT: - 
                 TYPE: - Editstring
                 PAGE: - RollTrack
                    Address  cmdID= 1417
                    preset= 0000:00:00*0\0*"
        ::= { iqhip10CmdEntry 1417 }


    iqhip10RollTrackCommand OBJECT-TYPE
        SYNTAX            RollCallString
        MAX-ACCESS        read-write
        STATUS            current
        DESCRIPTION
                "CMNT: - 
                 TYPE: - Editstring
                 PAGE: - RollTrack
                    Command  cmdID= 1418
                    preset= 0:0\0"
        ::= { iqhip10CmdEntry 1418 }


    iqhip10RollTrackStatus OBJECT-TYPE
        SYNTAX            RollCallString
        MAX-ACCESS        read-only
        STATUS            current
        DESCRIPTION
                "CMNT: - 
                 TYPE: - Display
                 PAGE: - RollTrack
                    Status  cmdID= 1411  "
        ::= { iqhip10CmdEntry 1411 }


    iqhip10RollTrackSending OBJECT-TYPE
        SYNTAX            RollCallString
        MAX-ACCESS        read-only
        STATUS            current
        DESCRIPTION
                "CMNT: - 
                 TYPE: - Display
                 PAGE: - RollTrack
                    Sending  cmdID= 1414  "
        ::= { iqhip10CmdEntry 1414 }


    iqhip10DialoguePagecontrolsConfig1 OBJECT-TYPE
        SYNTAX            RollCallString
        MAX-ACCESS        read-only
        STATUS            current
        DESCRIPTION
                "CMNT: - 
                 TYPE: - Display
                 PAGE: - Dialogue Page controls
                    Config 1  cmdID= 37201  "
        ::= { iqhip10CmdEntry 37201 }


    iqhip10DialoguePagecontrolsConfig2 OBJECT-TYPE
        SYNTAX            RollCallString
        MAX-ACCESS        read-only
        STATUS            current
        DESCRIPTION
                "CMNT: - 
                 TYPE: - Display
                 PAGE: - Dialogue Page controls
                    Config 2  cmdID= 37202  "
        ::= { iqhip10CmdEntry 37202 }


    iqhip10DialoguePagecontrolsConfig3 OBJECT-TYPE
        SYNTAX            RollCallString
        MAX-ACCESS        read-only
        STATUS            current
        DESCRIPTION
                "CMNT: - 
                 TYPE: - Display
                 PAGE: - Dialogue Page controls
                    Config 3  cmdID= 37203  "
        ::= { iqhip10CmdEntry 37203 }


    iqhip10DialoguePagecontrolsConfig4 OBJECT-TYPE
        SYNTAX            RollCallString
        MAX-ACCESS        read-only
        STATUS            current
        DESCRIPTION
                "CMNT: - 
                 TYPE: - Display
                 PAGE: - Dialogue Page controls
                    Config 4  cmdID= 37204  "
        ::= { iqhip10CmdEntry 37204 }


    iqhip10PatternEnable OBJECT-TYPE
        SYNTAX            INTEGER { disable(0), enable(1)  }
        MAX-ACCESS        read-write
        STATUS            current
        DESCRIPTION
                "CMNT: - 
                 TYPE: - Checkbox
                 PAGE: - Pattern
                    Enable  cmdID= 33038  "
        ::= { iqhip10CmdEntry 33038 }


    iqhip10PatternEnableOnIPLoss OBJECT-TYPE
        SYNTAX            INTEGER { disable(0), enable(1)  }
        MAX-ACCESS        read-write
        STATUS            current
        DESCRIPTION
                "CMNT: - 
                 TYPE: - Checkbox
                 PAGE: - Pattern
                    Enable On IP Loss  cmdID= 33050  "
        ::= { iqhip10CmdEntry 33050 }


    iqhip10PatternScroll OBJECT-TYPE
        SYNTAX            INTEGER { disable(0), enable(1)  }
        MAX-ACCESS        read-write
        STATUS            current
        DESCRIPTION
                "CMNT: - 
                 TYPE: - Checkbox
                 PAGE: - Pattern
                    Scroll  cmdID= 33040  "
        ::= { iqhip10CmdEntry 33040 }


    iqhip10PatternType OBJECT-TYPE
        SYNTAX            INTEGER {
                            val100ColorBars(1),
                            val75ColorBars(2),
                            valSMPTEBars(3),
                            valTartan(4),
                            valPLUGE(5),
                            valRamp(6),
                            valSweep(7),
                            valPulseandBar(8),
                            valBurst(9),
                            valBlack(10)
                            }
        MAX-ACCESS        read-write
        STATUS            current
        DESCRIPTION
                "CMNT: - 
                 TYPE: - RadiobuttonList
                 PAGE: - Pattern
                    Pattern Type  cmdID= 33039
                    100% Color Bars  value= 1
                    75% Color Bars  value= 2
                    SMPTE Bars  value= 3
                    Tartan  value= 4
                    PLUGE  value= 5
                    Ramp  value= 6
                    Sweep  value= 7
                    Pulse and Bar  value= 8
                    Burst  value= 9
                    Black  value= 10  "
        ::= { iqhip10CmdEntry 33039 }

END

---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: 52051947
-- Comments		: Serial number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 000:00:49:00
-- Comments		: Uptime of unit
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
--
-- Value(s)		: 54
-- Comments		: ID Number of the Rear Connector
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: INPUT_1_VI
--
-- MIB ref		: swCardEventLogSlotXX       .10.73.78.80.85.84.95.49.95.86.73
-- absolute OID	: 1.3.6.1.4.1.7995.2.6.1.1.XX.10.73.78.80.85.84.95.49.95.86.73
--
-- Value(s)		: AFD2:16:9
-- Comments		:
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: QOS 6.5.0
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
--
-- Value(s)		: Disabled
-- Comments		:
--
---------------------------------------------------------------------------------------------------
-- Header		: SFP_1_TYPE
--
-- MIB ref		: swCardEventLogSlotXX       .10.83.70.80.95.49.95.84.89.80.69
-- absolute OID	: 1.3.6.1.4.1.7995.2.6.1.1.XX.10.83.70.80.95.49.95.84.89.80.69
--
-- Value(s)		: Tx
--				:   Rx
-- Comments		:
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
--
-- Value(s)		: 14
-- Comments		:
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
--
-- Value(s)		: 1
-- Comments		:
--
---------------------------------------------------------------------------------------------------
-- Header		: INPUT_1_APL
--
-- MIB ref		: swCardEventLogSlotXX       .11.73.78.80.85.84.95.49.95.65.80.76
-- absolute OID	: 1.3.6.1.4.1.7995.2.6.1.1.XX.11.73.78.80.85.84.95.49.95.65.80.76
--
-- Value(s)		: OK
--				: WARN:MAX APL
-- Comments		:
--
---------------------------------------------------------------------------------------------------
-- Header		: INPUT_1_CRC
--
-- MIB ref		: swCardEventLogSlotXX       .11.73.78.80.85.84.95.49.95.67.82.67
-- absolute OID	: 1.3.6.1.4.1.7995.2.6.1.1.XX.11.73.78.80.85.84.95.49.95.67.82.67
--
-- Value(s)		: OK
--				: WARN:CRC Error
-- Comments		:
--
---------------------------------------------------------------------------------------------------
-- Header		: INPUT_1_EDH
--
-- MIB ref		: swCardEventLogSlotXX       .11.73.78.80.85.84.95.49.95.69.68.72
-- absolute OID	: 1.3.6.1.4.1.7995.2.6.1.1.XX.11.73.78.80.85.84.95.49.95.69.68.72
--
-- Value(s)		: OK
--				: WARN:EDH Error
--				: NONE
-- Comments		:
--
---------------------------------------------------------------------------------------------------
-- Header		: INPUT_1_WSS
--
-- MIB ref		: swCardEventLogSlotXX       .11.73.78.80.85.84.95.49.95.87.83.83
-- absolute OID	: 1.3.6.1.4.1.7995.2.6.1.1.XX.11.73.78.80.85.84.95.49.95.87.83.83
--
-- Value(s)		: AFD0:CodedFrame
-- Comments		:
--
---------------------------------------------------------------------------------------------------
-- Header		: POWER_USAGE
--
-- MIB ref		: swCardEventLogSlotXX       .11.80.79.87.69.82.95.85.83.65.71.69
-- absolute OID	: 1.3.6.1.4.1.7995.2.6.1.1.XX.11.80.79.87.69.82.95.85.83.65.71.69
--
-- Value(s)		: 14.0W/12.6LU
-- Comments		:
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
--
-- Value(s)		: OK
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 113
-- Comments		: Embedded code build number
--
---------------------------------------------------------------------------------------------------
-- Header		: INPUT_1_2016
--
-- MIB ref		: swCardEventLogSlotXX       .12.73.78.80.85.84.95.49.95.50.48.49.54
-- absolute OID	: 1.3.6.1.4.1.7995.2.6.1.1.XX.12.73.78.80.85.84.95.49.95.50.48.49.54
--
-- Value(s)		: AFD10:16:9 center
-- Comments		:
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
--
-- Value(s)		: INPUT 1 SERIAL IN
-- Comments		:
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD/SD/3G SDI
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: SFP_1_STATUS
--
-- MIB ref		: swCardEventLogSlotXX       .12.83.70.80.95.49.95.83.84.65.84.85.83
-- absolute OID	: 1.3.6.1.4.1.7995.2.6.1.1.XX.12.83.70.80.95.49.95.83.84.65.84.85.83
--
-- Value(s)		: OK
-- Comments		:
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
--
-- Value(s)		: SERIAL IN
-- Comments		:
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: OK
--				: FAIL:Lost
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_UMID
--
-- MIB ref		: swCardEventLogSlotXX       .13.79.85.84.80.85.84.95.49.95.85.77.73.68
-- absolute OID	: 1.3.6.1.4.1.7995.2.6.1.1.XX.13.79.85.84.80.85.84.95.49.95.85.77.73.68
--
-- Value(s)		: 060A2B3401010124010105241312234567891023908765437788990011223344
-- Comments		:
--
---------------------------------------------------------------------------------------------------
-- Header		: REGION_1_BLACK
--
-- MIB ref		: swCardEventLogSlotXX       .14.82.69.71.73.79.78.95.49.95.66.76.65.67.75
-- absolute OID	: 1.3.6.1.4.1.7995.2.6.1.1.XX.14.82.69.71.73.79.78.95.49.95.66.76.65.67.75
--
-- Value(s)		: OK
--				: FAIL:BLACK 1
-- Comments		:
--
---------------------------------------------------------------------------------------------------
-- Header		: REGION_2_BLACK
--
-- MIB ref		: swCardEventLogSlotXX       .14.82.69.71.73.79.78.95.50.95.66.76.65.67.75
-- absolute OID	: 1.3.6.1.4.1.7995.2.6.1.1.XX.14.82.69.71.73.79.78.95.50.95.66.76.65.67.75
--
-- Value(s)		: OK
--				: FAIL:BLACK 2
-- Comments		:
--
---------------------------------------------------------------------------------------------------
-- Header		: INPUT_A_RX_NAME
--
-- MIB ref		: swCardEventLogSlotXX       .15.73.78.80.85.84.95.65.95.82.88.95.78.65.77.69
-- absolute OID	: 1.3.6.1.4.1.7995.2.6.1.1.XX.15.73.78.80.85.84.95.65.95.82.88.95.78.65.77.69
--
-- Value(s)		: INPUT SFP A
-- Comments		:
--
---------------------------------------------------------------------------------------------------
-- Header		: REGION_1_FREEZE
--
-- MIB ref		: swCardEventLogSlotXX       .15.82.69.71.73.79.78.95.49.95.70.82.69.69.90.69
-- absolute OID	: 1.3.6.1.4.1.7995.2.6.1.1.XX.15.82.69.71.73.79.78.95.49.95.70.82.69.69.90.69
--
-- Value(s)		: OK
--				: FAIL:FREEZE 1
-- Comments		:
--
---------------------------------------------------------------------------------------------------
-- Header		: REGION_2_FREEZE
--
-- MIB ref		: swCardEventLogSlotXX       .15.82.69.71.73.79.78.95.50.95.70.82.69.69.90.69
-- absolute OID	: 1.3.6.1.4.1.7995.2.6.1.1.XX.15.82.69.71.73.79.78.95.50.95.70.82.69.69.90.69
--
-- Value(s)		: OK
--				: FAIL:FREEZE 2
-- Comments		:
--
---------------------------------------------------------------------------------------------------
-- Header		: SFP_1_CONNECTOR
--
-- MIB ref		: swCardEventLogSlotXX       .15.83.70.80.95.49.95.67.79.78.78.69.67.84.79.82
-- absolute OID	: 1.3.6.1.4.1.7995.2.6.1.1.XX.15.83.70.80.95.49.95.67.79.78.78.69.67.84.79.82
--
-- Value(s)		: Fiber LC
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: V160
-- Comments		:
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: RSUMO1B
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: 1080/29i
-- Comments		:
--
---------------------------------------------------------------------------------------------------
-- Header		: INPUT_1_VI_STATE
--
-- MIB ref		: swCardEventLogSlotXX       .16.73.78.80.85.84.95.49.95.86.73.95.83.84.65.84.69
-- absolute OID	: 1.3.6.1.4.1.7995.2.6.1.1.XX.16.73.78.80.85.84.95.49.95.86.73.95.83.84.65.84.69
--
-- Value(s)		: OK
--				: FAIL:No VI
-- Comments		:
--
---------------------------------------------------------------------------------------------------
-- Header		: INPUT_A_RX_IDENT
--
-- MIB ref		: swCardEventLogSlotXX       .16.73.78.80.85.84.95.65.95.82.88.95.73.68.69.78.84
-- absolute OID	: 1.3.6.1.4.1.7995.2.6.1.1.XX.16.73.78.80.85.84.95.65.95.82.88.95.73.68.69.78.84
--
-- Value(s)		: SERIAL I/O
-- Comments		:
--
---------------------------------------------------------------------------------------------------
-- Header		: INPUT_A_RX_POWER
--
-- MIB ref		: swCardEventLogSlotXX       .16.73.78.80.85.84.95.65.95.82.88.95.80.79.87.69.82
-- absolute OID	: 1.3.6.1.4.1.7995.2.6.1.1.XX.16.73.78.80.85.84.95.65.95.82.88.95.80.79.87.69.82
--
-- Value(s)		: -5.2dBm
--				: < -40.0dBm
-- Comments		:
--
---------------------------------------------------------------------------------------------------
-- Header		: INPUT_B_RX_POWER
--
-- MIB ref		: swCardEventLogSlotXX       .16.73.78.80.85.84.95.66.95.82.88.95.80.79.87.69.82
-- absolute OID	: 1.3.6.1.4.1.7995.2.6.1.1.XX.16.73.78.80.85.84.95.66.95.82.88.95.80.79.87.69.82
--
-- Value(s)		: -5.2dBm
--				: < -40.0dBm
-- Comments		:
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
--
-- Value(s)		: "3G
--				: SDHD"
--				: FAIL:No File
-- Comments		:
--
---------------------------------------------------------------------------------------------------
-- Header		: INPUT_1_CAPTION_1
--
-- MIB ref		: swCardEventLogSlotXX       .17.73.78.80.85.84.95.49.95.67.65.80.84.73.79.78.95.49
-- absolute OID	: 1.3.6.1.4.1.7995.2.6.1.1.XX.17.73.78.80.85.84.95.49.95.67.65.80.84.73.79.78.95.49
--
-- Value(s)		: Caption 1
-- Comments		:
--
---------------------------------------------------------------------------------------------------
-- Header		: INPUT_1_CAPTION_2
--
-- MIB ref		: swCardEventLogSlotXX       .17.73.78.80.85.84.95.49.95.67.65.80.84.73.79.78.95.50
-- absolute OID	: 1.3.6.1.4.1.7995.2.6.1.1.XX.17.73.78.80.85.84.95.49.95.67.65.80.84.73.79.78.95.50
--
-- Value(s)		: Caption 2
-- Comments		:
--
---------------------------------------------------------------------------------------------------
-- Header		: INPUT_1_ETSI_DATA
--
-- MIB ref		: swCardEventLogSlotXX       .17.73.78.80.85.84.95.49.95.69.84.83.73.95.68.65.84.65
-- absolute OID	: 1.3.6.1.4.1.7995.2.6.1.1.XX.17.73.78.80.85.84.95.49.95.69.84.83.73.95.68.65.84.65
--
-- Value(s)		: OK
--				: FAIL:No User1 ANC
-- Comments		:
--
---------------------------------------------------------------------------------------------------
-- Header		: INPUT_1_PID_STATE
--
-- MIB ref		: swCardEventLogSlotXX       .17.73.78.80.85.84.95.49.95.80.73.68.95.83.84.65.84.69
-- absolute OID	: 1.3.6.1.4.1.7995.2.6.1.1.XX.17.73.78.80.85.84.95.49.95.80.73.68.95.83.84.65.84.69
--
-- Value(s)		: OK
-- Comments		:
--
---------------------------------------------------------------------------------------------------
-- Header		: INPUT_1_PID_TITLE
--
-- MIB ref		: swCardEventLogSlotXX       .17.73.78.80.85.84.95.49.95.80.73.68.95.84.73.84.76.69
-- absolute OID	: 1.3.6.1.4.1.7995.2.6.1.1.XX.17.73.78.80.85.84.95.49.95.80.73.68.95.84.73.84.76.69
--
-- Value(s)		: Title
-- Comments		:
--
---------------------------------------------------------------------------------------------------
-- Header		: INPUT_1_VI_ASPECT
--
-- MIB ref		: swCardEventLogSlotXX       .17.73.78.80.85.84.95.49.95.86.73.95.65.83.80.69.67.84
-- absolute OID	: 1.3.6.1.4.1.7995.2.6.1.1.XX.17.73.78.80.85.84.95.49.95.86.73.95.65.83.80.69.67.84
--
-- Value(s)		: 16:9
-- Comments		:
--
---------------------------------------------------------------------------------------------------
-- Header		: INPUT_1_WSS_STATE
--
-- MIB ref		: swCardEventLogSlotXX       .17.73.78.80.85.84.95.49.95.87.83.83.95.83.84.65.84.69
-- absolute OID	: 1.3.6.1.4.1.7995.2.6.1.1.XX.17.73.78.80.85.84.95.49.95.87.83.83.95.83.84.65.84.69
--
-- Value(s)		: OK
-- Comments		:
--
---------------------------------------------------------------------------------------------------
-- Header		: OUTPUT_A_TX_POWER
--
-- MIB ref		: swCardEventLogSlotXX       .17.79.85.84.80.85.84.95.65.95.84.88.95.80.79.87.69.82
-- absolute OID	: 1.3.6.1.4.1.7995.2.6.1.1.XX.17.79.85.84.80.85.84.95.65.95.84.88.95.80.79.87.69.82
--
-- Value(s)		: -2.0dBm
--				: < -40.0dBm
-- Comments		:
--
---------------------------------------------------------------------------------------------------
-- Header		: OUTPUT_B_TX_POWER
--
-- MIB ref		: swCardEventLogSlotXX       .17.79.85.84.80.85.84.95.66.95.84.88.95.80.79.87.69.82
-- absolute OID	: 1.3.6.1.4.1.7995.2.6.1.1.XX.17.79.85.84.80.85.84.95.66.95.84.88.95.80.79.87.69.82
--
-- Value(s)		: -2.0dBm
--				: < -40.0dBm
-- Comments		:
--
---------------------------------------------------------------------------------------------------
-- Header		: REGION_1_BLACKISH
--
-- MIB ref		: swCardEventLogSlotXX       .17.82.69.71.73.79.78.95.49.95.66.76.65.67.75.73.83.72
-- absolute OID	: 1.3.6.1.4.1.7995.2.6.1.1.XX.17.82.69.71.73.79.78.95.49.95.66.76.65.67.75.73.83.72
--
-- Value(s)		: OK
--				: FAIL:BLACKISH 1
-- Comments		:
--
---------------------------------------------------------------------------------------------------
-- Header		: REGION_1_STILLISH
--
-- MIB ref		: swCardEventLogSlotXX       .17.82.69.71.73.79.78.95.49.95.83.84.73.76.76.73.83.72
-- absolute OID	: 1.3.6.1.4.1.7995.2.6.1.1.XX.17.82.69.71.73.79.78.95.49.95.83.84.73.76.76.73.83.72
--
-- Value(s)		: OK
--				: FAIL:STILLISH 1
-- Comments		:
--
---------------------------------------------------------------------------------------------------
-- Header		: REGION_2_BLACKISH
--
-- MIB ref		: swCardEventLogSlotXX       .17.82.69.71.73.79.78.95.50.95.66.76.65.67.75.73.83.72
-- absolute OID	: 1.3.6.1.4.1.7995.2.6.1.1.XX.17.82.69.71.73.79.78.95.50.95.66.76.65.67.75.73.83.72
--
-- Value(s)		: OK
--				: FAIL:BLACKISH 2
-- Comments		:
--
---------------------------------------------------------------------------------------------------
-- Header		: REGION_2_STILLISH
--
-- MIB ref		: swCardEventLogSlotXX       .17.82.69.71.73.79.78.95.50.95.83.84.73.76.76.73.83.72
-- absolute OID	: 1.3.6.1.4.1.7995.2.6.1.1.XX.17.82.69.71.73.79.78.95.50.95.83.84.73.76.76.73.83.72
--
-- Value(s)		: OK
--				: FAIL:STILLISH 2
-- Comments		:
--
---------------------------------------------------------------------------------------------------
-- Header		: INPUT_1_2016_STATE
--
-- MIB ref		: swCardEventLogSlotXX       .18.73.78.80.85.84.95.49.95.50.48.49.54.95.83.84.65.84.69
-- absolute OID	: 1.3.6.1.4.1.7995.2.6.1.1.XX.18.73.78.80.85.84.95.49.95.50.48.49.54.95.83.84.65.84.69
--
-- Value(s)		: OK
--				: FAIL:No AFD
-- Comments		:
--
---------------------------------------------------------------------------------------------------
-- Header		: INPUT_1_UMID_STATE
--
-- MIB ref		: swCardEventLogSlotXX       .18.73.78.80.85.84.95.49.95.85.77.73.68.95.83.84.65.84.69
-- absolute OID	: 1.3.6.1.4.1.7995.2.6.1.1.XX.18.73.78.80.85.84.95.49.95.85.77.73.68.95.83.84.65.84.69
--
-- Value(s)		: OK
-- Comments		:
--
---------------------------------------------------------------------------------------------------
-- Header		: INPUT_1_VITC_STATE
--
-- MIB ref		: swCardEventLogSlotXX       .18.73.78.80.85.84.95.49.95.86.73.84.67.95.83.84.65.84.69
-- absolute OID	: 1.3.6.1.4.1.7995.2.6.1.1.XX.18.73.78.80.85.84.95.49.95.86.73.84.67.95.83.84.65.84.69
--
-- Value(s)		: OK
--				: FAIL:No VITC
-- Comments		:
--
---------------------------------------------------------------------------------------------------
-- Header		: INPUT_1_WSS_ASPECT
--
-- MIB ref		: swCardEventLogSlotXX       .18.73.78.80.85.84.95.49.95.87.83.83.95.65.83.80.69.67.84
-- absolute OID	: 1.3.6.1.4.1.7995.2.6.1.1.XX.18.73.78.80.85.84.95.49.95.87.83.83.95.65.83.80.69.67.84
--
-- Value(s)		: 16:9
-- Comments		:
--
---------------------------------------------------------------------------------------------------
-- Header		: OUTPUT_1_PID_STATE
--
-- MIB ref		: swCardEventLogSlotXX       .18.79.85.84.80.85.84.95.49.95.80.73.68.95.83.84.65.84.69
-- absolute OID	: 1.3.6.1.4.1.7995.2.6.1.1.XX.18.79.85.84.80.85.84.95.49.95.80.73.68.95.83.84.65.84.69
--
-- Value(s)		: Pass
-- Comments		:
--
---------------------------------------------------------------------------------------------------
-- Header		: OUTPUT_1_PID_TITLE
--
-- MIB ref		: swCardEventLogSlotXX       .18.79.85.84.80.85.84.95.49.95.80.73.68.95.84.73.84.76.69
-- absolute OID	: 1.3.6.1.4.1.7995.2.6.1.1.XX.18.79.85.84.80.85.84.95.49.95.80.73.68.95.84.73.84.76.69
--
-- Value(s)		: Title
-- Comments		:
--
---------------------------------------------------------------------------------------------------
-- Header		: INPUT_1_2016_ASPECT
--
-- MIB ref		: swCardEventLogSlotXX       .19.73.78.80.85.84.95.49.95.50.48.49.54.95.65.83.80.69.67.84
-- absolute OID	: 1.3.6.1.4.1.7995.2.6.1.1.XX.19.73.78.80.85.84.95.49.95.50.48.49.54.95.65.83.80.69.67.84
--
-- Value(s)		: 16:9
-- Comments		:
--
---------------------------------------------------------------------------------------------------
-- Header		: INPUT_1_C_BIT_DEPTH
--
-- MIB ref		: swCardEventLogSlotXX       .19.73.78.80.85.84.95.49.95.67.95.66.73.84.95.68.69.80.84.72
-- absolute OID	: 1.3.6.1.4.1.7995.2.6.1.1.XX.19.73.78.80.85.84.95.49.95.67.95.66.73.84.95.68.69.80.84.72
--
-- Value(s)		: 10
--				: 9
-- Comments		:
--
---------------------------------------------------------------------------------------------------
-- Header		: INPUT_1_C_VIDEO_LOW
--
-- MIB ref		: swCardEventLogSlotXX       .19.73.78.80.85.84.95.49.95.67.95.86.73.68.69.79.95.76.79.87
-- absolute OID	: 1.3.6.1.4.1.7995.2.6.1.1.XX.19.73.78.80.85.84.95.49.95.67.95.86.73.68.69.79.95.76.79.87
--
-- Value(s)		: OK
--				: FAIL:Low
-- Comments		:
--
---------------------------------------------------------------------------------------------------
-- Header		: INPUT_1_PID_SEG_NUM
--
-- MIB ref		: swCardEventLogSlotXX       .19.73.78.80.85.84.95.49.95.80.73.68.95.83.69.71.95.78.85.77
-- absolute OID	: 1.3.6.1.4.1.7995.2.6.1.1.XX.19.73.78.80.85.84.95.49.95.80.73.68.95.83.69.71.95.78.85.77
--
-- Value(s)		: 0
-- Comments		:
--
---------------------------------------------------------------------------------------------------
-- Header		: INPUT_1_Y_BIT_DEPTH
--
-- MIB ref		: swCardEventLogSlotXX       .19.73.78.80.85.84.95.49.95.89.95.66.73.84.95.68.69.80.84.72
-- absolute OID	: 1.3.6.1.4.1.7995.2.6.1.1.XX.19.73.78.80.85.84.95.49.95.89.95.66.73.84.95.68.69.80.84.72
--
-- Value(s)		: 10
--				: 9
-- Comments		:
--
---------------------------------------------------------------------------------------------------
-- Header		: INPUT_1_Y_VIDEO_LOW
--
-- MIB ref		: swCardEventLogSlotXX       .19.73.78.80.85.84.95.49.95.89.95.86.73.68.69.79.95.76.79.87
-- absolute OID	: 1.3.6.1.4.1.7995.2.6.1.1.XX.19.73.78.80.85.84.95.49.95.89.95.86.73.68.69.79.95.76.79.87
--
-- Value(s)		: OK
--				: FAIL:Low
-- Comments		:
--
---------------------------------------------------------------------------------------------------
-- Header		: OUTPUT_1_OSD_STATUS
--
-- MIB ref		: swCardEventLogSlotXX       .19.79.85.84.80.85.84.95.49.95.79.83.68.95.83.84.65.84.85.83
-- absolute OID	: 1.3.6.1.4.1.7995.2.6.1.1.XX.19.79.85.84.80.85.84.95.49.95.79.83.68.95.83.84.65.84.85.83
--
-- Value(s)		: WARN:ON
--				: OFF
-- Comments		:
--
---------------------------------------------------------------------------------------------------
-- Header		: OUTPUT_1_UMID_STATE
--
-- MIB ref		: swCardEventLogSlotXX       .19.79.85.84.80.85.84.95.49.95.85.77.73.68.95.83.84.65.84.69
-- absolute OID	: 1.3.6.1.4.1.7995.2.6.1.1.XX.19.79.85.84.80.85.84.95.49.95.85.77.73.68.95.83.84.65.84.69
--
-- Value(s)		: Pass
-- Comments		:
--
---------------------------------------------------------------------------------------------------
-- Header		: OUTPUT_A_LASER_BIAS
--
-- MIB ref		: swCardEventLogSlotXX       .19.79.85.84.80.85.84.95.65.95.76.65.83.69.82.95.66.73.65.83
-- absolute OID	: 1.3.6.1.4.1.7995.2.6.1.1.XX.19.79.85.84.80.85.84.95.65.95.76.65.83.69.82.95.66.73.65.83
--
-- Value(s)		: 10.1mA
-- Comments		:
--
---------------------------------------------------------------------------------------------------
-- Header		: OUTPUT_A_WAVELENGTH
--
-- MIB ref		: swCardEventLogSlotXX       .19.79.85.84.80.85.84.95.65.95.87.65.86.69.76.69.78.71.84.72
-- absolute OID	: 1.3.6.1.4.1.7995.2.6.1.1.XX.19.79.85.84.80.85.84.95.65.95.87.65.86.69.76.69.78.71.84.72
--
-- Value(s)		: 1310nm
-- Comments		:
--
---------------------------------------------------------------------------------------------------
-- Header		: OUTPUT_B_LASER_BIAS
--
-- MIB ref		: swCardEventLogSlotXX       .19.79.85.84.80.85.84.95.66.95.76.65.83.69.82.95.66.73.65.83
-- absolute OID	: 1.3.6.1.4.1.7995.2.6.1.1.XX.19.79.85.84.80.85.84.95.66.95.76.65.83.69.82.95.66.73.65.83
--
-- Value(s)		: 10.1mA
-- Comments		:
--
---------------------------------------------------------------------------------------------------
-- Header		: OUTPUT_B_WAVELENGTH
--
-- MIB ref		: swCardEventLogSlotXX       .19.79.85.84.80.85.84.95.66.95.87.65.86.69.76.69.78.71.84.72
-- absolute OID	: 1.3.6.1.4.1.7995.2.6.1.1.XX.19.79.85.84.80.85.84.95.66.95.87.65.86.69.76.69.78.71.84.72
--
-- Value(s)		: 1310nm
-- Comments		:
--
---------------------------------------------------------------------------------------------------
-- Header		: INPUT_1_C_VIDEO_HIGH
--
-- MIB ref		: swCardEventLogSlotXX       .20.73.78.80.85.84.95.49.95.67.95.86.73.68.69.79.95.72.73.71.72
-- absolute OID	: 1.3.6.1.4.1.7995.2.6.1.1.XX.20.73.78.80.85.84.95.49.95.67.95.86.73.68.69.79.95.72.73.71.72
--
-- Value(s)		: OK
--				: FAIL:High
-- Comments		:
--
---------------------------------------------------------------------------------------------------
-- Header		: INPUT_1_PID_DURATION
--
-- MIB ref		: swCardEventLogSlotXX       .20.73.78.80.85.84.95.49.95.80.73.68.95.68.85.82.65.84.73.79.78
-- absolute OID	: 1.3.6.1.4.1.7995.2.6.1.1.XX.20.73.78.80.85.84.95.49.95.80.73.68.95.68.85.82.65.84.73.79.78
--
-- Value(s)		: 0
-- Comments		:
--
---------------------------------------------------------------------------------------------------
-- Header		: INPUT_1_PID_HOUSE_ID
--
-- MIB ref		: swCardEventLogSlotXX       .20.73.78.80.85.84.95.49.95.80.73.68.95.72.79.85.83.69.95.73.68
-- absolute OID	: 1.3.6.1.4.1.7995.2.6.1.1.XX.20.73.78.80.85.84.95.49.95.80.73.68.95.72.79.85.83.69.95.73.68
--
-- Value(s)		: House ID
-- Comments		:
--
---------------------------------------------------------------------------------------------------
-- Header		: INPUT_1_UMID_CURRENT
--
-- MIB ref		: swCardEventLogSlotXX       .20.73.78.80.85.84.95.49.95.85.77.73.68.95.67.85.82.82.69.78.84
-- absolute OID	: 1.3.6.1.4.1.7995.2.6.1.1.XX.20.73.78.80.85.84.95.49.95.85.77.73.68.95.67.85.82.82.69.78.84
--
-- Value(s)		: 060A2B3401010124010105241312234567891023908765437788990011223344
-- Comments		:
--
---------------------------------------------------------------------------------------------------
-- Header		: INPUT_1_Y_VIDEO_HIGH
--
-- MIB ref		: swCardEventLogSlotXX       .20.73.78.80.85.84.95.49.95.89.95.86.73.68.69.79.95.72.73.71.72
-- absolute OID	: 1.3.6.1.4.1.7995.2.6.1.1.XX.20.73.78.80.85.84.95.49.95.89.95.86.73.68.69.79.95.72.73.71.72
--
-- Value(s)		: OK
--				: FAIL:High
-- Comments		:
--
---------------------------------------------------------------------------------------------------
-- Header		: LAST_RECALLED_MEMORY
--
-- MIB ref		: swCardEventLogSlotXX       .20.76.65.83.84.95.82.69.67.65.76.76.69.68.95.77.69.77.79.82.89
-- absolute OID	: 1.3.6.1.4.1.7995.2.6.1.1.XX.20.76.65.83.84.95.82.69.67.65.76.76.69.68.95.77.69.77.79.82.89
--
-- Value(s)		: User Memeory 1
-- Comments		:
--
---------------------------------------------------------------------------------------------------
-- Header		: OUTPUT_1_PID_SEG_NUM
--
-- MIB ref		: swCardEventLogSlotXX       .20.79.85.84.80.85.84.95.49.95.80.73.68.95.83.69.71.95.78.85.77
-- absolute OID	: 1.3.6.1.4.1.7995.2.6.1.1.XX.20.79.85.84.80.85.84.95.49.95.80.73.68.95.83.69.71.95.78.85.77
--
-- Value(s)		: 0
-- Comments		:
--
---------------------------------------------------------------------------------------------------
-- Header		: INPUT_1_UMID_PREVIOUS
--
-- MIB ref		: swCardEventLogSlotXX       .21.73.78.80.85.84.95.49.95.85.77.73.68.95.80.82.69.86.73.79.85.83
-- absolute OID	: 1.3.6.1.4.1.7995.2.6.1.1.XX.21.73.78.80.85.84.95.49.95.85.77.73.68.95.80.82.69.86.73.79.85.83
--
-- Value(s)		: 060A2B3401010124010105241312234567891023908765437788990011223344
-- Comments		:
--
---------------------------------------------------------------------------------------------------
-- Header		: OUTPUT_1_PID_DURATION
--
-- MIB ref		: swCardEventLogSlotXX       .21.79.85.84.80.85.84.95.49.95.80.73.68.95.68.85.82.65.84.73.79.78
-- absolute OID	: 1.3.6.1.4.1.7995.2.6.1.1.XX.21.79.85.84.80.85.84.95.49.95.80.73.68.95.68.85.82.65.84.73.79.78
--
-- Value(s)		: 0
-- Comments		:
--
---------------------------------------------------------------------------------------------------
-- Header		: OUTPUT_1_PID_HOUSE_ID
--
-- MIB ref		: swCardEventLogSlotXX       .21.79.85.84.80.85.84.95.49.95.80.73.68.95.72.79.85.83.69.95.73.68
-- absolute OID	: 1.3.6.1.4.1.7995.2.6.1.1.XX.21.79.85.84.80.85.84.95.49.95.80.73.68.95.72.79.85.83.69.95.73.68
--
-- Value(s)		: House ID
-- Comments		:
--
---------------------------------------------------------------------------------------------------
-- Header		: INPUT_1_PID_FRAME_RATE
--
-- MIB ref		: swCardEventLogSlotXX       .22.73.78.80.85.84.95.49.95.80.73.68.95.70.82.65.77.69.95.82.65.84.69
-- absolute OID	: 1.3.6.1.4.1.7995.2.6.1.1.XX.22.73.78.80.85.84.95.49.95.80.73.68.95.70.82.65.77.69.95.82.65.84.69
--
-- Value(s)		: 29.97
-- Comments		:
--
---------------------------------------------------------------------------------------------------
-- Header		: INPUT_A_RX_POWER_STATE
--
-- MIB ref		: swCardEventLogSlotXX       .22.73.78.80.85.84.95.65.95.82.88.95.80.79.87.69.82.95.83.84.65.84.69
-- absolute OID	: 1.3.6.1.4.1.7995.2.6.1.1.XX.22.73.78.80.85.84.95.65.95.82.88.95.80.79.87.69.82.95.83.84.65.84.69
--
-- Value(s)		: OK
--				: FAIL:LOW
-- Comments		:
--
---------------------------------------------------------------------------------------------------
-- Header		: INPUT_B_RX_POWER_STATE
--
-- MIB ref		: swCardEventLogSlotXX       .22.73.78.80.85.84.95.66.95.82.88.95.80.79.87.69.82.95.83.84.65.84.69
-- absolute OID	: 1.3.6.1.4.1.7995.2.6.1.1.XX.22.73.78.80.85.84.95.66.95.82.88.95.80.79.87.69.82.95.83.84.65.84.69
--
-- Value(s)		: OK
--				: FAIL:LOW
-- Comments		:
--
---------------------------------------------------------------------------------------------------
-- Header		: OUTPUT_1_PID_FRAME_RATE
--
-- MIB ref		: swCardEventLogSlotXX       .23.79.85.84.80.85.84.95.49.95.80.73.68.95.70.82.65.77.69.95.82.65.84.69
-- absolute OID	: 1.3.6.1.4.1.7995.2.6.1.1.XX.23.79.85.84.80.85.84.95.49.95.80.73.68.95.70.82.65.77.69.95.82.65.84.69
--
-- Value(s)		: 29.97
-- Comments		:
--
---------------------------------------------------------------------------------------------------
-- Header		: OUTPUT_A_TX_POWER_STATE
--
-- MIB ref		: swCardEventLogSlotXX       .23.79.85.84.80.85.84.95.65.95.84.88.95.80.79.87.69.82.95.83.84.65.84.69
-- absolute OID	: 1.3.6.1.4.1.7995.2.6.1.1.XX.23.79.85.84.80.85.84.95.65.95.84.88.95.80.79.87.69.82.95.83.84.65.84.69
--
-- Value(s)		: OK
--				: FAIL:LOW
-- Comments		:
--
---------------------------------------------------------------------------------------------------
-- Header		: OUTPUT_B_TX_POWER_STATE
--
-- MIB ref		: swCardEventLogSlotXX       .23.79.85.84.80.85.84.95.66.95.84.88.95.80.79.87.69.82.95.83.84.65.84.69
-- absolute OID	: 1.3.6.1.4.1.7995.2.6.1.1.XX.23.79.85.84.80.85.84.95.66.95.84.88.95.80.79.87.69.82.95.83.84.65.84.69
--
-- Value(s)		: OK
--				: FAIL:LOW
-- Comments		:
--
---------------------------------------------------------------------------------------------------
-- Header		: INPUT_1_HYPERION_SUMMARY
--
-- MIB ref		: swCardEventLogSlotXX       .24.73.78.80.85.84.95.49.95.72.89.80.69.82.73.79.78.95.83.85.77.77.65.82.89
-- absolute OID	: 1.3.6.1.4.1.7995.2.6.1.1.XX.24.73.78.80.85.84.95.49.95.72.89.80.69.82.73.79.78.95.83.85.77.77.65.82.89
--
-- Value(s)		: OK
--				: FAIL
-- Comments		:
--
---------------------------------------------------------------------------------------------------
-- Header		: OUTPUT_A_LASER_BIAS_STATE
--
-- MIB ref		: swCardEventLogSlotXX       .25.79.85.84.80.85.84.95.65.95.76.65.83.69.82.95.66.73.65.83.95.83.84.65.84.69
-- absolute OID	: 1.3.6.1.4.1.7995.2.6.1.1.XX.25.79.85.84.80.85.84.95.65.95.76.65.83.69.82.95.66.73.65.83.95.83.84.65.84.69
--
-- Value(s)		: OK
--				: FAIL:LOW
-- Comments		:
--
---------------------------------------------------------------------------------------------------
-- Header		: OUTPUT_B_LASER_BIAS_STATE
--
-- MIB ref		: swCardEventLogSlotXX       .25.79.85.84.80.85.84.95.66.95.76.65.83.69.82.95.66.73.65.83.95.83.84.65.84.69
-- absolute OID	: 1.3.6.1.4.1.7995.2.6.1.1.XX.25.79.85.84.80.85.84.95.66.95.76.65.83.69.82.95.66.73.65.83.95.83.84.65.84.69
--
-- Value(s)		: OK
--				: FAIL:LOW
-- Comments		:
--
---------------------------------------------------------------------------------------------------
-- Header		: INPUT_1_PID_PREVIOUS_COUNT
--
-- MIB ref		: swCardEventLogSlotXX       .26.73.78.80.85.84.95.49.95.80.73.68.95.80.82.69.86.73.79.85.83.95.67.79.85.78.84
-- absolute OID	: 1.3.6.1.4.1.7995.2.6.1.1.XX.26.73.78.80.85.84.95.49.95.80.73.68.95.80.82.69.86.73.79.85.83.95.67.79.85.78.84
--
-- Value(s)		: 517
-- Comments		:
--
---------------------------------------------------------------------------------------------------
-- Header		: INPUT_1_PID_PREVIOUS_TITLE
--
-- MIB ref		: swCardEventLogSlotXX       .26.73.78.80.85.84.95.49.95.80.73.68.95.80.82.69.86.73.79.85.83.95.84.73.84.76.69
-- absolute OID	: 1.3.6.1.4.1.7995.2.6.1.1.XX.26.73.78.80.85.84.95.49.95.80.73.68.95.80.82.69.86.73.79.85.83.95.84.73.84.76.69
--
-- Value(s)		: Title
-- Comments		:
--
---------------------------------------------------------------------------------------------------
-- Header		: INPUT_1_CLOSED_CAPTION_TYPE
--
-- MIB ref		: swCardEventLogSlotXX       .27.73.78.80.85.84.95.49.95.67.76.79.83.69.68.95.67.65.80.84.73.79.78.95.84.89.80.69
-- absolute OID	: 1.3.6.1.4.1.7995.2.6.1.1.XX.27.73.78.80.85.84.95.49.95.67.76.79.83.69.68.95.67.65.80.84.73.79.78.95.84.89.80.69
--
-- Value(s)		: EIA608
--				: EIA708
-- Comments		:
--
---------------------------------------------------------------------------------------------------
-- Header		: INPUT_1_CLOSED_CAPTION_STATE
--
-- MIB ref		: swCardEventLogSlotXX       .28.73.78.80.85.84.95.49.95.67.76.79.83.69.68.95.67.65.80.84.73.79.78.95.83.84.65.84.69
-- absolute OID	: 1.3.6.1.4.1.7995.2.6.1.1.XX.28.73.78.80.85.84.95.49.95.67.76.79.83.69.68.95.67.65.80.84.73.79.78.95.83.84.65.84.69
--
-- Value(s)		: OK
--				: FAIL:No Closed Caption
-- Comments		:
--
---------------------------------------------------------------------------------------------------
-- Header		: INPUT_1_CLOSED_CAPTION_TITLE
--
-- MIB ref		: swCardEventLogSlotXX       .28.73.78.80.85.84.95.49.95.67.76.79.83.69.68.95.67.65.80.84.73.79.78.95.84.73.84.76.69
-- absolute OID	: 1.3.6.1.4.1.7995.2.6.1.1.XX.28.73.78.80.85.84.95.49.95.67.76.79.83.69.68.95.67.65.80.84.73.79.78.95.84.73.84.76.69
--
-- Value(s)		: Hello World
-- Comments		:
--
---------------------------------------------------------------------------------------------------
-- Header		: INPUT_1_EMBED_AUDIO_1_1_TYPE
--
-- MIB ref		: swCardEventLogSlotXX       .28.73.78.80.85.84.95.49.95.69.77.66.69.68.95.65.85.68.73.79.95.49.95.49.95.84.89.80.69
-- absolute OID	: 1.3.6.1.4.1.7995.2.6.1.1.XX.28.73.78.80.85.84.95.49.95.69.77.66.69.68.95.65.85.68.73.79.95.49.95.49.95.84.89.80.69
--
-- Value(s)		: WARN:No Input
--				: PCM
-- Comments		:
--
---------------------------------------------------------------------------------------------------
-- Header		: INPUT_1_EMBED_AUDIO_1_2_TYPE
--
-- MIB ref		: swCardEventLogSlotXX       .28.73.78.80.85.84.95.49.95.69.77.66.69.68.95.65.85.68.73.79.95.49.95.50.95.84.89.80.69
-- absolute OID	: 1.3.6.1.4.1.7995.2.6.1.1.XX.28.73.78.80.85.84.95.49.95.69.77.66.69.68.95.65.85.68.73.79.95.49.95.50.95.84.89.80.69
--
-- Value(s)		: WARN:No Input
--				: PCM
-- Comments		:
--
---------------------------------------------------------------------------------------------------
-- Header		: INPUT_1_EMBED_AUDIO_2_1_TYPE
--
-- MIB ref		: swCardEventLogSlotXX       .28.73.78.80.85.84.95.49.95.69.77.66.69.68.95.65.85.68.73.79.95.50.95.49.95.84.89.80.69
-- absolute OID	: 1.3.6.1.4.1.7995.2.6.1.1.XX.28.73.78.80.85.84.95.49.95.69.77.66.69.68.95.65.85.68.73.79.95.50.95.49.95.84.89.80.69
--
-- Value(s)		: WARN:No Input
--				: PCM
-- Comments		:
--
---------------------------------------------------------------------------------------------------
-- Header		: INPUT_1_EMBED_AUDIO_2_2_TYPE
--
-- MIB ref		: swCardEventLogSlotXX       .28.73.78.80.85.84.95.49.95.69.77.66.69.68.95.65.85.68.73.79.95.50.95.50.95.84.89.80.69
-- absolute OID	: 1.3.6.1.4.1.7995.2.6.1.1.XX.28.73.78.80.85.84.95.49.95.69.77.66.69.68.95.65.85.68.73.79.95.50.95.50.95.84.89.80.69
--
-- Value(s)		: WARN:No Input
--				: PCM
-- Comments		:
--
---------------------------------------------------------------------------------------------------
-- Header		: INPUT_1_EMBED_AUDIO_3_1_TYPE
--
-- MIB ref		: swCardEventLogSlotXX       .28.73.78.80.85.84.95.49.95.69.77.66.69.68.95.65.85.68.73.79.95.51.95.49.95.84.89.80.69
-- absolute OID	: 1.3.6.1.4.1.7995.2.6.1.1.XX.28.73.78.80.85.84.95.49.95.69.77.66.69.68.95.65.85.68.73.79.95.51.95.49.95.84.89.80.69
--
-- Value(s)		: WARN:No Input
--				: PCM
-- Comments		:
--
---------------------------------------------------------------------------------------------------
-- Header		: INPUT_1_EMBED_AUDIO_3_2_TYPE
--
-- MIB ref		: swCardEventLogSlotXX       .28.73.78.80.85.84.95.49.95.69.77.66.69.68.95.65.85.68.73.79.95.51.95.50.95.84.89.80.69
-- absolute OID	: 1.3.6.1.4.1.7995.2.6.1.1.XX.28.73.78.80.85.84.95.49.95.69.77.66.69.68.95.65.85.68.73.79.95.51.95.50.95.84.89.80.69
--
-- Value(s)		: WARN:No Input
--				: PCM
-- Comments		:
--
---------------------------------------------------------------------------------------------------
-- Header		: INPUT_1_EMBED_AUDIO_4_1_TYPE
--
-- MIB ref		: swCardEventLogSlotXX       .28.73.78.80.85.84.95.49.95.69.77.66.69.68.95.65.85.68.73.79.95.52.95.49.95.84.89.80.69
-- absolute OID	: 1.3.6.1.4.1.7995.2.6.1.1.XX.28.73.78.80.85.84.95.49.95.69.77.66.69.68.95.65.85.68.73.79.95.52.95.49.95.84.89.80.69
--
-- Value(s)		: WARN:No Input
--				: PCM
-- Comments		:
--
---------------------------------------------------------------------------------------------------
-- Header		: INPUT_1_EMBED_AUDIO_4_2_TYPE
--
-- MIB ref		: swCardEventLogSlotXX       .28.73.78.80.85.84.95.49.95.69.77.66.69.68.95.65.85.68.73.79.95.52.95.50.95.84.89.80.69
-- absolute OID	: 1.3.6.1.4.1.7995.2.6.1.1.XX.28.73.78.80.85.84.95.49.95.69.77.66.69.68.95.65.85.68.73.79.95.52.95.50.95.84.89.80.69
--
-- Value(s)		: WARN:No Input
--				: PCM
-- Comments		:
--
---------------------------------------------------------------------------------------------------
-- Header		: INPUT_1_EMBED_AUDIO_5_1_TYPE
--
-- MIB ref		: swCardEventLogSlotXX       .28.73.78.80.85.84.95.49.95.69.77.66.69.68.95.65.85.68.73.79.95.53.95.49.95.84.89.80.69
-- absolute OID	: 1.3.6.1.4.1.7995.2.6.1.1.XX.28.73.78.80.85.84.95.49.95.69.77.66.69.68.95.65.85.68.73.79.95.53.95.49.95.84.89.80.69
--
-- Value(s)		: WARN:No Input
--				: PCM
-- Comments		:
--
---------------------------------------------------------------------------------------------------
-- Header		: INPUT_1_EMBED_AUDIO_5_2_TYPE
--
-- MIB ref		: swCardEventLogSlotXX       .28.73.78.80.85.84.95.49.95.69.77.66.69.68.95.65.85.68.73.79.95.53.95.50.95.84.89.80.69
-- absolute OID	: 1.3.6.1.4.1.7995.2.6.1.1.XX.28.73.78.80.85.84.95.49.95.69.77.66.69.68.95.65.85.68.73.79.95.53.95.50.95.84.89.80.69
--
-- Value(s)		: WARN:No Input
--				: PCM
-- Comments		:
--
---------------------------------------------------------------------------------------------------
-- Header		: INPUT_1_EMBED_AUDIO_6_1_TYPE
--
-- MIB ref		: swCardEventLogSlotXX       .28.73.78.80.85.84.95.49.95.69.77.66.69.68.95.65.85.68.73.79.95.54.95.49.95.84.89.80.69
-- absolute OID	: 1.3.6.1.4.1.7995.2.6.1.1.XX.28.73.78.80.85.84.95.49.95.69.77.66.69.68.95.65.85.68.73.79.95.54.95.49.95.84.89.80.69
--
-- Value(s)		: WARN:No Input
--				: PCM
-- Comments		:
--
---------------------------------------------------------------------------------------------------
-- Header		: INPUT_1_EMBED_AUDIO_6_2_TYPE
--
-- MIB ref		: swCardEventLogSlotXX       .28.73.78.80.85.84.95.49.95.69.77.66.69.68.95.65.85.68.73.79.95.54.95.50.95.84.89.80.69
-- absolute OID	: 1.3.6.1.4.1.7995.2.6.1.1.XX.28.73.78.80.85.84.95.49.95.69.77.66.69.68.95.65.85.68.73.79.95.54.95.50.95.84.89.80.69
--
-- Value(s)		: WARN:No Input
--				: PCM
-- Comments		:
--
---------------------------------------------------------------------------------------------------
-- Header		: INPUT_1_EMBED_AUDIO_7_1_TYPE
--
-- MIB ref		: swCardEventLogSlotXX       .28.73.78.80.85.84.95.49.95.69.77.66.69.68.95.65.85.68.73.79.95.55.95.49.95.84.89.80.69
-- absolute OID	: 1.3.6.1.4.1.7995.2.6.1.1.XX.28.73.78.80.85.84.95.49.95.69.77.66.69.68.95.65.85.68.73.79.95.55.95.49.95.84.89.80.69
--
-- Value(s)		: WARN:No Input
--				: PCM
-- Comments		:
--
---------------------------------------------------------------------------------------------------
-- Header		: INPUT_1_EMBED_AUDIO_7_2_TYPE
--
-- MIB ref		: swCardEventLogSlotXX       .28.73.78.80.85.84.95.49.95.69.77.66.69.68.95.65.85.68.73.79.95.55.95.50.95.84.89.80.69
-- absolute OID	: 1.3.6.1.4.1.7995.2.6.1.1.XX.28.73.78.80.85.84.95.49.95.69.77.66.69.68.95.65.85.68.73.79.95.55.95.50.95.84.89.80.69
--
-- Value(s)		: WARN:No Input
--				: PCM
-- Comments		:
--
---------------------------------------------------------------------------------------------------
-- Header		: INPUT_1_EMBED_AUDIO_8_1_TYPE
--
-- MIB ref		: swCardEventLogSlotXX       .28.73.78.80.85.84.95.49.95.69.77.66.69.68.95.65.85.68.73.79.95.56.95.49.95.84.89.80.69
-- absolute OID	: 1.3.6.1.4.1.7995.2.6.1.1.XX.28.73.78.80.85.84.95.49.95.69.77.66.69.68.95.65.85.68.73.79.95.56.95.49.95.84.89.80.69
--
-- Value(s)		: WARN:No Input
--				: PCM
-- Comments		:
--
---------------------------------------------------------------------------------------------------
-- Header		: INPUT_1_EMBED_AUDIO_8_2_TYPE
--
-- MIB ref		: swCardEventLogSlotXX       .28.73.78.80.85.84.95.49.95.69.77.66.69.68.95.65.85.68.73.79.95.56.95.50.95.84.89.80.69
-- absolute OID	: 1.3.6.1.4.1.7995.2.6.1.1.XX.28.73.78.80.85.84.95.49.95.69.77.66.69.68.95.65.85.68.73.79.95.56.95.50.95.84.89.80.69
--
-- Value(s)		: WARN:No Input
--				: PCM
-- Comments		:
--
---------------------------------------------------------------------------------------------------
-- Header		: INPUT_1_PID_PREVIOUS_SEG_NUM
--
-- MIB ref		: swCardEventLogSlotXX       .28.73.78.80.85.84.95.49.95.80.73.68.95.80.82.69.86.73.79.85.83.95.83.69.71.95.78.85.77
-- absolute OID	: 1.3.6.1.4.1.7995.2.6.1.1.XX.28.73.78.80.85.84.95.49.95.80.73.68.95.80.82.69.86.73.79.85.83.95.83.69.71.95.78.85.77
--
-- Value(s)		: 0
-- Comments		:
--
---------------------------------------------------------------------------------------------------
-- Header		: INPUT_1_EMBED_AUDIO_1_1_LEVEL
--
-- MIB ref		: swCardEventLogSlotXX       .29.73.78.80.85.84.95.49.95.69.77.66.69.68.95.65.85.68.73.79.95.49.95.49.95.76.69.86.69.76
-- absolute OID	: 1.3.6.1.4.1.7995.2.6.1.1.XX.29.73.78.80.85.84.95.49.95.69.77.66.69.68.95.65.85.68.73.79.95.49.95.49.95.76.69.86.69.76
--
-- Value(s)		: WARN:No Input
--				: OK
--				: FAIL:Silent
--				: FAIL:Quiet
-- Comments		:
--
---------------------------------------------------------------------------------------------------
-- Header		: INPUT_1_EMBED_AUDIO_1_1_STATE
--
-- MIB ref		: swCardEventLogSlotXX       .29.73.78.80.85.84.95.49.95.69.77.66.69.68.95.65.85.68.73.79.95.49.95.49.95.83.84.65.84.69
-- absolute OID	: 1.3.6.1.4.1.7995.2.6.1.1.XX.29.73.78.80.85.84.95.49.95.69.77.66.69.68.95.65.85.68.73.79.95.49.95.49.95.83.84.65.84.69
--
-- Value(s)		: OK
--				: WARN:No Input
--				: WARN:CS Error
-- Comments		:
--
---------------------------------------------------------------------------------------------------
-- Header		: INPUT_1_EMBED_AUDIO_1_2_LEVEL
--
-- MIB ref		: swCardEventLogSlotXX       .29.73.78.80.85.84.95.49.95.69.77.66.69.68.95.65.85.68.73.79.95.49.95.50.95.76.69.86.69.76
-- absolute OID	: 1.3.6.1.4.1.7995.2.6.1.1.XX.29.73.78.80.85.84.95.49.95.69.77.66.69.68.95.65.85.68.73.79.95.49.95.50.95.76.69.86.69.76
--
-- Value(s)		: WARN:No Input
--				: OK
--				: FAIL:Silent
--				: FAIL:Quiet
-- Comments		:
--
---------------------------------------------------------------------------------------------------
-- Header		: INPUT_1_EMBED_AUDIO_1_2_STATE
--
-- MIB ref		: swCardEventLogSlotXX       .29.73.78.80.85.84.95.49.95.69.77.66.69.68.95.65.85.68.73.79.95.49.95.50.95.83.84.65.84.69
-- absolute OID	: 1.3.6.1.4.1.7995.2.6.1.1.XX.29.73.78.80.85.84.95.49.95.69.77.66.69.68.95.65.85.68.73.79.95.49.95.50.95.83.84.65.84.69
--
-- Value(s)		: OK
--				: WARN:No Input
--				: WARN:CS Error
-- Comments		:
--
---------------------------------------------------------------------------------------------------
-- Header		: INPUT_1_EMBED_AUDIO_2_1_LEVEL
--
-- MIB ref		: swCardEventLogSlotXX       .29.73.78.80.85.84.95.49.95.69.77.66.69.68.95.65.85.68.73.79.95.50.95.49.95.76.69.86.69.76
-- absolute OID	: 1.3.6.1.4.1.7995.2.6.1.1.XX.29.73.78.80.85.84.95.49.95.69.77.66.69.68.95.65.85.68.73.79.95.50.95.49.95.76.69.86.69.76
--
-- Value(s)		: WARN:No Input
--				: OK
--				: FAIL:Silent
--				: FAIL:Quiet
-- Comments		:
--
---------------------------------------------------------------------------------------------------
-- Header		: INPUT_1_EMBED_AUDIO_2_1_STATE
--
-- MIB ref		: swCardEventLogSlotXX       .29.73.78.80.85.84.95.49.95.69.77.66.69.68.95.65.85.68.73.79.95.50.95.49.95.83.84.65.84.69
-- absolute OID	: 1.3.6.1.4.1.7995.2.6.1.1.XX.29.73.78.80.85.84.95.49.95.69.77.66.69.68.95.65.85.68.73.79.95.50.95.49.95.83.84.65.84.69
--
-- Value(s)		: OK
--				: WARN:No Input
--				: WARN:CS Error
-- Comments		:
--
---------------------------------------------------------------------------------------------------
-- Header		: INPUT_1_EMBED_AUDIO_2_2_LEVEL
--
-- MIB ref		: swCardEventLogSlotXX       .29.73.78.80.85.84.95.49.95.69.77.66.69.68.95.65.85.68.73.79.95.50.95.50.95.76.69.86.69.76
-- absolute OID	: 1.3.6.1.4.1.7995.2.6.1.1.XX.29.73.78.80.85.84.95.49.95.69.77.66.69.68.95.65.85.68.73.79.95.50.95.50.95.76.69.86.69.76
--
-- Value(s)		: WARN:No Input
--				: OK
--				: FAIL:Silent
--				: FAIL:Quiet
-- Comments		:
--
---------------------------------------------------------------------------------------------------
-- Header		: INPUT_1_EMBED_AUDIO_2_2_STATE
--
-- MIB ref		: swCardEventLogSlotXX       .29.73.78.80.85.84.95.49.95.69.77.66.69.68.95.65.85.68.73.79.95.50.95.50.95.83.84.65.84.69
-- absolute OID	: 1.3.6.1.4.1.7995.2.6.1.1.XX.29.73.78.80.85.84.95.49.95.69.77.66.69.68.95.65.85.68.73.79.95.50.95.50.95.83.84.65.84.69
--
-- Value(s)		: OK
--				: WARN:No Input
--				: WARN:CS Error
-- Comments		:
--
---------------------------------------------------------------------------------------------------
-- Header		: INPUT_1_EMBED_AUDIO_3_1_LEVEL
--
-- MIB ref		: swCardEventLogSlotXX       .29.73.78.80.85.84.95.49.95.69.77.66.69.68.95.65.85.68.73.79.95.51.95.49.95.76.69.86.69.76
-- absolute OID	: 1.3.6.1.4.1.7995.2.6.1.1.XX.29.73.78.80.85.84.95.49.95.69.77.66.69.68.95.65.85.68.73.79.95.51.95.49.95.76.69.86.69.76
--
-- Value(s)		: WARN:No Input
--				: OK
--				: FAIL:Silent
--				: FAIL:Quiet
-- Comments		:
--
---------------------------------------------------------------------------------------------------
-- Header		: INPUT_1_EMBED_AUDIO_3_1_STATE
--
-- MIB ref		: swCardEventLogSlotXX       .29.73.78.80.85.84.95.49.95.69.77.66.69.68.95.65.85.68.73.79.95.51.95.49.95.83.84.65.84.69
-- absolute OID	: 1.3.6.1.4.1.7995.2.6.1.1.XX.29.73.78.80.85.84.95.49.95.69.77.66.69.68.95.65.85.68.73.79.95.51.95.49.95.83.84.65.84.69
--
-- Value(s)		: OK
--				: WARN:No Input
--				: WARN:CS Error
-- Comments		:
--
---------------------------------------------------------------------------------------------------
-- Header		: INPUT_1_EMBED_AUDIO_3_2_LEVEL
--
-- MIB ref		: swCardEventLogSlotXX       .29.73.78.80.85.84.95.49.95.69.77.66.69.68.95.65.85.68.73.79.95.51.95.50.95.76.69.86.69.76
-- absolute OID	: 1.3.6.1.4.1.7995.2.6.1.1.XX.29.73.78.80.85.84.95.49.95.69.77.66.69.68.95.65.85.68.73.79.95.51.95.50.95.76.69.86.69.76
--
-- Value(s)		: WARN:No Input
--				: OK
--				: FAIL:Silent
--				: FAIL:Quiet
-- Comments		:
--
---------------------------------------------------------------------------------------------------
-- Header		: INPUT_1_EMBED_AUDIO_3_2_STATE
--
-- MIB ref		: swCardEventLogSlotXX       .29.73.78.80.85.84.95.49.95.69.77.66.69.68.95.65.85.68.73.79.95.51.95.50.95.83.84.65.84.69
-- absolute OID	: 1.3.6.1.4.1.7995.2.6.1.1.XX.29.73.78.80.85.84.95.49.95.69.77.66.69.68.95.65.85.68.73.79.95.51.95.50.95.83.84.65.84.69
--
-- Value(s)		: OK
--				: WARN:No Input
--				: WARN:CS Error
-- Comments		:
--
---------------------------------------------------------------------------------------------------
-- Header		: INPUT_1_EMBED_AUDIO_4_1_LEVEL
--
-- MIB ref		: swCardEventLogSlotXX       .29.73.78.80.85.84.95.49.95.69.77.66.69.68.95.65.85.68.73.79.95.52.95.49.95.76.69.86.69.76
-- absolute OID	: 1.3.6.1.4.1.7995.2.6.1.1.XX.29.73.78.80.85.84.95.49.95.69.77.66.69.68.95.65.85.68.73.79.95.52.95.49.95.76.69.86.69.76
--
-- Value(s)		: WARN:No Input
--				: OK
--				: FAIL:Silent
--				: FAIL:Quiet
-- Comments		:
--
---------------------------------------------------------------------------------------------------
-- Header		: INPUT_1_EMBED_AUDIO_4_1_STATE
--
-- MIB ref		: swCardEventLogSlotXX       .29.73.78.80.85.84.95.49.95.69.77.66.69.68.95.65.85.68.73.79.95.52.95.49.95.83.84.65.84.69
-- absolute OID	: 1.3.6.1.4.1.7995.2.6.1.1.XX.29.73.78.80.85.84.95.49.95.69.77.66.69.68.95.65.85.68.73.79.95.52.95.49.95.83.84.65.84.69
--
-- Value(s)		: OK
--				: WARN:No Input
--				: WARN:CS Error
-- Comments		:
--
---------------------------------------------------------------------------------------------------
-- Header		: INPUT_1_EMBED_AUDIO_4_2_LEVEL
--
-- MIB ref		: swCardEventLogSlotXX       .29.73.78.80.85.84.95.49.95.69.77.66.69.68.95.65.85.68.73.79.95.52.95.50.95.76.69.86.69.76
-- absolute OID	: 1.3.6.1.4.1.7995.2.6.1.1.XX.29.73.78.80.85.84.95.49.95.69.77.66.69.68.95.65.85.68.73.79.95.52.95.50.95.76.69.86.69.76
--
-- Value(s)		: WARN:No Input
--				: OK
--				: FAIL:Silent
--				: FAIL:Quiet
-- Comments		:
--
---------------------------------------------------------------------------------------------------
-- Header		: INPUT_1_EMBED_AUDIO_4_2_STATE
--
-- MIB ref		: swCardEventLogSlotXX       .29.73.78.80.85.84.95.49.95.69.77.66.69.68.95.65.85.68.73.79.95.52.95.50.95.83.84.65.84.69
-- absolute OID	: 1.3.6.1.4.1.7995.2.6.1.1.XX.29.73.78.80.85.84.95.49.95.69.77.66.69.68.95.65.85.68.73.79.95.52.95.50.95.83.84.65.84.69
--
-- Value(s)		: OK
--				: WARN:No Input
--				: WARN:CS Error
-- Comments		:
--
---------------------------------------------------------------------------------------------------
-- Header		: INPUT_1_EMBED_AUDIO_5_1_LEVEL
--
-- MIB ref		: swCardEventLogSlotXX       .29.73.78.80.85.84.95.49.95.69.77.66.69.68.95.65.85.68.73.79.95.53.95.49.95.76.69.86.69.76
-- absolute OID	: 1.3.6.1.4.1.7995.2.6.1.1.XX.29.73.78.80.85.84.95.49.95.69.77.66.69.68.95.65.85.68.73.79.95.53.95.49.95.76.69.86.69.76
--
-- Value(s)		: WARN:No Input
--				: OK
--				: FAIL:Silent
--				: FAIL:Quiet
-- Comments		:
--
---------------------------------------------------------------------------------------------------
-- Header		: INPUT_1_EMBED_AUDIO_5_1_STATE
--
-- MIB ref		: swCardEventLogSlotXX       .29.73.78.80.85.84.95.49.95.69.77.66.69.68.95.65.85.68.73.79.95.53.95.49.95.83.84.65.84.69
-- absolute OID	: 1.3.6.1.4.1.7995.2.6.1.1.XX.29.73.78.80.85.84.95.49.95.69.77.66.69.68.95.65.85.68.73.79.95.53.95.49.95.83.84.65.84.69
--
-- Value(s)		: OK
--				: WARN:No Input
--				: WARN:CS Error
-- Comments		:
--
---------------------------------------------------------------------------------------------------
-- Header		: INPUT_1_EMBED_AUDIO_5_2_LEVEL
--
-- MIB ref		: swCardEventLogSlotXX       .29.73.78.80.85.84.95.49.95.69.77.66.69.68.95.65.85.68.73.79.95.53.95.50.95.76.69.86.69.76
-- absolute OID	: 1.3.6.1.4.1.7995.2.6.1.1.XX.29.73.78.80.85.84.95.49.95.69.77.66.69.68.95.65.85.68.73.79.95.53.95.50.95.76.69.86.69.76
--
-- Value(s)		: WARN:No Input
--				: OK
--				: FAIL:Silent
--				: FAIL:Quiet
-- Comments		:
--
---------------------------------------------------------------------------------------------------
-- Header		: INPUT_1_EMBED_AUDIO_5_2_STATE
--
-- MIB ref		: swCardEventLogSlotXX       .29.73.78.80.85.84.95.49.95.69.77.66.69.68.95.65.85.68.73.79.95.53.95.50.95.83.84.65.84.69
-- absolute OID	: 1.3.6.1.4.1.7995.2.6.1.1.XX.29.73.78.80.85.84.95.49.95.69.77.66.69.68.95.65.85.68.73.79.95.53.95.50.95.83.84.65.84.69
--
-- Value(s)		: OK
--				: WARN:No Input
--				: WARN:CS Error
-- Comments		:
--
---------------------------------------------------------------------------------------------------
-- Header		: INPUT_1_EMBED_AUDIO_6_1_LEVEL
--
-- MIB ref		: swCardEventLogSlotXX       .29.73.78.80.85.84.95.49.95.69.77.66.69.68.95.65.85.68.73.79.95.54.95.49.95.76.69.86.69.76
-- absolute OID	: 1.3.6.1.4.1.7995.2.6.1.1.XX.29.73.78.80.85.84.95.49.95.69.77.66.69.68.95.65.85.68.73.79.95.54.95.49.95.76.69.86.69.76
--
-- Value(s)		: WARN:No Input
--				: OK
--				: FAIL:Silent
--				: FAIL:Quiet
-- Comments		:
--
---------------------------------------------------------------------------------------------------
-- Header		: INPUT_1_EMBED_AUDIO_6_1_STATE
--
-- MIB ref		: swCardEventLogSlotXX       .29.73.78.80.85.84.95.49.95.69.77.66.69.68.95.65.85.68.73.79.95.54.95.49.95.83.84.65.84.69
-- absolute OID	: 1.3.6.1.4.1.7995.2.6.1.1.XX.29.73.78.80.85.84.95.49.95.69.77.66.69.68.95.65.85.68.73.79.95.54.95.49.95.83.84.65.84.69
--
-- Value(s)		: OK
--				: WARN:No Input
--				: WARN:CS Error
-- Comments		:
--
---------------------------------------------------------------------------------------------------
-- Header		: INPUT_1_EMBED_AUDIO_6_2_LEVEL
--
-- MIB ref		: swCardEventLogSlotXX       .29.73.78.80.85.84.95.49.95.69.77.66.69.68.95.65.85.68.73.79.95.54.95.50.95.76.69.86.69.76
-- absolute OID	: 1.3.6.1.4.1.7995.2.6.1.1.XX.29.73.78.80.85.84.95.49.95.69.77.66.69.68.95.65.85.68.73.79.95.54.95.50.95.76.69.86.69.76
--
-- Value(s)		: WARN:No Input
--				: OK
--				: FAIL:Silent
--				: FAIL:Quiet
-- Comments		:
--
---------------------------------------------------------------------------------------------------
-- Header		: INPUT_1_EMBED_AUDIO_6_2_STATE
--
-- MIB ref		: swCardEventLogSlotXX       .29.73.78.80.85.84.95.49.95.69.77.66.69.68.95.65.85.68.73.79.95.54.95.50.95.83.84.65.84.69
-- absolute OID	: 1.3.6.1.4.1.7995.2.6.1.1.XX.29.73.78.80.85.84.95.49.95.69.77.66.69.68.95.65.85.68.73.79.95.54.95.50.95.83.84.65.84.69
--
-- Value(s)		: OK
--				: WARN:No Input
--				: WARN:CS Error
-- Comments		:
--
---------------------------------------------------------------------------------------------------
-- Header		: INPUT_1_EMBED_AUDIO_7_1_LEVEL
--
-- MIB ref		: swCardEventLogSlotXX       .29.73.78.80.85.84.95.49.95.69.77.66.69.68.95.65.85.68.73.79.95.55.95.49.95.76.69.86.69.76
-- absolute OID	: 1.3.6.1.4.1.7995.2.6.1.1.XX.29.73.78.80.85.84.95.49.95.69.77.66.69.68.95.65.85.68.73.79.95.55.95.49.95.76.69.86.69.76
--
-- Value(s)		: WARN:No Input
--				: OK
--				: FAIL:Silent
--				: FAIL:Quiet
-- Comments		:
--
---------------------------------------------------------------------------------------------------
-- Header		: INPUT_1_EMBED_AUDIO_7_1_STATE
--
-- MIB ref		: swCardEventLogSlotXX       .29.73.78.80.85.84.95.49.95.69.77.66.69.68.95.65.85.68.73.79.95.55.95.49.95.83.84.65.84.69
-- absolute OID	: 1.3.6.1.4.1.7995.2.6.1.1.XX.29.73.78.80.85.84.95.49.95.69.77.66.69.68.95.65.85.68.73.79.95.55.95.49.95.83.84.65.84.69
--
-- Value(s)		: OK
--				: WARN:No Input
--				: WARN:CS Error
-- Comments		:
--
---------------------------------------------------------------------------------------------------
-- Header		: INPUT_1_EMBED_AUDIO_7_2_LEVEL
--
-- MIB ref		: swCardEventLogSlotXX       .29.73.78.80.85.84.95.49.95.69.77.66.69.68.95.65.85.68.73.79.95.55.95.50.95.76.69.86.69.76
-- absolute OID	: 1.3.6.1.4.1.7995.2.6.1.1.XX.29.73.78.80.85.84.95.49.95.69.77.66.69.68.95.65.85.68.73.79.95.55.95.50.95.76.69.86.69.76
--
-- Value(s)		: WARN:No Input
--				: OK
--				: FAIL:Silent
--				: FAIL:Quiet
-- Comments		:
--
---------------------------------------------------------------------------------------------------
-- Header		: INPUT_1_EMBED_AUDIO_7_2_STATE
--
-- MIB ref		: swCardEventLogSlotXX       .29.73.78.80.85.84.95.49.95.69.77.66.69.68.95.65.85.68.73.79.95.55.95.50.95.83.84.65.84.69
-- absolute OID	: 1.3.6.1.4.1.7995.2.6.1.1.XX.29.73.78.80.85.84.95.49.95.69.77.66.69.68.95.65.85.68.73.79.95.55.95.50.95.83.84.65.84.69
--
-- Value(s)		: OK
--				: WARN:No Input
--				: WARN:CS Error
-- Comments		:
--
---------------------------------------------------------------------------------------------------
-- Header		: INPUT_1_EMBED_AUDIO_8_1_LEVEL
--
-- MIB ref		: swCardEventLogSlotXX       .29.73.78.80.85.84.95.49.95.69.77.66.69.68.95.65.85.68.73.79.95.56.95.49.95.76.69.86.69.76
-- absolute OID	: 1.3.6.1.4.1.7995.2.6.1.1.XX.29.73.78.80.85.84.95.49.95.69.77.66.69.68.95.65.85.68.73.79.95.56.95.49.95.76.69.86.69.76
--
-- Value(s)		: WARN:No Input
--				: OK
--				: FAIL:Silent
--				: FAIL:Quiet
-- Comments		:
--
---------------------------------------------------------------------------------------------------
-- Header		: INPUT_1_EMBED_AUDIO_8_1_STATE
--
-- MIB ref		: swCardEventLogSlotXX       .29.73.78.80.85.84.95.49.95.69.77.66.69.68.95.65.85.68.73.79.95.56.95.49.95.83.84.65.84.69
-- absolute OID	: 1.3.6.1.4.1.7995.2.6.1.1.XX.29.73.78.80.85.84.95.49.95.69.77.66.69.68.95.65.85.68.73.79.95.56.95.49.95.83.84.65.84.69
--
-- Value(s)		: OK
--				: WARN:No Input
--				: WARN:CS Error
-- Comments		:
--
---------------------------------------------------------------------------------------------------
-- Header		: INPUT_1_EMBED_AUDIO_8_2_LEVEL
--
-- MIB ref		: swCardEventLogSlotXX       .29.73.78.80.85.84.95.49.95.69.77.66.69.68.95.65.85.68.73.79.95.56.95.50.95.76.69.86.69.76
-- absolute OID	: 1.3.6.1.4.1.7995.2.6.1.1.XX.29.73.78.80.85.84.95.49.95.69.77.66.69.68.95.65.85.68.73.79.95.56.95.50.95.76.69.86.69.76
--
-- Value(s)		: WARN:No Input
--				: OK
--				: FAIL:Silent
--				: FAIL:Quiet
-- Comments		:
--
---------------------------------------------------------------------------------------------------
-- Header		: INPUT_1_EMBED_AUDIO_8_2_STATE
--
-- MIB ref		: swCardEventLogSlotXX       .29.73.78.80.85.84.95.49.95.69.77.66.69.68.95.65.85.68.73.79.95.56.95.50.95.83.84.65.84.69
-- absolute OID	: 1.3.6.1.4.1.7995.2.6.1.1.XX.29.73.78.80.85.84.95.49.95.69.77.66.69.68.95.65.85.68.73.79.95.56.95.50.95.83.84.65.84.69
--
-- Value(s)		: OK
--				: WARN:No Input
--				: WARN:CS Error
-- Comments		:
--
---------------------------------------------------------------------------------------------------
-- Header		: INPUT_1_PID_PREVIOUS_DURATION
--
-- MIB ref		: swCardEventLogSlotXX       .29.73.78.80.85.84.95.49.95.80.73.68.95.80.82.69.86.73.79.85.83.95.68.85.82.65.84.73.79.78
-- absolute OID	: 1.3.6.1.4.1.7995.2.6.1.1.XX.29.73.78.80.85.84.95.49.95.80.73.68.95.80.82.69.86.73.79.85.83.95.68.85.82.65.84.73.79.78
--
-- Value(s)		: 0
-- Comments		:
--
---------------------------------------------------------------------------------------------------
-- Header		: INPUT_1_PID_PREVIOUS_HOUSE_ID
--
-- MIB ref		: swCardEventLogSlotXX       .29.73.78.80.85.84.95.49.95.80.73.68.95.80.82.69.86.73.79.85.83.95.72.79.85.83.69.95.73.68
-- absolute OID	: 1.3.6.1.4.1.7995.2.6.1.1.XX.29.73.78.80.85.84.95.49.95.80.73.68.95.80.82.69.86.73.79.85.83.95.72.79.85.83.69.95.73.68
--
-- Value(s)		: House ID
-- Comments		:
--
---------------------------------------------------------------------------------------------------
-- Header		: INPUT_1_USER1_ANC_PACKET_NAME
--
-- MIB ref		: swCardEventLogSlotXX       .29.73.78.80.85.84.95.49.95.85.83.69.82.49.95.65.78.67.95.80.65.67.75.69.84.95.78.65.77.69
-- absolute OID	: 1.3.6.1.4.1.7995.2.6.1.1.XX.29.73.78.80.85.84.95.49.95.85.83.69.82.49.95.65.78.67.95.80.65.67.75.69.84.95.78.65.77.69
--
-- Value(s)		: User Anc 1
-- Comments		:
--
---------------------------------------------------------------------------------------------------
-- Header		: INPUT_1_USER2_ANC_PACKET_NAME
--
-- MIB ref		: swCardEventLogSlotXX       .29.73.78.80.85.84.95.49.95.85.83.69.82.50.95.65.78.67.95.80.65.67.75.69.84.95.78.65.77.69
-- absolute OID	: 1.3.6.1.4.1.7995.2.6.1.1.XX.29.73.78.80.85.84.95.49.95.85.83.69.82.50.95.65.78.67.95.80.65.67.75.69.84.95.78.65.77.69
--
-- Value(s)		: User Anc 2
-- Comments		:
--
---------------------------------------------------------------------------------------------------
-- Header		: INPUT_1_CONTENT_ADVISORY_STATE
--
-- MIB ref		: swCardEventLogSlotXX       .30.73.78.80.85.84.95.49.95.67.79.78.84.69.78.84.95.65.68.86.73.83.79.82.89.95.83.84.65.84.69
-- absolute OID	: 1.3.6.1.4.1.7995.2.6.1.1.XX.30.73.78.80.85.84.95.49.95.67.79.78.84.69.78.84.95.65.68.86.73.83.79.82.89.95.83.84.65.84.69
--
-- Value(s)		: OK
--				: FAIL:No CA
-- Comments		:
--
---------------------------------------------------------------------------------------------------
-- Header		: INPUT_1_TIMECODE_DISCONTINUITY
--
-- MIB ref		: swCardEventLogSlotXX       .30.73.78.80.85.84.95.49.95.84.73.77.69.67.79.68.69.95.68.73.83.67.79.78.84.73.78.85.73.84.89
-- absolute OID	: 1.3.6.1.4.1.7995.2.6.1.1.XX.30.73.78.80.85.84.95.49.95.84.73.77.69.67.79.68.69.95.68.73.83.67.79.78.84.73.78.85.73.84.89
--
-- Value(s)		: FAIL:MISSING **:**:**:**
-- Comments		:
--
---------------------------------------------------------------------------------------------------
-- Header		: INPUT_1_USER1_ANC_PACKET_STATE
--
-- MIB ref		: swCardEventLogSlotXX       .30.73.78.80.85.84.95.49.95.85.83.69.82.49.95.65.78.67.95.80.65.67.75.69.84.95.83.84.65.84.69
-- absolute OID	: 1.3.6.1.4.1.7995.2.6.1.1.XX.30.73.78.80.85.84.95.49.95.85.83.69.82.49.95.65.78.67.95.80.65.67.75.69.84.95.83.84.65.84.69
--
-- Value(s)		: OK
--				: FAIL:No User1 ANC
-- Comments		:
--
---------------------------------------------------------------------------------------------------
-- Header		: INPUT_1_USER2_ANC_PACKET_STATE
--
-- MIB ref		: swCardEventLogSlotXX       .30.73.78.80.85.84.95.49.95.85.83.69.82.50.95.65.78.67.95.80.65.67.75.69.84.95.83.84.65.84.69
-- absolute OID	: 1.3.6.1.4.1.7995.2.6.1.1.XX.30.73.78.80.85.84.95.49.95.85.83.69.82.50.95.65.78.67.95.80.65.67.75.69.84.95.83.84.65.84.69
--
-- Value(s)		: OK
--				: FAIL:No User2 ANC
-- Comments		:
--
---------------------------------------------------------------------------------------------------
-- Header		: INPUT_1_CONTENT_ADVISORY_SYSTEM
--
-- MIB ref		: swCardEventLogSlotXX       .31.73.78.80.85.84.95.49.95.67.79.78.84.69.78.84.95.65.68.86.73.83.79.82.89.95.83.89.83.84.69.77
-- absolute OID	: 1.3.6.1.4.1.7995.2.6.1.1.XX.31.73.78.80.85.84.95.49.95.67.79.78.84.69.78.84.95.65.68.86.73.83.79.82.89.95.83.89.83.84.69.77
--
-- Value(s)		: 1-US TV PG
-- Comments		:
--
---------------------------------------------------------------------------------------------------
-- Header		: INPUT_1_EMBED_DOLBY_E_PR1_STATE
--
-- MIB ref		: swCardEventLogSlotXX       .31.73.78.80.85.84.95.49.95.69.77.66.69.68.95.68.79.76.66.89.95.69.95.80.82.49.95.83.84.65.84.69
-- absolute OID	: 1.3.6.1.4.1.7995.2.6.1.1.XX.31.73.78.80.85.84.95.49.95.69.77.66.69.68.95.68.79.76.66.89.95.69.95.80.82.49.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR2_STATE
--
-- MIB ref		: swCardEventLogSlotXX       .31.73.78.80.85.84.95.49.95.69.77.66.69.68.95.68.79.76.66.89.95.69.95.80.82.50.95.83.84.65.84.69
-- absolute OID	: 1.3.6.1.4.1.7995.2.6.1.1.XX.31.73.78.80.85.84.95.49.95.69.77.66.69.68.95.68.79.76.66.89.95.69.95.80.82.50.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR3_STATE
--
-- MIB ref		: swCardEventLogSlotXX       .31.73.78.80.85.84.95.49.95.69.77.66.69.68.95.68.79.76.66.89.95.69.95.80.82.51.95.83.84.65.84.69
-- absolute OID	: 1.3.6.1.4.1.7995.2.6.1.1.XX.31.73.78.80.85.84.95.49.95.69.77.66.69.68.95.68.79.76.66.89.95.69.95.80.82.51.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR4_STATE
--
-- MIB ref		: swCardEventLogSlotXX       .31.73.78.80.85.84.95.49.95.69.77.66.69.68.95.68.79.76.66.89.95.69.95.80.82.52.95.83.84.65.84.69
-- absolute OID	: 1.3.6.1.4.1.7995.2.6.1.1.XX.31.73.78.80.85.84.95.49.95.69.77.66.69.68.95.68.79.76.66.89.95.69.95.80.82.52.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR5_STATE
--
-- MIB ref		: swCardEventLogSlotXX       .31.73.78.80.85.84.95.49.95.69.77.66.69.68.95.68.79.76.66.89.95.69.95.80.82.53.95.83.84.65.84.69
-- absolute OID	: 1.3.6.1.4.1.7995.2.6.1.1.XX.31.73.78.80.85.84.95.49.95.69.77.66.69.68.95.68.79.76.66.89.95.69.95.80.82.53.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR6_STATE
--
-- MIB ref		: swCardEventLogSlotXX       .31.73.78.80.85.84.95.49.95.69.77.66.69.68.95.68.79.76.66.89.95.69.95.80.82.54.95.83.84.65.84.69
-- absolute OID	: 1.3.6.1.4.1.7995.2.6.1.1.XX.31.73.78.80.85.84.95.49.95.69.77.66.69.68.95.68.79.76.66.89.95.69.95.80.82.54.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR7_STATE
--
-- MIB ref		: swCardEventLogSlotXX       .31.73.78.80.85.84.95.49.95.69.77.66.69.68.95.68.79.76.66.89.95.69.95.80.82.55.95.83.84.65.84.69
-- absolute OID	: 1.3.6.1.4.1.7995.2.6.1.1.XX.31.73.78.80.85.84.95.49.95.69.77.66.69.68.95.68.79.76.66.89.95.69.95.80.82.55.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_EMBED_DOLBY_E_PR8_STATE
--
-- MIB ref		: swCardEventLogSlotXX       .31.73.78.80.85.84.95.49.95.69.77.66.69.68.95.68.79.76.66.89.95.69.95.80.82.56.95.83.84.65.84.69
-- absolute OID	: 1.3.6.1.4.1.7995.2.6.1.1.XX.31.73.78.80.85.84.95.49.95.69.77.66.69.68.95.68.79.76.66.89.95.69.95.80.82.56.95.83.84.65.84.69
--
-- Value(s)		: OK
--				: WARN:Early
--				: WARN:Late
--				: FAIL:Early
--				: FAIL:Late
--				: FAIL:Not Dolby E
--				: WARN:Std Not Sup
-- Comments		:
--
---------------------------------------------------------------------------------------------------
-- Header		: INPUT_1_PID_PREVIOUS_FRAME_RATE
--
-- MIB ref		: swCardEventLogSlotXX       .31.73.78.80.85.84.95.49.95.80.73.68.95.80.82.69.86.73.79.85.83.95.70.82.65.77.69.95.82.65.84.69
-- absolute OID	: 1.3.6.1.4.1.7995.2.6.1.1.XX.31.73.78.80.85.84.95.49.95.80.73.68.95.80.82.69.86.73.79.85.83.95.70.82.65.77.69.95.82.65.84.69
--
-- Value(s)		: 29.97
-- Comments		:
--
---------------------------------------------------------------------------------------------------
-- Header		: INPUT_1_ANCILLARY_TIMECODE_STATE
--
-- MIB ref		: swCardEventLogSlotXX       .32.73.78.80.85.84.95.49.95.65.78.67.73.76.76.65.82.89.95.84.73.77.69.67.79.68.69.95.83.84.65.84.69
-- absolute OID	: 1.3.6.1.4.1.7995.2.6.1.1.XX.32.73.78.80.85.84.95.49.95.65.78.67.73.76.76.65.82.89.95.84.73.77.69.67.79.68.69.95.83.84.65.84.69
--
-- Value(s)		: FAIL:No ANC TC
-- Comments		:
--
---------------------------------------------------------------------------------------------------
-- Header		: INPUT_1_EMBED_AUDIO_1_1_CLIPPING
--
-- MIB ref		: swCardEventLogSlotXX       .32.73.78.80.85.84.95.49.95.69.77.66.69.68.95.65.85.68.73.79.95.49.95.49.95.67.76.73.80.80.73.78.71
-- absolute OID	: 1.3.6.1.4.1.7995.2.6.1.1.XX.32.73.78.80.85.84.95.49.95.69.77.66.69.68.95.65.85.68.73.79.95.49.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_1_2_CLIPPING
--
-- MIB ref		: swCardEventLogSlotXX       .32.73.78.80.85.84.95.49.95.69.77.66.69.68.95.65.85.68.73.79.95.49.95.50.95.67.76.73.80.80.73.78.71
-- absolute OID	: 1.3.6.1.4.1.7995.2.6.1.1.XX.32.73.78.80.85.84.95.49.95.69.77.66.69.68.95.65.85.68.73.79.95.49.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_2_1_CLIPPING
--
-- MIB ref		: swCardEventLogSlotXX       .32.73.78.80.85.84.95.49.95.69.77.66.69.68.95.65.85.68.73.79.95.50.95.49.95.67.76.73.80.80.73.78.71
-- absolute OID	: 1.3.6.1.4.1.7995.2.6.1.1.XX.32.73.78.80.85.84.95.49.95.69.77.66.69.68.95.65.85.68.73.79.95.50.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_2_2_CLIPPING
--
-- MIB ref		: swCardEventLogSlotXX       .32.73.78.80.85.84.95.49.95.69.77.66.69.68.95.65.85.68.73.79.95.50.95.50.95.67.76.73.80.80.73.78.71
-- absolute OID	: 1.3.6.1.4.1.7995.2.6.1.1.XX.32.73.78.80.85.84.95.49.95.69.77.66.69.68.95.65.85.68.73.79.95.50.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_3_1_CLIPPING
--
-- MIB ref		: swCardEventLogSlotXX       .32.73.78.80.85.84.95.49.95.69.77.66.69.68.95.65.85.68.73.79.95.51.95.49.95.67.76.73.80.80.73.78.71
-- absolute OID	: 1.3.6.1.4.1.7995.2.6.1.1.XX.32.73.78.80.85.84.95.49.95.69.77.66.69.68.95.65.85.68.73.79.95.51.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_3_2_CLIPPING
--
-- MIB ref		: swCardEventLogSlotXX       .32.73.78.80.85.84.95.49.95.69.77.66.69.68.95.65.85.68.73.79.95.51.95.50.95.67.76.73.80.80.73.78.71
-- absolute OID	: 1.3.6.1.4.1.7995.2.6.1.1.XX.32.73.78.80.85.84.95.49.95.69.77.66.69.68.95.65.85.68.73.79.95.51.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_4_1_CLIPPING
--
-- MIB ref		: swCardEventLogSlotXX       .32.73.78.80.85.84.95.49.95.69.77.66.69.68.95.65.85.68.73.79.95.52.95.49.95.67.76.73.80.80.73.78.71
-- absolute OID	: 1.3.6.1.4.1.7995.2.6.1.1.XX.32.73.78.80.85.84.95.49.95.69.77.66.69.68.95.65.85.68.73.79.95.52.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_4_2_CLIPPING
--
-- MIB ref		: swCardEventLogSlotXX       .32.73.78.80.85.84.95.49.95.69.77.66.69.68.95.65.85.68.73.79.95.52.95.50.95.67.76.73.80.80.73.78.71
-- absolute OID	: 1.3.6.1.4.1.7995.2.6.1.1.XX.32.73.78.80.85.84.95.49.95.69.77.66.69.68.95.65.85.68.73.79.95.52.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_5_1_CLIPPING
--
-- MIB ref		: swCardEventLogSlotXX       .32.73.78.80.85.84.95.49.95.69.77.66.69.68.95.65.85.68.73.79.95.53.95.49.95.67.76.73.80.80.73.78.71
-- absolute OID	: 1.3.6.1.4.1.7995.2.6.1.1.XX.32.73.78.80.85.84.95.49.95.69.77.66.69.68.95.65.85.68.73.79.95.53.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_5_2_CLIPPING
--
-- MIB ref		: swCardEventLogSlotXX       .32.73.78.80.85.84.95.49.95.69.77.66.69.68.95.65.85.68.73.79.95.53.95.50.95.67.76.73.80.80.73.78.71
-- absolute OID	: 1.3.6.1.4.1.7995.2.6.1.1.XX.32.73.78.80.85.84.95.49.95.69.77.66.69.68.95.65.85.68.73.79.95.53.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_6_1_CLIPPING
--
-- MIB ref		: swCardEventLogSlotXX       .32.73.78.80.85.84.95.49.95.69.77.66.69.68.95.65.85.68.73.79.95.54.95.49.95.67.76.73.80.80.73.78.71
-- absolute OID	: 1.3.6.1.4.1.7995.2.6.1.1.XX.32.73.78.80.85.84.95.49.95.69.77.66.69.68.95.65.85.68.73.79.95.54.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_6_2_CLIPPING
--
-- MIB ref		: swCardEventLogSlotXX       .32.73.78.80.85.84.95.49.95.69.77.66.69.68.95.65.85.68.73.79.95.54.95.50.95.67.76.73.80.80.73.78.71
-- absolute OID	: 1.3.6.1.4.1.7995.2.6.1.1.XX.32.73.78.80.85.84.95.49.95.69.77.66.69.68.95.65.85.68.73.79.95.54.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_7_1_CLIPPING
--
-- MIB ref		: swCardEventLogSlotXX       .32.73.78.80.85.84.95.49.95.69.77.66.69.68.95.65.85.68.73.79.95.55.95.49.95.67.76.73.80.80.73.78.71
-- absolute OID	: 1.3.6.1.4.1.7995.2.6.1.1.XX.32.73.78.80.85.84.95.49.95.69.77.66.69.68.95.65.85.68.73.79.95.55.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_7_2_CLIPPING
--
-- MIB ref		: swCardEventLogSlotXX       .32.73.78.80.85.84.95.49.95.69.77.66.69.68.95.65.85.68.73.79.95.55.95.50.95.67.76.73.80.80.73.78.71
-- absolute OID	: 1.3.6.1.4.1.7995.2.6.1.1.XX.32.73.78.80.85.84.95.49.95.69.77.66.69.68.95.65.85.68.73.79.95.55.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_8_1_CLIPPING
--
-- MIB ref		: swCardEventLogSlotXX       .32.73.78.80.85.84.95.49.95.69.77.66.69.68.95.65.85.68.73.79.95.56.95.49.95.67.76.73.80.80.73.78.71
-- absolute OID	: 1.3.6.1.4.1.7995.2.6.1.1.XX.32.73.78.80.85.84.95.49.95.69.77.66.69.68.95.65.85.68.73.79.95.56.95.49.95.67.76.73.80.80.73.78.71
--
-- Value(s)		: OK
--				: WARN:No Input
--				: WARN:NON PCM
--				: WARN:Clipping
-- Comments		:
--
---------------------------------------------------------------------------------------------------
-- Header		: INPUT_1_EMBED_AUDIO_8_2_CLIPPING
--
-- MIB ref		: swCardEventLogSlotXX       .32.73.78.80.85.84.95.49.95.69.77.66.69.68.95.65.85.68.73.79.95.56.95.50.95.67.76.73.80.80.73.78.71
-- absolute OID	: 1.3.6.1.4.1.7995.2.6.1.1.XX.32.73.78.80.85.84.95.49.95.69.77.66.69.68.95.65.85.68.73.79.95.56.95.50.95.67.76.73.80.80.73.78.71
--
-- Value(s)		: OK
--				: WARN:No Input
--				: WARN:NON PCM
--				: WARN:Clipping
-- Comments		:
--
---------------------------------------------------------------------------------------------------
-- Header		: INPUT_1_EMBED_AUDIO_1_1_BIT_DEPTH
--
-- MIB ref		: swCardEventLogSlotXX       .33.73.78.80.85.84.95.49.95.69.77.66.69.68.95.65.85.68.73.79.95.49.95.49.95.66.73.84.95.68.69.80.84.72
-- absolute OID	: 1.3.6.1.4.1.7995.2.6.1.1.XX.33.73.78.80.85.84.95.49.95.69.77.66.69.68.95.65.85.68.73.79.95.49.95.49.95.66.73.84.95.68.69.80.84.72
--
-- Value(s)		: WARN:No Input
--				: 16
--				: 20
--				: 24
-- Comments		:
--
---------------------------------------------------------------------------------------------------
-- Header		: INPUT_1_EMBED_AUDIO_1_2_BIT_DEPTH
--
-- MIB ref		: swCardEventLogSlotXX       .33.73.78.80.85.84.95.49.95.69.77.66.69.68.95.65.85.68.73.79.95.49.95.50.95.66.73.84.95.68.69.80.84.72
-- absolute OID	: 1.3.6.1.4.1.7995.2.6.1.1.XX.33.73.78.80.85.84.95.49.95.69.77.66.69.68.95.65.85.68.73.79.95.49.95.50.95.66.73.84.95.68.69.80.84.72
--
-- Value(s)		: WARN:No Input
--				: 16
--				: 20
--				: 24
-- Comments		:
--
---------------------------------------------------------------------------------------------------
-- Header		: INPUT_1_EMBED_AUDIO_2_1_BIT_DEPTH
--
-- MIB ref		: swCardEventLogSlotXX       .33.73.78.80.85.84.95.49.95.69.77.66.69.68.95.65.85.68.73.79.95.50.95.49.95.66.73.84.95.68.69.80.84.72
-- absolute OID	: 1.3.6.1.4.1.7995.2.6.1.1.XX.33.73.78.80.85.84.95.49.95.69.77.66.69.68.95.65.85.68.73.79.95.50.95.49.95.66.73.84.95.68.69.80.84.72
--
-- Value(s)		: WARN:No Input
--				: 16
--				: 20
--				: 24
-- Comments		:
--
---------------------------------------------------------------------------------------------------
-- Header		: INPUT_1_EMBED_AUDIO_2_2_BIT_DEPTH
--
-- MIB ref		: swCardEventLogSlotXX       .33.73.78.80.85.84.95.49.95.69.77.66.69.68.95.65.85.68.73.79.95.50.95.50.95.66.73.84.95.68.69.80.84.72
-- absolute OID	: 1.3.6.1.4.1.7995.2.6.1.1.XX.33.73.78.80.85.84.95.49.95.69.77.66.69.68.95.65.85.68.73.79.95.50.95.50.95.66.73.84.95.68.69.80.84.72
--
-- Value(s)		: WARN:No Input
--				: 16
--				: 20
--				: 24
-- Comments		:
--
---------------------------------------------------------------------------------------------------
-- Header		: INPUT_1_EMBED_AUDIO_3_1_BIT_DEPTH
--
-- MIB ref		: swCardEventLogSlotXX       .33.73.78.80.85.84.95.49.95.69.77.66.69.68.95.65.85.68.73.79.95.51.95.49.95.66.73.84.95.68.69.80.84.72
-- absolute OID	: 1.3.6.1.4.1.7995.2.6.1.1.XX.33.73.78.80.85.84.95.49.95.69.77.66.69.68.95.65.85.68.73.79.95.51.95.49.95.66.73.84.95.68.69.80.84.72
--
-- Value(s)		: WARN:No Input
--				: 16
--				: 20
--				: 24
-- Comments		:
--
---------------------------------------------------------------------------------------------------
-- Header		: INPUT_1_EMBED_AUDIO_3_2_BIT_DEPTH
--
-- MIB ref		: swCardEventLogSlotXX       .33.73.78.80.85.84.95.49.95.69.77.66.69.68.95.65.85.68.73.79.95.51.95.50.95.66.73.84.95.68.69.80.84.72
-- absolute OID	: 1.3.6.1.4.1.7995.2.6.1.1.XX.33.73.78.80.85.84.95.49.95.69.77.66.69.68.95.65.85.68.73.79.95.51.95.50.95.66.73.84.95.68.69.80.84.72
--
-- Value(s)		: WARN:No Input
--				: 16
--				: 20
--				: 24
-- Comments		:
--
---------------------------------------------------------------------------------------------------
-- Header		: INPUT_1_EMBED_AUDIO_4_1_BIT_DEPTH
--
-- MIB ref		: swCardEventLogSlotXX       .33.73.78.80.85.84.95.49.95.69.77.66.69.68.95.65.85.68.73.79.95.52.95.49.95.66.73.84.95.68.69.80.84.72
-- absolute OID	: 1.3.6.1.4.1.7995.2.6.1.1.XX.33.73.78.80.85.84.95.49.95.69.77.66.69.68.95.65.85.68.73.79.95.52.95.49.95.66.73.84.95.68.69.80.84.72
--
-- Value(s)		: WARN:No Input
--				: 16
--				: 20
--				: 24
-- Comments		:
--
---------------------------------------------------------------------------------------------------
-- Header		: INPUT_1_EMBED_AUDIO_4_2_BIT_DEPTH
--
-- MIB ref		: swCardEventLogSlotXX       .33.73.78.80.85.84.95.49.95.69.77.66.69.68.95.65.85.68.73.79.95.52.95.50.95.66.73.84.95.68.69.80.84.72
-- absolute OID	: 1.3.6.1.4.1.7995.2.6.1.1.XX.33.73.78.80.85.84.95.49.95.69.77.66.69.68.95.65.85.68.73.79.95.52.95.50.95.66.73.84.95.68.69.80.84.72
--
-- Value(s)		: WARN:No Input
--				: 16
--				: 20
--				: 24
-- Comments		:
--
---------------------------------------------------------------------------------------------------
-- Header		: INPUT_1_EMBED_AUDIO_5_1_BIT_DEPTH
--
-- MIB ref		: swCardEventLogSlotXX       .33.73.78.80.85.84.95.49.95.69.77.66.69.68.95.65.85.68.73.79.95.53.95.49.95.66.73.84.95.68.69.80.84.72
-- absolute OID	: 1.3.6.1.4.1.7995.2.6.1.1.XX.33.73.78.80.85.84.95.49.95.69.77.66.69.68.95.65.85.68.73.79.95.53.95.49.95.66.73.84.95.68.69.80.84.72
--
-- Value(s)		: WARN:No Input
--				: 16
--				: 20
--				: 24
-- Comments		:
--
---------------------------------------------------------------------------------------------------
-- Header		: INPUT_1_EMBED_AUDIO_5_2_BIT_DEPTH
--
-- MIB ref		: swCardEventLogSlotXX       .33.73.78.80.85.84.95.49.95.69.77.66.69.68.95.65.85.68.73.79.95.53.95.50.95.66.73.84.95.68.69.80.84.72
-- absolute OID	: 1.3.6.1.4.1.7995.2.6.1.1.XX.33.73.78.80.85.84.95.49.95.69.77.66.69.68.95.65.85.68.73.79.95.53.95.50.95.66.73.84.95.68.69.80.84.72
--
-- Value(s)		: WARN:No Input
--				: 16
--				: 20
--				: 24
-- Comments		:
--
---------------------------------------------------------------------------------------------------
-- Header		: INPUT_1_EMBED_AUDIO_6_1_BIT_DEPTH
--
-- MIB ref		: swCardEventLogSlotXX       .33.73.78.80.85.84.95.49.95.69.77.66.69.68.95.65.85.68.73.79.95.54.95.49.95.66.73.84.95.68.69.80.84.72
-- absolute OID	: 1.3.6.1.4.1.7995.2.6.1.1.XX.33.73.78.80.85.84.95.49.95.69.77.66.69.68.95.65.85.68.73.79.95.54.95.49.95.66.73.84.95.68.69.80.84.72
--
-- Value(s)		: WARN:No Input
--				: 16
--				: 20
--				: 24
-- Comments		:
--
---------------------------------------------------------------------------------------------------
-- Header		: INPUT_1_EMBED_AUDIO_6_2_BIT_DEPTH
--
-- MIB ref		: swCardEventLogSlotXX       .33.73.78.80.85.84.95.49.95.69.77.66.69.68.95.65.85.68.73.79.95.54.95.50.95.66.73.84.95.68.69.80.84.72
-- absolute OID	: 1.3.6.1.4.1.7995.2.6.1.1.XX.33.73.78.80.85.84.95.49.95.69.77.66.69.68.95.65.85.68.73.79.95.54.95.50.95.66.73.84.95.68.69.80.84.72
--
-- Value(s)		: WARN:No Input
--				: 16
--				: 20
--				: 24
-- Comments		:
--
---------------------------------------------------------------------------------------------------
-- Header		: INPUT_1_EMBED_AUDIO_7_1_BIT_DEPTH
--
-- MIB ref		: swCardEventLogSlotXX       .33.73.78.80.85.84.95.49.95.69.77.66.69.68.95.65.85.68.73.79.95.55.95.49.95.66.73.84.95.68.69.80.84.72
-- absolute OID	: 1.3.6.1.4.1.7995.2.6.1.1.XX.33.73.78.80.85.84.95.49.95.69.77.66.69.68.95.65.85.68.73.79.95.55.95.49.95.66.73.84.95.68.69.80.84.72
--
-- Value(s)		: WARN:No Input
--				: 16
--				: 20
--				: 24
-- Comments		:
--
---------------------------------------------------------------------------------------------------
-- Header		: INPUT_1_EMBED_AUDIO_7_2_BIT_DEPTH
--
-- MIB ref		: swCardEventLogSlotXX       .33.73.78.80.85.84.95.49.95.69.77.66.69.68.95.65.85.68.73.79.95.55.95.50.95.66.73.84.95.68.69.80.84.72
-- absolute OID	: 1.3.6.1.4.1.7995.2.6.1.1.XX.33.73.78.80.85.84.95.49.95.69.77.66.69.68.95.65.85.68.73.79.95.55.95.50.95.66.73.84.95.68.69.80.84.72
--
-- Value(s)		: WARN:No Input
--				: 16
--				: 20
--				: 24
-- Comments		:
--
---------------------------------------------------------------------------------------------------
-- Header		: INPUT_1_EMBED_AUDIO_8_1_BIT_DEPTH
--
-- MIB ref		: swCardEventLogSlotXX       .33.73.78.80.85.84.95.49.95.69.77.66.69.68.95.65.85.68.73.79.95.56.95.49.95.66.73.84.95.68.69.80.84.72
-- absolute OID	: 1.3.6.1.4.1.7995.2.6.1.1.XX.33.73.78.80.85.84.95.49.95.69.77.66.69.68.95.65.85.68.73.79.95.56.95.49.95.66.73.84.95.68.69.80.84.72
--
-- Value(s)		: WARN:No Input
--				: 16
--				: 20
--				: 24
-- Comments		:
--
---------------------------------------------------------------------------------------------------
-- Header		: INPUT_1_EMBED_AUDIO_8_2_BIT_DEPTH
--
-- MIB ref		: swCardEventLogSlotXX       .33.73.78.80.85.84.95.49.95.69.77.66.69.68.95.65.85.68.73.79.95.56.95.50.95.66.73.84.95.68.69.80.84.72
-- absolute OID	: 1.3.6.1.4.1.7995.2.6.1.1.XX.33.73.78.80.85.84.95.49.95.69.77.66.69.68.95.65.85.68.73.79.95.56.95.50.95.66.73.84.95.68.69.80.84.72
--
-- Value(s)		: WARN:No Input
--				: 16
--				: 20
--				: 24
-- Comments		:
--
---------------------------------------------------------------------------------------------------
-- Header		: INPUT_1_UMID_PREVIOUS_FRAME_COUNT
--
-- MIB ref		: swCardEventLogSlotXX       .33.73.78.80.85.84.95.49.95.85.77.73.68.95.80.82.69.86.73.79.85.83.95.70.82.65.77.69.95.67.79.85.78.84
-- absolute OID	: 1.3.6.1.4.1.7995.2.6.1.1.XX.33.73.78.80.85.84.95.49.95.85.77.73.68.95.80.82.69.86.73.79.85.83.95.70.82.65.77.69.95.67.79.85.78.84
--
-- Value(s)		: 517
-- Comments		:
--
---------------------------------------------------------------------------------------------------
-- Header		: INPUT_1_CONTENT_ADVISORY_AGE_RATING
--
-- MIB ref		: swCardEventLogSlotXX       .35.73.78.80.85.84.95.49.95.67.79.78.84.69.78.84.95.65.68.86.73.83.79.82.89.95.65.71.69.95.82.65.84.73.78.71
-- absolute OID	: 1.3.6.1.4.1.7995.2.6.1.1.XX.35.73.78.80.85.84.95.49.95.67.79.78.84.69.78.84.95.65.68.86.73.83.79.82.89.95.65.71.69.95.82.65.84.73.78.71
--
-- Value(s)		: TV-PG(VL)
-- Comments		:
--
---------------------------------------------------------------------------------------------------
-- Header		: INPUT_1_EMBEDDED_AUDIO_LIKE_1_CHANS
--
-- MIB ref		: swCardEventLogSlotXX       .35.73.78.80.85.84.95.49.95.69.77.66.69.68.68.69.68.95.65.85.68.73.79.95.76.73.75.69.95.49.95.67.72.65.78.83
-- absolute OID	: 1.3.6.1.4.1.7995.2.6.1.1.XX.35.73.78.80.85.84.95.49.95.69.77.66.69.68.68.69.68.95.65.85.68.73.79.95.76.73.75.69.95.49.95.67.72.65.78.83
--
-- Value(s)		: Ch1+2
-- Comments		:
--
---------------------------------------------------------------------------------------------------
-- Header		: INPUT_1_EMBEDDED_AUDIO_LIKE_1_STATE
--
-- MIB ref		: swCardEventLogSlotXX       .35.73.78.80.85.84.95.49.95.69.77.66.69.68.68.69.68.95.65.85.68.73.79.95.76.73.75.69.95.49.95.83.84.65.84.69
-- absolute OID	: 1.3.6.1.4.1.7995.2.6.1.1.XX.35.73.78.80.85.84.95.49.95.69.77.66.69.68.68.69.68.95.65.85.68.73.79.95.76.73.75.69.95.49.95.83.84.65.84.69
--
-- Value(s)		: Mono
--				: Stereo
--				: FAIL:Inverted Mono
-- Comments		:
--
---------------------------------------------------------------------------------------------------
-- Header		: INPUT_1_EMBEDDED_AUDIO_LIKE_2_CHANS
--
-- MIB ref		: swCardEventLogSlotXX       .35.73.78.80.85.84.95.49.95.69.77.66.69.68.68.69.68.95.65.85.68.73.79.95.76.73.75.69.95.50.95.67.72.65.78.83
-- absolute OID	: 1.3.6.1.4.1.7995.2.6.1.1.XX.35.73.78.80.85.84.95.49.95.69.77.66.69.68.68.69.68.95.65.85.68.73.79.95.76.73.75.69.95.50.95.67.72.65.78.83
--
-- Value(s)		: Ch3+4
-- Comments		:
--
---------------------------------------------------------------------------------------------------
-- Header		: INPUT_1_EMBEDDED_AUDIO_LIKE_2_STATE
--
-- MIB ref		: swCardEventLogSlotXX       .35.73.78.80.85.84.95.49.95.69.77.66.69.68.68.69.68.95.65.85.68.73.79.95.76.73.75.69.95.50.95.83.84.65.84.69
-- absolute OID	: 1.3.6.1.4.1.7995.2.6.1.1.XX.35.73.78.80.85.84.95.49.95.69.77.66.69.68.68.69.68.95.65.85.68.73.79.95.76.73.75.69.95.50.95.83.84.65.84.69
--
-- Value(s)		: Mono
--				: Stereo
--				: FAIL:Inverted Mono
-- Comments		:
--
---------------------------------------------------------------------------------------------------
-- Header		: INPUT_1_EMBEDDED_AUDIO_LIKE_3_CHANS
--
-- MIB ref		: swCardEventLogSlotXX       .35.73.78.80.85.84.95.49.95.69.77.66.69.68.68.69.68.95.65.85.68.73.79.95.76.73.75.69.95.51.95.67.72.65.78.83
-- absolute OID	: 1.3.6.1.4.1.7995.2.6.1.1.XX.35.73.78.80.85.84.95.49.95.69.77.66.69.68.68.69.68.95.65.85.68.73.79.95.76.73.75.69.95.51.95.67.72.65.78.83
--
-- Value(s)		: Ch5+6
-- Comments		:
--
---------------------------------------------------------------------------------------------------
-- Header		: INPUT_1_EMBEDDED_AUDIO_LIKE_3_STATE
--
-- MIB ref		: swCardEventLogSlotXX       .35.73.78.80.85.84.95.49.95.69.77.66.69.68.68.69.68.95.65.85.68.73.79.95.76.73.75.69.95.51.95.83.84.65.84.69
-- absolute OID	: 1.3.6.1.4.1.7995.2.6.1.1.XX.35.73.78.80.85.84.95.49.95.69.77.66.69.68.68.69.68.95.65.85.68.73.79.95.76.73.75.69.95.51.95.83.84.65.84.69
--
-- Value(s)		: Mono
--				: Stereo
--				: FAIL:Inverted Mono
-- Comments		:
--
---------------------------------------------------------------------------------------------------
-- Header		: INPUT_1_EMBEDDED_AUDIO_LIKE_4_CHANS
--
-- MIB ref		: swCardEventLogSlotXX       .35.73.78.80.85.84.95.49.95.69.77.66.69.68.68.69.68.95.65.85.68.73.79.95.76.73.75.69.95.52.95.67.72.65.78.83
-- absolute OID	: 1.3.6.1.4.1.7995.2.6.1.1.XX.35.73.78.80.85.84.95.49.95.69.77.66.69.68.68.69.68.95.65.85.68.73.79.95.76.73.75.69.95.52.95.67.72.65.78.83
--
-- Value(s)		: Ch7+8
-- Comments		:
--
---------------------------------------------------------------------------------------------------
-- Header		: INPUT_1_EMBEDDED_AUDIO_LIKE_4_STATE
--
-- MIB ref		: swCardEventLogSlotXX       .35.73.78.80.85.84.95.49.95.69.77.66.69.68.68.69.68.95.65.85.68.73.79.95.76.73.75.69.95.52.95.83.84.65.84.69
-- absolute OID	: 1.3.6.1.4.1.7995.2.6.1.1.XX.35.73.78.80.85.84.95.49.95.69.77.66.69.68.68.69.68.95.65.85.68.73.79.95.76.73.75.69.95.52.95.83.84.65.84.69
--
-- Value(s)		: Mono
--				: Stereo
--				: FAIL:Inverted Mono
-- Comments		:
--
---------------------------------------------------------------------------------------------------
