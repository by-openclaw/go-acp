-- ************************************************************************************
--        Snell Card:IQUDC30
--        Module Id#:680
--       Command Set:5
--          Filename:SNELL-IQUDC30-CMD-MIB.mib
--            Author:n hext
--              Date:15/01/2014
--              Time:09:39
--
-- Copyright (c) 2010 Snell Ltd
-- All rights reserved.
--
-- ************************************************************************************

SNELL-IQUDC30-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUDC30,
    moduleIQUDC30MIB
        FROM SNELL-WILCOX-PRODUCT-REG;

 moduleIQUDC30CmdMi MODULE-IDENTITY
    LAST-UPDATED "1401150939Z"
    ORGANIZATION "Snell Ltd"
    CONTACT-INFO
        "Primary Author:n hext

         postal:    Southleigh Park House
                    Eastleigh Road
                    Havant, Hants
                    PO9 2PE
         phone:     +44 (0)23 92489000
         email:     snmp.support@snellgroup.com"
    DESCRIPTION
        "This file defines the Snell card, command set  translations."
    ::= { moduleIQUDC30MIB 1 }




--********************************************************************************
--*
--*  Snell Card:
--*  command set:
--*  list commands/menus:
--*
--******************************************************************************
	iqudc30CmdTable OBJECT-TYPE
		SYNTAX			SEQUENCE OF Iqudc30CmdEntry
		MAX-ACCESS		not-accessible
		STATUS			current
		DESCRIPTION
				"Note the instance of this table is relected in the command set Version"
		::= { moduleIQUDC30 1 }

	iqudc30CmdEntry OBJECT-TYPE
		SYNTAX		Iqudc30CmdEntry
		MAX-ACCESS		not-accessible
		STATUS			current
		DESCRIPTION
				"Entry in command table."
		INDEX	{ iqudc30SlotIndex }
		::= { iqudc30CmdTable 1 }

	Iqudc30CmdEntry ::=
		SEQUENCE {
			iqudc30SlotIndex
				Unsigned32,
			iqudc30InputInputSourceCh1InputSelect
				INTEGER,
			iqudc30InputSourceCh1StatusSDI1
				RollCallString,
			iqudc30InputSourceCh1StatusSDI2
				RollCallString,
			iqudc30InputSourceCh1StatusCVBS
				RollCallString,
			iqudc30InputSourceCh1StatusSFP1
				RollCallString,
			iqudc30InputSourceCh1StatusSFP2
				RollCallString,
			iqudc30InputSourceCh1StatusCurrentInputStand
				RollCallString,
			iqudc30InputInputSourceCh2InputSelect
				INTEGER,
			iqudc30InputSourceCh2StatusSDI1
				RollCallString,
			iqudc30InputSourceCh2StatusSDI2
				RollCallString,
			iqudc30InputSourceCh2StatusCVBS
				RollCallString,
			iqudc30InputSourceCh2StatusSFP1
				RollCallString,
			iqudc30InputSourceCh2StatusSFP2
				RollCallString,
			iqudc30InputSourceCh2StatusCurrentInputStand
				RollCallString,
			iqudc30CVBSDecoderSetupACC
				INTEGER,
			iqudc30CVBSDecoderSetupCTI
				INTEGER,
			iqudc30CVBSDecoderSetupPedestal
				INTEGER,
			iqudc30InputCVBSDecoderNTSCHue
				INTEGER,
			iqudc30CVBSDecoderCalibrationLumaGain
				INTEGER,
			iqudc30CVBSDecoderCalibrationSaveDecoder
				INTEGER,
			iqudc30OutputCh1OutputStandardStandard
				INTEGER,
			iqudc30MenuOutputCh1Format
				INTEGER,
			iqudc30MenuOutputCh1DefaultFieldRate
				INTEGER,
			iqudc30MenuOutputCh1CurrentOutputStan
				RollCallString,
			iqudc30OutputCh1ScrollingCaptionGCaptionEntry
				RollCallString,
			iqudc30OutputCh1ScrollingCaptionGCaptionScroll
				INTEGER,
			iqudc30OutputCh1ScrollingCaptionGCaptionEnable
				INTEGER,
			iqudc30MenuOutputCh1Freeze
				INTEGER,
			iqudc30MenuOutputCh1Legalizer
				INTEGER,
			iqudc30OutputCh1SFPOutputRoutingSFP1Source
				INTEGER,
			iqudc30MenuOutputCh1SFP2Source
				INTEGER,
			iqudc30MenuOutputCh1TestPatterns
				INTEGER,
			iqudc30CVBSEncoderASetupFormat
				INTEGER,
			iqudc30OutputCh1CalibrationDACGain
				INTEGER,
			iqudc30OutputCh1CalibrationSaveEncoder
				INTEGER,
			iqudc30OutputCh1BlankingEmbeddedAudio
				INTEGER,
			iqudc30MenuOutputCh1VAncillaryData
				INTEGER,
			iqudc30MenuOutputCh1SDHalfLine
				INTEGER,
			iqudc30OutputCh2OutputStandardStandard
				INTEGER,
			iqudc30MenuOutputCh2Format
				INTEGER,
			iqudc30MenuOutputCh2DefaultFieldRate
				INTEGER,
			iqudc30MenuOutputCh2CurrentOutputStan
				RollCallString,
			iqudc30OutputCh2ScrollingCaptionGCaptionEntry
				RollCallString,
			iqudc30OutputCh2ScrollingCaptionGCaptionScroll
				INTEGER,
			iqudc30OutputCh2ScrollingCaptionGCaptionEnable
				INTEGER,
			iqudc30MenuOutputCh2Freeze
				INTEGER,
			iqudc30MenuOutputCh2Legalizer
				INTEGER,
			iqudc30MenuOutputCh2TestPatterns
				INTEGER,
			iqudc30CVBSEncoderBSetupFormat
				INTEGER,
			iqudc30OutputCh2CalibrationDACGain
				INTEGER,
			iqudc30OutputCh2CalibrationSaveEncoder
				INTEGER,
			iqudc30OutputCh2BlankingEmbeddedAudio
				INTEGER,
			iqudc30MenuOutputCh2VAncillaryData
				INTEGER,
			iqudc30MenuOutputCh2SDHalfLine
				INTEGER,
			iqudc30MenuOutputCh2NewDisplay
				RollCallString,
			iqudc30VideoCh1ProcAmpEnable
				INTEGER,
			iqudc30VideoCh1ProcAmpContrast
				INTEGER,
			iqudc30VideoCh1ProcAmpSaturation
				INTEGER,
			iqudc30VideoCh1ProcAmpBlackLevel
				INTEGER,
			iqudc30VideoCh1ProcAmpGamma
				INTEGER,
			iqudc30VideoCh1ProcAmpYCOffset
				INTEGER,
			iqudc30VideoCh1NonlinearEnhancerEnable
				INTEGER,
			iqudc30VideoCh1NonlinearEnhancerLevel
				INTEGER,
			iqudc30VideoCh1NonlinearEnhancerMode
				INTEGER,
			iqudc30MenuVideoCh1FrequencyBand20052
				INTEGER,
			iqudc30MenuVideoCh1NoiseRejection
				INTEGER,
			iqudc30VideoCh1ConversionAperturePreset
				INTEGER,
			iqudc30ConversionApertureHorizontalSharpness30100
				INTEGER,
			iqudc30MenuVideoCh1Detail
				INTEGER,
			iqudc30VideoCh1VerticalLevel
				INTEGER,
			iqudc30MenuVideoCh1FrequencyBand20060
				INTEGER,
			iqudc30VideoCh1NoiseReductionEnable
				INTEGER,
			iqudc30NoiseReductionRecursiveLuma20005
				INTEGER,
			iqudc30NoiseReductionRecursiveChroma20001
				INTEGER,
			iqudc30NoiseReductionRecursiveMode20002
				INTEGER,
			iqudc30VideoCh1NoiseReductionThreshold
				INTEGER,
			iqudc30NoiseReductionSpatialLevel20011
				INTEGER,
			iqudc30NoiseReductionSpatialMode20010
				INTEGER,
			iqudc30MenuVideoCh1Threshold
				INTEGER,
			iqudc30MenuVideoCh1SplitScreen
				INTEGER,
			iqudc30VideoCh2ProcAmpEnable
				INTEGER,
			iqudc30VideoCh2ProcAmpContrast
				INTEGER,
			iqudc30VideoCh2ProcAmpSaturation
				INTEGER,
			iqudc30VideoCh2ProcAmpBlackLevel
				INTEGER,
			iqudc30VideoCh2ProcAmpGamma
				INTEGER,
			iqudc30VideoCh2ProcAmpYCOffset
				INTEGER,
			iqudc30VideoCh2NonlinearEnhancerEnable
				INTEGER,
			iqudc30VideoCh2NonlinearEnhancerLevel
				INTEGER,
			iqudc30VideoCh2NonlinearEnhancerMode
				INTEGER,
			iqudc30MenuVideoCh2FrequencyBand20152
				INTEGER,
			iqudc30MenuVideoCh2NoiseRejection
				INTEGER,
			iqudc30VideoCh2ConversionAperturePreset
				INTEGER,
			iqudc30ConversionApertureHorizontalSharpness30200
				INTEGER,
			iqudc30MenuVideoCh2Detail
				INTEGER,
			iqudc30VideoCh2VerticalLevel
				INTEGER,
			iqudc30MenuVideoCh2FrequencyBand20160
				INTEGER,
			iqudc30VideoCh2NoiseReductionEnable
				INTEGER,
			iqudc30NoiseReductionRecursiveLuma20105
				INTEGER,
			iqudc30NoiseReductionRecursiveChroma20101
				INTEGER,
			iqudc30NoiseReductionRecursiveMode20107
				INTEGER,
			iqudc30VideoCh2NoiseReductionThreshold
				INTEGER,
			iqudc30NoiseReductionSpatialLevel20111
				INTEGER,
			iqudc30NoiseReductionSpatialMode20110
				INTEGER,
			iqudc30MenuVideoCh2Threshold
				INTEGER,
			iqudc30MenuVideoCh2SplitScreen
				INTEGER,
			iqudc30MenuVideoCh2NewDisplay
				RollCallString,
			iqudc30ConvertCh1UpConversionCleanEdgeUpconver
				INTEGER,
			iqudc30ConvertCh1MotionProcessing
				INTEGER,
			iqudc30ConvertCh1MotionProcessingEnhancedMotion
				INTEGER,
			iqudc30ConvertCh1MotionProcessingStillProcess
				INTEGER,
			iqudc30ConvertCh1MotionProcessingEnhancedStill
				INTEGER,
			iqudc30ConvertCh1MotionProcessingInputispsf
				INTEGER,
			iqudc30ConvertCh1MotionProcessingEnhancedFilm
				INTEGER,
			iqudc30ConvertCh1InputCadenceFilmCadence
				INTEGER,
			iqudc30ConvertCh1InputCadence59Cadence
				INTEGER,
			iqudc30MenuConvertCh123Source30052
				INTEGER,
			iqudc30MenuConvertCh123StartHour30053
				INTEGER,
			iqudc30ConvertCh1OutputCadenceFilmCadence
				INTEGER,
			iqudc30ConvertCh1OutputCadence59Cadence
				INTEGER,
			iqudc30MenuConvertCh123Source30062
				INTEGER,
			iqudc30MenuConvertCh123StartHour30063
				INTEGER,
			iqudc30ConvertCh2UpConversionCleanEdgeUpconver
				INTEGER,
			iqudc30ConvertCh2MotionProcessing
				INTEGER,
			iqudc30ConvertCh2MotionProcessingEnhancedMotion
				INTEGER,
			iqudc30ConvertCh2MotionProcessingStillProcess
				INTEGER,
			iqudc30ConvertCh2MotionProcessingEnhancedStill
				INTEGER,
			iqudc30ConvertCh2MotionProcessingInputispsf
				INTEGER,
			iqudc30ConvertCh2MotionProcessingEnhancedFilm
				INTEGER,
			iqudc30ConvertCh2InputCadenceFilmCadence
				INTEGER,
			iqudc30ConvertCh2InputCadence59Cadence
				INTEGER,
			iqudc30MenuConvertCh223Source30152
				INTEGER,
			iqudc30MenuConvertCh223StartHour30153
				INTEGER,
			iqudc30ConvertCh2OutputCadenceFilmCadence
				INTEGER,
			iqudc30ConvertCh2OutputCadence59Cadence
				INTEGER,
			iqudc30MenuConvertCh223Source30162
				INTEGER,
			iqudc30MenuConvertCh223StartHour30163
				INTEGER,
			iqudc30MenuConvertCh2NewDisplay
				RollCallString,
			iqudc30MenuARCSidebarKeyerSyncMode40007
				INTEGER,
			iqudc30MenuARCSidebarKeyerAspectSignallingC40136
				INTEGER,
			iqudc30MenuARCSidebarKeyerSignallingDetected64020
				RollCallString,
			iqudc30ARCSidebarKeyerSidebarKeyingOuMode40017
				INTEGER,
			iqudc30MenuARCSidebarKeyerSidebarKeySource40018
				INTEGER,
			iqudc30ARCSidebarKeyerOutputCropPositioTop40013
				INTEGER,
			iqudc30ARCSidebarKeyerOutputCropPositioBottom40014
				INTEGER,
			iqudc30ARCSidebarKeyerOutputCropPositioLeft40015
				INTEGER,
			iqudc30ARCSidebarKeyerOutputCropPositioRight40016
				INTEGER,
			iqudc30ARCSidebarKeyerPostScalingControPostScalingEnable40003
				INTEGER,
			iqudc30ARCSidebarKeyerPostScalingControSize40008
				INTEGER,
			iqudc30ARCSidebarKeyerPostScalingControAspect40009
				INTEGER,
			iqudc30ARCSidebarKeyerPostScalingControPan40006
				INTEGER,
			iqudc30ARCSidebarKeyerPostScalingControTilt40002
				INTEGER,
			iqudc30ARCSidebarKeyerStandardPresetsWhSDInputis70240030
				INTEGER,
			iqudc30ARCSidebarKeyerStandardPresetsWhSDOutputis70240037
				INTEGER,
			iqudc30StandardPresetsWhSDCrossConversionSelectStdPreset40031
				INTEGER,
			iqudc30ARCSidebarKeyerUpConversionSelectStdPreset40033
				INTEGER,
			iqudc30MenuARCSidebarKeyer
				INTEGER,
			iqudc30ScalingControlSDInputFormatifUseManualifUnkno40135
				INTEGER,
			iqudc30ScalingControlSDInputFormatif40010
				INTEGER,
			iqudc30ARCSidebarKeyerAspectSignallingCSDOutputFormat40011
				INTEGER,
			iqudc30ARCSidebarKeyerAspectSignallingCConversionScaling40012
				INTEGER,
			iqudc30AspectSignallingCSignallingConfigSource40100
				INTEGER,
			iqudc30SignallingConfigSMPTE2016Mode40130
				INTEGER,
			iqudc30AspectSignallingCSignallingConfigOutputLinePAL40139
				INTEGER,
			iqudc30AspectSignallingCSignallingConfigOutputLineNTSC40140
				INTEGER,
			iqudc30AspectSignallingCSignallingConfigOutputLineHD40138
				INTEGER,
			iqudc30SignallingConfigVIMode40120
				INTEGER,
			iqudc30MenuARCSidebarKeyerOutputFormat40121
				INTEGER,
			iqudc30MenuARCSidebarKeyerVIPassData40122
				INTEGER,
			iqudc30ARCSidebarKeyerL23Mode40112
				INTEGER,
			iqudc30MenuARCSidebarKeyerOutputFormat40113
				INTEGER,
			iqudc30MenuARCSidebarKeyerInputLine40110
				INTEGER,
			iqudc30MenuARCSidebarKeyerOutputLine40111
				INTEGER,
			iqudc30MenuARCSidebarKeyerUserBitsLine40137
				INTEGER,
			iqudc30ARCSidebarKeyerForceOutputSignalSMPTE201640133
				INTEGER,
			iqudc30MenuARCSidebarKeyerSMPTERP18640134
				INTEGER,
			iqudc30MenuARCSidebarKeyerAFD40131
				INTEGER,
			iqudc30MenuARCSidebarKeyerETSI40132
				INTEGER,
			iqudc30MenuARCSidebarKeyerSyncMode40107
				INTEGER,
			iqudc30MenuARCSidebarKeyerAspectSignallingC40236
				INTEGER,
			iqudc30MenuARCSidebarKeyerSignallingDetected64220
				RollCallString,
			iqudc30ARCSidebarKeyerSidebarKeyingOuMode40023
				INTEGER,
			iqudc30MenuARCSidebarKeyerSidebarKeySource40024
				INTEGER,
			iqudc30ARCSidebarKeyerOutputCropPositioTop40019
				INTEGER,
			iqudc30ARCSidebarKeyerOutputCropPositioBottom40020
				INTEGER,
			iqudc30ARCSidebarKeyerOutputCropPositioLeft40021
				INTEGER,
			iqudc30ARCSidebarKeyerOutputCropPositioRight40022
				INTEGER,
			iqudc30ARCSidebarKeyerPostScalingControPostScalingEnable40103
				INTEGER,
			iqudc30ARCSidebarKeyerPostScalingControSize40108
				INTEGER,
			iqudc30ARCSidebarKeyerPostScalingControAspect40109
				INTEGER,
			iqudc30ARCSidebarKeyerPostScalingControPan40106
				INTEGER,
			iqudc30ARCSidebarKeyerPostScalingControTilt40102
				INTEGER,
			iqudc30ARCSidebarKeyerStandardPresetsWhSDInputis70240040
				INTEGER,
			iqudc30ARCSidebarKeyerStandardPresetsWhSDOutputis70240047
				INTEGER,
			iqudc30StandardPresetsWhSDCrossConversionSelectStdPreset40041
				INTEGER,
			iqudc30ARCSidebarKeyerUpConversionSelectStdPreset40043
				INTEGER,
			iqudc30ARCSidebarKeyerDownConversionSelectStdPreset
				INTEGER,
			iqudc30ScalingControlSDInputFormatifUseManualifUnkno40235
				INTEGER,
			iqudc30ScalingControlSDInputFormatif40114
				INTEGER,
			iqudc30ARCSidebarKeyerAspectSignallingCSDOutputFormat40115
				INTEGER,
			iqudc30ARCSidebarKeyerAspectSignallingCConversionScaling40116
				INTEGER,
			iqudc30AspectSignallingCSignallingConfigSource40202
				INTEGER,
			iqudc30SignallingConfigSMPTE2016Mode40230
				INTEGER,
			iqudc30AspectSignallingCSignallingConfigOutputLinePAL40239
				INTEGER,
			iqudc30AspectSignallingCSignallingConfigOutputLineNTSC40240
				INTEGER,
			iqudc30AspectSignallingCSignallingConfigOutputLineHD40238
				INTEGER,
			iqudc30SignallingConfigVIMode40220
				INTEGER,
			iqudc30MenuARCSidebarKeyerOutputFormat40221
				INTEGER,
			iqudc30MenuARCSidebarKeyerVIPassData40222
				INTEGER,
			iqudc30ARCSidebarKeyerL23Mode40212
				INTEGER,
			iqudc30MenuARCSidebarKeyerOutputFormat40213
				INTEGER,
			iqudc30MenuARCSidebarKeyerInputLine40210
				INTEGER,
			iqudc30MenuARCSidebarKeyerOutputLine40211
				INTEGER,
			iqudc30MenuARCSidebarKeyerUserBitsLine40237
				INTEGER,
			iqudc30ARCSidebarKeyerForceOutputSignalSMPTE201640233
				INTEGER,
			iqudc30MenuARCSidebarKeyerSMPTERP18640234
				INTEGER,
			iqudc30MenuARCSidebarKeyerAFD40231
				INTEGER,
			iqudc30MenuARCSidebarKeyerETSI40232
				INTEGER,
			iqudc30MenuARCSidebarKeyerNewDisplay
				RollCallString,
			iqudc30AudioRoutingCh1InputPairsStatusEmbedded1
				RollCallString,
			iqudc30AudioRoutingCh1InputPairsStatusEmbedded2
				RollCallString,
			iqudc30AudioRoutingCh1InputPairsStatusEmbedded3
				RollCallString,
			iqudc30AudioRoutingCh1InputPairsStatusEmbedded4
				RollCallString,
			iqudc30AudioRoutingCh1InputPairsStatusEmbedded5
				RollCallString,
			iqudc30AudioRoutingCh1InputPairsStatusEmbedded6
				RollCallString,
			iqudc30AudioRoutingCh1InputPairsStatusEmbedded7
				RollCallString,
			iqudc30AudioRoutingCh1InputPairsStatusEmbedded8
				RollCallString,
			iqudc30AudioRoutingCh1InputPairsStatusAES1
				RollCallString,
			iqudc30AudioRoutingCh1InputPairsStatusAES2
				RollCallString,
			iqudc30AudioRoutingCh1InputPairsStatusAES3
				RollCallString,
			iqudc30AudioRoutingCh1InputPairsStatusAES4
				RollCallString,
			iqudc30AudioRoutingCh1InputPairsStatusAES5
				RollCallString,
			iqudc30AudioRoutingCh1InputPairsStatusAES6
				RollCallString,
			iqudc30AudioRoutingCh1InputPairsStatusAES7
				RollCallString,
			iqudc30AudioRoutingCh1InputPairsStatusAES8
				RollCallString,
			iqudc30AudioRoutingCh1InputPairsStatusAnalog1
				RollCallString,
			iqudc30AudioRoutingCh1InputPairsStatusAnalog2
				RollCallString,
			iqudc30AudioRoutingCh1InputPairsStatusDolbyDecoder1
				RollCallString,
			iqudc30AudioRoutingCh1InputPairsStatusDolbyDecoder2
				RollCallString,
			iqudc30AudioRoutingCh1InputPairsStatusDolbyDecoder3
				RollCallString,
			iqudc30AudioRoutingCh1InputPairsStatusDolbyDecoder4
				RollCallString,
			iqudc30AudioRoutingCh1InputPairsStatusDolbyDownmix
				RollCallString,
			iqudc30AudioRoutingCh1InputPairsStatusDolbyEncoder
				RollCallString,
			iqudc30ProcessPairs18Pair1InputPairsSource
				INTEGER,
			iqudc30ProcessPairs18Pair2InputPairsSource
				INTEGER,
			iqudc30ProcessPairs18Pair3InputPairsSource
				INTEGER,
			iqudc30ProcessPairs18Pair4InputPairsSource
				INTEGER,
			iqudc30ProcessPairs18Pair5InputPairsSource
				INTEGER,
			iqudc30ProcessPairs18Pair6InputPairsSource
				INTEGER,
			iqudc30ProcessPairs18Pair7InputPairsSource
				INTEGER,
			iqudc30ProcessPairs18Pair8InputPairsSource
				INTEGER,
			iqudc30AudioRoutingCh1ProcessPairs18SPair1
				RollCallString,
			iqudc30AudioRoutingCh1ProcessPairs18SPair2
				RollCallString,
			iqudc30AudioRoutingCh1ProcessPairs18SPair3
				RollCallString,
			iqudc30AudioRoutingCh1ProcessPairs18SPair4
				RollCallString,
			iqudc30AudioRoutingCh1ProcessPairs18SPair5
				RollCallString,
			iqudc30AudioRoutingCh1ProcessPairs18SPair6
				RollCallString,
			iqudc30AudioRoutingCh1ProcessPairs18SPair7
				RollCallString,
			iqudc30AudioRoutingCh1ProcessPairs18SPair8
				RollCallString,
			iqudc30AudioRoutingCh2InputPairsStatusEmbedded1
				RollCallString,
			iqudc30AudioRoutingCh2InputPairsStatusEmbedded2
				RollCallString,
			iqudc30AudioRoutingCh2InputPairsStatusEmbedded3
				RollCallString,
			iqudc30AudioRoutingCh2InputPairsStatusEmbedded4
				RollCallString,
			iqudc30AudioRoutingCh2InputPairsStatusEmbedded5
				RollCallString,
			iqudc30AudioRoutingCh2InputPairsStatusEmbedded6
				RollCallString,
			iqudc30AudioRoutingCh2InputPairsStatusEmbedded7
				RollCallString,
			iqudc30AudioRoutingCh2InputPairsStatusEmbedded8
				RollCallString,
			iqudc30AudioRoutingCh2InputPairsStatusAES1
				RollCallString,
			iqudc30AudioRoutingCh2InputPairsStatusAES2
				RollCallString,
			iqudc30AudioRoutingCh2InputPairsStatusAES3
				RollCallString,
			iqudc30AudioRoutingCh2InputPairsStatusAES4
				RollCallString,
			iqudc30AudioRoutingCh2InputPairsStatusAES5
				RollCallString,
			iqudc30AudioRoutingCh2InputPairsStatusAES6
				RollCallString,
			iqudc30AudioRoutingCh2InputPairsStatusAES7
				RollCallString,
			iqudc30AudioRoutingCh2InputPairsStatusAES8
				RollCallString,
			iqudc30AudioRoutingCh2InputPairsStatusAnalog1
				RollCallString,
			iqudc30AudioRoutingCh2InputPairsStatusAnalog2
				RollCallString,
			iqudc30AudioRoutingCh2InputPairsStatusDolbyDecoder1
				RollCallString,
			iqudc30AudioRoutingCh2InputPairsStatusDolbyDecoder2
				RollCallString,
			iqudc30AudioRoutingCh2InputPairsStatusDolbyDecoder3
				RollCallString,
			iqudc30AudioRoutingCh2InputPairsStatusDolbyDecoder4
				RollCallString,
			iqudc30AudioRoutingCh2InputPairsStatusDolbyDownmix
				RollCallString,
			iqudc30AudioRoutingCh2InputPairsStatusDolbyEncoder
				RollCallString,
			iqudc30ProcessPairs18ProcessPair1InputPairsSource
				INTEGER,
			iqudc30ProcessPairs18ProcessPair2InputPairsSource
				INTEGER,
			iqudc30ProcessPairs18ProcessPair3InputPairsSource
				INTEGER,
			iqudc30ProcessPairs18ProcessPair4InputPairsSource
				INTEGER,
			iqudc30ProcessPairs18ProcessPair5InputPairsSource
				INTEGER,
			iqudc30ProcessPairs18ProcessPair6InputPairsSource
				INTEGER,
			iqudc30ProcessPairs18ProcessPair7InputPairsSource
				INTEGER,
			iqudc30ProcessPairs18ProcessPair8InputPairsSource
				INTEGER,
			iqudc30AudioRoutingCh2ProcessPairs18SPair1
				RollCallString,
			iqudc30AudioRoutingCh2ProcessPairs18SPair2
				RollCallString,
			iqudc30AudioRoutingCh2ProcessPairs18SPair3
				RollCallString,
			iqudc30AudioRoutingCh2ProcessPairs18SPair4
				RollCallString,
			iqudc30AudioRoutingCh2ProcessPairs18SPair5
				RollCallString,
			iqudc30AudioRoutingCh2ProcessPairs18SPair6
				RollCallString,
			iqudc30AudioRoutingCh2ProcessPairs18SPair7
				RollCallString,
			iqudc30AudioRoutingCh2ProcessPairs18SPair8
				RollCallString,
			iqudc30MenuAudioRoutingCh2NewDisplay
				RollCallString,
			iqudc30OutputPairs18OutputPair1LProcessPairsSourc52000
				INTEGER,
			iqudc30OutputPairs18OutputPair1LInvertPhase50700
				INTEGER,
			iqudc30OutputPairs18OutputPair1LControl50100
				INTEGER,
			iqudc30OutputPairs18OutputPair1RProcessPairsSourc52008
				INTEGER,
			iqudc30OutputPairs18OutputPair1RInvertPhase50708
				INTEGER,
			iqudc30OutputPairs18OutputPair1RControl50108
				INTEGER,
			iqudc30OutputPairs18OutputPair2LProcessPairsSourc52001
				INTEGER,
			iqudc30OutputPairs18OutputPair2LInvertPhase50701
				INTEGER,
			iqudc30OutputPairs18OutputPair2LControl50101
				INTEGER,
			iqudc30OutputPairs18OutputPair2RProcessPairsSourc52009
				INTEGER,
			iqudc30OutputPairs18OutputPair2RInvertPhase50709
				INTEGER,
			iqudc30OutputPairs18OutputPair2RControl50109
				INTEGER,
			iqudc30OutputPairs18OutputPair3LProcessPairsSourc52002
				INTEGER,
			iqudc30OutputPairs18OutputPair3LInvertPhase50702
				INTEGER,
			iqudc30OutputPairs18OutputPair3LControl50102
				INTEGER,
			iqudc30OutputPairs18OutputPair3RProcessPairsSourc52010
				INTEGER,
			iqudc30OutputPairs18OutputPair3RInvertPhase50710
				INTEGER,
			iqudc30OutputPairs18OutputPair3RControl50110
				INTEGER,
			iqudc30OutputPairs18OutputPair4LProcessPairsSourc52003
				INTEGER,
			iqudc30OutputPairs18OutputPair4LInvertPhase50703
				INTEGER,
			iqudc30OutputPairs18OutputPair4LControl50103
				INTEGER,
			iqudc30OutputPairs18OutputPair4RProcessPairsSourc52011
				INTEGER,
			iqudc30OutputPairs18OutputPair4RInvertPhase50711
				INTEGER,
			iqudc30OutputPairs18OutputPair4RControl50111
				INTEGER,
			iqudc30OutputPairs18OutputPair5LProcessPairsSourc52004
				INTEGER,
			iqudc30OutputPairs18OutputPair5LInvertPhase50704
				INTEGER,
			iqudc30OutputPairs18OutputPair5LControl50104
				INTEGER,
			iqudc30OutputPairs18OutputPair5RProcessPairsSourc52012
				INTEGER,
			iqudc30OutputPairs18OutputPair5RInvertPhase50712
				INTEGER,
			iqudc30OutputPairs18OutputPair5RControl50112
				INTEGER,
			iqudc30OutputPairs18OutputPair6LProcessPairsSourc52005
				INTEGER,
			iqudc30OutputPairs18OutputPair6LInvertPhase50705
				INTEGER,
			iqudc30OutputPairs18OutputPair6LControl50105
				INTEGER,
			iqudc30OutputPairs18OutputPair6RProcessPairsSourc52013
				INTEGER,
			iqudc30OutputPairs18OutputPair6RInvertPhase50713
				INTEGER,
			iqudc30OutputPairs18OutputPair6RControl50113
				INTEGER,
			iqudc30OutputPairs18OutputPair7LProcessPairsSourc52006
				INTEGER,
			iqudc30OutputPairs18OutputPair7LInvertPhase50706
				INTEGER,
			iqudc30OutputPairs18OutputPair7LControl50106
				INTEGER,
			iqudc30OutputPairs18OutputPair7RProcessPairsSourc52014
				INTEGER,
			iqudc30OutputPairs18OutputPair7RInvertPhase50714
				INTEGER,
			iqudc30OutputPairs18OutputPair7RControl50114
				INTEGER,
			iqudc30OutputPairs18OutputPair8LProcessPairsSourc52007
				INTEGER,
			iqudc30OutputPairs18OutputPair8LInvertPhase50707
				INTEGER,
			iqudc30OutputPairs18OutputPair8LControl50107
				INTEGER,
			iqudc30OutputPairs18OutputPair8RProcessPairsSourc52015
				INTEGER,
			iqudc30OutputPairs18OutputPair8RInvertPhase50715
				INTEGER,
			iqudc30OutputPairs18OutputPair8RControl50115
				INTEGER,
			iqudc30AudioShuffleCh1OutputPairs18StPair1
				RollCallString,
			iqudc30AudioShuffleCh1OutputPairs18StPair2
				RollCallString,
			iqudc30AudioShuffleCh1OutputPairs18StPair3
				RollCallString,
			iqudc30AudioShuffleCh1OutputPairs18StPair4
				RollCallString,
			iqudc30AudioShuffleCh1OutputPairs18StPair5
				RollCallString,
			iqudc30AudioShuffleCh1OutputPairs18StPair6
				RollCallString,
			iqudc30AudioShuffleCh1OutputPairs18StPair7
				RollCallString,
			iqudc30AudioShuffleCh1OutputPairs18StPair8
				RollCallString,
			iqudc30MenuAudioShuffleCh1NewDisplay
				RollCallString,
			iqudc30OutputPairs18OutputPair1LProcessPairsSourc50800
				INTEGER,
			iqudc30OutputPairs18OutputPair1LInvertPhase50816
				INTEGER,
			iqudc30OutputPairs18OutputPair1LControl50832
				INTEGER,
			iqudc30OutputPairs18OutputPair1RProcessPairsSourc50808
				INTEGER,
			iqudc30OutputPairs18OutputPair1RInvertPhase50824
				INTEGER,
			iqudc30OutputPairs18OutputPair1RControl50840
				INTEGER,
			iqudc30OutputPairs18OutputPair2LProcessPairsSourc50801
				INTEGER,
			iqudc30OutputPairs18OutputPair2LInvertPhase50817
				INTEGER,
			iqudc30OutputPairs18OutputPair2LControl50833
				INTEGER,
			iqudc30OutputPairs18OutputPair2RProcessPairsSourc50809
				INTEGER,
			iqudc30OutputPairs18OutputPair2RInvertPhase50825
				INTEGER,
			iqudc30OutputPairs18OutputPair2RControl50841
				INTEGER,
			iqudc30OutputPairs18OutputPair3LProcessPairsSourc50802
				INTEGER,
			iqudc30OutputPairs18OutputPair3LInvertPhase50818
				INTEGER,
			iqudc30OutputPairs18OutputPair3LControl50834
				INTEGER,
			iqudc30OutputPairs18OutputPair3RProcessPairsSourc50810
				INTEGER,
			iqudc30OutputPairs18OutputPair3RInvertPhase50826
				INTEGER,
			iqudc30OutputPairs18OutputPair3RControl50842
				INTEGER,
			iqudc30OutputPairs18OutputPair4LProcessPairsSourc50803
				INTEGER,
			iqudc30OutputPairs18OutputPair4LInvertPhase50819
				INTEGER,
			iqudc30OutputPairs18OutputPair4LControl50835
				INTEGER,
			iqudc30OutputPairs18OutputPair4RProcessPairsSourc50811
				INTEGER,
			iqudc30OutputPairs18OutputPair4RInvertPhase50827
				INTEGER,
			iqudc30OutputPairs18OutputPair4RControl50843
				INTEGER,
			iqudc30OutputPairs18OutputPair5LProcessPairsSourc50804
				INTEGER,
			iqudc30OutputPairs18OutputPair5LInvertPhase50820
				INTEGER,
			iqudc30OutputPairs18OutputPair5LControl50836
				INTEGER,
			iqudc30OutputPairs18OutputPair5RProcessPairsSourc50812
				INTEGER,
			iqudc30OutputPairs18OutputPair5RInvertPhase50828
				INTEGER,
			iqudc30OutputPairs18OutputPair5RControl50844
				INTEGER,
			iqudc30OutputPairs18OutputPair6LProcessPairsSourc50805
				INTEGER,
			iqudc30OutputPairs18OutputPair6LInvertPhase50821
				INTEGER,
			iqudc30OutputPairs18OutputPair6LControl50837
				INTEGER,
			iqudc30OutputPairs18OutputPair6RProcessPairsSourc50813
				INTEGER,
			iqudc30OutputPairs18OutputPair6RInvertPhase50829
				INTEGER,
			iqudc30OutputPairs18OutputPair6RControl50845
				INTEGER,
			iqudc30OutputPairs18OutputPair7LProcessPairsSourc50806
				INTEGER,
			iqudc30OutputPairs18OutputPair7LInvertPhase50822
				INTEGER,
			iqudc30OutputPairs18OutputPair7LControl50838
				INTEGER,
			iqudc30OutputPairs18OutputPair7RProcessPairsSourc50814
				INTEGER,
			iqudc30OutputPairs18OutputPair7RInvertPhase50830
				INTEGER,
			iqudc30OutputPairs18OutputPair7RControl50846
				INTEGER,
			iqudc30OutputPairs18OutputPair8LProcessPairsSourc50807
				INTEGER,
			iqudc30OutputPairs18OutputPair8LInvertPhase50823
				INTEGER,
			iqudc30OutputPairs18OutputPair8LControl50839
				INTEGER,
			iqudc30OutputPairs18OutputPair8RProcessPairsSourc50815
				INTEGER,
			iqudc30OutputPairs18OutputPair8RInvertPhase50831
				INTEGER,
			iqudc30OutputPairs18OutputPair8RControl50847
				INTEGER,
			iqudc30AudioShuffleCh2OutputPairs18StPair1
				RollCallString,
			iqudc30AudioShuffleCh2OutputPairs18StPair2
				RollCallString,
			iqudc30AudioShuffleCh2OutputPairs18StPair3
				RollCallString,
			iqudc30AudioShuffleCh2OutputPairs18StPair4
				RollCallString,
			iqudc30AudioShuffleCh2OutputPairs18StPair5
				RollCallString,
			iqudc30AudioShuffleCh2OutputPairs18StPair6
				RollCallString,
			iqudc30AudioShuffleCh2OutputPairs18StPair7
				RollCallString,
			iqudc30AudioShuffleCh2OutputPairs18StPair8
				RollCallString,
			iqudc30MenuAudioShuffleCh2NewDisplay
				RollCallString,
			iqudc30AudioControlCh1GainPair1L
				INTEGER,
			iqudc30AudioControlCh1GainPair1R
				INTEGER,
			iqudc30AudioControlCh1GainPair2L
				INTEGER,
			iqudc30AudioControlCh1GainPair2R
				INTEGER,
			iqudc30AudioControlCh1GainPair3L
				INTEGER,
			iqudc30AudioControlCh1GainPair3R
				INTEGER,
			iqudc30AudioControlCh1GainPair4L
				INTEGER,
			iqudc30AudioControlCh1GainPair4R
				INTEGER,
			iqudc30AudioControlCh1GainPair5L
				INTEGER,
			iqudc30AudioControlCh1GainPair5R
				INTEGER,
			iqudc30AudioControlCh1GainPair6L
				INTEGER,
			iqudc30AudioControlCh1GainPair6R
				INTEGER,
			iqudc30AudioControlCh1GainPair7L
				INTEGER,
			iqudc30AudioControlCh1GainPair7R
				INTEGER,
			iqudc30AudioControlCh1GainPair8L
				INTEGER,
			iqudc30AudioControlCh1GainPair8R
				INTEGER,
			iqudc30MenuAudioControlCh1ToneFrequency
				INTEGER,
			iqudc30MenuAudioControlCh1DolbyEAlignmentO
				INTEGER,
			iqudc30DelayGlobalDelayPairOPair150319
				INTEGER,
			iqudc30DelayGlobalDelayPairOPair1Total50327
				RollCallString,
			iqudc30DelayGlobalDelayPairOPair250320
				INTEGER,
			iqudc30DelayGlobalDelayPairOPair2Total50328
				RollCallString,
			iqudc30DelayGlobalDelayPairOPair350321
				INTEGER,
			iqudc30DelayGlobalDelayPairOPair3Total50329
				RollCallString,
			iqudc30DelayGlobalDelayPairOPair450322
				INTEGER,
			iqudc30DelayGlobalDelayPairOPair4Total50330
				RollCallString,
			iqudc30DelayGlobalDelayPairOPair550323
				INTEGER,
			iqudc30DelayGlobalDelayPairOPair5Total50331
				RollCallString,
			iqudc30DelayGlobalDelayPairOPair650324
				INTEGER,
			iqudc30DelayGlobalDelayPairOPair6Total50332
				RollCallString,
			iqudc30DelayGlobalDelayPairOPair750325
				INTEGER,
			iqudc30DelayGlobalDelayPairOPair7Total50333
				RollCallString,
			iqudc30DelayGlobalDelayPairOPair850326
				INTEGER,
			iqudc30DelayGlobalDelayPairOPair8Total50334
				RollCallString,
			iqudc30AudioControlCh1GlobalDelayAudio
				INTEGER,
			iqudc30AudioControlCh1GlobalDelayAudioTotal
				RollCallString,
			iqudc30AudioControlCh1GlobalDelayVideoTotal
				RollCallString,
			iqudc30MenuAudioControlCh1NewDisplay
				RollCallString,
			iqudc30AudioControlCh2GainPair1L
				INTEGER,
			iqudc30AudioControlCh2GainPair1R
				INTEGER,
			iqudc30AudioControlCh2GainPair2L
				INTEGER,
			iqudc30AudioControlCh2GainPair2R
				INTEGER,
			iqudc30AudioControlCh2GainPair3L
				INTEGER,
			iqudc30AudioControlCh2GainPair3R
				INTEGER,
			iqudc30AudioControlCh2GainPair4L
				INTEGER,
			iqudc30AudioControlCh2GainPair4R
				INTEGER,
			iqudc30AudioControlCh2GainPair5L
				INTEGER,
			iqudc30AudioControlCh2GainPair5R
				INTEGER,
			iqudc30AudioControlCh2GainPair6L
				INTEGER,
			iqudc30AudioControlCh2GainPair6R
				INTEGER,
			iqudc30AudioControlCh2GainPair7L
				INTEGER,
			iqudc30AudioControlCh2GainPair7R
				INTEGER,
			iqudc30AudioControlCh2GainPair8L
				INTEGER,
			iqudc30AudioControlCh2GainPair8R
				INTEGER,
			iqudc30MenuAudioControlCh2ToneFrequency
				INTEGER,
			iqudc30MenuAudioControlCh2DolbyEAlignmentO
				INTEGER,
			iqudc30DelayGlobalDelayPairOPair150505
				INTEGER,
			iqudc30DelayGlobalDelayPairOPair1Total50513
				RollCallString,
			iqudc30DelayGlobalDelayPairOPair250506
				INTEGER,
			iqudc30DelayGlobalDelayPairOPair2Total50514
				RollCallString,
			iqudc30DelayGlobalDelayPairOPair350507
				INTEGER,
			iqudc30DelayGlobalDelayPairOPair3Total50515
				RollCallString,
			iqudc30DelayGlobalDelayPairOPair450508
				INTEGER,
			iqudc30DelayGlobalDelayPairOPair4Total50516
				RollCallString,
			iqudc30DelayGlobalDelayPairOPair550509
				INTEGER,
			iqudc30DelayGlobalDelayPairOPair5Total50517
				RollCallString,
			iqudc30DelayGlobalDelayPairOPair650510
				INTEGER,
			iqudc30DelayGlobalDelayPairOPair6Total50518
				RollCallString,
			iqudc30DelayGlobalDelayPairOPair750511
				INTEGER,
			iqudc30DelayGlobalDelayPairOPair7Total50519
				RollCallString,
			iqudc30DelayGlobalDelayPairOPair850512
				INTEGER,
			iqudc30DelayGlobalDelayPairOPair8Total50520
				RollCallString,
			iqudc30AudioControlCh2GlobalDelay
				INTEGER,
			iqudc30AudioControlCh2GlobalDelayGlobalTotal
				RollCallString,
			iqudc30AudioControlCh2GlobalDelayVideoTotal
				RollCallString,
			iqudc30MenuAudioControlCh2NewDisplay
				RollCallString,
			iqudc30AudioIOAESAESOutput14AES1
				INTEGER,
			iqudc30MenuAudioIOAESAES2
				INTEGER,
			iqudc30MenuAudioIOAESAES3
				INTEGER,
			iqudc30MenuAudioIOAESAES4
				INTEGER,
			iqudc30AudioIOAESAESOutput58AES5
				INTEGER,
			iqudc30MenuAudioIOAESAES6
				INTEGER,
			iqudc30MenuAudioIOAESAES7
				INTEGER,
			iqudc30MenuAudioIOAESAES8
				INTEGER,
			iqudc30MenuAudioIOAESNewDisplay
				RollCallString,
			iqudc30AudioIOAnalogAnalogOutput12Analog1
				INTEGER,
			iqudc30MenuAudioIOAnalogAnalog2
				INTEGER,
			iqudc30InputAnalogInADCHeadrPair1
				INTEGER,
			iqudc30InputAnalogInADCHeadrPair2
				INTEGER,
			iqudc30OutputAnalogOutDACLevePair1
				INTEGER,
			iqudc30OutputAnalogOutDACLevePair2
				INTEGER,
			iqudc30MenuAudioIOAnalogNewDisplay
				RollCallString,
			iqudc30DolbySetupDolbyCh1Mode
				INTEGER,
			iqudc30DolbySetupDolbyCh1DolbyEDelayCompen
				INTEGER,
			iqudc30DolbySetupDolbyCh1MetadataSource
				INTEGER,
			iqudc30DolbyCh1SMPTE2020OutputOutputLine
				INTEGER,
			iqudc30DolbyCh1SMPTE2020OutputOutputEnable
				INTEGER,
			iqudc30DolbySetupDolbyCh1DecoderSource
				INTEGER,
			iqudc30MenuDolbySetupEncoderSource1
				INTEGER,
			iqudc30MenuDolbySetupEncoderSource2
				INTEGER,
			iqudc30MenuDolbySetupEncoderSource3
				INTEGER,
			iqudc30MenuDolbySetupEncoderSource4
				INTEGER,
			iqudc30MenuDolbySetupEncoderFormat
				INTEGER,
			iqudc30MenuDolbySetupEncoderFormatED
				INTEGER,
			iqudc30MenuDolbySetupEncoderRate
				INTEGER,
			iqudc30MenuDolbySetupEncoderBitDepth
				INTEGER,
			iqudc30MenuDolbySetupEncoderConfig
				INTEGER,
			iqudc30MenuDolbySetupInputStatus
				RollCallString,
			iqudc30MenuDolbySetupDecoderRate
				RollCallString,
			iqudc30MenuDolbySetupDecoderFormat
				RollCallString,
			iqudc30MenuDolbySetupDecoderVersion
				RollCallString,
			iqudc30MenuDolbySetupEncoderVersion
				RollCallString,
			iqudc30MenuDolbySetupNewDisplay
				RollCallString,
			iqudc30MenuGenlockSourceCh12
				INTEGER,
			iqudc30GenlockTimingCh1VerticalTiming
				INTEGER,
			iqudc30GenlockTimingCh1HorizontalTiming
				INTEGER,
			iqudc30GenlockTimingCh1Status
				RollCallString,
			iqudc30GenlockTimingCh2VerticalTiming
				INTEGER,
			iqudc30GenlockTimingCh2HorizontalTiming
				INTEGER,
			iqudc30GenlockTimingCh2Status
				RollCallString,
			iqudc30MenuTimecodeCh1SourceHD
				INTEGER,
			iqudc30MenuTimecodeCh1SourceSD
				INTEGER,
			iqudc30MenuTimecodeCh1Status
				RollCallString,
			iqudc30MenuTimecodeCh1Mode
				INTEGER,
			iqudc30MenuTimecodeCh1OnTimecodeLoss
				INTEGER,
			iqudc30MenuTimecodeCh1TimecodeEntry
				RollCallString,
			iqudc30MenuTimecodeCh1TimecodeLoad
				INTEGER,
			iqudc30MenuTimecodeCh1NondropFrame
				INTEGER,
			iqudc30MenuTimecodeCh1VITCEnable
				INTEGER,
			iqudc30MenuTimecodeCh1OutputLine525
				INTEGER,
			iqudc30MenuTimecodeCh1OutputLine625
				INTEGER,
			iqudc30MenuTimecodeCh1NewDisplay
				RollCallString,
			iqudc30MenuTimecodeCh2SourceHD
				INTEGER,
			iqudc30MenuTimecodeCh2SourceSD
				INTEGER,
			iqudc30MenuTimecodeCh2Status
				RollCallString,
			iqudc30MenuTimecodeCh2Mode
				INTEGER,
			iqudc30MenuTimecodeCh2OnTimecodeLoss
				INTEGER,
			iqudc30MenuTimecodeCh2TimecodeEntry
				RollCallString,
			iqudc30MenuTimecodeCh2TimecodeLoad
				INTEGER,
			iqudc30MenuTimecodeCh2NondropFrame
				INTEGER,
			iqudc30MenuTimecodeCh2VITCEnable
				INTEGER,
			iqudc30MenuTimecodeCh2OutputLine525
				INTEGER,
			iqudc30MenuTimecodeCh2OutputLine625
				INTEGER,
			iqudc30MenuTimecodeCh2NewDisplay
				RollCallString,
			iqudc30MetadataCh1ClosedCaptionsStatus
				RollCallString,
			iqudc30MetadataCh1ClosedCaptionsCEA608OutputEnab
				INTEGER,
			iqudc30MenuMetadataCh1CEA708OutputEnab
				INTEGER,
			iqudc30MenuMetadataCh1CEA708OutputLine
				INTEGER,
			iqudc30MetadataCh1TeletextStatus
				RollCallString,
			iqudc30MetadataCh1TeletextWSTInputLine
				INTEGER,
			iqudc30MetadataCh1TeletextWSTOutputEnable
				INTEGER,
			iqudc30MenuMetadataCh1
				INTEGER,
			iqudc30MenuMetadataCh1RDD08OutputEnabl
				INTEGER,
			iqudc30MenuMetadataCh1RDD08OutputLine
				INTEGER,
			iqudc30MenuMetadataCh1NewDisplay
				RollCallString,
			iqudc30MetadataCh2ClosedCaptionsStatus
				RollCallString,
			iqudc30MetadataCh2ClosedCaptionsCEA608OutputEnab
				INTEGER,
			iqudc30MenuMetadataCh2CEA708OutputEnab
				INTEGER,
			iqudc30MenuMetadataCh2CEA708OutputLine
				INTEGER,
			iqudc30MetadataCh2TeletextStatus
				RollCallString,
			iqudc30MetadataCh2TeletextWSTInputLine
				INTEGER,
			iqudc30MetadataCh2TeletextWSTOutputEnable
				INTEGER,
			iqudc30MenuMetadataCh2
				INTEGER,
			iqudc30MenuMetadataCh2RDD08OutputEnabl
				INTEGER,
			iqudc30MenuMetadataCh2RDD08OutputLine
				INTEGER,
			iqudc30MenuMetadataCh2NewDisplay
				RollCallString,
			iqudc30GPIOGPI1GPIO1Mode
				INTEGER,
			iqudc30MenuGPIOGPI1ipSelect
				INTEGER,
			iqudc30MenuGPIOGPO1opSelect
				INTEGER,
			iqudc30GPIOGPI2GPIO2Mode
				INTEGER,
			iqudc30MenuGPIOGPI2ipSelect
				INTEGER,
			iqudc30MenuGPIOGPO2opSelect
				INTEGER,
			iqudc30MenuGPIONewDisplay
				RollCallString,
			iqudc30MenuRollCallUnitName
				RollCallString,
			iqudc30MenuRollCallIPSharePort
				INTEGER,
			iqudc30MenuRollCallIPBridgingPort
				INTEGER,
			iqudc30MenuMemoriesRecallMemory
				INTEGER,
			iqudc30MenuMemoriesSelMemory
				INTEGER,
			iqudc30MenuMemoriesSaveMemory
				INTEGER,
			iqudc30MenuMemoriesClearMemory
				INTEGER,
			iqudc30MemoriesMemoryNameChangeName
				RollCallString,
			iqudc30MenuMemoriesLastDisplayMemory
				RollCallString,
			iqudc30MenuRollTrackDisableAll
				INTEGER,
			iqudc30MenuRollTrackIndex
				INTEGER,
			iqudc30MenuRollTrackSource
				INTEGER,
			iqudc30MenuRollTrackAddress
				RollCallString,
			iqudc30MenuRollTrackCommand
				RollCallString,
			iqudc30MenuRollTrackStatus
				RollCallString,
			iqudc30MenuRollTrackSending
				RollCallString,
			iqudc30MenuMiscLoggingSerialNumberEnabl
				INTEGER,
			iqudc30MenuMiscLoggingSerialNumberStatu
				RollCallString,
			iqudc30MenuMiscLoggingUpTimeEnable
				INTEGER,
			iqudc30MenuMiscLoggingUpTimeStatus
				RollCallString,
			iqudc30MenuMiscLoggingPowerUsageStateE
				INTEGER,
			iqudc30MenuMiscLoggingPowerUsageStateS
				RollCallString,
			iqudc30MenuMiscLoggingBuild62011
				INTEGER,
			iqudc30MenuMiscLoggingBuild62010
				RollCallString,
			iqudc30MenuMiscLoggingAESOutput14Place
				RollCallString,
			iqudc30MenuMiscLoggingAESOutput58Place
				RollCallString,
			iqudc30MenuMiscLoggingInputADCPlacehold
				RollCallString,
			iqudc30MenuMiscLoggingSourceCh1Ch2Pl
				RollCallString,
			iqudc30MenuMiscLoggingCVBSDecoderPlaceh
				RollCallString,
			iqudc30MenuVideoInputLoggingInput1Type62100
				INTEGER,
			iqudc30MenuVideoInputLoggingInput1Type62101
				RollCallString,
			iqudc30MenuVideoInputLoggingInput1State62102
				INTEGER,
			iqudc30MenuVideoInputLoggingInput1State62103
				RollCallString,
			iqudc30MenuVideoInputLoggingInput1Std62104
				INTEGER,
			iqudc30MenuVideoInputLoggingInput1Std62105
				RollCallString,
			iqudc30MenuVideoInputLoggingInput2Type62200
				INTEGER,
			iqudc30MenuVideoInputLoggingInput2Type62201
				RollCallString,
			iqudc30MenuVideoInputLoggingInput2State62202
				INTEGER,
			iqudc30MenuVideoInputLoggingInput2State62203
				RollCallString,
			iqudc30MenuVideoInputLoggingInput2Std62204
				INTEGER,
			iqudc30MenuVideoInputLoggingInput2Std62205
				RollCallString,
			iqudc30MenuVideoInputLoggingInput3Type62300
				INTEGER,
			iqudc30MenuVideoInputLoggingInput3Type62301
				RollCallString,
			iqudc30MenuVideoInputLoggingInput3State62302
				INTEGER,
			iqudc30MenuVideoInputLoggingInput3State62303
				RollCallString,
			iqudc30MenuVideoInputLoggingInput3Std62304
				INTEGER,
			iqudc30MenuVideoInputLoggingInput3Std62305
				RollCallString,
			iqudc30MenuVideoInputLoggingInput4Type62400
				INTEGER,
			iqudc30MenuVideoInputLoggingInput4Type62401
				RollCallString,
			iqudc30MenuVideoInputLoggingInput4State62402
				INTEGER,
			iqudc30MenuVideoInputLoggingInput4State62403
				RollCallString,
			iqudc30MenuVideoInputLoggingInput4Std62404
				INTEGER,
			iqudc30MenuVideoInputLoggingInput4Std62405
				RollCallString,
			iqudc30MenuVideoInputLoggingInput5Type62500
				INTEGER,
			iqudc30MenuVideoInputLoggingInput5Type62501
				RollCallString,
			iqudc30MenuVideoInputLoggingInput5State62502
				INTEGER,
			iqudc30MenuVideoInputLoggingInput5State62503
				RollCallString,
			iqudc30MenuVideoInputLoggingInput5Std62504
				INTEGER,
			iqudc30MenuVideoInputLoggingInput5Std62505
				RollCallString,
			iqudc30MenuOutputLoggingOutput1Type62600
				INTEGER,
			iqudc30MenuOutputLoggingOutput1Type62601
				RollCallString,
			iqudc30MenuOutputLoggingOutput1State62602
				INTEGER,
			iqudc30MenuOutputLoggingOutput1State62603
				RollCallString,
			iqudc30MenuOutputLoggingOutput1Std62604
				INTEGER,
			iqudc30MenuOutputLoggingOutput1Std62605
				RollCallString,
			iqudc30MenuOutputLoggingOutput2Type62612
				INTEGER,
			iqudc30MenuOutputLoggingOutput2Type62613
				RollCallString,
			iqudc30MenuOutputLoggingOutput2State62614
				INTEGER,
			iqudc30MenuOutputLoggingOutput2State62615
				RollCallString,
			iqudc30MenuOutputLoggingOutput2Std62616
				INTEGER,
			iqudc30MenuOutputLoggingOutput2Std62617
				RollCallString,
			iqudc30MenuOPAudioStateCh1OutputEmbPair1s62620
				INTEGER,
			iqudc30MenuOPAudioStateCh1OutputEmbPair1s62621
				RollCallString,
			iqudc30MenuOPAudioStateCh1OutputEmbPair2s62622
				INTEGER,
			iqudc30MenuOPAudioStateCh1OutputEmbPair2s62623
				RollCallString,
			iqudc30MenuOPAudioStateCh1OutputEmbPair3s62624
				INTEGER,
			iqudc30MenuOPAudioStateCh1OutputEmbPair3s62625
				RollCallString,
			iqudc30MenuOPAudioStateCh1OutputEmbPair4s62626
				INTEGER,
			iqudc30MenuOPAudioStateCh1OutputEmbPair4s62627
				RollCallString,
			iqudc30MenuOPAudioStateCh1OutputEmbPair5s62628
				INTEGER,
			iqudc30MenuOPAudioStateCh1OutputEmbPair5s62629
				RollCallString,
			iqudc30MenuOPAudioStateCh1OutputEmbPair6s62630
				INTEGER,
			iqudc30MenuOPAudioStateCh1OutputEmbPair6s62631
				RollCallString,
			iqudc30MenuOPAudioStateCh1OutputEmbPair7s62632
				INTEGER,
			iqudc30MenuOPAudioStateCh1OutputEmbPair7s62633
				RollCallString,
			iqudc30MenuOPAudioStateCh1OutputEmbPair8s62634
				INTEGER,
			iqudc30MenuOPAudioStateCh1OutputEmbPair8s62635
				RollCallString,
			iqudc30MenuOPAudioStateCh2OutputEmbPair1s62636
				INTEGER,
			iqudc30MenuOPAudioStateCh2OutputEmbPair1s62637
				RollCallString,
			iqudc30MenuOPAudioStateCh2OutputEmbPair2s62638
				INTEGER,
			iqudc30MenuOPAudioStateCh2OutputEmbPair2s62639
				RollCallString,
			iqudc30MenuOPAudioStateCh2OutputEmbPair3s62640
				INTEGER,
			iqudc30MenuOPAudioStateCh2OutputEmbPair3s62641
				RollCallString,
			iqudc30MenuOPAudioStateCh2OutputEmbPair4s62642
				INTEGER,
			iqudc30MenuOPAudioStateCh2OutputEmbPair4s62643
				RollCallString,
			iqudc30MenuOPAudioStateCh2OutputEmbPair5s62644
				INTEGER,
			iqudc30MenuOPAudioStateCh2OutputEmbPair5s62645
				RollCallString,
			iqudc30MenuOPAudioStateCh2OutputEmbPair6s62646
				INTEGER,
			iqudc30MenuOPAudioStateCh2OutputEmbPair6s62647
				RollCallString,
			iqudc30MenuOPAudioStateCh2OutputEmbPair7s62648
				INTEGER,
			iqudc30MenuOPAudioStateCh2OutputEmbPair7s62649
				RollCallString,
			iqudc30MenuOPAudioStateCh2OutputEmbPair8s62650
				INTEGER,
			iqudc30MenuOPAudioStateCh2OutputEmbPair8s62651
				RollCallString,
			iqudc30MenuOPAudioStateCh2NewDisplay
				RollCallString,
			iqudc30MenuOPAudioTypeCh1OutputEmbPair1t62653
				INTEGER,
			iqudc30MenuOPAudioTypeCh1OutputEmbPair1t62654
				RollCallString,
			iqudc30MenuOPAudioTypeCh1OutputEmbPair2t
				INTEGER,
			iqudc30MenuOPAudioTypeCh1OutputEmbPair2s
				RollCallString,
			iqudc30MenuOPAudioTypeCh1OutputEmbPair3t62657
				INTEGER,
			iqudc30MenuOPAudioTypeCh1OutputEmbPair3t62658
				RollCallString,
			iqudc30MenuOPAudioTypeCh1OutputEmbPair4t62659
				INTEGER,
			iqudc30MenuOPAudioTypeCh1OutputEmbPair4t62660
				RollCallString,
			iqudc30MenuOPAudioTypeCh1OutputEmbPair5t62661
				INTEGER,
			iqudc30MenuOPAudioTypeCh1OutputEmbPair5t62662
				RollCallString,
			iqudc30MenuOPAudioTypeCh1OutputEmbPair6t62663
				INTEGER,
			iqudc30MenuOPAudioTypeCh1OutputEmbPair6t62664
				RollCallString,
			iqudc30MenuOPAudioTypeCh1OutputEmbPair7t62665
				INTEGER,
			iqudc30MenuOPAudioTypeCh1OutputEmbPair7t62666
				RollCallString,
			iqudc30MenuOPAudioTypeCh1OutputEmbPair8t62667
				INTEGER,
			iqudc30MenuOPAudioTypeCh1OutputEmbPair8t62668
				RollCallString,
			iqudc30MenuOPAudioTypeCh2OutputEmbPair1t62669
				INTEGER,
			iqudc30MenuOPAudioTypeCh2OutputEmbPair1t62670
				RollCallString,
			iqudc30MenuOPAudioTypeCh2OutputEmbPair2t62671
				INTEGER,
			iqudc30MenuOPAudioTypeCh2OutputEmbPair2t62672
				RollCallString,
			iqudc30MenuOPAudioTypeCh2OutputEmbPair3t62673
				INTEGER,
			iqudc30MenuOPAudioTypeCh2OutputEmbPair3t62674
				RollCallString,
			iqudc30MenuOPAudioTypeCh2OutputEmbPair4t62675
				INTEGER,
			iqudc30MenuOPAudioTypeCh2OutputEmbPair4t62676
				RollCallString,
			iqudc30MenuOPAudioTypeCh2OutputEmbPair5t62677
				INTEGER,
			iqudc30MenuOPAudioTypeCh2OutputEmbPair5t62678
				RollCallString,
			iqudc30MenuOPAudioTypeCh2OutputEmbPair6t62679
				INTEGER,
			iqudc30MenuOPAudioTypeCh2OutputEmbPair6t62680
				RollCallString,
			iqudc30MenuOPAudioTypeCh2OutputEmbPair7t62681
				INTEGER,
			iqudc30MenuOPAudioTypeCh2OutputEmbPair7t62682
				RollCallString,
			iqudc30MenuOPAudioTypeCh2OutputEmbPair8t62683
				INTEGER,
			iqudc30MenuOPAudioTypeCh2OutputEmbPair8t62684
				RollCallString,
			iqudc30MenuOPAudioTypeCh2NewDisplay
				RollCallString,
			iqudc30MenuSetupSoftwareVersion
				RollCallString,
			iqudc30MenuSetupSerialNumber
				RollCallString,
			iqudc30MenuSetupNumberOfChannels
				RollCallString,
			iqudc30MenuSetupFrameSlotNumber
				RollCallString,
			iqudc30MenuSetupRearId
				RollCallString,
			iqudc30MenuSetupFanSpeed
				RollCallString,
			iqudc30MenuSetupIQOPTMNR
				RollCallString,
			iqudc30MenuSetupIQOPTMSBK
				RollCallString,
			iqudc30MenuSetupIQOPTMLFR
				RollCallString,
			iqudc30MenuSetupIQOPTMLOG
				RollCallString,
			iqudc30MenuSetupIQOPTMLC
				RollCallString,
			iqudc30MenuSetupIQOPTMDBD
				RollCallString,
			iqudc30MenuSetupIQOPTMDBEE
				RollCallString,
			iqudc30MenuSetupIQOPTMDBED
				RollCallString,
			iqudc30MenuSetupIQOPTMLOUDJ
				RollCallString,
			iqudc30MenuSetupIQOPTMLOUDMC
				RollCallString,
			iqudc30MenuSetupBuild
				RollCallString,
			iqudc30MenuSetupLicencedOptionsH
				RollCallString,
			iqudc30MenuSetupFactoryDefaults
				INTEGER,
			iqudc30MenuSetupDefaultSettings
				INTEGER,
			iqudc30MenuSetupRestart
				INTEGER,
			iqudc30MenuSetupUpgradeStartHide
				INTEGER,
			iqudc30MenuSetupUpgradeFinishHid
				INTEGER,
			iqudc30MenuDisplaymenu
				INTEGER,
			iqudc30MenuPlaceholderCh1ScrollingCaptionG
				RollCallString,
			iqudc30MenuPlaceholderCh1SFPOutputRouting
				RollCallString,
			iqudc30MenuPlaceholderCh1CVBSEncoderPlaceh
				RollCallString,
			iqudc30MenuPlaceholderCh1NonlinearEnhancer
				RollCallString,
			iqudc30MenuPlaceholderCh1ConversionAperture
				RollCallString,
			iqudc30MenuPlaceholderCh1NoiseReducerPlace
				RollCallString,
			iqudc30MenuPlaceholderCh1UpConversionPlace
				RollCallString,
			iqudc30MenuPlaceholderCh1GenlockTimingPlac
				RollCallString,
			iqudc30MenuPlaceholderCh1FanSpeedPlacehold
				RollCallString,
			iqudc30MenuPlaceholderCh2InputSourcePlaceh
				RollCallString,
			iqudc30MenuPlaceholderCh2ScrollingCaptionG
				RollCallString,
			iqudc30MenuPlaceholderCh2SFPOutputRouting
				RollCallString,
			iqudc30MenuPlaceholderCh2CVBSEncoderPlaceh
				RollCallString,
			iqudc30MenuPlaceholderCh2NonlinearEnhancer
				RollCallString,
			iqudc30MenuPlaceholderCh2ConversionAperture
				RollCallString,
			iqudc30MenuPlaceholderCh2NoiseReducerPlace
				RollCallString,
			iqudc30MenuPlaceholderCh2UpConversionPlace
				RollCallString,
			iqudc30MenuPlaceholderCh2GenlockTimingPlac
				RollCallString
		}

	iqudc30SlotIndex OBJECT-TYPE
		SYNTAX		Unsigned32
		MAX-ACCESS		not-accessible
		STATUS			current
		DESCRIPTION
				"The unique Index value for each slot.  Its value
					ranges between 1 and the value of slotNumber."
		::= { iqudc30CmdEntry 0 }


	iqudc30InputInputSourceCh1InputSelect OBJECT-TYPE
		SYNTAX		INTEGER {
							val-SDI-1(0),
							val-SDI-2(1),
							val-CVBS(2),
							val-SFP-1(3),
							val-SFP-2(4)
							}
		MAX-ACCESS		read-write
		STATUS			current
		DESCRIPTION
				"TYPE: - RadiobuttonList
				 PAGE: - Input- Input Source Ch 1
					Input Select  cmdID= 10006 
					SDI 1  value= 0  
					SDI 2  value= 1  
					CVBS  value= 2  
					SFP 1  value= 3  
					SFP 2  value= 4  "
		::= { iqudc30CmdEntry 10006 }


	iqudc30InputSourceCh1StatusSDI1 OBJECT-TYPE
		SYNTAX		RollCallString
		MAX-ACCESS		read-only
		STATUS			current
		DESCRIPTION
				"TYPE: - Display
				 PAGE: - Input- Input Source Ch 1
					SDI 1  cmdID= 63000  format=   "
		::= { iqudc30CmdEntry 63000 }


	iqudc30InputSourceCh1StatusSDI2 OBJECT-TYPE
		SYNTAX		RollCallString
		MAX-ACCESS		read-only
		STATUS			current
		DESCRIPTION
				"TYPE: - Display
				 PAGE: - Input- Input Source Ch 1
					SDI 2  cmdID= 63001  format=   "
		::= { iqudc30CmdEntry 63001 }


	iqudc30InputSourceCh1StatusCVBS OBJECT-TYPE
		SYNTAX		RollCallString
		MAX-ACCESS		read-only
		STATUS			current
		DESCRIPTION
				"TYPE: - Display
				 PAGE: - Input- Input Source Ch 1
					CVBS  cmdID= 63004  format=   "
		::= { iqudc30CmdEntry 63004 }


	iqudc30InputSourceCh1StatusSFP1 OBJECT-TYPE
		SYNTAX		RollCallString
		MAX-ACCESS		read-only
		STATUS			current
		DESCRIPTION
				"TYPE: - Display
				 PAGE: - Input- Input Source Ch 1
					SFP 1  cmdID= 63008  format=   "
		::= { iqudc30CmdEntry 63008 }


	iqudc30InputSourceCh1StatusSFP2 OBJECT-TYPE
		SYNTAX		RollCallString
		MAX-ACCESS		read-only
		STATUS			current
		DESCRIPTION
				"TYPE: - Display
				 PAGE: - Input- Input Source Ch 1
					SFP 2  cmdID= 63009  format=   "
		::= { iqudc30CmdEntry 63009 }


	iqudc30InputSourceCh1StatusCurrentInputStand OBJECT-TYPE
		SYNTAX		RollCallString
		MAX-ACCESS		read-only
		STATUS			current
		DESCRIPTION
				"TYPE: - Display
				 PAGE: - Input- Input Source Ch 1
					Current Input Stand  cmdID= 64010  format=   "
		::= { iqudc30CmdEntry 64010 }


	iqudc30InputInputSourceCh2InputSelect OBJECT-TYPE
		SYNTAX		INTEGER {
							val-SDI-1(0),
							val-SDI-2(1),
							val-CVBS(2),
							val-SFP-1(3),
							val-SFP-2(4)
							}
		MAX-ACCESS		read-write
		STATUS			current
		DESCRIPTION
				"TYPE: - RadiobuttonList
				 PAGE: - Input- Input Source Ch 2
					Input Select  cmdID= 10106 
					SDI 1  value= 0  
					SDI 2  value= 1  
					CVBS  value= 2  
					SFP 1  value= 3  
					SFP 2  value= 4  "
		::= { iqudc30CmdEntry 10106 }


	iqudc30InputSourceCh2StatusSDI1 OBJECT-TYPE
		SYNTAX		RollCallString
		MAX-ACCESS		read-only
		STATUS			current
		DESCRIPTION
				"TYPE: - Display
				 PAGE: - Input- Input Source Ch 2
					SDI 1  cmdID= 63100  format=   "
		::= { iqudc30CmdEntry 63100 }


	iqudc30InputSourceCh2StatusSDI2 OBJECT-TYPE
		SYNTAX		RollCallString
		MAX-ACCESS		read-only
		STATUS			current
		DESCRIPTION
				"TYPE: - Display
				 PAGE: - Input- Input Source Ch 2
					SDI 2  cmdID= 63101  format=   "
		::= { iqudc30CmdEntry 63101 }


	iqudc30InputSourceCh2StatusCVBS OBJECT-TYPE
		SYNTAX		RollCallString
		MAX-ACCESS		read-only
		STATUS			current
		DESCRIPTION
				"TYPE: - Display
				 PAGE: - Input- Input Source Ch 2
					CVBS  cmdID= 63104  format=   "
		::= { iqudc30CmdEntry 63104 }


	iqudc30InputSourceCh2StatusSFP1 OBJECT-TYPE
		SYNTAX		RollCallString
		MAX-ACCESS		read-only
		STATUS			current
		DESCRIPTION
				"TYPE: - Display
				 PAGE: - Input- Input Source Ch 2
					SFP 1  cmdID= 63108  format=   "
		::= { iqudc30CmdEntry 63108 }


	iqudc30InputSourceCh2StatusSFP2 OBJECT-TYPE
		SYNTAX		RollCallString
		MAX-ACCESS		read-only
		STATUS			current
		DESCRIPTION
				"TYPE: - Display
				 PAGE: - Input- Input Source Ch 2
					SFP 2  cmdID= 63109  format=   "
		::= { iqudc30CmdEntry 63109 }


	iqudc30InputSourceCh2StatusCurrentInputStand OBJECT-TYPE
		SYNTAX		RollCallString
		MAX-ACCESS		read-only
		STATUS			current
		DESCRIPTION
				"TYPE: - Display
				 PAGE: - Input- Input Source Ch 2
					Current Input Stand  cmdID= 64110  format=   "
		::= { iqudc30CmdEntry 64110 }


	iqudc30CVBSDecoderSetupACC OBJECT-TYPE
		SYNTAX		INTEGER { disable(0), enable(1) }
		MAX-ACCESS		read-write
		STATUS			current
		DESCRIPTION
				"TYPE: - Checkbox
				 PAGE: - Input- CVBS Decoder
					ACC  cmdID= 20501 "
		::= { iqudc30CmdEntry 20501 }


	iqudc30CVBSDecoderSetupCTI OBJECT-TYPE
		SYNTAX		INTEGER { disable(0), enable(1) }
		MAX-ACCESS		read-write
		STATUS			current
		DESCRIPTION
				"TYPE: - Checkbox
				 PAGE: - Input- CVBS Decoder
					CTI  cmdID= 20502 "
		::= { iqudc30CmdEntry 20502 }


	iqudc30CVBSDecoderSetupPedestal OBJECT-TYPE
		SYNTAX		INTEGER {
							val-Off(0),
							val-On(1)
							}
		MAX-ACCESS		read-write
		STATUS			current
		DESCRIPTION
				"TYPE: - RadiobuttonList
				 PAGE: - Input- CVBS Decoder
					Pedestal  cmdID= 20503 
					Off  value= 0  
					On  value= 1  "
		::= { iqudc30CmdEntry 20503 }


	iqudc30InputCVBSDecoderNTSCHue OBJECT-TYPE
		SYNTAX		INTEGER
		MAX-ACCESS		read-write
		STATUS			current
		DESCRIPTION
				"TYPE: - Number
				 PAGE: - Input- CVBS Decoder
					NTSC Hue  cmdID= 20504  min= -180  max= 180  step= 1  format= %d deg  div_scale= 1 
					Min = -180 deg  Max = 180 deg  Step = 1 deg "
		::= { iqudc30CmdEntry 20504 }


	iqudc30CVBSDecoderCalibrationLumaGain OBJECT-TYPE
		SYNTAX		INTEGER
		MAX-ACCESS		read-write
		STATUS			current
		DESCRIPTION
				"TYPE: - Number
				 PAGE: - Input- CVBS Decoder
					Luma Gain  cmdID= 20505  min= 0  max= 2047  step= 1  format= %d  div_scale= 1 
					Min = 0  Max = 2047  Step = 1 "
		::= { iqudc30CmdEntry 20505 }


	iqudc30CVBSDecoderCalibrationSaveDecoder OBJECT-TYPE
		SYNTAX		INTEGER { noAction(0),val-Save-Decoder(1) }
		MAX-ACCESS		read-write
		STATUS			current
		DESCRIPTION
				"TYPE: - Button
				 PAGE: - Input- CVBS Decoder
					Save Decoder  cmdID= 20506  value= 1  "
		::= { iqudc30CmdEntry 20506 }


	iqudc30OutputCh1OutputStandardStandard OBJECT-TYPE
		SYNTAX		INTEGER {
							val-Follow-Input(0),
							val-625-50i(2),
							val-525-59i(3),
							val-720-23p(4),
							val-720-24p(5),
							val-720-25p(6),
							val-720-29p(7),
							val-720-50p(9),
							val-720-59p(10),
							val-1080-23p(12),
							val-1080-24p(13),
							val-1080-25p(14),
							val-1080-29p(15),
							val-1080-50i(17),
							val-1080-59i(18),
							val-1080-23psf(20),
							val-1080-24psf(21),
							val-1080-25psf(50),
							val-1080-29psf(51),
							val-1080-50p-A(22),
							val-1080-59p-A(23),
							val-1080-50p-B(25),
							val-1080-59p-B(26)
							}
		MAX-ACCESS		read-write
		STATUS			current
		DESCRIPTION
				"TYPE: - RadiobuttonList
				 PAGE: - Output-Ch1
					Standard  cmdID= 10100 
					Follow Input  value= 0  
					625 50i  value= 2  
					525 59i  value= 3  
					720 23p  value= 4  
					720 24p  value= 5  
					720 25p  value= 6  
					720 29p  value= 7  
					720 50p  value= 9  
					720 59p  value= 10  
					1080 23p  value= 12  
					1080 24p  value= 13  
					1080 25p  value= 14  
					1080 29p  value= 15  
					1080 50i  value= 17  
					1080 59i  value= 18  
					1080 23psf  value= 20  
					1080 24psf  value= 21  
					1080 25psf  value= 50  
					1080 29psf  value= 51  
					1080 50p-A  value= 22  
					1080 59p-A  value= 23  
					1080 50p-B  value= 25  
					1080 59p-B  value= 26  "
		::= { iqudc30CmdEntry 10100 }


	iqudc30MenuOutputCh1Format OBJECT-TYPE
		SYNTAX		INTEGER {
							val-525-625(0),
							val-720p(1),
							val-1080i(2),
							val-1080p-A(3),
							val-1080p-B(4)
							}
		MAX-ACCESS		read-write
		STATUS			current
		DESCRIPTION
				"TYPE: - RadiobuttonList
				 PAGE: - Output-Ch1
					Format  cmdID= 10101 
					525/625  value= 0  
					720p  value= 1  
					1080i  value= 2  
					1080p-A  value= 3  
					1080p-B  value= 4  "
		::= { iqudc30CmdEntry 10101 }


	iqudc30MenuOutputCh1DefaultFieldRate OBJECT-TYPE
		SYNTAX		INTEGER {
							val-Last-Valid-Input(0),
							val-23-Hz(1),
							val-24-Hz(2),
							val-25-Hz(3),
							val-29-Hz(4),
							val-50-Hz(6),
							val-59-Hz(7)
							}
		MAX-ACCESS		read-write
		STATUS			current
		DESCRIPTION
				"TYPE: - RadiobuttonList
				 PAGE: - Output-Ch1
					Default Field Rate  cmdID= 10102 
					Last Valid Input  value= 0  
					23 Hz  value= 1  
					24 Hz  value= 2  
					25 Hz  value= 3  
					29 Hz  value= 4  
					50 Hz  value= 6  
					59 Hz  value= 7  "
		::= { iqudc30CmdEntry 10102 }


	iqudc30MenuOutputCh1CurrentOutputStan OBJECT-TYPE
		SYNTAX		RollCallString
		MAX-ACCESS		read-only
		STATUS			current
		DESCRIPTION
				"TYPE: - Display
				 PAGE: - Output-Ch1
					Current Output Stan  cmdID= 64011  format=   "
		::= { iqudc30CmdEntry 64011 }


	iqudc30OutputCh1ScrollingCaptionGCaptionEntry OBJECT-TYPE
		SYNTAX		RollCallString
		MAX-ACCESS		read-write
		STATUS			current
		DESCRIPTION
				"TYPE: - Editstring
				 PAGE: - Output-Ch1
					Caption Entry  cmdID= 10013  "
		::= { iqudc30CmdEntry 10013 }


	iqudc30OutputCh1ScrollingCaptionGCaptionScroll OBJECT-TYPE
		SYNTAX		INTEGER { disable(0), enable(1) }
		MAX-ACCESS		read-write
		STATUS			current
		DESCRIPTION
				"TYPE: - Checkbox
				 PAGE: - Output-Ch1
					Caption Scroll  cmdID= 10015 "
		::= { iqudc30CmdEntry 10015 }


	iqudc30OutputCh1ScrollingCaptionGCaptionEnable OBJECT-TYPE
		SYNTAX		INTEGER { disable(0), enable(1) }
		MAX-ACCESS		read-write
		STATUS			current
		DESCRIPTION
				"TYPE: - Checkbox
				 PAGE: - Output-Ch1
					Caption Enable  cmdID= 10014 "
		::= { iqudc30CmdEntry 10014 }


	iqudc30MenuOutputCh1Freeze OBJECT-TYPE
		SYNTAX		INTEGER { disable(0), enable(1) }
		MAX-ACCESS		read-write
		STATUS			current
		DESCRIPTION
				"TYPE: - Checkbox
				 PAGE: - Output-Ch1
					Freeze  cmdID= 20302 "
		::= { iqudc30CmdEntry 20302 }


	iqudc30MenuOutputCh1Legalizer OBJECT-TYPE
		SYNTAX		INTEGER { disable(0), enable(1) }
		MAX-ACCESS		read-write
		STATUS			current
		DESCRIPTION
				"TYPE: - Checkbox
				 PAGE: - Output-Ch1
					Legalizer  cmdID= 20205 "
		::= { iqudc30CmdEntry 20205 }


	iqudc30OutputCh1SFPOutputRoutingSFP1Source OBJECT-TYPE
		SYNTAX		INTEGER {
							val-Ch-1(0),
							val-Ch-2(1)
							}
		MAX-ACCESS		read-write
		STATUS			current
		DESCRIPTION
				"TYPE: - RadiobuttonList
				 PAGE: - Output-Ch1
					SFP 1 Source  cmdID= 20519 
					Ch 1  value= 0  
					Ch 2  value= 1  "
		::= { iqudc30CmdEntry 20519 }


	iqudc30MenuOutputCh1SFP2Source OBJECT-TYPE
		SYNTAX		INTEGER {
							val-Ch-1(0),
							val-Ch-2(1)
							}
		MAX-ACCESS		read-write
		STATUS			current
		DESCRIPTION
				"TYPE: - RadiobuttonList
				 PAGE: - Output-Ch1
					SFP 2 Source  cmdID= 20520 
					Ch 1  value= 0  
					Ch 2  value= 1  "
		::= { iqudc30CmdEntry 20520 }


	iqudc30MenuOutputCh1TestPatterns OBJECT-TYPE
		SYNTAX		INTEGER {
							val-Off(0),
							val-Black(1),
							val-Ramp(2),
							val-Bars(3)
							}
		MAX-ACCESS		read-write
		STATUS			current
		DESCRIPTION
				"TYPE: - RadiobuttonList
				 PAGE: - Output-Ch1
					Test Patterns  cmdID= 20301 
					Off  value= 0  
					Black  value= 1  
					Ramp  value= 2  
					Bars  value= 3  "
		::= { iqudc30CmdEntry 20301 }


	iqudc30CVBSEncoderASetupFormat OBJECT-TYPE
		SYNTAX		INTEGER {
							val-PAL-NTSC(0),
							val-PAL-N-PAL-M(1),
							val-PAL-NTSC-J(2)
							}
		MAX-ACCESS		read-write
		STATUS			current
		DESCRIPTION
				"TYPE: - RadiobuttonList
				 PAGE: - Output-Ch1
					Format  cmdID= 20508 
					PAL/NTSC  value= 0  
					PAL-N/PAL-M  value= 1  
					PAL/NTSC-J  value= 2  "
		::= { iqudc30CmdEntry 20508 }


	iqudc30OutputCh1CalibrationDACGain OBJECT-TYPE
		SYNTAX		INTEGER
		MAX-ACCESS		read-write
		STATUS			current
		DESCRIPTION
				"TYPE: - Number
				 PAGE: - Output-Ch1
					DAC Gain  cmdID= 20509  min= -64  max= 64  step= 1  format= %d  div_scale= 1 
					Min = -64  Max = 64  Step = 1 "
		::= { iqudc30CmdEntry 20509 }


	iqudc30OutputCh1CalibrationSaveEncoder OBJECT-TYPE
		SYNTAX		INTEGER { noAction(0),val-Save-Encoder(1) }
		MAX-ACCESS		read-write
		STATUS			current
		DESCRIPTION
				"TYPE: - Button
				 PAGE: - Output-Ch1
					Save Encoder  cmdID= 20510  value= 1  "
		::= { iqudc30CmdEntry 20510 }


	iqudc30OutputCh1BlankingEmbeddedAudio OBJECT-TYPE
		SYNTAX		INTEGER {
							val-Enable(0),
							val-Blank(1)
							}
		MAX-ACCESS		read-write
		STATUS			current
		DESCRIPTION
				"TYPE: - RadiobuttonList
				 PAGE: - Output-Ch1
					Embedded Audio  cmdID= 10010 
					Enable  value= 0  
					Blank  value= 1  "
		::= { iqudc30CmdEntry 10010 }


	iqudc30MenuOutputCh1VAncillaryData OBJECT-TYPE
		SYNTAX		INTEGER {
							val-Pass(0),
							val-Strip(1)
							}
		MAX-ACCESS		read-write
		STATUS			current
		DESCRIPTION
				"TYPE: - RadiobuttonList
				 PAGE: - Output-Ch1
					V Ancillary Data  cmdID= 10011 
					Pass  value= 0  
					Strip  value= 1  "
		::= { iqudc30CmdEntry 10011 }


	iqudc30MenuOutputCh1SDHalfLine OBJECT-TYPE
		SYNTAX		INTEGER {
							val-Pass(0),
							val-Blank(1)
							}
		MAX-ACCESS		read-write
		STATUS			current
		DESCRIPTION
				"TYPE: - RadiobuttonList
				 PAGE: - Output-Ch1
					SD Half Line  cmdID= 10012 
					Pass  value= 0  
					Blank  value= 1  "
		::= { iqudc30CmdEntry 10012 }


	iqudc30OutputCh2OutputStandardStandard OBJECT-TYPE
		SYNTAX		INTEGER {
							val-Follow-Input(0),
							val-625-50i(2),
							val-525-59i(3),
							val-720-23p(4),
							val-720-24p(5),
							val-720-25p(6),
							val-720-29p(7),
							val-720-50p(9),
							val-720-59p(10),
							val-1080-23p(12),
							val-1080-24p(13),
							val-1080-25p(14),
							val-1080-29p(15),
							val-1080-50i(17),
							val-1080-59i(18),
							val-1080-23psf(20),
							val-1080-24psf(21),
							val-1080-25psf(50),
							val-1080-29psf(51),
							val-1080-50p-A(22),
							val-1080-59p-A(23),
							val-1080-50p-B(25),
							val-1080-59p-B(26)
							}
		MAX-ACCESS		read-write
		STATUS			current
		DESCRIPTION
				"TYPE: - RadiobuttonList
				 PAGE: - Output-Ch2
					Standard  cmdID= 10200 
					Follow Input  value= 0  
					625 50i  value= 2  
					525 59i  value= 3  
					720 23p  value= 4  
					720 24p  value= 5  
					720 25p  value= 6  
					720 29p  value= 7  
					720 50p  value= 9  
					720 59p  value= 10  
					1080 23p  value= 12  
					1080 24p  value= 13  
					1080 25p  value= 14  
					1080 29p  value= 15  
					1080 50i  value= 17  
					1080 59i  value= 18  
					1080 23psf  value= 20  
					1080 24psf  value= 21  
					1080 25psf  value= 50  
					1080 29psf  value= 51  
					1080 50p-A  value= 22  
					1080 59p-A  value= 23  
					1080 50p-B  value= 25  
					1080 59p-B  value= 26  "
		::= { iqudc30CmdEntry 10200 }


	iqudc30MenuOutputCh2Format OBJECT-TYPE
		SYNTAX		INTEGER {
							val-525-625(0),
							val-720p(1),
							val-1080i(2),
							val-1080p-A(3),
							val-1080p-B(4)
							}
		MAX-ACCESS		read-write
		STATUS			current
		DESCRIPTION
				"TYPE: - RadiobuttonList
				 PAGE: - Output-Ch2
					Format  cmdID= 10201 
					525/625  value= 0  
					720p  value= 1  
					1080i  value= 2  
					1080p-A  value= 3  
					1080p-B  value= 4  "
		::= { iqudc30CmdEntry 10201 }


	iqudc30MenuOutputCh2DefaultFieldRate OBJECT-TYPE
		SYNTAX		INTEGER {
							val-Last-Valid-Input(0),
							val-23-Hz(1),
							val-24-Hz(2),
							val-25-Hz(3),
							val-29-Hz(4),
							val-50-Hz(6),
							val-59-Hz(7)
							}
		MAX-ACCESS		read-write
		STATUS			current
		DESCRIPTION
				"TYPE: - RadiobuttonList
				 PAGE: - Output-Ch2
					Default Field Rate  cmdID= 10202 
					Last Valid Input  value= 0  
					23 Hz  value= 1  
					24 Hz  value= 2  
					25 Hz  value= 3  
					29 Hz  value= 4  
					50 Hz  value= 6  
					59 Hz  value= 7  "
		::= { iqudc30CmdEntry 10202 }


	iqudc30MenuOutputCh2CurrentOutputStan OBJECT-TYPE
		SYNTAX		RollCallString
		MAX-ACCESS		read-only
		STATUS			current
		DESCRIPTION
				"TYPE: - Display
				 PAGE: - Output-Ch2
					Current Output Stan  cmdID= 64111  format=   "
		::= { iqudc30CmdEntry 64111 }


	iqudc30OutputCh2ScrollingCaptionGCaptionEntry OBJECT-TYPE
		SYNTAX		RollCallString
		MAX-ACCESS		read-write
		STATUS			current
		DESCRIPTION
				"TYPE: - Editstring
				 PAGE: - Output-Ch2
					Caption Entry  cmdID= 10113  "
		::= { iqudc30CmdEntry 10113 }


	iqudc30OutputCh2ScrollingCaptionGCaptionScroll OBJECT-TYPE
		SYNTAX		INTEGER { disable(0), enable(1) }
		MAX-ACCESS		read-write
		STATUS			current
		DESCRIPTION
				"TYPE: - Checkbox
				 PAGE: - Output-Ch2
					Caption Scroll  cmdID= 10115 "
		::= { iqudc30CmdEntry 10115 }


	iqudc30OutputCh2ScrollingCaptionGCaptionEnable OBJECT-TYPE
		SYNTAX		INTEGER { disable(0), enable(1) }
		MAX-ACCESS		read-write
		STATUS			current
		DESCRIPTION
				"TYPE: - Checkbox
				 PAGE: - Output-Ch2
					Caption Enable  cmdID= 10114 "
		::= { iqudc30CmdEntry 10114 }


	iqudc30MenuOutputCh2Freeze OBJECT-TYPE
		SYNTAX		INTEGER { disable(0), enable(1) }
		MAX-ACCESS		read-write
		STATUS			current
		DESCRIPTION
				"TYPE: - Checkbox
				 PAGE: - Output-Ch2
					Freeze  cmdID= 20400 "
		::= { iqudc30CmdEntry 20400 }


	iqudc30MenuOutputCh2Legalizer OBJECT-TYPE
		SYNTAX		INTEGER { disable(0), enable(1) }
		MAX-ACCESS		read-write
		STATUS			current
		DESCRIPTION
				"TYPE: - Checkbox
				 PAGE: - Output-Ch2
					Legalizer  cmdID= 20300 "
		::= { iqudc30CmdEntry 20300 }


	iqudc30MenuOutputCh2TestPatterns OBJECT-TYPE
		SYNTAX		INTEGER {
							val-Off(0),
							val-Black(1),
							val-Ramp(2),
							val-Bars(3)
							}
		MAX-ACCESS		read-write
		STATUS			current
		DESCRIPTION
				"TYPE: - RadiobuttonList
				 PAGE: - Output-Ch2
					Test Patterns  cmdID= 20401 
					Off  value= 0  
					Black  value= 1  
					Ramp  value= 2  
					Bars  value= 3  "
		::= { iqudc30CmdEntry 20401 }


	iqudc30CVBSEncoderBSetupFormat OBJECT-TYPE
		SYNTAX		INTEGER {
							val-PAL-NTSC(0),
							val-PAL-N-PAL-M(1),
							val-PAL-NTSC-J(2)
							}
		MAX-ACCESS		read-write
		STATUS			current
		DESCRIPTION
				"TYPE: - RadiobuttonList
				 PAGE: - Output-Ch2
					Format  cmdID= 20512 
					PAL/NTSC  value= 0  
					PAL-N/PAL-M  value= 1  
					PAL/NTSC-J  value= 2  "
		::= { iqudc30CmdEntry 20512 }


	iqudc30OutputCh2CalibrationDACGain OBJECT-TYPE
		SYNTAX		INTEGER
		MAX-ACCESS		read-write
		STATUS			current
		DESCRIPTION
				"TYPE: - Number
				 PAGE: - Output-Ch2
					DAC Gain  cmdID= 20513  min= -64  max= 64  step= 1  format= %d  div_scale= 1 
					Min = -64  Max = 64  Step = 1 "
		::= { iqudc30CmdEntry 20513 }


	iqudc30OutputCh2CalibrationSaveEncoder OBJECT-TYPE
		SYNTAX		INTEGER { noAction(0),val-Save-Encoder(1) }
		MAX-ACCESS		read-write
		STATUS			current
		DESCRIPTION
				"TYPE: - Button
				 PAGE: - Output-Ch2
					Save Encoder  cmdID= 20514  value= 1  "
		::= { iqudc30CmdEntry 20514 }


	iqudc30OutputCh2BlankingEmbeddedAudio OBJECT-TYPE
		SYNTAX		INTEGER {
							val-Enable(0),
							val-Blank(1)
							}
		MAX-ACCESS		read-write
		STATUS			current
		DESCRIPTION
				"TYPE: - RadiobuttonList
				 PAGE: - Output-Ch2
					Embedded Audio  cmdID= 10110 
					Enable  value= 0  
					Blank  value= 1  "
		::= { iqudc30CmdEntry 10110 }


	iqudc30MenuOutputCh2VAncillaryData OBJECT-TYPE
		SYNTAX		INTEGER {
							val-Pass(0),
							val-Strip(1)
							}
		MAX-ACCESS		read-write
		STATUS			current
		DESCRIPTION
				"TYPE: - RadiobuttonList
				 PAGE: - Output-Ch2
					V Ancillary Data  cmdID= 10111 
					Pass  value= 0  
					Strip  value= 1  "
		::= { iqudc30CmdEntry 10111 }


	iqudc30MenuOutputCh2SDHalfLine OBJECT-TYPE
		SYNTAX		INTEGER {
							val-Pass(0),
							val-Blank(1)
							}
		MAX-ACCESS		read-write
		STATUS			current
		DESCRIPTION
				"TYPE: - RadiobuttonList
				 PAGE: - Output-Ch2
					SD Half Line  cmdID= 10112 
					Pass  value= 0  
					Blank  value= 1  "
		::= { iqudc30CmdEntry 10112 }


	iqudc30MenuOutputCh2NewDisplay OBJECT-TYPE
		SYNTAX		RollCallString
		MAX-ACCESS		read-only
		STATUS			current
		DESCRIPTION
				"TYPE: - Display
				 PAGE: - Output-Ch2
					New Display  cmdID= 44446  format=   "
		::= { iqudc30CmdEntry 44446 }


	iqudc30VideoCh1ProcAmpEnable OBJECT-TYPE
		SYNTAX		INTEGER { disable(0), enable(1) }
		MAX-ACCESS		read-write
		STATUS			current
		DESCRIPTION
				"TYPE: - Checkbox
				 PAGE: - Video-Ch1
					Enable  cmdID= 20109 "
		::= { iqudc30CmdEntry 20109 }


	iqudc30VideoCh1ProcAmpContrast OBJECT-TYPE
		SYNTAX		INTEGER
		MAX-ACCESS		read-write
		STATUS			current
		DESCRIPTION
				"TYPE: - Number
				 PAGE: - Video-Ch1
					Contrast  cmdID= 20100  min= -60  max= 60  step= 2  format= %0.1fdB  div_scale= 10 
					Min = -6.0dB  Max = 6.0dB  Step = 0.2dB "
		::= { iqudc30CmdEntry 20100 }


	iqudc30VideoCh1ProcAmpSaturation OBJECT-TYPE
		SYNTAX		INTEGER
		MAX-ACCESS		read-write
		STATUS			current
		DESCRIPTION
				"TYPE: - Number
				 PAGE: - Video-Ch1
					Saturation  cmdID= 20106  min= -60  max= 60  step= 2  format= %0.1fdB  div_scale= 10 
					Min = -6.0dB  Max = 6.0dB  Step = 0.2dB "
		::= { iqudc30CmdEntry 20106 }


	iqudc30VideoCh1ProcAmpBlackLevel OBJECT-TYPE
		SYNTAX		INTEGER
		MAX-ACCESS		read-write
		STATUS			current
		DESCRIPTION
				"TYPE: - Number
				 PAGE: - Video-Ch1
					Black Level  cmdID= 20102  min= -1000  max= 1000  step= 8  format= %0.1fmV  div_scale= 10 
					Min = -100.0mV  Max = 100.0mV  Step = 0.8mV "
		::= { iqudc30CmdEntry 20102 }


	iqudc30VideoCh1ProcAmpGamma OBJECT-TYPE
		SYNTAX		INTEGER
		MAX-ACCESS		read-write
		STATUS			current
		DESCRIPTION
				"TYPE: - Number
				 PAGE: - Video-Ch1
					Gamma  cmdID= 20103  min= 4  max= 17  step= 1  format= %0.1f  div_scale= 10 
					Min = 0.4  Max = 1.7  Step = 0.1 "
		::= { iqudc30CmdEntry 20103 }


	iqudc30VideoCh1ProcAmpYCOffset OBJECT-TYPE
		SYNTAX		INTEGER
		MAX-ACCESS		read-write
		STATUS			current
		DESCRIPTION
				"TYPE: - Number
				 PAGE: - Video-Ch1
					YC Offset  cmdID= 20114  min= -20  max= 20  step= 2  format= %0.0f  div_scale= 1 
					Min = -20  Max = 20  Step = 2 "
		::= { iqudc30CmdEntry 20114 }


	iqudc30VideoCh1NonlinearEnhancerEnable OBJECT-TYPE
		SYNTAX		INTEGER { disable(0), enable(1) }
		MAX-ACCESS		read-write
		STATUS			current
		DESCRIPTION
				"TYPE: - Checkbox
				 PAGE: - Video-Ch1
					Enable  cmdID= 20050 "
		::= { iqudc30CmdEntry 20050 }


	iqudc30VideoCh1NonlinearEnhancerLevel OBJECT-TYPE
		SYNTAX		INTEGER
		MAX-ACCESS		read-write
		STATUS			current
		DESCRIPTION
				"TYPE: - Number
				 PAGE: - Video-Ch1
					Level  cmdID= 20053  min= 0  max= 192  step= 1  format= %0.0f  div_scale= 1 
					Min = 0  Max = 192  Step = 1 "
		::= { iqudc30CmdEntry 20053 }


	iqudc30VideoCh1NonlinearEnhancerMode OBJECT-TYPE
		SYNTAX		INTEGER {
							val-Low(0),
							val-Medium(1),
							val-High(2),
							val-Super(3),
							val-Manual(4)
							}
		MAX-ACCESS		read-write
		STATUS			current
		DESCRIPTION
				"TYPE: - RadiobuttonList
				 PAGE: - Video-Ch1
					Mode  cmdID= 20051 
					Low  value= 0  
					Medium  value= 1  
					High  value= 2  
					Super  value= 3  
					Manual  value= 4  "
		::= { iqudc30CmdEntry 20051 }


	iqudc30MenuVideoCh1FrequencyBand20052 OBJECT-TYPE
		SYNTAX		INTEGER {
							val-Low(0),
							val-Medium(1),
							val-High(2)
							}
		MAX-ACCESS		read-write
		STATUS			current
		DESCRIPTION
				"TYPE: - RadiobuttonList
				 PAGE: - Video-Ch1
					Frequency Band  cmdID= 20052 
					Low  value= 0  
					Medium  value= 1  
					High  value= 2  "
		::= { iqudc30CmdEntry 20052 }


	iqudc30MenuVideoCh1NoiseRejection OBJECT-TYPE
		SYNTAX		INTEGER
		MAX-ACCESS		read-write
		STATUS			current
		DESCRIPTION
				"TYPE: - Number
				 PAGE: - Video-Ch1
					Noise Rejection  cmdID= 20054  min= 0  max= 100  step= 1  format= %0.0f  div_scale= 1 
					Min = 0  Max = 100  Step = 1 "
		::= { iqudc30CmdEntry 20054 }


	iqudc30VideoCh1ConversionAperturePreset OBJECT-TYPE
		SYNTAX		INTEGER { noAction(0),val-Preset(1) }
		MAX-ACCESS		read-write
		STATUS			current
		DESCRIPTION
				"TYPE: - Button
				 PAGE: - Video-Ch1
					Preset  cmdID= 20162  value= 1  "
		::= { iqudc30CmdEntry 20162 }


	iqudc30ConversionApertureHorizontalSharpness30100 OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch1
					Sharpness  cmdID= 30100 
					Soft 2  value= 0  
					Soft 1  value= 1  
					Normal  value= 2  
					Sharp 1  value= 3  
					Sharp 2  value= 4  "
		::= { iqudc30CmdEntry 30100 }


	iqudc30MenuVideoCh1Detail OBJECT-TYPE
		SYNTAX		INTEGER {
							val-Low-2(0),
							val-Low-1(1),
							val-Normal(2),
							val-High-1(3),
							val-High-2(4)
							}
		MAX-ACCESS		read-write
		STATUS			current
		DESCRIPTION
				"TYPE: - RadiobuttonList
				 PAGE: - Video-Ch1
					Detail  cmdID= 30101 
					Low 2  value= 0  
					Low 1  value= 1  
					Normal  value= 2  
					High 1  value= 3  
					High 2  value= 4  "
		::= { iqudc30CmdEntry 30101 }


	iqudc30VideoCh1VerticalLevel OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch1
					Level  cmdID= 20061 
					Soft 2  value= 0  
					Soft 1  value= 1  
					Normal  value= 2  
					Sharp 1  value= 3  
					Sharp 2  value= 4  "
		::= { iqudc30CmdEntry 20061 }


	iqudc30MenuVideoCh1FrequencyBand20060 OBJECT-TYPE
		SYNTAX		INTEGER {
							val-Low(0),
							val-Medium(1),
							val-High(2)
							}
		MAX-ACCESS		read-write
		STATUS			current
		DESCRIPTION
				"TYPE: - RadiobuttonList
				 PAGE: - Video-Ch1
					Frequency Band  cmdID= 20060 
					Low  value= 0  
					Medium  value= 1  
					High  value= 2  "
		::= { iqudc30CmdEntry 20060 }


	iqudc30VideoCh1NoiseReductionEnable OBJECT-TYPE
		SYNTAX		INTEGER { disable(0), enable(1) }
		MAX-ACCESS		read-write
		STATUS			current
		DESCRIPTION
				"TYPE: - Checkbox
				 PAGE: - Video-Ch1
					Enable  cmdID= 20004 "
		::= { iqudc30CmdEntry 20004 }


	iqudc30NoiseReductionRecursiveLuma20005 OBJECT-TYPE
		SYNTAX		INTEGER
		MAX-ACCESS		read-write
		STATUS			current
		DESCRIPTION
				"TYPE: - Number
				 PAGE: - Video-Ch1
					Luma  cmdID= 20005  min= 0  max= 7  step= 1  format= %0.0f  div_scale= 1 
					Min = 0  Max = 7  Step = 1 "
		::= { iqudc30CmdEntry 20005 }


	iqudc30NoiseReductionRecursiveChroma20001 OBJECT-TYPE
		SYNTAX		INTEGER
		MAX-ACCESS		read-write
		STATUS			current
		DESCRIPTION
				"TYPE: - Number
				 PAGE: - Video-Ch1
					Chroma  cmdID= 20001  min= 0  max= 7  step= 1  format= %0.0f  div_scale= 1 
					Min = 0  Max = 7  Step = 1 "
		::= { iqudc30CmdEntry 20001 }


	iqudc30NoiseReductionRecursiveMode20002 OBJECT-TYPE
		SYNTAX		INTEGER {
							val-Auto(0),
							val-Manual(1)
							}
		MAX-ACCESS		read-write
		STATUS			current
		DESCRIPTION
				"TYPE: - RadiobuttonList
				 PAGE: - Video-Ch1
					Mode  cmdID= 20002 
					Auto  value= 0  
					Manual  value= 1  "
		::= { iqudc30CmdEntry 20002 }


	iqudc30VideoCh1NoiseReductionThreshold OBJECT-TYPE
		SYNTAX		INTEGER
		MAX-ACCESS		read-write
		STATUS			current
		DESCRIPTION
				"TYPE: - Number
				 PAGE: - Video-Ch1
					Threshold  cmdID= 20008  min= 0  max= 7  step= 1  format= %0.0f  div_scale= 1 
					Min = 0  Max = 7  Step = 1 "
		::= { iqudc30CmdEntry 20008 }


	iqudc30NoiseReductionSpatialLevel20011 OBJECT-TYPE
		SYNTAX		INTEGER
		MAX-ACCESS		read-write
		STATUS			current
		DESCRIPTION
				"TYPE: - Number
				 PAGE: - Video-Ch1
					Level  cmdID= 20011  min= 0  max= 7  step= 1  format= %0.0f  div_scale= 1 
					Min = 0  Max = 7  Step = 1 "
		::= { iqudc30CmdEntry 20011 }


	iqudc30NoiseReductionSpatialMode20010 OBJECT-TYPE
		SYNTAX		INTEGER {
							val-Auto(0),
							val-Manual(1)
							}
		MAX-ACCESS		read-write
		STATUS			current
		DESCRIPTION
				"TYPE: - RadiobuttonList
				 PAGE: - Video-Ch1
					Mode  cmdID= 20010 
					Auto  value= 0  
					Manual  value= 1  "
		::= { iqudc30CmdEntry 20010 }


	iqudc30MenuVideoCh1Threshold OBJECT-TYPE
		SYNTAX		INTEGER
		MAX-ACCESS		read-write
		STATUS			current
		DESCRIPTION
				"TYPE: - Number
				 PAGE: - Video-Ch1
					Threshold  cmdID= 20012  min= 1  max= 4  step= 1  format= %0.0f  div_scale= 1 
					Min = 1  Max = 4  Step = 1 "
		::= { iqudc30CmdEntry 20012 }


	iqudc30MenuVideoCh1SplitScreen OBJECT-TYPE
		SYNTAX		INTEGER { disable(0), enable(1) }
		MAX-ACCESS		read-write
		STATUS			current
		DESCRIPTION
				"TYPE: - Checkbox
				 PAGE: - Video-Ch1
					Split Screen  cmdID= 20013 "
		::= { iqudc30CmdEntry 20013 }


	iqudc30VideoCh2ProcAmpEnable OBJECT-TYPE
		SYNTAX		INTEGER { disable(0), enable(1) }
		MAX-ACCESS		read-write
		STATUS			current
		DESCRIPTION
				"TYPE: - Checkbox
				 PAGE: - Video-Ch2
					Enable  cmdID= 20204 "
		::= { iqudc30CmdEntry 20204 }


	iqudc30VideoCh2ProcAmpContrast OBJECT-TYPE
		SYNTAX		INTEGER
		MAX-ACCESS		read-write
		STATUS			current
		DESCRIPTION
				"TYPE: - Number
				 PAGE: - Video-Ch2
					Contrast  cmdID= 20200  min= -60  max= 60  step= 2  format= %0.1fdB  div_scale= 10 
					Min = -6.0dB  Max = 6.0dB  Step = 0.2dB "
		::= { iqudc30CmdEntry 20200 }


	iqudc30VideoCh2ProcAmpSaturation OBJECT-TYPE
		SYNTAX		INTEGER
		MAX-ACCESS		read-write
		STATUS			current
		DESCRIPTION
				"TYPE: - Number
				 PAGE: - Video-Ch2
					Saturation  cmdID= 20201  min= -60  max= 60  step= 2  format= %0.1fdB  div_scale= 10 
					Min = -6.0dB  Max = 6.0dB  Step = 0.2dB "
		::= { iqudc30CmdEntry 20201 }


	iqudc30VideoCh2ProcAmpBlackLevel OBJECT-TYPE
		SYNTAX		INTEGER
		MAX-ACCESS		read-write
		STATUS			current
		DESCRIPTION
				"TYPE: - Number
				 PAGE: - Video-Ch2
					Black Level  cmdID= 20202  min= -1000  max= 1000  step= 8  format= %0.1fmV  div_scale= 10 
					Min = -100.0mV  Max = 100.0mV  Step = 0.8mV "
		::= { iqudc30CmdEntry 20202 }


	iqudc30VideoCh2ProcAmpGamma OBJECT-TYPE
		SYNTAX		INTEGER
		MAX-ACCESS		read-write
		STATUS			current
		DESCRIPTION
				"TYPE: - Number
				 PAGE: - Video-Ch2
					Gamma  cmdID= 20203  min= 4  max= 17  step= 1  format= %0.1f  div_scale= 10 
					Min = 0.4  Max = 1.7  Step = 0.1 "
		::= { iqudc30CmdEntry 20203 }


	iqudc30VideoCh2ProcAmpYCOffset OBJECT-TYPE
		SYNTAX		INTEGER
		MAX-ACCESS		read-write
		STATUS			current
		DESCRIPTION
				"TYPE: - Number
				 PAGE: - Video-Ch2
					YC Offset  cmdID= 20214  min= -20  max= 20  step= 2  format= %0.0f  div_scale= 1 
					Min = -20  Max = 20  Step = 2 "
		::= { iqudc30CmdEntry 20214 }


	iqudc30VideoCh2NonlinearEnhancerEnable OBJECT-TYPE
		SYNTAX		INTEGER { disable(0), enable(1) }
		MAX-ACCESS		read-write
		STATUS			current
		DESCRIPTION
				"TYPE: - Checkbox
				 PAGE: - Video-Ch2
					Enable  cmdID= 20150 "
		::= { iqudc30CmdEntry 20150 }


	iqudc30VideoCh2NonlinearEnhancerLevel OBJECT-TYPE
		SYNTAX		INTEGER
		MAX-ACCESS		read-write
		STATUS			current
		DESCRIPTION
				"TYPE: - Number
				 PAGE: - Video-Ch2
					Level  cmdID= 20153  min= 0  max= 192  step= 1  format= %0.0f  div_scale= 1 
					Min = 0  Max = 192  Step = 1 "
		::= { iqudc30CmdEntry 20153 }


	iqudc30VideoCh2NonlinearEnhancerMode OBJECT-TYPE
		SYNTAX		INTEGER {
							val-Low(0),
							val-Medium(1),
							val-High(2),
							val-Super(3),
							val-Manual(4)
							}
		MAX-ACCESS		read-write
		STATUS			current
		DESCRIPTION
				"TYPE: - RadiobuttonList
				 PAGE: - Video-Ch2
					Mode  cmdID= 20151 
					Low  value= 0  
					Medium  value= 1  
					High  value= 2  
					Super  value= 3  
					Manual  value= 4  "
		::= { iqudc30CmdEntry 20151 }


	iqudc30MenuVideoCh2FrequencyBand20152 OBJECT-TYPE
		SYNTAX		INTEGER {
							val-Low(0),
							val-Medium(1),
							val-High(2)
							}
		MAX-ACCESS		read-write
		STATUS			current
		DESCRIPTION
				"TYPE: - RadiobuttonList
				 PAGE: - Video-Ch2
					Frequency Band  cmdID= 20152 
					Low  value= 0  
					Medium  value= 1  
					High  value= 2  "
		::= { iqudc30CmdEntry 20152 }


	iqudc30MenuVideoCh2NoiseRejection OBJECT-TYPE
		SYNTAX		INTEGER
		MAX-ACCESS		read-write
		STATUS			current
		DESCRIPTION
				"TYPE: - Number
				 PAGE: - Video-Ch2
					Noise Rejection  cmdID= 20154  min= 0  max= 100  step= 1  format= %0.0f  div_scale= 1 
					Min = 0  Max = 100  Step = 1 "
		::= { iqudc30CmdEntry 20154 }


	iqudc30VideoCh2ConversionAperturePreset OBJECT-TYPE
		SYNTAX		INTEGER { noAction(0),val-Preset(1) }
		MAX-ACCESS		read-write
		STATUS			current
		DESCRIPTION
				"TYPE: - Button
				 PAGE: - Video-Ch2
					Preset  cmdID= 20262  value= 1  "
		::= { iqudc30CmdEntry 20262 }


	iqudc30ConversionApertureHorizontalSharpness30200 OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch2
					Sharpness  cmdID= 30200 
					Soft 2  value= 0  
					Soft 1  value= 1  
					Normal  value= 2  
					Sharp 1  value= 3  
					Sharp 2  value= 4  "
		::= { iqudc30CmdEntry 30200 }


	iqudc30MenuVideoCh2Detail OBJECT-TYPE
		SYNTAX		INTEGER {
							val-Low-2(0),
							val-Low-1(1),
							val-Normal(2),
							val-High-1(3),
							val-High-2(4)
							}
		MAX-ACCESS		read-write
		STATUS			current
		DESCRIPTION
				"TYPE: - RadiobuttonList
				 PAGE: - Video-Ch2
					Detail  cmdID= 30201 
					Low 2  value= 0  
					Low 1  value= 1  
					Normal  value= 2  
					High 1  value= 3  
					High 2  value= 4  "
		::= { iqudc30CmdEntry 30201 }


	iqudc30VideoCh2VerticalLevel OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch2
					Level  cmdID= 20161 
					Soft 2  value= 0  
					Soft 1  value= 1  
					Normal  value= 2  
					Sharp 1  value= 3  
					Sharp 2  value= 4  "
		::= { iqudc30CmdEntry 20161 }


	iqudc30MenuVideoCh2FrequencyBand20160 OBJECT-TYPE
		SYNTAX		INTEGER {
							val-Low(0),
							val-Medium(1),
							val-High(2)
							}
		MAX-ACCESS		read-write
		STATUS			current
		DESCRIPTION
				"TYPE: - RadiobuttonList
				 PAGE: - Video-Ch2
					Frequency Band  cmdID= 20160 
					Low  value= 0  
					Medium  value= 1  
					High  value= 2  "
		::= { iqudc30CmdEntry 20160 }


	iqudc30VideoCh2NoiseReductionEnable OBJECT-TYPE
		SYNTAX		INTEGER { disable(0), enable(1) }
		MAX-ACCESS		read-write
		STATUS			current
		DESCRIPTION
				"TYPE: - Checkbox
				 PAGE: - Video-Ch2
					Enable  cmdID= 20104 "
		::= { iqudc30CmdEntry 20104 }


	iqudc30NoiseReductionRecursiveLuma20105 OBJECT-TYPE
		SYNTAX		INTEGER
		MAX-ACCESS		read-write
		STATUS			current
		DESCRIPTION
				"TYPE: - Number
				 PAGE: - Video-Ch2
					Luma  cmdID= 20105  min= 0  max= 7  step= 1  format= %0.0f  div_scale= 1 
					Min = 0  Max = 7  Step = 1 "
		::= { iqudc30CmdEntry 20105 }


	iqudc30NoiseReductionRecursiveChroma20101 OBJECT-TYPE
		SYNTAX		INTEGER
		MAX-ACCESS		read-write
		STATUS			current
		DESCRIPTION
				"TYPE: - Number
				 PAGE: - Video-Ch2
					Chroma  cmdID= 20101  min= 0  max= 7  step= 1  format= %0.0f  div_scale= 1 
					Min = 0  Max = 7  Step = 1 "
		::= { iqudc30CmdEntry 20101 }


	iqudc30NoiseReductionRecursiveMode20107 OBJECT-TYPE
		SYNTAX		INTEGER {
							val-Auto(0),
							val-Manual(1)
							}
		MAX-ACCESS		read-write
		STATUS			current
		DESCRIPTION
				"TYPE: - RadiobuttonList
				 PAGE: - Video-Ch2
					Mode  cmdID= 20107 
					Auto  value= 0  
					Manual  value= 1  "
		::= { iqudc30CmdEntry 20107 }


	iqudc30VideoCh2NoiseReductionThreshold OBJECT-TYPE
		SYNTAX		INTEGER
		MAX-ACCESS		read-write
		STATUS			current
		DESCRIPTION
				"TYPE: - Number
				 PAGE: - Video-Ch2
					Threshold  cmdID= 20108  min= 0  max= 7  step= 1  format= %0.0f  div_scale= 1 
					Min = 0  Max = 7  Step = 1 "
		::= { iqudc30CmdEntry 20108 }


	iqudc30NoiseReductionSpatialLevel20111 OBJECT-TYPE
		SYNTAX		INTEGER
		MAX-ACCESS		read-write
		STATUS			current
		DESCRIPTION
				"TYPE: - Number
				 PAGE: - Video-Ch2
					Level  cmdID= 20111  min= 0  max= 7  step= 1  format= %0.0f  div_scale= 1 
					Min = 0  Max = 7  Step = 1 "
		::= { iqudc30CmdEntry 20111 }


	iqudc30NoiseReductionSpatialMode20110 OBJECT-TYPE
		SYNTAX		INTEGER {
							val-Auto(0),
							val-Manual(1)
							}
		MAX-ACCESS		read-write
		STATUS			current
		DESCRIPTION
				"TYPE: - RadiobuttonList
				 PAGE: - Video-Ch2
					Mode  cmdID= 20110 
					Auto  value= 0  
					Manual  value= 1  "
		::= { iqudc30CmdEntry 20110 }


	iqudc30MenuVideoCh2Threshold OBJECT-TYPE
		SYNTAX		INTEGER
		MAX-ACCESS		read-write
		STATUS			current
		DESCRIPTION
				"TYPE: - Number
				 PAGE: - Video-Ch2
					Threshold  cmdID= 20112  min= 1  max= 4  step= 1  format= %0.0f  div_scale= 1 
					Min = 1  Max = 4  Step = 1 "
		::= { iqudc30CmdEntry 20112 }


	iqudc30MenuVideoCh2SplitScreen OBJECT-TYPE
		SYNTAX		INTEGER { disable(0), enable(1) }
		MAX-ACCESS		read-write
		STATUS			current
		DESCRIPTION
				"TYPE: - Checkbox
				 PAGE: - Video-Ch2
					Split Screen  cmdID= 20113 "
		::= { iqudc30CmdEntry 20113 }


	iqudc30MenuVideoCh2NewDisplay OBJECT-TYPE
		SYNTAX		RollCallString
		MAX-ACCESS		read-only
		STATUS			current
		DESCRIPTION
				"TYPE: - Display
				 PAGE: - Video-Ch2
					New Display  cmdID= 44447  format=   "
		::= { iqudc30CmdEntry 44447 }


	iqudc30ConvertCh1UpConversionCleanEdgeUpconver OBJECT-TYPE
		SYNTAX		INTEGER { disable(0), enable(1) }
		MAX-ACCESS		read-write
		STATUS			current
		DESCRIPTION
				"TYPE: - Checkbox
				 PAGE: - Convert-Ch1
					Clean Edge Upconver  cmdID= 30072 "
		::= { iqudc30CmdEntry 30072 }


	iqudc30ConvertCh1MotionProcessing OBJECT-TYPE
		SYNTAX		INTEGER { disable(0), enable(1) }
		MAX-ACCESS		read-write
		STATUS			current
		DESCRIPTION
				"TYPE: - Checkbox
				 PAGE: - Convert-Ch1
					Motion Process  cmdID= 30005 "
		::= { iqudc30CmdEntry 30005 }


	iqudc30ConvertCh1MotionProcessingEnhancedMotion OBJECT-TYPE
		SYNTAX		INTEGER { disable(0), enable(1) }
		MAX-ACCESS		read-write
		STATUS			current
		DESCRIPTION
				"TYPE: - Checkbox
				 PAGE: - Convert-Ch1
					Enhanced Motion  cmdID= 30002 "
		::= { iqudc30CmdEntry 30002 }


	iqudc30ConvertCh1MotionProcessingStillProcess OBJECT-TYPE
		SYNTAX		INTEGER { disable(0), enable(1) }
		MAX-ACCESS		read-write
		STATUS			current
		DESCRIPTION
				"TYPE: - Checkbox
				 PAGE: - Convert-Ch1
					Still Process  cmdID= 30003 "
		::= { iqudc30CmdEntry 30003 }


	iqudc30ConvertCh1MotionProcessingEnhancedStill OBJECT-TYPE
		SYNTAX		INTEGER { disable(0), enable(1) }
		MAX-ACCESS		read-write
		STATUS			current
		DESCRIPTION
				"TYPE: - Checkbox
				 PAGE: - Convert-Ch1
					Enhanced Still  cmdID= 30004 "
		::= { iqudc30CmdEntry 30004 }


	iqudc30ConvertCh1MotionProcessingInputispsf OBJECT-TYPE
		SYNTAX		INTEGER { disable(0), enable(1) }
		MAX-ACCESS		read-write
		STATUS			current
		DESCRIPTION
				"TYPE: - Checkbox
				 PAGE: - Convert-Ch1
					Input is psf  cmdID= 30071 "
		::= { iqudc30CmdEntry 30071 }


	iqudc30ConvertCh1MotionProcessingEnhancedFilm OBJECT-TYPE
		SYNTAX		INTEGER { disable(0), enable(1) }
		MAX-ACCESS		read-write
		STATUS			current
		DESCRIPTION
				"TYPE: - Checkbox
				 PAGE: - Convert-Ch1
					Enhanced Film  cmdID= 30070 "
		::= { iqudc30CmdEntry 30070 }


	iqudc30ConvertCh1InputCadenceFilmCadence OBJECT-TYPE
		SYNTAX		INTEGER { disable(0), enable(1) }
		MAX-ACCESS		read-write
		STATUS			current
		DESCRIPTION
				"TYPE: - Checkbox
				 PAGE: - Convert-Ch1
					Film Cadence  cmdID= 30050 "
		::= { iqudc30CmdEntry 30050 }


	iqudc30ConvertCh1InputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch1
					59 Cadence  cmdID= 30051 
					2:3  value= 0  
					2:2 (psf)  value= 1  "
		::= { iqudc30CmdEntry 30051 }


	iqudc30MenuConvertCh123Source30052 OBJECT-TYPE
		SYNTAX		INTEGER {
							val-Automatic(0),
							val-Input-Timecode(1)
							}
		MAX-ACCESS		read-write
		STATUS			current
		DESCRIPTION
				"TYPE: - RadiobuttonList
				 PAGE: - Convert-Ch1
					2:3 Source  cmdID= 30052 
					Automatic  value= 0  
					Input Timecode  value= 1  "
		::= { iqudc30CmdEntry 30052 }


	iqudc30MenuConvertCh123StartHour30053 OBJECT-TYPE
		SYNTAX		INTEGER
		MAX-ACCESS		read-write
		STATUS			current
		DESCRIPTION
				"TYPE: - Number
				 PAGE: - Convert-Ch1
					2:3 Start Hour  cmdID= 30053  min= 0  max= 23  step= 1  format= %0.0f  div_scale= 1 
					Min = 0  Max = 23  Step = 1 "
		::= { iqudc30CmdEntry 30053 }


	iqudc30ConvertCh1OutputCadenceFilmCadence OBJECT-TYPE
		SYNTAX		INTEGER { disable(0), enable(1) }
		MAX-ACCESS		read-write
		STATUS			current
		DESCRIPTION
				"TYPE: - Checkbox
				 PAGE: - Convert-Ch1
					Film Cadence  cmdID= 30060 "
		::= { iqudc30CmdEntry 30060 }


	iqudc30ConvertCh1OutputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch1
					59 Cadence  cmdID= 30061 
					2:3  value= 0  
					2:2 (psf)  value= 1  "
		::= { iqudc30CmdEntry 30061 }


	iqudc30MenuConvertCh123Source30062 OBJECT-TYPE
		SYNTAX		INTEGER {
							val-Free-Run(0),
							val-Output-Timecode(1)
							}
		MAX-ACCESS		read-write
		STATUS			current
		DESCRIPTION
				"TYPE: - RadiobuttonList
				 PAGE: - Convert-Ch1
					2:3 Source  cmdID= 30062 
					Free Run  value= 0  
					Output Timecode  value= 1  "
		::= { iqudc30CmdEntry 30062 }


	iqudc30MenuConvertCh123StartHour30063 OBJECT-TYPE
		SYNTAX		INTEGER
		MAX-ACCESS		read-write
		STATUS			current
		DESCRIPTION
				"TYPE: - Number
				 PAGE: - Convert-Ch1
					2:3 Start Hour  cmdID= 30063  min= 0  max= 23  step= 1  format= %0.0f  div_scale= 1 
					Min = 0  Max = 23  Step = 1 "
		::= { iqudc30CmdEntry 30063 }


	iqudc30ConvertCh2UpConversionCleanEdgeUpconver OBJECT-TYPE
		SYNTAX		INTEGER { disable(0), enable(1) }
		MAX-ACCESS		read-write
		STATUS			current
		DESCRIPTION
				"TYPE: - Checkbox
				 PAGE: - Convert-Ch2
					Clean Edge Upconver  cmdID= 30172 "
		::= { iqudc30CmdEntry 30172 }


	iqudc30ConvertCh2MotionProcessing OBJECT-TYPE
		SYNTAX		INTEGER { disable(0), enable(1) }
		MAX-ACCESS		read-write
		STATUS			current
		DESCRIPTION
				"TYPE: - Checkbox
				 PAGE: - Convert-Ch2
					Motion Process  cmdID= 30105 "
		::= { iqudc30CmdEntry 30105 }


	iqudc30ConvertCh2MotionProcessingEnhancedMotion OBJECT-TYPE
		SYNTAX		INTEGER { disable(0), enable(1) }
		MAX-ACCESS		read-write
		STATUS			current
		DESCRIPTION
				"TYPE: - Checkbox
				 PAGE: - Convert-Ch2
					Enhanced Motion  cmdID= 30102 "
		::= { iqudc30CmdEntry 30102 }


	iqudc30ConvertCh2MotionProcessingStillProcess OBJECT-TYPE
		SYNTAX		INTEGER { disable(0), enable(1) }
		MAX-ACCESS		read-write
		STATUS			current
		DESCRIPTION
				"TYPE: - Checkbox
				 PAGE: - Convert-Ch2
					Still Process  cmdID= 30103 "
		::= { iqudc30CmdEntry 30103 }


	iqudc30ConvertCh2MotionProcessingEnhancedStill OBJECT-TYPE
		SYNTAX		INTEGER { disable(0), enable(1) }
		MAX-ACCESS		read-write
		STATUS			current
		DESCRIPTION
				"TYPE: - Checkbox
				 PAGE: - Convert-Ch2
					Enhanced Still  cmdID= 30104 "
		::= { iqudc30CmdEntry 30104 }


	iqudc30ConvertCh2MotionProcessingInputispsf OBJECT-TYPE
		SYNTAX		INTEGER { disable(0), enable(1) }
		MAX-ACCESS		read-write
		STATUS			current
		DESCRIPTION
				"TYPE: - Checkbox
				 PAGE: - Convert-Ch2
					Input is psf  cmdID= 30171 "
		::= { iqudc30CmdEntry 30171 }


	iqudc30ConvertCh2MotionProcessingEnhancedFilm OBJECT-TYPE
		SYNTAX		INTEGER { disable(0), enable(1) }
		MAX-ACCESS		read-write
		STATUS			current
		DESCRIPTION
				"TYPE: - Checkbox
				 PAGE: - Convert-Ch2
					Enhanced Film  cmdID= 30170 "
		::= { iqudc30CmdEntry 30170 }


	iqudc30ConvertCh2InputCadenceFilmCadence OBJECT-TYPE
		SYNTAX		INTEGER { disable(0), enable(1) }
		MAX-ACCESS		read-write
		STATUS			current
		DESCRIPTION
				"TYPE: - Checkbox
				 PAGE: - Convert-Ch2
					Film Cadence  cmdID= 30150 "
		::= { iqudc30CmdEntry 30150 }


	iqudc30ConvertCh2InputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch2
					59 Cadence  cmdID= 30151 
					2:3  value= 0  
					2:2 (psf)  value= 1  "
		::= { iqudc30CmdEntry 30151 }


	iqudc30MenuConvertCh223Source30152 OBJECT-TYPE
		SYNTAX		INTEGER {
							val-Automatic(0),
							val-Input-Timecode(1)
							}
		MAX-ACCESS		read-write
		STATUS			current
		DESCRIPTION
				"TYPE: - RadiobuttonList
				 PAGE: - Convert-Ch2
					2:3 Source  cmdID= 30152 
					Automatic  value= 0  
					Input Timecode  value= 1  "
		::= { iqudc30CmdEntry 30152 }


	iqudc30MenuConvertCh223StartHour30153 OBJECT-TYPE
		SYNTAX		INTEGER
		MAX-ACCESS		read-write
		STATUS			current
		DESCRIPTION
				"TYPE: - Number
				 PAGE: - Convert-Ch2
					2:3 Start Hour  cmdID= 30153  min= 0  max= 23  step= 1  format= %0.0f  div_scale= 1 
					Min = 0  Max = 23  Step = 1 "
		::= { iqudc30CmdEntry 30153 }


	iqudc30ConvertCh2OutputCadenceFilmCadence OBJECT-TYPE
		SYNTAX		INTEGER { disable(0), enable(1) }
		MAX-ACCESS		read-write
		STATUS			current
		DESCRIPTION
				"TYPE: - Checkbox
				 PAGE: - Convert-Ch2
					Film Cadence  cmdID= 30160 "
		::= { iqudc30CmdEntry 30160 }


	iqudc30ConvertCh2OutputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch2
					59 Cadence  cmdID= 30161 
					2:3  value= 0  
					2:2 (psf)  value= 1  "
		::= { iqudc30CmdEntry 30161 }


	iqudc30MenuConvertCh223Source30162 OBJECT-TYPE
		SYNTAX		INTEGER {
							val-Free-Run(0),
							val-Output-Timecode(1)
							}
		MAX-ACCESS		read-write
		STATUS			current
		DESCRIPTION
				"TYPE: - RadiobuttonList
				 PAGE: - Convert-Ch2
					2:3 Source  cmdID= 30162 
					Free Run  value= 0  
					Output Timecode  value= 1  "
		::= { iqudc30CmdEntry 30162 }


	iqudc30MenuConvertCh223StartHour30163 OBJECT-TYPE
		SYNTAX		INTEGER
		MAX-ACCESS		read-write
		STATUS			current
		DESCRIPTION
				"TYPE: - Number
				 PAGE: - Convert-Ch2
					2:3 Start Hour  cmdID= 30163  min= 0  max= 23  step= 1  format= %0.0f  div_scale= 1 
					Min = 0  Max = 23  Step = 1 "
		::= { iqudc30CmdEntry 30163 }


	iqudc30MenuConvertCh2NewDisplay OBJECT-TYPE
		SYNTAX		RollCallString
		MAX-ACCESS		read-only
		STATUS			current
		DESCRIPTION
				"TYPE: - Display
				 PAGE: - Convert-Ch2
					New Display  cmdID= 44448  format=   "
		::= { iqudc30CmdEntry 44448 }


	iqudc30MenuARCSidebarKeyerSyncMode40007 OBJECT-TYPE
		SYNTAX		INTEGER { disable(0), enable(1) }
		MAX-ACCESS		read-write
		STATUS			current
		DESCRIPTION
				"TYPE: - Checkbox
				 PAGE: - ARC & Sidebar Keyer
					Sync Mode  cmdID= 40007 "
		::= { iqudc30CmdEntry 40007 }


	iqudc30MenuARCSidebarKeyerAspectSignallingC40136 OBJECT-TYPE
		SYNTAX		INTEGER { disable(0), enable(1) }
		MAX-ACCESS		read-write
		STATUS			current
		DESCRIPTION
				"TYPE: - Checkbox
				 PAGE: - ARC & Sidebar Keyer
					Aspect Signalling C  cmdID= 40136 "
		::= { iqudc30CmdEntry 40136 }


	iqudc30MenuARCSidebarKeyerSignallingDetected64020 OBJECT-TYPE
		SYNTAX		RollCallString
		MAX-ACCESS		read-only
		STATUS			current
		DESCRIPTION
				"TYPE: - Display
				 PAGE: - ARC & Sidebar Keyer
					Signalling Detected  cmdID= 64020  format=   "
		::= { iqudc30CmdEntry 64020 }


	iqudc30ARCSidebarKeyerSidebarKeyingOuMode40017 OBJECT-TYPE
		SYNTAX		INTEGER {
							val-Off(0),
							val-Output-Crop(1),
							val-Sidebar-Key(2)
							}
		MAX-ACCESS		read-write
		STATUS			current
		DESCRIPTION
				"TYPE: - RadiobuttonList
				 PAGE: - ARC & Sidebar Keyer
					Mode  cmdID= 40017 
					Off  value= 0  
					Output Crop  value= 1  
					Sidebar Key  value= 2  "
		::= { iqudc30CmdEntry 40017 }


	iqudc30MenuARCSidebarKeyerSidebarKeySource40018 OBJECT-TYPE
		SYNTAX		INTEGER {
							val-SDI-1(0),
							val-SDI-2(1),
							val-CVBS(2),
							val-SFP-1(3),
							val-SFP-2(4),
							val-Ch-2-Output(20)
							}
		MAX-ACCESS		read-write
		STATUS			current
		DESCRIPTION
				"TYPE: - RadiobuttonList
				 PAGE: - ARC & Sidebar Keyer
					Sidebar Key Source  cmdID= 40018 
					SDI 1  value= 0  
					SDI 2  value= 1  
					CVBS  value= 2  
					SFP 1  value= 3  
					SFP 2  value= 4  
					Ch 2 Output  value= 20  "
		::= { iqudc30CmdEntry 40018 }


	iqudc30ARCSidebarKeyerOutputCropPositioTop40013 OBJECT-TYPE
		SYNTAX		INTEGER
		MAX-ACCESS		read-write
		STATUS			current
		DESCRIPTION
				"TYPE: - Number
				 PAGE: - ARC & Sidebar Keyer
					Top  cmdID= 40013  min= 0  max= 99  step= 1  format= %0.0f%%  div_scale= 1 
					Min = 0%  Max = 99%  Step = 1% "
		::= { iqudc30CmdEntry 40013 }


	iqudc30ARCSidebarKeyerOutputCropPositioBottom40014 OBJECT-TYPE
		SYNTAX		INTEGER
		MAX-ACCESS		read-write
		STATUS			current
		DESCRIPTION
				"TYPE: - Number
				 PAGE: - ARC & Sidebar Keyer
					Bottom  cmdID= 40014  min= 0  max= 99  step= 1  format= %0.0f%%  div_scale= 1 
					Min = 0%  Max = 99%  Step = 1% "
		::= { iqudc30CmdEntry 40014 }


	iqudc30ARCSidebarKeyerOutputCropPositioLeft40015 OBJECT-TYPE
		SYNTAX		INTEGER
		MAX-ACCESS		read-write
		STATUS			current
		DESCRIPTION
				"TYPE: - Number
				 PAGE: - ARC & Sidebar Keyer
					Left  cmdID= 40015  min= 0  max= 99  step= 1  format= %0.0f%%  div_scale= 1 
					Min = 0%  Max = 99%  Step = 1% "
		::= { iqudc30CmdEntry 40015 }


	iqudc30ARCSidebarKeyerOutputCropPositioRight40016 OBJECT-TYPE
		SYNTAX		INTEGER
		MAX-ACCESS		read-write
		STATUS			current
		DESCRIPTION
				"TYPE: - Number
				 PAGE: - ARC & Sidebar Keyer
					Right  cmdID= 40016  min= 0  max= 99  step= 1  format= %0.0f%%  div_scale= 1 
					Min = 0%  Max = 99%  Step = 1% "
		::= { iqudc30CmdEntry 40016 }


	iqudc30ARCSidebarKeyerPostScalingControPostScalingEnable40003 OBJECT-TYPE
		SYNTAX		INTEGER { disable(0), enable(1) }
		MAX-ACCESS		read-write
		STATUS			current
		DESCRIPTION
				"TYPE: - Checkbox
				 PAGE: - ARC & Sidebar Keyer
					Post Scaling Enable  cmdID= 40003 "
		::= { iqudc30CmdEntry 40003 }


	iqudc30ARCSidebarKeyerPostScalingControSize40008 OBJECT-TYPE
		SYNTAX		INTEGER
		MAX-ACCESS		read-write
		STATUS			current
		DESCRIPTION
				"TYPE: - Number
				 PAGE: - ARC & Sidebar Keyer
					Size  cmdID= 40008  min= 80  max= 120  step= 1  format= %0.0f%%  div_scale= 1 
					Min = 80%  Max = 120%  Step = 1% "
		::= { iqudc30CmdEntry 40008 }


	iqudc30ARCSidebarKeyerPostScalingControAspect40009 OBJECT-TYPE
		SYNTAX		INTEGER
		MAX-ACCESS		read-write
		STATUS			current
		DESCRIPTION
				"TYPE: - Number
				 PAGE: - ARC & Sidebar Keyer
					Aspect  cmdID= 40009  min= 70  max= 150  step= 1  format= %0.0f%%  div_scale= 1 
					Min = 70%  Max = 150%  Step = 1% "
		::= { iqudc30CmdEntry 40009 }


	iqudc30ARCSidebarKeyerPostScalingControPan40006 OBJECT-TYPE
		SYNTAX		INTEGER
		MAX-ACCESS		read-write
		STATUS			current
		DESCRIPTION
				"TYPE: - Number
				 PAGE: - ARC & Sidebar Keyer
					Pan  cmdID= 40006  min= -50  max= 50  step= 1  format= %0.0f%  div_scale= 1 
					Min = -50 Max = 50 Step = 1"
		::= { iqudc30CmdEntry 40006 }


	iqudc30ARCSidebarKeyerPostScalingControTilt40002 OBJECT-TYPE
		SYNTAX		INTEGER
		MAX-ACCESS		read-write
		STATUS			current
		DESCRIPTION
				"TYPE: - Number
				 PAGE: - ARC & Sidebar Keyer
					Tilt  cmdID= 40002  min= -50  max= 50  step= 1  format= %0.0f%  div_scale= 1 
					Min = -50 Max = 50 Step = 1"
		::= { iqudc30CmdEntry 40002 }


	iqudc30ARCSidebarKeyerStandardPresetsWhSDInputis70240030 OBJECT-TYPE
		SYNTAX		INTEGER { disable(0), enable(1) }
		MAX-ACCESS		read-write
		STATUS			current
		DESCRIPTION
				"TYPE: - Checkbox
				 PAGE: - ARC & Sidebar Keyer
					SD Input is 702  cmdID= 40030 "
		::= { iqudc30CmdEntry 40030 }


	iqudc30ARCSidebarKeyerStandardPresetsWhSDOutputis70240037 OBJECT-TYPE
		SYNTAX		INTEGER { disable(0), enable(1) }
		MAX-ACCESS		read-write
		STATUS			current
		DESCRIPTION
				"TYPE: - Checkbox
				 PAGE: - ARC & Sidebar Keyer
					SD Output is 702  cmdID= 40037 "
		::= { iqudc30CmdEntry 40037 }


	iqudc30StandardPresetsWhSDCrossConversionSelectStdPreset40031 OBJECT-TYPE
		SYNTAX		INTEGER {
							val-None(0),
							val-16-9-LB-4-3-H-Cr(1),
							val-16-9-LB-16-9-Ana(2),
							val-16-9-LB-14-9-LB(3),
							val-16-9-Ana-4-3-H-Cr(4),
							val-16-9-Ana-16-9-LB(5),
							val-16-9-Ana-14-9-LB(6)
							}
		MAX-ACCESS		read-write
		STATUS			current
		DESCRIPTION
				"TYPE: - RadiobuttonList
				 PAGE: - ARC & Sidebar Keyer
					Select Std Preset  cmdID= 40031 
					None  value= 0  
					16:9 LB > 4:3 H-Cr  value= 1  
					16:9 LB > 16:9 Ana  value= 2  
					16:9 LB > 14:9 LB  value= 3  
					16:9 Ana > 4:3 H-Cr  value= 4  
					16:9 Ana > 16:9 LB  value= 5  
					16:9 Ana > 14:9 LB  value= 6  "
		::= { iqudc30CmdEntry 40031 }


	iqudc30ARCSidebarKeyerUpConversionSelectStdPreset40033 OBJECT-TYPE
		SYNTAX		INTEGER {
							val-4-3-16-9-V-Cr(0),
							val-4-3-4-3-PB(1),
							val-16-9-LB-16-9(2),
							val-16-9-Ana-16-9(3),
							val-14-9-LB-14-9-PB(4)
							}
		MAX-ACCESS		read-write
		STATUS			current
		DESCRIPTION
				"TYPE: - RadiobuttonList
				 PAGE: - ARC & Sidebar Keyer
					Select Std Preset  cmdID= 40033 
					4:3 > 16:9 V-Cr  value= 0  
					4:3 > 4:3 PB  value= 1  
					16:9 LB > 16:9  value= 2  
					16:9 Ana > 16:9  value= 3  
					14:9 LB > 14:9 PB  value= 4  "
		::= { iqudc30CmdEntry 40033 }


	iqudc30MenuARCSidebarKeyer OBJECT-TYPE
		SYNTAX		INTEGER {
							val-16-9-4-3-H-Cr(0),
							val-16-9-16-9-LB(1),
							val-16-9-16-9-Ana(2),
							val-4-3-PB-4-3(3),
							val-14-9-PB-14-9-LB(4)
							}
		MAX-ACCESS		read-write
		STATUS			current
		DESCRIPTION
				"TYPE: - RadiobuttonList
				 PAGE: - ARC & Sidebar Keyer
					Select Std Preset  cmdID= 40035 
					16:9 > 4:3 H-Cr  value= 0  
					16:9 > 16:9 LB  value= 1  
					16:9 > 16:9 Ana  value= 2  
					4:3 PB > 4:3  value= 3  
					14:9 PB > 14:9 LB  value= 4  
					Select Std Preset  cmdID= 40035 "
		::= { iqudc30CmdEntry 40035 }


	iqudc30ScalingControlSDInputFormatifUseManualifUnkno40135 OBJECT-TYPE
		SYNTAX		INTEGER { disable(0), enable(1) }
		MAX-ACCESS		read-write
		STATUS			current
		DESCRIPTION
				"TYPE: - Checkbox
				 PAGE: - ARC & Sidebar Keyer
					Use Manual if Unkno  cmdID= 40135 "
		::= { iqudc30CmdEntry 40135 }


	iqudc30ScalingControlSDInputFormatif40010 OBJECT-TYPE
		SYNTAX		INTEGER {
							val-Normal(0),
							val-Anamorphic(1),
							val-Letterbox(2)
							}
		MAX-ACCESS		read-write
		STATUS			current
		DESCRIPTION
				"TYPE: - RadiobuttonList
				 PAGE: - ARC & Sidebar Keyer
					SD Input Format  cmdID= 40010 
					Normal  value= 0  
					Anamorphic  value= 1  
					Letterbox  value= 2  "
		::= { iqudc30CmdEntry 40010 }


	iqudc30ARCSidebarKeyerAspectSignallingCSDOutputFormat40011 OBJECT-TYPE
		SYNTAX		INTEGER {
							val-Normal(0),
							val-Anamorphic(1)
							}
		MAX-ACCESS		read-write
		STATUS			current
		DESCRIPTION
				"TYPE: - RadiobuttonList
				 PAGE: - ARC & Sidebar Keyer
					SD Output Format  cmdID= 40011 
					Normal  value= 0  
					Anamorphic  value= 1  "
		::= { iqudc30CmdEntry 40011 }


	iqudc30ARCSidebarKeyerAspectSignallingCConversionScaling40012 OBJECT-TYPE
		SYNTAX		INTEGER {
							val-Fit-to-Height(0),
							val-Fit-to-Width(1),
							val-14-9(2)
							}
		MAX-ACCESS		read-write
		STATUS			current
		DESCRIPTION
				"TYPE: - RadiobuttonList
				 PAGE: - ARC & Sidebar Keyer
					Conversion Scaling  cmdID= 40012 
					Fit to Height  value= 0  
					Fit to Width  value= 1  
					14:9  value= 2  "
		::= { iqudc30CmdEntry 40012 }


	iqudc30AspectSignallingCSignallingConfigSource40100 OBJECT-TYPE
		SYNTAX		INTEGER {
							val-SMPTE-2016(0),
							val-L23-ETSI(1),
							val-L23-AFD(2),
							val-VI-SMPTE(3),
							val-VI-AFD(4)
							}
		MAX-ACCESS		read-write
		STATUS			current
		DESCRIPTION
				"TYPE: - RadiobuttonList
				 PAGE: - ARC & Sidebar Keyer
					Source  cmdID= 40100 
					SMPTE 2016  value= 0  
					L23 ETSI  value= 1  
					L23 AFD  value= 2  
					VI SMPTE  value= 3  
					VI AFD  value= 4  "
		::= { iqudc30CmdEntry 40100 }


	iqudc30SignallingConfigSMPTE2016Mode40130 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40130 
					Auto  value= 0  
					Pass  value= 1  
					Force  value= 2  
					Delete  value= 3  "
		::= { iqudc30CmdEntry 40130 }


	iqudc30AspectSignallingCSignallingConfigOutputLinePAL40139 OBJECT-TYPE
		SYNTAX		INTEGER
		MAX-ACCESS		read-write
		STATUS			current
		DESCRIPTION
				"TYPE: - Number
				 PAGE: - ARC & Sidebar Keyer
					Output Line PAL  cmdID= 40139  min= 7  max= 22  step= 1  format= %0.0f  div_scale= 1 
					Min = 7  Max = 22  Step = 1 "
		::= { iqudc30CmdEntry 40139 }


	iqudc30AspectSignallingCSignallingConfigOutputLineNTSC40140 OBJECT-TYPE
		SYNTAX		INTEGER
		MAX-ACCESS		read-write
		STATUS			current
		DESCRIPTION
				"TYPE: - Number
				 PAGE: - ARC & Sidebar Keyer
					Output Line NTSC  cmdID= 40140  min= 11  max= 19  step= 1  format= %0.0f  div_scale= 1 
					Min = 11  Max = 19  Step = 1 "
		::= { iqudc30CmdEntry 40140 }


	iqudc30AspectSignallingCSignallingConfigOutputLineHD40138 OBJECT-TYPE
		SYNTAX		INTEGER
		MAX-ACCESS		read-write
		STATUS			current
		DESCRIPTION
				"TYPE: - Number
				 PAGE: - ARC & Sidebar Keyer
					Output Line HD  cmdID= 40138  min= 9  max= 20  step= 1  format= %0.0f  div_scale= 1 
					Min = 9  Max = 20  Step = 1 "
		::= { iqudc30CmdEntry 40138 }


	iqudc30SignallingConfigVIMode40120 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40120 
					Auto  value= 0  
					Pass  value= 1  
					Force  value= 2  
					Delete  value= 3  "
		::= { iqudc30CmdEntry 40120 }


	iqudc30MenuARCSidebarKeyerOutputFormat40121 OBJECT-TYPE
		SYNTAX		INTEGER {
							val-SMPTE(0),
							val-AFD(1)
							}
		MAX-ACCESS		read-write
		STATUS			current
		DESCRIPTION
				"TYPE: - RadiobuttonList
				 PAGE: - ARC & Sidebar Keyer
					Output Format  cmdID= 40121 
					SMPTE  value= 0  
					AFD  value= 1  "
		::= { iqudc30CmdEntry 40121 }


	iqudc30MenuARCSidebarKeyerVIPassData40122 OBJECT-TYPE
		SYNTAX		INTEGER { disable(0), enable(1) }
		MAX-ACCESS		read-write
		STATUS			current
		DESCRIPTION
				"TYPE: - Checkbox
				 PAGE: - ARC & Sidebar Keyer
					VI Pass Data  cmdID= 40122 "
		::= { iqudc30CmdEntry 40122 }


	iqudc30ARCSidebarKeyerL23Mode40112 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40112 
					Auto  value= 0  
					Pass  value= 1  
					Force  value= 2  
					Delete  value= 3  "
		::= { iqudc30CmdEntry 40112 }


	iqudc30MenuARCSidebarKeyerOutputFormat40113 OBJECT-TYPE
		SYNTAX		INTEGER {
							val-ETSI(0),
							val-AFD(1)
							}
		MAX-ACCESS		read-write
		STATUS			current
		DESCRIPTION
				"TYPE: - RadiobuttonList
				 PAGE: - ARC & Sidebar Keyer
					Output Format  cmdID= 40113 
					ETSI  value= 0  
					AFD  value= 1  "
		::= { iqudc30CmdEntry 40113 }


	iqudc30MenuARCSidebarKeyerInputLine40110 OBJECT-TYPE
		SYNTAX		INTEGER
		MAX-ACCESS		read-write
		STATUS			current
		DESCRIPTION
				"TYPE: - Number
				 PAGE: - ARC & Sidebar Keyer
					Input Line  cmdID= 40110  min= 10  max= 23  step= 1  format= %0.0f  div_scale= 1 
					Min = 10  Max = 23  Step = 1 "
		::= { iqudc30CmdEntry 40110 }


	iqudc30MenuARCSidebarKeyerOutputLine40111 OBJECT-TYPE
		SYNTAX		INTEGER
		MAX-ACCESS		read-write
		STATUS			current
		DESCRIPTION
				"TYPE: - Number
				 PAGE: - ARC & Sidebar Keyer
					Output Line  cmdID= 40111  min= 10  max= 23  step= 1  format= %0.0f  div_scale= 1 
					Min = 10  Max = 23  Step = 1 "
		::= { iqudc30CmdEntry 40111 }


	iqudc30MenuARCSidebarKeyerUserBitsLine40137 OBJECT-TYPE
		SYNTAX		INTEGER
		MAX-ACCESS		read-write
		STATUS			current
		DESCRIPTION
				"TYPE: - Number
				 PAGE: - ARC & Sidebar Keyer
					User Bits Line  cmdID= 40137  min= 0  max= 15  step= 1  format= %0.0f  div_scale= 1 
					Min = 0  Max = 15  Step = 1 "
		::= { iqudc30CmdEntry 40137 }


	iqudc30ARCSidebarKeyerForceOutputSignalSMPTE201640133 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-4-3-AFD-8(8),
							val-4-3-AFD-9(9),
							val-4-3-AFD-10(10),
							val-4-3-AFD-11(11),
							val-4-3-AFD-12(12),
							val-4-3-AFD-13(13),
							val-4-3-AFD-14(14),
							val-4-3-AFD-15(15),
							val-16-9-AFD-0(16),
							val-16-9-AFD-1(17),
							val-16-9-AFD-2(18),
							val-16-9-AFD-3(19),
							val-16-9-AFD-4(20),
							val-16-9-AFD-5(21),
							val-16-9-AFD-6(22),
							val-16-9-AFD-7(23),
							val-16-9-AFD-8(24),
							val-16-9-AFD-9(25),
							val-16-9-AFD-10(26),
							val-16-9-AFD-11(27),
							val-16-9-AFD-12(28),
							val-16-9-AFD-13(29),
							val-16-9-AFD-14(30),
							val-16-9-AFD-15(31)
							}
		MAX-ACCESS		read-write
		STATUS			current
		DESCRIPTION
				"TYPE: - RadiobuttonList
				 PAGE: - ARC & Sidebar Keyer
					SMPTE 2016  cmdID= 40133 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					4:3 AFD 8  value= 8  
					4:3 AFD 9  value= 9  
					4:3 AFD 10  value= 10  
					4:3 AFD 11  value= 11  
					4:3 AFD 12  value= 12  
					4:3 AFD 13  value= 13  
					4:3 AFD 14  value= 14  
					4:3 AFD 15  value= 15  
					16:9 AFD 0  value= 16  
					16:9 AFD 1  value= 17  
					16:9 AFD 2  value= 18  
					16:9 AFD 3  value= 19  
					16:9 AFD 4  value= 20  
					16:9 AFD 5  value= 21  
					16:9 AFD 6  value= 22  
					16:9 AFD 7  value= 23  
					16:9 AFD 8  value= 24  
					16:9 AFD 9  value= 25  
					16:9 AFD 10  value= 26  
					16:9 AFD 11  value= 27  
					16:9 AFD 12  value= 28  
					16:9 AFD 13  value= 29  
					16:9 AFD 14  value= 30  
					16:9 AFD 15  value= 31  "
		::= { iqudc30CmdEntry 40133 }


	iqudc30MenuARCSidebarKeyerSMPTERP18640134 OBJECT-TYPE
		SYNTAX		INTEGER {
							val-4-3(0),
							val-16-9(1)
							}
		MAX-ACCESS		read-write
		STATUS			current
		DESCRIPTION
				"TYPE: - RadiobuttonList
				 PAGE: - ARC & Sidebar Keyer
					SMPTE RP186  cmdID= 40134 
					4:3  value= 0  
					16:9  value= 1  "
		::= { iqudc30CmdEntry 40134 }


	iqudc30MenuARCSidebarKeyerAFD40131 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-16-9-AFD-0(8),
							val-16-9-AFD-1(9),
							val-16-9-AFD-2(10),
							val-16-9-AFD-3(11),
							val-16-9-AFD-4(12),
							val-16-9-AFD-5(13),
							val-16-9-AFD-6(14),
							val-16-9-AFD-7(15)
							}
		MAX-ACCESS		read-write
		STATUS			current
		DESCRIPTION
				"TYPE: - RadiobuttonList
				 PAGE: - ARC & Sidebar Keyer
					AFD  cmdID= 40131 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					16:9 AFD 0  value= 8  
					16:9 AFD 1  value= 9  
					16:9 AFD 2  value= 10  
					16:9 AFD 3  value= 11  
					16:9 AFD 4  value= 12  
					16:9 AFD 5  value= 13  
					16:9 AFD 6  value= 14  
					16:9 AFD 7  value= 15  "
		::= { iqudc30CmdEntry 40131 }


	iqudc30MenuARCSidebarKeyerETSI40132 OBJECT-TYPE
		SYNTAX		INTEGER {
							val-4-3-FF(0),
							val-14-9-Centre(1),
							val-14-9-Top(2),
							val-16-9-Centre(3),
							val-16-9-Top(4),
							val-grt-16-9-Centre(5),
							val-4-3-SP-14-9(6),
							val-16-9-FF(7)
							}
		MAX-ACCESS		read-write
		STATUS			current
		DESCRIPTION
				"TYPE: - RadiobuttonList
				 PAGE: - ARC & Sidebar Keyer
					ETSI  cmdID= 40132 
					4:3 FF  value= 0  
					14:9 Centre  value= 1  
					14:9 Top  value= 2  
					16:9 Centre  value= 3  
					16:9 Top  value= 4  
					>16:9 Centre  value= 5  
					4:3 SP 14:9  value= 6  
					16:9 FF  value= 7  "
		::= { iqudc30CmdEntry 40132 }


	iqudc30MenuARCSidebarKeyerSyncMode40107 OBJECT-TYPE
		SYNTAX		INTEGER { disable(0), enable(1) }
		MAX-ACCESS		read-write
		STATUS			current
		DESCRIPTION
				"TYPE: - Checkbox
				 PAGE: - ARC & Sidebar Keyer
					Sync Mode  cmdID= 40107 "
		::= { iqudc30CmdEntry 40107 }


	iqudc30MenuARCSidebarKeyerAspectSignallingC40236 OBJECT-TYPE
		SYNTAX		INTEGER { disable(0), enable(1) }
		MAX-ACCESS		read-write
		STATUS			current
		DESCRIPTION
				"TYPE: - Checkbox
				 PAGE: - ARC & Sidebar Keyer
					Aspect Signalling C  cmdID= 40236 "
		::= { iqudc30CmdEntry 40236 }


	iqudc30MenuARCSidebarKeyerSignallingDetected64220 OBJECT-TYPE
		SYNTAX		RollCallString
		MAX-ACCESS		read-only
		STATUS			current
		DESCRIPTION
				"TYPE: - Display
				 PAGE: - ARC & Sidebar Keyer
					Signalling Detected  cmdID= 64220  format=   "
		::= { iqudc30CmdEntry 64220 }


	iqudc30ARCSidebarKeyerSidebarKeyingOuMode40023 OBJECT-TYPE
		SYNTAX		INTEGER {
							val-Off(0),
							val-Output-Crop(1),
							val-Sidebar-Key(2)
							}
		MAX-ACCESS		read-write
		STATUS			current
		DESCRIPTION
				"TYPE: - RadiobuttonList
				 PAGE: - ARC & Sidebar Keyer
					Mode  cmdID= 40023 
					Off  value= 0  
					Output Crop  value= 1  
					Sidebar Key  value= 2  "
		::= { iqudc30CmdEntry 40023 }


	iqudc30MenuARCSidebarKeyerSidebarKeySource40024 OBJECT-TYPE
		SYNTAX		INTEGER {
							val-SDI-1(0),
							val-SDI-2(1),
							val-CVBS(2),
							val-SFP-1(3),
							val-SFP-2(4),
							val-Ch-1-Output(20)
							}
		MAX-ACCESS		read-write
		STATUS			current
		DESCRIPTION
				"TYPE: - RadiobuttonList
				 PAGE: - ARC & Sidebar Keyer
					Sidebar Key Source  cmdID= 40024 
					SDI 1  value= 0  
					SDI 2  value= 1  
					CVBS  value= 2  
					SFP 1  value= 3  
					SFP 2  value= 4  
					Ch 1 Output  value= 20  "
		::= { iqudc30CmdEntry 40024 }


	iqudc30ARCSidebarKeyerOutputCropPositioTop40019 OBJECT-TYPE
		SYNTAX		INTEGER
		MAX-ACCESS		read-write
		STATUS			current
		DESCRIPTION
				"TYPE: - Number
				 PAGE: - ARC & Sidebar Keyer
					Top  cmdID= 40019  min= 0  max= 99  step= 1  format= %0.0f%%  div_scale= 1 
					Min = 0%  Max = 99%  Step = 1% "
		::= { iqudc30CmdEntry 40019 }


	iqudc30ARCSidebarKeyerOutputCropPositioBottom40020 OBJECT-TYPE
		SYNTAX		INTEGER
		MAX-ACCESS		read-write
		STATUS			current
		DESCRIPTION
				"TYPE: - Number
				 PAGE: - ARC & Sidebar Keyer
					Bottom  cmdID= 40020  min= 0  max= 99  step= 1  format= %0.0f%%  div_scale= 1 
					Min = 0%  Max = 99%  Step = 1% "
		::= { iqudc30CmdEntry 40020 }


	iqudc30ARCSidebarKeyerOutputCropPositioLeft40021 OBJECT-TYPE
		SYNTAX		INTEGER
		MAX-ACCESS		read-write
		STATUS			current
		DESCRIPTION
				"TYPE: - Number
				 PAGE: - ARC & Sidebar Keyer
					Left  cmdID= 40021  min= 0  max= 99  step= 1  format= %0.0f%%  div_scale= 1 
					Min = 0%  Max = 99%  Step = 1% "
		::= { iqudc30CmdEntry 40021 }


	iqudc30ARCSidebarKeyerOutputCropPositioRight40022 OBJECT-TYPE
		SYNTAX		INTEGER
		MAX-ACCESS		read-write
		STATUS			current
		DESCRIPTION
				"TYPE: - Number
				 PAGE: - ARC & Sidebar Keyer
					Right  cmdID= 40022  min= 0  max= 99  step= 1  format= %0.0f%%  div_scale= 1 
					Min = 0%  Max = 99%  Step = 1% "
		::= { iqudc30CmdEntry 40022 }


	iqudc30ARCSidebarKeyerPostScalingControPostScalingEnable40103 OBJECT-TYPE
		SYNTAX		INTEGER { disable(0), enable(1) }
		MAX-ACCESS		read-write
		STATUS			current
		DESCRIPTION
				"TYPE: - Checkbox
				 PAGE: - ARC & Sidebar Keyer
					Post Scaling Enable  cmdID= 40103 "
		::= { iqudc30CmdEntry 40103 }


	iqudc30ARCSidebarKeyerPostScalingControSize40108 OBJECT-TYPE
		SYNTAX		INTEGER
		MAX-ACCESS		read-write
		STATUS			current
		DESCRIPTION
				"TYPE: - Number
				 PAGE: - ARC & Sidebar Keyer
					Size  cmdID= 40108  min= 80  max= 120  step= 1  format= %0.0f%%  div_scale= 1 
					Min = 80%  Max = 120%  Step = 1% "
		::= { iqudc30CmdEntry 40108 }


	iqudc30ARCSidebarKeyerPostScalingControAspect40109 OBJECT-TYPE
		SYNTAX		INTEGER
		MAX-ACCESS		read-write
		STATUS			current
		DESCRIPTION
				"TYPE: - Number
				 PAGE: - ARC & Sidebar Keyer
					Aspect  cmdID= 40109  min= 70  max= 150  step= 1  format= %0.0f%%  div_scale= 1 
					Min = 70%  Max = 150%  Step = 1% "
		::= { iqudc30CmdEntry 40109 }


	iqudc30ARCSidebarKeyerPostScalingControPan40106 OBJECT-TYPE
		SYNTAX		INTEGER
		MAX-ACCESS		read-write
		STATUS			current
		DESCRIPTION
				"TYPE: - Number
				 PAGE: - ARC & Sidebar Keyer
					Pan  cmdID= 40106  min= -50  max= 50  step= 1  format= %0.0f%  div_scale= 1 
					Min = -50 Max = 50 Step = 1"
		::= { iqudc30CmdEntry 40106 }


	iqudc30ARCSidebarKeyerPostScalingControTilt40102 OBJECT-TYPE
		SYNTAX		INTEGER
		MAX-ACCESS		read-write
		STATUS			current
		DESCRIPTION
				"TYPE: - Number
				 PAGE: - ARC & Sidebar Keyer
					Tilt  cmdID= 40102  min= -50  max= 50  step= 1  format= %0.0f%  div_scale= 1 
					Min = -50 Max = 50 Step = 1"
		::= { iqudc30CmdEntry 40102 }


	iqudc30ARCSidebarKeyerStandardPresetsWhSDInputis70240040 OBJECT-TYPE
		SYNTAX		INTEGER { disable(0), enable(1) }
		MAX-ACCESS		read-write
		STATUS			current
		DESCRIPTION
				"TYPE: - Checkbox
				 PAGE: - ARC & Sidebar Keyer
					SD Input is 702  cmdID= 40040 "
		::= { iqudc30CmdEntry 40040 }


	iqudc30ARCSidebarKeyerStandardPresetsWhSDOutputis70240047 OBJECT-TYPE
		SYNTAX		INTEGER { disable(0), enable(1) }
		MAX-ACCESS		read-write
		STATUS			current
		DESCRIPTION
				"TYPE: - Checkbox
				 PAGE: - ARC & Sidebar Keyer
					SD Output is 702  cmdID= 40047 "
		::= { iqudc30CmdEntry 40047 }


	iqudc30StandardPresetsWhSDCrossConversionSelectStdPreset40041 OBJECT-TYPE
		SYNTAX		INTEGER {
							val-None(0),
							val-16-9-LB-4-3-H-Cr(1),
							val-16-9-LB-16-9-Ana(2),
							val-16-9-LB-14-9-LB(3),
							val-16-9-Ana-4-3-H-Cr(4),
							val-16-9-Ana-16-9-LB(5),
							val-16-9-Ana-14-9-LB(6)
							}
		MAX-ACCESS		read-write
		STATUS			current
		DESCRIPTION
				"TYPE: - RadiobuttonList
				 PAGE: - ARC & Sidebar Keyer
					Select Std Preset  cmdID= 40041 
					None  value= 0  
					16:9 LB > 4:3 H-Cr  value= 1  
					16:9 LB > 16:9 Ana  value= 2  
					16:9 LB > 14:9 LB  value= 3  
					16:9 Ana > 4:3 H-Cr  value= 4  
					16:9 Ana > 16:9 LB  value= 5  
					16:9 Ana > 14:9 LB  value= 6  "
		::= { iqudc30CmdEntry 40041 }


	iqudc30ARCSidebarKeyerUpConversionSelectStdPreset40043 OBJECT-TYPE
		SYNTAX		INTEGER {
							val-4-3-16-9-V-Cr(0),
							val-4-3-4-3-PB(1),
							val-16-9-LB-16-9(2),
							val-16-9-Ana-16-9(3),
							val-14-9-LB-14-9-PB(4)
							}
		MAX-ACCESS		read-write
		STATUS			current
		DESCRIPTION
				"TYPE: - RadiobuttonList
				 PAGE: - ARC & Sidebar Keyer
					Select Std Preset  cmdID= 40043 
					4:3 > 16:9 V-Cr  value= 0  
					4:3 > 4:3 PB  value= 1  
					16:9 LB > 16:9  value= 2  
					16:9 Ana > 16:9  value= 3  
					14:9 LB > 14:9 PB  value= 4  "
		::= { iqudc30CmdEntry 40043 }


	iqudc30ARCSidebarKeyerDownConversionSelectStdPreset OBJECT-TYPE
		SYNTAX		INTEGER {
							val-16-9-4-3-H-Cr(0),
							val-16-9-16-9-LB(1),
							val-16-9-16-9-Ana(2),
							val-4-3-PB-4-3(3),
							val-14-9-PB-14-9-LB(4)
							}
		MAX-ACCESS		read-write
		STATUS			current
		DESCRIPTION
				"TYPE: - RadiobuttonList
				 PAGE: - ARC & Sidebar Keyer
					Select Std Preset  cmdID= 40045 
					16:9 > 4:3 H-Cr  value= 0  
					16:9 > 16:9 LB  value= 1  
					16:9 > 16:9 Ana  value= 2  
					4:3 PB > 4:3  value= 3  
					14:9 PB > 14:9 LB  value= 4  "
		::= { iqudc30CmdEntry 40045 }


	iqudc30ScalingControlSDInputFormatifUseManualifUnkno40235 OBJECT-TYPE
		SYNTAX		INTEGER { disable(0), enable(1) }
		MAX-ACCESS		read-write
		STATUS			current
		DESCRIPTION
				"TYPE: - Checkbox
				 PAGE: - ARC & Sidebar Keyer
					Use Manual if Unkno  cmdID= 40235 "
		::= { iqudc30CmdEntry 40235 }


	iqudc30ScalingControlSDInputFormatif40114 OBJECT-TYPE
		SYNTAX		INTEGER {
							val-Normal(0),
							val-Anamorphic(1),
							val-Letterbox(2)
							}
		MAX-ACCESS		read-write
		STATUS			current
		DESCRIPTION
				"TYPE: - RadiobuttonList
				 PAGE: - ARC & Sidebar Keyer
					SD Input Format  cmdID= 40114 
					Normal  value= 0  
					Anamorphic  value= 1  
					Letterbox  value= 2  "
		::= { iqudc30CmdEntry 40114 }


	iqudc30ARCSidebarKeyerAspectSignallingCSDOutputFormat40115 OBJECT-TYPE
		SYNTAX		INTEGER {
							val-Normal(0),
							val-Anamorphic(1)
							}
		MAX-ACCESS		read-write
		STATUS			current
		DESCRIPTION
				"TYPE: - RadiobuttonList
				 PAGE: - ARC & Sidebar Keyer
					SD Output Format  cmdID= 40115 
					Normal  value= 0  
					Anamorphic  value= 1  "
		::= { iqudc30CmdEntry 40115 }


	iqudc30ARCSidebarKeyerAspectSignallingCConversionScaling40116 OBJECT-TYPE
		SYNTAX		INTEGER {
							val-Fit-to-Height(0),
							val-Fit-to-Width(1),
							val-14-9(2)
							}
		MAX-ACCESS		read-write
		STATUS			current
		DESCRIPTION
				"TYPE: - RadiobuttonList
				 PAGE: - ARC & Sidebar Keyer
					Conversion Scaling  cmdID= 40116 
					Fit to Height  value= 0  
					Fit to Width  value= 1  
					14:9  value= 2  "
		::= { iqudc30CmdEntry 40116 }


	iqudc30AspectSignallingCSignallingConfigSource40202 OBJECT-TYPE
		SYNTAX		INTEGER {
							val-SMPTE-2016(0),
							val-L23-ETSI(1),
							val-L23-AFD(2),
							val-VI-SMPTE(3),
							val-VI-AFD(4)
							}
		MAX-ACCESS		read-write
		STATUS			current
		DESCRIPTION
				"TYPE: - RadiobuttonList
				 PAGE: - ARC & Sidebar Keyer
					Source  cmdID= 40202 
					SMPTE 2016  value= 0  
					L23 ETSI  value= 1  
					L23 AFD  value= 2  
					VI SMPTE  value= 3  
					VI AFD  value= 4  "
		::= { iqudc30CmdEntry 40202 }


	iqudc30SignallingConfigSMPTE2016Mode40230 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40230 
					Auto  value= 0  
					Pass  value= 1  
					Force  value= 2  
					Delete  value= 3  "
		::= { iqudc30CmdEntry 40230 }


	iqudc30AspectSignallingCSignallingConfigOutputLinePAL40239 OBJECT-TYPE
		SYNTAX		INTEGER
		MAX-ACCESS		read-write
		STATUS			current
		DESCRIPTION
				"TYPE: - Number
				 PAGE: - ARC & Sidebar Keyer
					Output Line PAL  cmdID= 40239  min= 7  max= 22  step= 1  format= %0.0f  div_scale= 1 
					Min = 7  Max = 22  Step = 1 "
		::= { iqudc30CmdEntry 40239 }


	iqudc30AspectSignallingCSignallingConfigOutputLineNTSC40240 OBJECT-TYPE
		SYNTAX		INTEGER
		MAX-ACCESS		read-write
		STATUS			current
		DESCRIPTION
				"TYPE: - Number
				 PAGE: - ARC & Sidebar Keyer
					Output Line NTSC  cmdID= 40240  min= 11  max= 19  step= 1  format= %0.0f  div_scale= 1 
					Min = 11  Max = 19  Step = 1 "
		::= { iqudc30CmdEntry 40240 }


	iqudc30AspectSignallingCSignallingConfigOutputLineHD40238 OBJECT-TYPE
		SYNTAX		INTEGER
		MAX-ACCESS		read-write
		STATUS			current
		DESCRIPTION
				"TYPE: - Number
				 PAGE: - ARC & Sidebar Keyer
					Output Line HD  cmdID= 40238  min= 9  max= 20  step= 1  format= %0.0f  div_scale= 1 
					Min = 9  Max = 20  Step = 1 "
		::= { iqudc30CmdEntry 40238 }


	iqudc30SignallingConfigVIMode40220 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40220 
					Auto  value= 0  
					Pass  value= 1  
					Force  value= 2  
					Delete  value= 3  "
		::= { iqudc30CmdEntry 40220 }


	iqudc30MenuARCSidebarKeyerOutputFormat40221 OBJECT-TYPE
		SYNTAX		INTEGER {
							val-SMPTE(0),
							val-AFD(1)
							}
		MAX-ACCESS		read-write
		STATUS			current
		DESCRIPTION
				"TYPE: - RadiobuttonList
				 PAGE: - ARC & Sidebar Keyer
					Output Format  cmdID= 40221 
					SMPTE  value= 0  
					AFD  value= 1  "
		::= { iqudc30CmdEntry 40221 }


	iqudc30MenuARCSidebarKeyerVIPassData40222 OBJECT-TYPE
		SYNTAX		INTEGER { disable(0), enable(1) }
		MAX-ACCESS		read-write
		STATUS			current
		DESCRIPTION
				"TYPE: - Checkbox
				 PAGE: - ARC & Sidebar Keyer
					VI Pass Data  cmdID= 40222 "
		::= { iqudc30CmdEntry 40222 }


	iqudc30ARCSidebarKeyerL23Mode40212 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40212 
					Auto  value= 0  
					Pass  value= 1  
					Force  value= 2  
					Delete  value= 3  "
		::= { iqudc30CmdEntry 40212 }


	iqudc30MenuARCSidebarKeyerOutputFormat40213 OBJECT-TYPE
		SYNTAX		INTEGER {
							val-ETSI(0),
							val-AFD(1)
							}
		MAX-ACCESS		read-write
		STATUS			current
		DESCRIPTION
				"TYPE: - RadiobuttonList
				 PAGE: - ARC & Sidebar Keyer
					Output Format  cmdID= 40213 
					ETSI  value= 0  
					AFD  value= 1  "
		::= { iqudc30CmdEntry 40213 }


	iqudc30MenuARCSidebarKeyerInputLine40210 OBJECT-TYPE
		SYNTAX		INTEGER
		MAX-ACCESS		read-write
		STATUS			current
		DESCRIPTION
				"TYPE: - Number
				 PAGE: - ARC & Sidebar Keyer
					Input Line  cmdID= 40210  min= 10  max= 23  step= 1  format= %0.0f  div_scale= 1 
					Min = 10  Max = 23  Step = 1 "
		::= { iqudc30CmdEntry 40210 }


	iqudc30MenuARCSidebarKeyerOutputLine40211 OBJECT-TYPE
		SYNTAX		INTEGER
		MAX-ACCESS		read-write
		STATUS			current
		DESCRIPTION
				"TYPE: - Number
				 PAGE: - ARC & Sidebar Keyer
					Output Line  cmdID= 40211  min= 10  max= 23  step= 1  format= %0.0f  div_scale= 1 
					Min = 10  Max = 23  Step = 1 "
		::= { iqudc30CmdEntry 40211 }


	iqudc30MenuARCSidebarKeyerUserBitsLine40237 OBJECT-TYPE
		SYNTAX		INTEGER
		MAX-ACCESS		read-write
		STATUS			current
		DESCRIPTION
				"TYPE: - Number
				 PAGE: - ARC & Sidebar Keyer
					User Bits Line  cmdID= 40237  min= 0  max= 15  step= 1  format= %0.0f  div_scale= 1 
					Min = 0  Max = 15  Step = 1 "
		::= { iqudc30CmdEntry 40237 }


	iqudc30ARCSidebarKeyerForceOutputSignalSMPTE201640233 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-4-3-AFD-8(8),
							val-4-3-AFD-9(9),
							val-4-3-AFD-10(10),
							val-4-3-AFD-11(11),
							val-4-3-AFD-12(12),
							val-4-3-AFD-13(13),
							val-4-3-AFD-14(14),
							val-4-3-AFD-15(15),
							val-16-9-AFD-0(16),
							val-16-9-AFD-1(17),
							val-16-9-AFD-2(18),
							val-16-9-AFD-3(19),
							val-16-9-AFD-4(20),
							val-16-9-AFD-5(21),
							val-16-9-AFD-6(22),
							val-16-9-AFD-7(23),
							val-16-9-AFD-8(24),
							val-16-9-AFD-9(25),
							val-16-9-AFD-10(26),
							val-16-9-AFD-11(27),
							val-16-9-AFD-12(28),
							val-16-9-AFD-13(29),
							val-16-9-AFD-14(30),
							val-16-9-AFD-15(31)
							}
		MAX-ACCESS		read-write
		STATUS			current
		DESCRIPTION
				"TYPE: - RadiobuttonList
				 PAGE: - ARC & Sidebar Keyer
					SMPTE 2016  cmdID= 40233 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					4:3 AFD 8  value= 8  
					4:3 AFD 9  value= 9  
					4:3 AFD 10  value= 10  
					4:3 AFD 11  value= 11  
					4:3 AFD 12  value= 12  
					4:3 AFD 13  value= 13  
					4:3 AFD 14  value= 14  
					4:3 AFD 15  value= 15  
					16:9 AFD 0  value= 16  
					16:9 AFD 1  value= 17  
					16:9 AFD 2  value= 18  
					16:9 AFD 3  value= 19  
					16:9 AFD 4  value= 20  
					16:9 AFD 5  value= 21  
					16:9 AFD 6  value= 22  
					16:9 AFD 7  value= 23  
					16:9 AFD 8  value= 24  
					16:9 AFD 9  value= 25  
					16:9 AFD 10  value= 26  
					16:9 AFD 11  value= 27  
					16:9 AFD 12  value= 28  
					16:9 AFD 13  value= 29  
					16:9 AFD 14  value= 30  
					16:9 AFD 15  value= 31  "
		::= { iqudc30CmdEntry 40233 }


	iqudc30MenuARCSidebarKeyerSMPTERP18640234 OBJECT-TYPE
		SYNTAX		INTEGER {
							val-4-3(0),
							val-16-9(1)
							}
		MAX-ACCESS		read-write
		STATUS			current
		DESCRIPTION
				"TYPE: - RadiobuttonList
				 PAGE: - ARC & Sidebar Keyer
					SMPTE RP186  cmdID= 40234 
					4:3  value= 0  
					16:9  value= 1  "
		::= { iqudc30CmdEntry 40234 }


	iqudc30MenuARCSidebarKeyerAFD40231 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-16-9-AFD-0(8),
							val-16-9-AFD-1(9),
							val-16-9-AFD-2(10),
							val-16-9-AFD-3(11),
							val-16-9-AFD-4(12),
							val-16-9-AFD-5(13),
							val-16-9-AFD-6(14),
							val-16-9-AFD-7(15)
							}
		MAX-ACCESS		read-write
		STATUS			current
		DESCRIPTION
				"TYPE: - RadiobuttonList
				 PAGE: - ARC & Sidebar Keyer
					AFD  cmdID= 40231 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					16:9 AFD 0  value= 8  
					16:9 AFD 1  value= 9  
					16:9 AFD 2  value= 10  
					16:9 AFD 3  value= 11  
					16:9 AFD 4  value= 12  
					16:9 AFD 5  value= 13  
					16:9 AFD 6  value= 14  
					16:9 AFD 7  value= 15  "
		::= { iqudc30CmdEntry 40231 }


	iqudc30MenuARCSidebarKeyerETSI40232 OBJECT-TYPE
		SYNTAX		INTEGER {
							val-4-3-FF(0),
							val-14-9-Centre(1),
							val-14-9-Top(2),
							val-16-9-Centre(3),
							val-16-9-Top(4),
							val-grt-16-9-Centre(5),
							val-4-3-SP-14-9(6),
							val-16-9-FF(7)
							}
		MAX-ACCESS		read-write
		STATUS			current
		DESCRIPTION
				"TYPE: - RadiobuttonList
				 PAGE: - ARC & Sidebar Keyer
					ETSI  cmdID= 40232 
					4:3 FF  value= 0  
					14:9 Centre  value= 1  
					14:9 Top  value= 2  
					16:9 Centre  value= 3  
					16:9 Top  value= 4  
					>16:9 Centre  value= 5  
					4:3 SP 14:9  value= 6  
					16:9 FF  value= 7  "
		::= { iqudc30CmdEntry 40232 }


	iqudc30MenuARCSidebarKeyerNewDisplay OBJECT-TYPE
		SYNTAX		RollCallString
		MAX-ACCESS		read-only
		STATUS			current
		DESCRIPTION
				"TYPE: - Display
				 PAGE: - ARC & Sidebar Keyer
					New Display  cmdID= 44449  format=   "
		::= { iqudc30CmdEntry 44449 }


	iqudc30AudioRoutingCh1InputPairsStatusEmbedded1 OBJECT-TYPE
		SYNTAX		RollCallString
		MAX-ACCESS		read-only
		STATUS			current
		DESCRIPTION
				"TYPE: - Display
				 PAGE: - Audio Routing-Ch1
					Embedded 1  cmdID= 63112  format=   "
		::= { iqudc30CmdEntry 63112 }


	iqudc30AudioRoutingCh1InputPairsStatusEmbedded2 OBJECT-TYPE
		SYNTAX		RollCallString
		MAX-ACCESS		read-only
		STATUS			current
		DESCRIPTION
				"TYPE: - Display
				 PAGE: - Audio Routing-Ch1
					Embedded 2  cmdID= 63113  format=   "
		::= { iqudc30CmdEntry 63113 }


	iqudc30AudioRoutingCh1InputPairsStatusEmbedded3 OBJECT-TYPE
		SYNTAX		RollCallString
		MAX-ACCESS		read-only
		STATUS			current
		DESCRIPTION
				"TYPE: - Display
				 PAGE: - Audio Routing-Ch1
					Embedded 3  cmdID= 63102  format=   "
		::= { iqudc30CmdEntry 63102 }


	iqudc30AudioRoutingCh1InputPairsStatusEmbedded4 OBJECT-TYPE
		SYNTAX		RollCallString
		MAX-ACCESS		read-only
		STATUS			current
		DESCRIPTION
				"TYPE: - Display
				 PAGE: - Audio Routing-Ch1
					Embedded 4  cmdID= 63103  format=   "
		::= { iqudc30CmdEntry 63103 }


	iqudc30AudioRoutingCh1InputPairsStatusEmbedded5 OBJECT-TYPE
		SYNTAX		RollCallString
		MAX-ACCESS		read-only
		STATUS			current
		DESCRIPTION
				"TYPE: - Display
				 PAGE: - Audio Routing-Ch1
					Embedded 5  cmdID= 63114  format=   "
		::= { iqudc30CmdEntry 63114 }


	iqudc30AudioRoutingCh1InputPairsStatusEmbedded6 OBJECT-TYPE
		SYNTAX		RollCallString
		MAX-ACCESS		read-only
		STATUS			current
		DESCRIPTION
				"TYPE: - Display
				 PAGE: - Audio Routing-Ch1
					Embedded 6  cmdID= 63105  format=   "
		::= { iqudc30CmdEntry 63105 }


	iqudc30AudioRoutingCh1InputPairsStatusEmbedded7 OBJECT-TYPE
		SYNTAX		RollCallString
		MAX-ACCESS		read-only
		STATUS			current
		DESCRIPTION
				"TYPE: - Display
				 PAGE: - Audio Routing-Ch1
					Embedded 7  cmdID= 63106  format=   "
		::= { iqudc30CmdEntry 63106 }


	iqudc30AudioRoutingCh1InputPairsStatusEmbedded8 OBJECT-TYPE
		SYNTAX		RollCallString
		MAX-ACCESS		read-only
		STATUS			current
		DESCRIPTION
				"TYPE: - Display
				 PAGE: - Audio Routing-Ch1
					Embedded 8  cmdID= 63107  format=   "
		::= { iqudc30CmdEntry 63107 }


	iqudc30AudioRoutingCh1InputPairsStatusAES1 OBJECT-TYPE
		SYNTAX		RollCallString
		MAX-ACCESS		read-only
		STATUS			current
		DESCRIPTION
				"TYPE: - Display
				 PAGE: - Audio Routing-Ch1
					AES 1  cmdID= 63120  format=   "
		::= { iqudc30CmdEntry 63120 }


	iqudc30AudioRoutingCh1InputPairsStatusAES2 OBJECT-TYPE
		SYNTAX		RollCallString
		MAX-ACCESS		read-only
		STATUS			current
		DESCRIPTION
				"TYPE: - Display
				 PAGE: - Audio Routing-Ch1
					AES 2  cmdID= 63121  format=   "
		::= { iqudc30CmdEntry 63121 }


	iqudc30AudioRoutingCh1InputPairsStatusAES3 OBJECT-TYPE
		SYNTAX		RollCallString
		MAX-ACCESS		read-only
		STATUS			current
		DESCRIPTION
				"TYPE: - Display
				 PAGE: - Audio Routing-Ch1
					AES 3  cmdID= 63123  format=   "
		::= { iqudc30CmdEntry 63123 }


	iqudc30AudioRoutingCh1InputPairsStatusAES4 OBJECT-TYPE
		SYNTAX		RollCallString
		MAX-ACCESS		read-only
		STATUS			current
		DESCRIPTION
				"TYPE: - Display
				 PAGE: - Audio Routing-Ch1
					AES 4  cmdID= 63124  format=   "
		::= { iqudc30CmdEntry 63124 }


	iqudc30AudioRoutingCh1InputPairsStatusAES5 OBJECT-TYPE
		SYNTAX		RollCallString
		MAX-ACCESS		read-only
		STATUS			current
		DESCRIPTION
				"TYPE: - Display
				 PAGE: - Audio Routing-Ch1
					AES 5  cmdID= 63125  format=   "
		::= { iqudc30CmdEntry 63125 }


	iqudc30AudioRoutingCh1InputPairsStatusAES6 OBJECT-TYPE
		SYNTAX		RollCallString
		MAX-ACCESS		read-only
		STATUS			current
		DESCRIPTION
				"TYPE: - Display
				 PAGE: - Audio Routing-Ch1
					AES 6  cmdID= 63126  format=   "
		::= { iqudc30CmdEntry 63126 }


	iqudc30AudioRoutingCh1InputPairsStatusAES7 OBJECT-TYPE
		SYNTAX		RollCallString
		MAX-ACCESS		read-only
		STATUS			current
		DESCRIPTION
				"TYPE: - Display
				 PAGE: - Audio Routing-Ch1
					AES 7  cmdID= 63127  format=   "
		::= { iqudc30CmdEntry 63127 }


	iqudc30AudioRoutingCh1InputPairsStatusAES8 OBJECT-TYPE
		SYNTAX		RollCallString
		MAX-ACCESS		read-only
		STATUS			current
		DESCRIPTION
				"TYPE: - Display
				 PAGE: - Audio Routing-Ch1
					AES 8  cmdID= 63128  format=   "
		::= { iqudc30CmdEntry 63128 }


	iqudc30AudioRoutingCh1InputPairsStatusAnalog1 OBJECT-TYPE
		SYNTAX		RollCallString
		MAX-ACCESS		read-only
		STATUS			current
		DESCRIPTION
				"TYPE: - Display
				 PAGE: - Audio Routing-Ch1
					Analog 1  cmdID= 63129  format=   "
		::= { iqudc30CmdEntry 63129 }


	iqudc30AudioRoutingCh1InputPairsStatusAnalog2 OBJECT-TYPE
		SYNTAX		RollCallString
		MAX-ACCESS		read-only
		STATUS			current
		DESCRIPTION
				"TYPE: - Display
				 PAGE: - Audio Routing-Ch1
					Analog 2  cmdID= 63130  format=   "
		::= { iqudc30CmdEntry 63130 }


	iqudc30AudioRoutingCh1InputPairsStatusDolbyDecoder1 OBJECT-TYPE
		SYNTAX		RollCallString
		MAX-ACCESS		read-only
		STATUS			current
		DESCRIPTION
				"TYPE: - Display
				 PAGE: - Audio Routing-Ch1
					Dolby Decoder 1  cmdID= 63131  format=   "
		::= { iqudc30CmdEntry 63131 }


	iqudc30AudioRoutingCh1InputPairsStatusDolbyDecoder2 OBJECT-TYPE
		SYNTAX		RollCallString
		MAX-ACCESS		read-only
		STATUS			current
		DESCRIPTION
				"TYPE: - Display
				 PAGE: - Audio Routing-Ch1
					Dolby Decoder 2  cmdID= 63132  format=   "
		::= { iqudc30CmdEntry 63132 }


	iqudc30AudioRoutingCh1InputPairsStatusDolbyDecoder3 OBJECT-TYPE
		SYNTAX		RollCallString
		MAX-ACCESS		read-only
		STATUS			current
		DESCRIPTION
				"TYPE: - Display
				 PAGE: - Audio Routing-Ch1
					Dolby Decoder 3  cmdID= 63133  format=   "
		::= { iqudc30CmdEntry 63133 }


	iqudc30AudioRoutingCh1InputPairsStatusDolbyDecoder4 OBJECT-TYPE
		SYNTAX		RollCallString
		MAX-ACCESS		read-only
		STATUS			current
		DESCRIPTION
				"TYPE: - Display
				 PAGE: - Audio Routing-Ch1
					Dolby Decoder 4  cmdID= 63134  format=   "
		::= { iqudc30CmdEntry 63134 }


	iqudc30AudioRoutingCh1InputPairsStatusDolbyDownmix OBJECT-TYPE
		SYNTAX		RollCallString
		MAX-ACCESS		read-only
		STATUS			current
		DESCRIPTION
				"TYPE: - Display
				 PAGE: - Audio Routing-Ch1
					Dolby Downmix  cmdID= 63135  format=   "
		::= { iqudc30CmdEntry 63135 }


	iqudc30AudioRoutingCh1InputPairsStatusDolbyEncoder OBJECT-TYPE
		SYNTAX		RollCallString
		MAX-ACCESS		read-only
		STATUS			current
		DESCRIPTION
				"TYPE: - Display
				 PAGE: - Audio Routing-Ch1
					Dolby Encoder  cmdID= 63136  format=   "
		::= { iqudc30CmdEntry 63136 }


	iqudc30ProcessPairs18Pair1InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 1
					Input Pairs Source  cmdID= 50005 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50005 }


	iqudc30ProcessPairs18Pair2InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 2
					Input Pairs Source  cmdID= 50007 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50007 }


	iqudc30ProcessPairs18Pair3InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 3
					Input Pairs Source  cmdID= 50004 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50004 }


	iqudc30ProcessPairs18Pair4InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 4
					Input Pairs Source  cmdID= 50006 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50006 }


	iqudc30ProcessPairs18Pair5InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 5
					Input Pairs Source  cmdID= 50008 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50008 }


	iqudc30ProcessPairs18Pair6InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 6
					Input Pairs Source  cmdID= 50010 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50010 }


	iqudc30ProcessPairs18Pair7InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 7
					Input Pairs Source  cmdID= 50012 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50012 }


	iqudc30ProcessPairs18Pair8InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 8
					Input Pairs Source  cmdID= 50017 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50017 }


	iqudc30AudioRoutingCh1ProcessPairs18SPair1 OBJECT-TYPE
		SYNTAX		RollCallString
		MAX-ACCESS		read-only
		STATUS			current
		DESCRIPTION
				"TYPE: - Display
				 PAGE: - Audio Routing-Ch1- Process Pairs 1-8 S
					Pair 1  cmdID= 63137  format=   "
		::= { iqudc30CmdEntry 63137 }


	iqudc30AudioRoutingCh1ProcessPairs18SPair2 OBJECT-TYPE
		SYNTAX		RollCallString
		MAX-ACCESS		read-only
		STATUS			current
		DESCRIPTION
				"TYPE: - Display
				 PAGE: - Audio Routing-Ch1- Process Pairs 1-8 S
					Pair 2  cmdID= 63138  format=   "
		::= { iqudc30CmdEntry 63138 }


	iqudc30AudioRoutingCh1ProcessPairs18SPair3 OBJECT-TYPE
		SYNTAX		RollCallString
		MAX-ACCESS		read-only
		STATUS			current
		DESCRIPTION
				"TYPE: - Display
				 PAGE: - Audio Routing-Ch1- Process Pairs 1-8 S
					Pair 3  cmdID= 63139  format=   "
		::= { iqudc30CmdEntry 63139 }


	iqudc30AudioRoutingCh1ProcessPairs18SPair4 OBJECT-TYPE
		SYNTAX		RollCallString
		MAX-ACCESS		read-only
		STATUS			current
		DESCRIPTION
				"TYPE: - Display
				 PAGE: - Audio Routing-Ch1- Process Pairs 1-8 S
					Pair 4  cmdID= 63140  format=   "
		::= { iqudc30CmdEntry 63140 }


	iqudc30AudioRoutingCh1ProcessPairs18SPair5 OBJECT-TYPE
		SYNTAX		RollCallString
		MAX-ACCESS		read-only
		STATUS			current
		DESCRIPTION
				"TYPE: - Display
				 PAGE: - Audio Routing-Ch1- Process Pairs 1-8 S
					Pair 5  cmdID= 63141  format=   "
		::= { iqudc30CmdEntry 63141 }


	iqudc30AudioRoutingCh1ProcessPairs18SPair6 OBJECT-TYPE
		SYNTAX		RollCallString
		MAX-ACCESS		read-only
		STATUS			current
		DESCRIPTION
				"TYPE: - Display
				 PAGE: - Audio Routing-Ch1- Process Pairs 1-8 S
					Pair 6  cmdID= 63142  format=   "
		::= { iqudc30CmdEntry 63142 }


	iqudc30AudioRoutingCh1ProcessPairs18SPair7 OBJECT-TYPE
		SYNTAX		RollCallString
		MAX-ACCESS		read-only
		STATUS			current
		DESCRIPTION
				"TYPE: - Display
				 PAGE: - Audio Routing-Ch1- Process Pairs 1-8 S
					Pair 7  cmdID= 63143  format=   "
		::= { iqudc30CmdEntry 63143 }


	iqudc30AudioRoutingCh1ProcessPairs18SPair8 OBJECT-TYPE
		SYNTAX		RollCallString
		MAX-ACCESS		read-only
		STATUS			current
		DESCRIPTION
				"TYPE: - Display
				 PAGE: - Audio Routing-Ch1- Process Pairs 1-8 S
					Pair 8  cmdID= 63144  format=   "
		::= { iqudc30CmdEntry 63144 }


	iqudc30AudioRoutingCh2InputPairsStatusEmbedded1 OBJECT-TYPE
		SYNTAX		RollCallString
		MAX-ACCESS		read-only
		STATUS			current
		DESCRIPTION
				"TYPE: - Display
				 PAGE: - Audio Routing-Ch2
					Embedded 1  cmdID= 63200  format=   "
		::= { iqudc30CmdEntry 63200 }


	iqudc30AudioRoutingCh2InputPairsStatusEmbedded2 OBJECT-TYPE
		SYNTAX		RollCallString
		MAX-ACCESS		read-only
		STATUS			current
		DESCRIPTION
				"TYPE: - Display
				 PAGE: - Audio Routing-Ch2
					Embedded 2  cmdID= 63201  format=   "
		::= { iqudc30CmdEntry 63201 }


	iqudc30AudioRoutingCh2InputPairsStatusEmbedded3 OBJECT-TYPE
		SYNTAX		RollCallString
		MAX-ACCESS		read-only
		STATUS			current
		DESCRIPTION
				"TYPE: - Display
				 PAGE: - Audio Routing-Ch2
					Embedded 3  cmdID= 63202  format=   "
		::= { iqudc30CmdEntry 63202 }


	iqudc30AudioRoutingCh2InputPairsStatusEmbedded4 OBJECT-TYPE
		SYNTAX		RollCallString
		MAX-ACCESS		read-only
		STATUS			current
		DESCRIPTION
				"TYPE: - Display
				 PAGE: - Audio Routing-Ch2
					Embedded 4  cmdID= 63203  format=   "
		::= { iqudc30CmdEntry 63203 }


	iqudc30AudioRoutingCh2InputPairsStatusEmbedded5 OBJECT-TYPE
		SYNTAX		RollCallString
		MAX-ACCESS		read-only
		STATUS			current
		DESCRIPTION
				"TYPE: - Display
				 PAGE: - Audio Routing-Ch2
					Embedded 5  cmdID= 63204  format=   "
		::= { iqudc30CmdEntry 63204 }


	iqudc30AudioRoutingCh2InputPairsStatusEmbedded6 OBJECT-TYPE
		SYNTAX		RollCallString
		MAX-ACCESS		read-only
		STATUS			current
		DESCRIPTION
				"TYPE: - Display
				 PAGE: - Audio Routing-Ch2
					Embedded 6  cmdID= 63205  format=   "
		::= { iqudc30CmdEntry 63205 }


	iqudc30AudioRoutingCh2InputPairsStatusEmbedded7 OBJECT-TYPE
		SYNTAX		RollCallString
		MAX-ACCESS		read-only
		STATUS			current
		DESCRIPTION
				"TYPE: - Display
				 PAGE: - Audio Routing-Ch2
					Embedded 7  cmdID= 63206  format=   "
		::= { iqudc30CmdEntry 63206 }


	iqudc30AudioRoutingCh2InputPairsStatusEmbedded8 OBJECT-TYPE
		SYNTAX		RollCallString
		MAX-ACCESS		read-only
		STATUS			current
		DESCRIPTION
				"TYPE: - Display
				 PAGE: - Audio Routing-Ch2
					Embedded 8  cmdID= 63207  format=   "
		::= { iqudc30CmdEntry 63207 }


	iqudc30AudioRoutingCh2InputPairsStatusAES1 OBJECT-TYPE
		SYNTAX		RollCallString
		MAX-ACCESS		read-only
		STATUS			current
		DESCRIPTION
				"TYPE: - Display
				 PAGE: - Audio Routing-Ch2
					AES 1  cmdID= 63220  format=   "
		::= { iqudc30CmdEntry 63220 }


	iqudc30AudioRoutingCh2InputPairsStatusAES2 OBJECT-TYPE
		SYNTAX		RollCallString
		MAX-ACCESS		read-only
		STATUS			current
		DESCRIPTION
				"TYPE: - Display
				 PAGE: - Audio Routing-Ch2
					AES 2  cmdID= 63221  format=   "
		::= { iqudc30CmdEntry 63221 }


	iqudc30AudioRoutingCh2InputPairsStatusAES3 OBJECT-TYPE
		SYNTAX		RollCallString
		MAX-ACCESS		read-only
		STATUS			current
		DESCRIPTION
				"TYPE: - Display
				 PAGE: - Audio Routing-Ch2
					AES 3  cmdID= 63223  format=   "
		::= { iqudc30CmdEntry 63223 }


	iqudc30AudioRoutingCh2InputPairsStatusAES4 OBJECT-TYPE
		SYNTAX		RollCallString
		MAX-ACCESS		read-only
		STATUS			current
		DESCRIPTION
				"TYPE: - Display
				 PAGE: - Audio Routing-Ch2
					AES 4  cmdID= 63224  format=   "
		::= { iqudc30CmdEntry 63224 }


	iqudc30AudioRoutingCh2InputPairsStatusAES5 OBJECT-TYPE
		SYNTAX		RollCallString
		MAX-ACCESS		read-only
		STATUS			current
		DESCRIPTION
				"TYPE: - Display
				 PAGE: - Audio Routing-Ch2
					AES 5  cmdID= 63225  format=   "
		::= { iqudc30CmdEntry 63225 }


	iqudc30AudioRoutingCh2InputPairsStatusAES6 OBJECT-TYPE
		SYNTAX		RollCallString
		MAX-ACCESS		read-only
		STATUS			current
		DESCRIPTION
				"TYPE: - Display
				 PAGE: - Audio Routing-Ch2
					AES 6  cmdID= 63226  format=   "
		::= { iqudc30CmdEntry 63226 }


	iqudc30AudioRoutingCh2InputPairsStatusAES7 OBJECT-TYPE
		SYNTAX		RollCallString
		MAX-ACCESS		read-only
		STATUS			current
		DESCRIPTION
				"TYPE: - Display
				 PAGE: - Audio Routing-Ch2
					AES 7  cmdID= 63227  format=   "
		::= { iqudc30CmdEntry 63227 }


	iqudc30AudioRoutingCh2InputPairsStatusAES8 OBJECT-TYPE
		SYNTAX		RollCallString
		MAX-ACCESS		read-only
		STATUS			current
		DESCRIPTION
				"TYPE: - Display
				 PAGE: - Audio Routing-Ch2
					AES 8  cmdID= 63228  format=   "
		::= { iqudc30CmdEntry 63228 }


	iqudc30AudioRoutingCh2InputPairsStatusAnalog1 OBJECT-TYPE
		SYNTAX		RollCallString
		MAX-ACCESS		read-only
		STATUS			current
		DESCRIPTION
				"TYPE: - Display
				 PAGE: - Audio Routing-Ch2
					Analog 1  cmdID= 63229  format=   "
		::= { iqudc30CmdEntry 63229 }


	iqudc30AudioRoutingCh2InputPairsStatusAnalog2 OBJECT-TYPE
		SYNTAX		RollCallString
		MAX-ACCESS		read-only
		STATUS			current
		DESCRIPTION
				"TYPE: - Display
				 PAGE: - Audio Routing-Ch2
					Analog 2  cmdID= 63236  format=   "
		::= { iqudc30CmdEntry 63236 }


	iqudc30AudioRoutingCh2InputPairsStatusDolbyDecoder1 OBJECT-TYPE
		SYNTAX		RollCallString
		MAX-ACCESS		read-only
		STATUS			current
		DESCRIPTION
				"TYPE: - Display
				 PAGE: - Audio Routing-Ch2
					Dolby Decoder 1  cmdID= 63230  format=   "
		::= { iqudc30CmdEntry 63230 }


	iqudc30AudioRoutingCh2InputPairsStatusDolbyDecoder2 OBJECT-TYPE
		SYNTAX		RollCallString
		MAX-ACCESS		read-only
		STATUS			current
		DESCRIPTION
				"TYPE: - Display
				 PAGE: - Audio Routing-Ch2
					Dolby Decoder 2  cmdID= 63231  format=   "
		::= { iqudc30CmdEntry 63231 }


	iqudc30AudioRoutingCh2InputPairsStatusDolbyDecoder3 OBJECT-TYPE
		SYNTAX		RollCallString
		MAX-ACCESS		read-only
		STATUS			current
		DESCRIPTION
				"TYPE: - Display
				 PAGE: - Audio Routing-Ch2
					Dolby Decoder 3  cmdID= 63232  format=   "
		::= { iqudc30CmdEntry 63232 }


	iqudc30AudioRoutingCh2InputPairsStatusDolbyDecoder4 OBJECT-TYPE
		SYNTAX		RollCallString
		MAX-ACCESS		read-only
		STATUS			current
		DESCRIPTION
				"TYPE: - Display
				 PAGE: - Audio Routing-Ch2
					Dolby Decoder 4  cmdID= 63233  format=   "
		::= { iqudc30CmdEntry 63233 }


	iqudc30AudioRoutingCh2InputPairsStatusDolbyDownmix OBJECT-TYPE
		SYNTAX		RollCallString
		MAX-ACCESS		read-only
		STATUS			current
		DESCRIPTION
				"TYPE: - Display
				 PAGE: - Audio Routing-Ch2
					Dolby Downmix  cmdID= 63234  format=   "
		::= { iqudc30CmdEntry 63234 }


	iqudc30AudioRoutingCh2InputPairsStatusDolbyEncoder OBJECT-TYPE
		SYNTAX		RollCallString
		MAX-ACCESS		read-only
		STATUS			current
		DESCRIPTION
				"TYPE: - Display
				 PAGE: - Audio Routing-Ch2
					Dolby Encoder  cmdID= 63235  format=   "
		::= { iqudc30CmdEntry 63235 }


	iqudc30ProcessPairs18ProcessPair1InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 1
					Input Pairs Source  cmdID= 50242 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50242 }


	iqudc30ProcessPairs18ProcessPair2InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 2
					Input Pairs Source  cmdID= 50243 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50243 }


	iqudc30ProcessPairs18ProcessPair3InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 3
					Input Pairs Source  cmdID= 50244 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50244 }


	iqudc30ProcessPairs18ProcessPair4InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 4
					Input Pairs Source  cmdID= 50245 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50245 }


	iqudc30ProcessPairs18ProcessPair5InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 5
					Input Pairs Source  cmdID= 50246 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50246 }


	iqudc30ProcessPairs18ProcessPair6InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 6
					Input Pairs Source  cmdID= 50247 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50247 }


	iqudc30ProcessPairs18ProcessPair7InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 7
					Input Pairs Source  cmdID= 50248 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50248 }


	iqudc30ProcessPairs18ProcessPair8InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 8
					Input Pairs Source  cmdID= 50249 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc30CmdEntry 50249 }


	iqudc30AudioRoutingCh2ProcessPairs18SPair1 OBJECT-TYPE
		SYNTAX		RollCallString
		MAX-ACCESS		read-only
		STATUS			current
		DESCRIPTION
				"TYPE: - Display
				 PAGE: - Audio Routing-Ch2- Process Pairs 1-8 S
					Pair 1  cmdID= 63145  format=   "
		::= { iqudc30CmdEntry 63145 }


	iqudc30AudioRoutingCh2ProcessPairs18SPair2 OBJECT-TYPE
		SYNTAX		RollCallString
		MAX-ACCESS		read-only
		STATUS			current
		DESCRIPTION
				"TYPE: - Display
				 PAGE: - Audio Routing-Ch2- Process Pairs 1-8 S
					Pair 2  cmdID= 63146  format=   "
		::= { iqudc30CmdEntry 63146 }


	iqudc30AudioRoutingCh2ProcessPairs18SPair3 OBJECT-TYPE
		SYNTAX		RollCallString
		MAX-ACCESS		read-only
		STATUS			current
		DESCRIPTION
				"TYPE: - Display
				 PAGE: - Audio Routing-Ch2- Process Pairs 1-8 S
					Pair 3  cmdID= 63147  format=   "
		::= { iqudc30CmdEntry 63147 }


	iqudc30AudioRoutingCh2ProcessPairs18SPair4 OBJECT-TYPE
		SYNTAX		RollCallString
		MAX-ACCESS		read-only
		STATUS			current
		DESCRIPTION
				"TYPE: - Display
				 PAGE: - Audio Routing-Ch2- Process Pairs 1-8 S
					Pair 4  cmdID= 63148  format=   "
		::= { iqudc30CmdEntry 63148 }


	iqudc30AudioRoutingCh2ProcessPairs18SPair5 OBJECT-TYPE
		SYNTAX		RollCallString
		MAX-ACCESS		read-only
		STATUS			current
		DESCRIPTION
				"TYPE: - Display
				 PAGE: - Audio Routing-Ch2- Process Pairs 1-8 S
					Pair 5  cmdID= 63149  format=   "
		::= { iqudc30CmdEntry 63149 }


	iqudc30AudioRoutingCh2ProcessPairs18SPair6 OBJECT-TYPE
		SYNTAX		RollCallString
		MAX-ACCESS		read-only
		STATUS			current
		DESCRIPTION
				"TYPE: - Display
				 PAGE: - Audio Routing-Ch2- Process Pairs 1-8 S
					Pair 6  cmdID= 63150  format=   "
		::= { iqudc30CmdEntry 63150 }


	iqudc30AudioRoutingCh2ProcessPairs18SPair7 OBJECT-TYPE
		SYNTAX		RollCallString
		MAX-ACCESS		read-only
		STATUS			current
		DESCRIPTION
				"TYPE: - Display
				 PAGE: - Audio Routing-Ch2- Process Pairs 1-8 S
					Pair 7  cmdID= 63151  format=   "
		::= { iqudc30CmdEntry 63151 }


	iqudc30AudioRoutingCh2ProcessPairs18SPair8 OBJECT-TYPE
		SYNTAX		RollCallString
		MAX-ACCESS		read-only
		STATUS			current
		DESCRIPTION
				"TYPE: - Display
				 PAGE: - Audio Routing-Ch2- Process Pairs 1-8 S
					Pair 8  cmdID= 63152  format=   "
		::= { iqudc30CmdEntry 63152 }


	iqudc30MenuAudioRoutingCh2NewDisplay OBJECT-TYPE
		SYNTAX		RollCallString
		MAX-ACCESS		read-only
		STATUS			current
		DESCRIPTION
				"TYPE: - Display
				 PAGE: - Audio Routing-Ch2
					New Display  cmdID= 44450  format=   "
		::= { iqudc30CmdEntry 44450 }


	iqudc30OutputPairs18OutputPair1LProcessPairsSourc52000 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 1 L
					Process Pairs Sourc  cmdID= 52000 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52000 }


	iqudc30OutputPairs18OutputPair1LInvertPhase50700 OBJECT-TYPE
		SYNTAX		INTEGER { disable(0), enable(1) }
		MAX-ACCESS		read-write
		STATUS			current
		DESCRIPTION
				"TYPE: - Checkbox
				 PAGE: - Audio Shuffle-Ch1- Output Pairs 1-8- Output Pair 1 L
					Invert Phase  cmdID= 50700 "
		::= { iqudc30CmdEntry 50700 }


	iqudc30OutputPairs18OutputPair1LControl50100 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 1 L
					Control  cmdID= 50100 
					Use Routing  value= 0  
					Tone  value= 1  
					Silence  value= 2  "
		::= { iqudc30CmdEntry 50100 }


	iqudc30OutputPairs18OutputPair1RProcessPairsSourc52008 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 1 R
					Process Pairs Sourc  cmdID= 52008 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52008 }


	iqudc30OutputPairs18OutputPair1RInvertPhase50708 OBJECT-TYPE
		SYNTAX		INTEGER { disable(0), enable(1) }
		MAX-ACCESS		read-write
		STATUS			current
		DESCRIPTION
				"TYPE: - Checkbox
				 PAGE: - Audio Shuffle-Ch1- Output Pairs 1-8- Output Pair 1 R
					Invert Phase  cmdID= 50708 "
		::= { iqudc30CmdEntry 50708 }


	iqudc30OutputPairs18OutputPair1RControl50108 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 1 R
					Control  cmdID= 50108 
					Use Routing  value= 0  
					Tone  value= 1  
					Silence  value= 2  "
		::= { iqudc30CmdEntry 50108 }


	iqudc30OutputPairs18OutputPair2LProcessPairsSourc52001 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 2 L
					Process Pairs Sourc  cmdID= 52001 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52001 }


	iqudc30OutputPairs18OutputPair2LInvertPhase50701 OBJECT-TYPE
		SYNTAX		INTEGER { disable(0), enable(1) }
		MAX-ACCESS		read-write
		STATUS			current
		DESCRIPTION
				"TYPE: - Checkbox
				 PAGE: - Audio Shuffle-Ch1- Output Pairs 1-8- Output Pair 2 L
					Invert Phase  cmdID= 50701 "
		::= { iqudc30CmdEntry 50701 }


	iqudc30OutputPairs18OutputPair2LControl50101 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 2 L
					Control  cmdID= 50101 
					Use Routing  value= 0  
					Tone  value= 1  
					Silence  value= 2  "
		::= { iqudc30CmdEntry 50101 }


	iqudc30OutputPairs18OutputPair2RProcessPairsSourc52009 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 2 R
					Process Pairs Sourc  cmdID= 52009 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52009 }


	iqudc30OutputPairs18OutputPair2RInvertPhase50709 OBJECT-TYPE
		SYNTAX		INTEGER { disable(0), enable(1) }
		MAX-ACCESS		read-write
		STATUS			current
		DESCRIPTION
				"TYPE: - Checkbox
				 PAGE: - Audio Shuffle-Ch1- Output Pairs 1-8- Output Pair 2 R
					Invert Phase  cmdID= 50709 "
		::= { iqudc30CmdEntry 50709 }


	iqudc30OutputPairs18OutputPair2RControl50109 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 2 R
					Control  cmdID= 50109 
					Use Routing  value= 0  
					Tone  value= 1  
					Silence  value= 2  "
		::= { iqudc30CmdEntry 50109 }


	iqudc30OutputPairs18OutputPair3LProcessPairsSourc52002 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 3 L
					Process Pairs Sourc  cmdID= 52002 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52002 }


	iqudc30OutputPairs18OutputPair3LInvertPhase50702 OBJECT-TYPE
		SYNTAX		INTEGER { disable(0), enable(1) }
		MAX-ACCESS		read-write
		STATUS			current
		DESCRIPTION
				"TYPE: - Checkbox
				 PAGE: - Audio Shuffle-Ch1- Output Pairs 1-8- Output Pair 3 L
					Invert Phase  cmdID= 50702 "
		::= { iqudc30CmdEntry 50702 }


	iqudc30OutputPairs18OutputPair3LControl50102 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 3 L
					Control  cmdID= 50102 
					Use Routing  value= 0  
					Tone  value= 1  
					Silence  value= 2  "
		::= { iqudc30CmdEntry 50102 }


	iqudc30OutputPairs18OutputPair3RProcessPairsSourc52010 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 3 R
					Process Pairs Sourc  cmdID= 52010 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52010 }


	iqudc30OutputPairs18OutputPair3RInvertPhase50710 OBJECT-TYPE
		SYNTAX		INTEGER { disable(0), enable(1) }
		MAX-ACCESS		read-write
		STATUS			current
		DESCRIPTION
				"TYPE: - Checkbox
				 PAGE: - Audio Shuffle-Ch1- Output Pairs 1-8- Output Pair 3 R
					Invert Phase  cmdID= 50710 "
		::= { iqudc30CmdEntry 50710 }


	iqudc30OutputPairs18OutputPair3RControl50110 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 3 R
					Control  cmdID= 50110 
					Use Routing  value= 0  
					Tone  value= 1  
					Silence  value= 2  "
		::= { iqudc30CmdEntry 50110 }


	iqudc30OutputPairs18OutputPair4LProcessPairsSourc52003 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 4 L
					Process Pairs Sourc  cmdID= 52003 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52003 }


	iqudc30OutputPairs18OutputPair4LInvertPhase50703 OBJECT-TYPE
		SYNTAX		INTEGER { disable(0), enable(1) }
		MAX-ACCESS		read-write
		STATUS			current
		DESCRIPTION
				"TYPE: - Checkbox
				 PAGE: - Audio Shuffle-Ch1- Output Pairs 1-8- Output Pair 4 L
					Invert Phase  cmdID= 50703 "
		::= { iqudc30CmdEntry 50703 }


	iqudc30OutputPairs18OutputPair4LControl50103 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 4 L
					Control  cmdID= 50103 
					Use Routing  value= 0  
					Tone  value= 1  
					Silence  value= 2  "
		::= { iqudc30CmdEntry 50103 }


	iqudc30OutputPairs18OutputPair4RProcessPairsSourc52011 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 4 R
					Process Pairs Sourc  cmdID= 52011 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52011 }


	iqudc30OutputPairs18OutputPair4RInvertPhase50711 OBJECT-TYPE
		SYNTAX		INTEGER { disable(0), enable(1) }
		MAX-ACCESS		read-write
		STATUS			current
		DESCRIPTION
				"TYPE: - Checkbox
				 PAGE: - Audio Shuffle-Ch1- Output Pairs 1-8- Output Pair 4 R
					Invert Phase  cmdID= 50711 "
		::= { iqudc30CmdEntry 50711 }


	iqudc30OutputPairs18OutputPair4RControl50111 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 4 R
					Control  cmdID= 50111 
					Use Routing  value= 0  
					Tone  value= 1  
					Silence  value= 2  "
		::= { iqudc30CmdEntry 50111 }


	iqudc30OutputPairs18OutputPair5LProcessPairsSourc52004 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 5 L
					Process Pairs Sourc  cmdID= 52004 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52004 }


	iqudc30OutputPairs18OutputPair5LInvertPhase50704 OBJECT-TYPE
		SYNTAX		INTEGER { disable(0), enable(1) }
		MAX-ACCESS		read-write
		STATUS			current
		DESCRIPTION
				"TYPE: - Checkbox
				 PAGE: - Audio Shuffle-Ch1- Output Pairs 1-8- Output Pair 5 L
					Invert Phase  cmdID= 50704 "
		::= { iqudc30CmdEntry 50704 }


	iqudc30OutputPairs18OutputPair5LControl50104 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 5 L
					Control  cmdID= 50104 
					Use Routing  value= 0  
					Tone  value= 1  
					Silence  value= 2  "
		::= { iqudc30CmdEntry 50104 }


	iqudc30OutputPairs18OutputPair5RProcessPairsSourc52012 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 5 R
					Process Pairs Sourc  cmdID= 52012 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52012 }


	iqudc30OutputPairs18OutputPair5RInvertPhase50712 OBJECT-TYPE
		SYNTAX		INTEGER { disable(0), enable(1) }
		MAX-ACCESS		read-write
		STATUS			current
		DESCRIPTION
				"TYPE: - Checkbox
				 PAGE: - Audio Shuffle-Ch1- Output Pairs 1-8- Output Pair 5 R
					Invert Phase  cmdID= 50712 "
		::= { iqudc30CmdEntry 50712 }


	iqudc30OutputPairs18OutputPair5RControl50112 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 5 R
					Control  cmdID= 50112 
					Use Routing  value= 0  
					Tone  value= 1  
					Silence  value= 2  "
		::= { iqudc30CmdEntry 50112 }


	iqudc30OutputPairs18OutputPair6LProcessPairsSourc52005 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 6 L
					Process Pairs Sourc  cmdID= 52005 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52005 }


	iqudc30OutputPairs18OutputPair6LInvertPhase50705 OBJECT-TYPE
		SYNTAX		INTEGER { disable(0), enable(1) }
		MAX-ACCESS		read-write
		STATUS			current
		DESCRIPTION
				"TYPE: - Checkbox
				 PAGE: - Audio Shuffle-Ch1- Output Pairs 1-8- Output Pair 6 L
					Invert Phase  cmdID= 50705 "
		::= { iqudc30CmdEntry 50705 }


	iqudc30OutputPairs18OutputPair6LControl50105 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 6 L
					Control  cmdID= 50105 
					Use Routing  value= 0  
					Tone  value= 1  
					Silence  value= 2  "
		::= { iqudc30CmdEntry 50105 }


	iqudc30OutputPairs18OutputPair6RProcessPairsSourc52013 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 6 R
					Process Pairs Sourc  cmdID= 52013 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52013 }


	iqudc30OutputPairs18OutputPair6RInvertPhase50713 OBJECT-TYPE
		SYNTAX		INTEGER { disable(0), enable(1) }
		MAX-ACCESS		read-write
		STATUS			current
		DESCRIPTION
				"TYPE: - Checkbox
				 PAGE: - Audio Shuffle-Ch1- Output Pairs 1-8- Output Pair 6 R
					Invert Phase  cmdID= 50713 "
		::= { iqudc30CmdEntry 50713 }


	iqudc30OutputPairs18OutputPair6RControl50113 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 6 R
					Control  cmdID= 50113 
					Use Routing  value= 0  
					Tone  value= 1  
					Silence  value= 2  "
		::= { iqudc30CmdEntry 50113 }


	iqudc30OutputPairs18OutputPair7LProcessPairsSourc52006 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 7 L
					Process Pairs Sourc  cmdID= 52006 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52006 }


	iqudc30OutputPairs18OutputPair7LInvertPhase50706 OBJECT-TYPE
		SYNTAX		INTEGER { disable(0), enable(1) }
		MAX-ACCESS		read-write
		STATUS			current
		DESCRIPTION
				"TYPE: - Checkbox
				 PAGE: - Audio Shuffle-Ch1- Output Pairs 1-8- Output Pair 7 L
					Invert Phase  cmdID= 50706 "
		::= { iqudc30CmdEntry 50706 }


	iqudc30OutputPairs18OutputPair7LControl50106 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 7 L
					Control  cmdID= 50106 
					Use Routing  value= 0  
					Tone  value= 1  
					Silence  value= 2  "
		::= { iqudc30CmdEntry 50106 }


	iqudc30OutputPairs18OutputPair7RProcessPairsSourc52014 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 7 R
					Process Pairs Sourc  cmdID= 52014 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52014 }


	iqudc30OutputPairs18OutputPair7RInvertPhase50714 OBJECT-TYPE
		SYNTAX		INTEGER { disable(0), enable(1) }
		MAX-ACCESS		read-write
		STATUS			current
		DESCRIPTION
				"TYPE: - Checkbox
				 PAGE: - Audio Shuffle-Ch1- Output Pairs 1-8- Output Pair 7 R
					Invert Phase  cmdID= 50714 "
		::= { iqudc30CmdEntry 50714 }


	iqudc30OutputPairs18OutputPair7RControl50114 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 7 R
					Control  cmdID= 50114 
					Use Routing  value= 0  
					Tone  value= 1  
					Silence  value= 2  "
		::= { iqudc30CmdEntry 50114 }


	iqudc30OutputPairs18OutputPair8LProcessPairsSourc52007 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 8 L
					Process Pairs Sourc  cmdID= 52007 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52007 }


	iqudc30OutputPairs18OutputPair8LInvertPhase50707 OBJECT-TYPE
		SYNTAX		INTEGER { disable(0), enable(1) }
		MAX-ACCESS		read-write
		STATUS			current
		DESCRIPTION
				"TYPE: - Checkbox
				 PAGE: - Audio Shuffle-Ch1- Output Pairs 1-8- Output Pair 8 L
					Invert Phase  cmdID= 50707 "
		::= { iqudc30CmdEntry 50707 }


	iqudc30OutputPairs18OutputPair8LControl50107 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 8 L
					Control  cmdID= 50107 
					Use Routing  value= 0  
					Tone  value= 1  
					Silence  value= 2  "
		::= { iqudc30CmdEntry 50107 }


	iqudc30OutputPairs18OutputPair8RProcessPairsSourc52015 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 8 R
					Process Pairs Sourc  cmdID= 52015 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 52015 }


	iqudc30OutputPairs18OutputPair8RInvertPhase50715 OBJECT-TYPE
		SYNTAX		INTEGER { disable(0), enable(1) }
		MAX-ACCESS		read-write
		STATUS			current
		DESCRIPTION
				"TYPE: - Checkbox
				 PAGE: - Audio Shuffle-Ch1- Output Pairs 1-8- Output Pair 8 R
					Invert Phase  cmdID= 50715 "
		::= { iqudc30CmdEntry 50715 }


	iqudc30OutputPairs18OutputPair8RControl50115 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 8 R
					Control  cmdID= 50115 
					Use Routing  value= 0  
					Tone  value= 1  
					Silence  value= 2  "
		::= { iqudc30CmdEntry 50115 }


	iqudc30AudioShuffleCh1OutputPairs18StPair1 OBJECT-TYPE
		SYNTAX		RollCallString
		MAX-ACCESS		read-only
		STATUS			current
		DESCRIPTION
				"TYPE: - Display
				 PAGE: - Audio Shuffle-Ch1- Output Pairs 1-8 St
					Pair 1  cmdID= 50335  format=   "
		::= { iqudc30CmdEntry 50335 }


	iqudc30AudioShuffleCh1OutputPairs18StPair2 OBJECT-TYPE
		SYNTAX		RollCallString
		MAX-ACCESS		read-only
		STATUS			current
		DESCRIPTION
				"TYPE: - Display
				 PAGE: - Audio Shuffle-Ch1- Output Pairs 1-8 St
					Pair 2  cmdID= 50336  format=   "
		::= { iqudc30CmdEntry 50336 }


	iqudc30AudioShuffleCh1OutputPairs18StPair3 OBJECT-TYPE
		SYNTAX		RollCallString
		MAX-ACCESS		read-only
		STATUS			current
		DESCRIPTION
				"TYPE: - Display
				 PAGE: - Audio Shuffle-Ch1- Output Pairs 1-8 St
					Pair 3  cmdID= 50337  format=   "
		::= { iqudc30CmdEntry 50337 }


	iqudc30AudioShuffleCh1OutputPairs18StPair4 OBJECT-TYPE
		SYNTAX		RollCallString
		MAX-ACCESS		read-only
		STATUS			current
		DESCRIPTION
				"TYPE: - Display
				 PAGE: - Audio Shuffle-Ch1- Output Pairs 1-8 St
					Pair 4  cmdID= 50338  format=   "
		::= { iqudc30CmdEntry 50338 }


	iqudc30AudioShuffleCh1OutputPairs18StPair5 OBJECT-TYPE
		SYNTAX		RollCallString
		MAX-ACCESS		read-only
		STATUS			current
		DESCRIPTION
				"TYPE: - Display
				 PAGE: - Audio Shuffle-Ch1- Output Pairs 1-8 St
					Pair 5  cmdID= 50339  format=   "
		::= { iqudc30CmdEntry 50339 }


	iqudc30AudioShuffleCh1OutputPairs18StPair6 OBJECT-TYPE
		SYNTAX		RollCallString
		MAX-ACCESS		read-only
		STATUS			current
		DESCRIPTION
				"TYPE: - Display
				 PAGE: - Audio Shuffle-Ch1- Output Pairs 1-8 St
					Pair 6  cmdID= 50340  format=   "
		::= { iqudc30CmdEntry 50340 }


	iqudc30AudioShuffleCh1OutputPairs18StPair7 OBJECT-TYPE
		SYNTAX		RollCallString
		MAX-ACCESS		read-only
		STATUS			current
		DESCRIPTION
				"TYPE: - Display
				 PAGE: - Audio Shuffle-Ch1- Output Pairs 1-8 St
					Pair 7  cmdID= 50341  format=   "
		::= { iqudc30CmdEntry 50341 }


	iqudc30AudioShuffleCh1OutputPairs18StPair8 OBJECT-TYPE
		SYNTAX		RollCallString
		MAX-ACCESS		read-only
		STATUS			current
		DESCRIPTION
				"TYPE: - Display
				 PAGE: - Audio Shuffle-Ch1- Output Pairs 1-8 St
					Pair 8  cmdID= 50342  format=   "
		::= { iqudc30CmdEntry 50342 }


	iqudc30MenuAudioShuffleCh1NewDisplay OBJECT-TYPE
		SYNTAX		RollCallString
		MAX-ACCESS		read-only
		STATUS			current
		DESCRIPTION
				"TYPE: - Display
				 PAGE: - Audio Shuffle-Ch1
					New Display  cmdID= 44461  format=   "
		::= { iqudc30CmdEntry 44461 }


	iqudc30OutputPairs18OutputPair1LProcessPairsSourc50800 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 1 L
					Process Pairs Sourc  cmdID= 50800 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50800 }


	iqudc30OutputPairs18OutputPair1LInvertPhase50816 OBJECT-TYPE
		SYNTAX		INTEGER { disable(0), enable(1) }
		MAX-ACCESS		read-write
		STATUS			current
		DESCRIPTION
				"TYPE: - Checkbox
				 PAGE: - Audio Shuffle-Ch2- Output Pairs 1-8- Output Pair 1 L
					Invert Phase  cmdID= 50816 "
		::= { iqudc30CmdEntry 50816 }


	iqudc30OutputPairs18OutputPair1LControl50832 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 1 L
					Control  cmdID= 50832 
					Use Routing  value= 0  
					Tone  value= 1  
					Silence  value= 2  "
		::= { iqudc30CmdEntry 50832 }


	iqudc30OutputPairs18OutputPair1RProcessPairsSourc50808 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 1 R
					Process Pairs Sourc  cmdID= 50808 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50808 }


	iqudc30OutputPairs18OutputPair1RInvertPhase50824 OBJECT-TYPE
		SYNTAX		INTEGER { disable(0), enable(1) }
		MAX-ACCESS		read-write
		STATUS			current
		DESCRIPTION
				"TYPE: - Checkbox
				 PAGE: - Audio Shuffle-Ch2- Output Pairs 1-8- Output Pair 1 R
					Invert Phase  cmdID= 50824 "
		::= { iqudc30CmdEntry 50824 }


	iqudc30OutputPairs18OutputPair1RControl50840 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 1 R
					Control  cmdID= 50840 
					Use Routing  value= 0  
					Tone  value= 1  
					Silence  value= 2  "
		::= { iqudc30CmdEntry 50840 }


	iqudc30OutputPairs18OutputPair2LProcessPairsSourc50801 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 2 L
					Process Pairs Sourc  cmdID= 50801 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50801 }


	iqudc30OutputPairs18OutputPair2LInvertPhase50817 OBJECT-TYPE
		SYNTAX		INTEGER { disable(0), enable(1) }
		MAX-ACCESS		read-write
		STATUS			current
		DESCRIPTION
				"TYPE: - Checkbox
				 PAGE: - Audio Shuffle-Ch2- Output Pairs 1-8- Output Pair 2 L
					Invert Phase  cmdID= 50817 "
		::= { iqudc30CmdEntry 50817 }


	iqudc30OutputPairs18OutputPair2LControl50833 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 2 L
					Control  cmdID= 50833 
					Use Routing  value= 0  
					Tone  value= 1  
					Silence  value= 2  "
		::= { iqudc30CmdEntry 50833 }


	iqudc30OutputPairs18OutputPair2RProcessPairsSourc50809 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 2 R
					Process Pairs Sourc  cmdID= 50809 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50809 }


	iqudc30OutputPairs18OutputPair2RInvertPhase50825 OBJECT-TYPE
		SYNTAX		INTEGER { disable(0), enable(1) }
		MAX-ACCESS		read-write
		STATUS			current
		DESCRIPTION
				"TYPE: - Checkbox
				 PAGE: - Audio Shuffle-Ch2- Output Pairs 1-8- Output Pair 2 R
					Invert Phase  cmdID= 50825 "
		::= { iqudc30CmdEntry 50825 }


	iqudc30OutputPairs18OutputPair2RControl50841 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 2 R
					Control  cmdID= 50841 
					Use Routing  value= 0  
					Tone  value= 1  
					Silence  value= 2  "
		::= { iqudc30CmdEntry 50841 }


	iqudc30OutputPairs18OutputPair3LProcessPairsSourc50802 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 3 L
					Process Pairs Sourc  cmdID= 50802 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50802 }


	iqudc30OutputPairs18OutputPair3LInvertPhase50818 OBJECT-TYPE
		SYNTAX		INTEGER { disable(0), enable(1) }
		MAX-ACCESS		read-write
		STATUS			current
		DESCRIPTION
				"TYPE: - Checkbox
				 PAGE: - Audio Shuffle-Ch2- Output Pairs 1-8- Output Pair 3 L
					Invert Phase  cmdID= 50818 "
		::= { iqudc30CmdEntry 50818 }


	iqudc30OutputPairs18OutputPair3LControl50834 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 3 L
					Control  cmdID= 50834 
					Use Routing  value= 0  
					Tone  value= 1  
					Silence  value= 2  "
		::= { iqudc30CmdEntry 50834 }


	iqudc30OutputPairs18OutputPair3RProcessPairsSourc50810 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 3 R
					Process Pairs Sourc  cmdID= 50810 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50810 }


	iqudc30OutputPairs18OutputPair3RInvertPhase50826 OBJECT-TYPE
		SYNTAX		INTEGER { disable(0), enable(1) }
		MAX-ACCESS		read-write
		STATUS			current
		DESCRIPTION
				"TYPE: - Checkbox
				 PAGE: - Audio Shuffle-Ch2- Output Pairs 1-8- Output Pair 3 R
					Invert Phase  cmdID= 50826 "
		::= { iqudc30CmdEntry 50826 }


	iqudc30OutputPairs18OutputPair3RControl50842 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 3 R
					Control  cmdID= 50842 
					Use Routing  value= 0  
					Tone  value= 1  
					Silence  value= 2  "
		::= { iqudc30CmdEntry 50842 }


	iqudc30OutputPairs18OutputPair4LProcessPairsSourc50803 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 4 L
					Process Pairs Sourc  cmdID= 50803 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50803 }


	iqudc30OutputPairs18OutputPair4LInvertPhase50819 OBJECT-TYPE
		SYNTAX		INTEGER { disable(0), enable(1) }
		MAX-ACCESS		read-write
		STATUS			current
		DESCRIPTION
				"TYPE: - Checkbox
				 PAGE: - Audio Shuffle-Ch2- Output Pairs 1-8- Output Pair 4 L
					Invert Phase  cmdID= 50819 "
		::= { iqudc30CmdEntry 50819 }


	iqudc30OutputPairs18OutputPair4LControl50835 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 4 L
					Control  cmdID= 50835 
					Use Routing  value= 0  
					Tone  value= 1  
					Silence  value= 2  "
		::= { iqudc30CmdEntry 50835 }


	iqudc30OutputPairs18OutputPair4RProcessPairsSourc50811 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 4 R
					Process Pairs Sourc  cmdID= 50811 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50811 }


	iqudc30OutputPairs18OutputPair4RInvertPhase50827 OBJECT-TYPE
		SYNTAX		INTEGER { disable(0), enable(1) }
		MAX-ACCESS		read-write
		STATUS			current
		DESCRIPTION
				"TYPE: - Checkbox
				 PAGE: - Audio Shuffle-Ch2- Output Pairs 1-8- Output Pair 4 R
					Invert Phase  cmdID= 50827 "
		::= { iqudc30CmdEntry 50827 }


	iqudc30OutputPairs18OutputPair4RControl50843 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 4 R
					Control  cmdID= 50843 
					Use Routing  value= 0  
					Tone  value= 1  
					Silence  value= 2  "
		::= { iqudc30CmdEntry 50843 }


	iqudc30OutputPairs18OutputPair5LProcessPairsSourc50804 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 5 L
					Process Pairs Sourc  cmdID= 50804 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50804 }


	iqudc30OutputPairs18OutputPair5LInvertPhase50820 OBJECT-TYPE
		SYNTAX		INTEGER { disable(0), enable(1) }
		MAX-ACCESS		read-write
		STATUS			current
		DESCRIPTION
				"TYPE: - Checkbox
				 PAGE: - Audio Shuffle-Ch2- Output Pairs 1-8- Output Pair 5 L
					Invert Phase  cmdID= 50820 "
		::= { iqudc30CmdEntry 50820 }


	iqudc30OutputPairs18OutputPair5LControl50836 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 5 L
					Control  cmdID= 50836 
					Use Routing  value= 0  
					Tone  value= 1  
					Silence  value= 2  "
		::= { iqudc30CmdEntry 50836 }


	iqudc30OutputPairs18OutputPair5RProcessPairsSourc50812 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 5 R
					Process Pairs Sourc  cmdID= 50812 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50812 }


	iqudc30OutputPairs18OutputPair5RInvertPhase50828 OBJECT-TYPE
		SYNTAX		INTEGER { disable(0), enable(1) }
		MAX-ACCESS		read-write
		STATUS			current
		DESCRIPTION
				"TYPE: - Checkbox
				 PAGE: - Audio Shuffle-Ch2- Output Pairs 1-8- Output Pair 5 R
					Invert Phase  cmdID= 50828 "
		::= { iqudc30CmdEntry 50828 }


	iqudc30OutputPairs18OutputPair5RControl50844 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 5 R
					Control  cmdID= 50844 
					Use Routing  value= 0  
					Tone  value= 1  
					Silence  value= 2  "
		::= { iqudc30CmdEntry 50844 }


	iqudc30OutputPairs18OutputPair6LProcessPairsSourc50805 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 6 L
					Process Pairs Sourc  cmdID= 50805 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50805 }


	iqudc30OutputPairs18OutputPair6LInvertPhase50821 OBJECT-TYPE
		SYNTAX		INTEGER { disable(0), enable(1) }
		MAX-ACCESS		read-write
		STATUS			current
		DESCRIPTION
				"TYPE: - Checkbox
				 PAGE: - Audio Shuffle-Ch2- Output Pairs 1-8- Output Pair 6 L
					Invert Phase  cmdID= 50821 "
		::= { iqudc30CmdEntry 50821 }


	iqudc30OutputPairs18OutputPair6LControl50837 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 6 L
					Control  cmdID= 50837 
					Use Routing  value= 0  
					Tone  value= 1  
					Silence  value= 2  "
		::= { iqudc30CmdEntry 50837 }


	iqudc30OutputPairs18OutputPair6RProcessPairsSourc50813 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 6 R
					Process Pairs Sourc  cmdID= 50813 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50813 }


	iqudc30OutputPairs18OutputPair6RInvertPhase50829 OBJECT-TYPE
		SYNTAX		INTEGER { disable(0), enable(1) }
		MAX-ACCESS		read-write
		STATUS			current
		DESCRIPTION
				"TYPE: - Checkbox
				 PAGE: - Audio Shuffle-Ch2- Output Pairs 1-8- Output Pair 6 R
					Invert Phase  cmdID= 50829 "
		::= { iqudc30CmdEntry 50829 }


	iqudc30OutputPairs18OutputPair6RControl50845 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 6 R
					Control  cmdID= 50845 
					Use Routing  value= 0  
					Tone  value= 1  
					Silence  value= 2  "
		::= { iqudc30CmdEntry 50845 }


	iqudc30OutputPairs18OutputPair7LProcessPairsSourc50806 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 7 L
					Process Pairs Sourc  cmdID= 50806 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50806 }


	iqudc30OutputPairs18OutputPair7LInvertPhase50822 OBJECT-TYPE
		SYNTAX		INTEGER { disable(0), enable(1) }
		MAX-ACCESS		read-write
		STATUS			current
		DESCRIPTION
				"TYPE: - Checkbox
				 PAGE: - Audio Shuffle-Ch2- Output Pairs 1-8- Output Pair 7 L
					Invert Phase  cmdID= 50822 "
		::= { iqudc30CmdEntry 50822 }


	iqudc30OutputPairs18OutputPair7LControl50838 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 7 L
					Control  cmdID= 50838 
					Use Routing  value= 0  
					Tone  value= 1  
					Silence  value= 2  "
		::= { iqudc30CmdEntry 50838 }


	iqudc30OutputPairs18OutputPair7RProcessPairsSourc50814 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 7 R
					Process Pairs Sourc  cmdID= 50814 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50814 }


	iqudc30OutputPairs18OutputPair7RInvertPhase50830 OBJECT-TYPE
		SYNTAX		INTEGER { disable(0), enable(1) }
		MAX-ACCESS		read-write
		STATUS			current
		DESCRIPTION
				"TYPE: - Checkbox
				 PAGE: - Audio Shuffle-Ch2- Output Pairs 1-8- Output Pair 7 R
					Invert Phase  cmdID= 50830 "
		::= { iqudc30CmdEntry 50830 }


	iqudc30OutputPairs18OutputPair7RControl50846 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 7 R
					Control  cmdID= 50846 
					Use Routing  value= 0  
					Tone  value= 1  
					Silence  value= 2  "
		::= { iqudc30CmdEntry 50846 }


	iqudc30OutputPairs18OutputPair8LProcessPairsSourc50807 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 8 L
					Process Pairs Sourc  cmdID= 50807 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50807 }


	iqudc30OutputPairs18OutputPair8LInvertPhase50823 OBJECT-TYPE
		SYNTAX		INTEGER { disable(0), enable(1) }
		MAX-ACCESS		read-write
		STATUS			current
		DESCRIPTION
				"TYPE: - Checkbox
				 PAGE: - Audio Shuffle-Ch2- Output Pairs 1-8- Output Pair 8 L
					Invert Phase  cmdID= 50823 "
		::= { iqudc30CmdEntry 50823 }


	iqudc30OutputPairs18OutputPair8LControl50839 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 8 L
					Control  cmdID= 50839 
					Use Routing  value= 0  
					Tone  value= 1  
					Silence  value= 2  "
		::= { iqudc30CmdEntry 50839 }


	iqudc30OutputPairs18OutputPair8RProcessPairsSourc50815 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 8 R
					Process Pairs Sourc  cmdID= 50815 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc30CmdEntry 50815 }


	iqudc30OutputPairs18OutputPair8RInvertPhase50831 OBJECT-TYPE
		SYNTAX		INTEGER { disable(0), enable(1) }
		MAX-ACCESS		read-write
		STATUS			current
		DESCRIPTION
				"TYPE: - Checkbox
				 PAGE: - Audio Shuffle-Ch2- Output Pairs 1-8- Output Pair 8 R
					Invert Phase  cmdID= 50831 "
		::= { iqudc30CmdEntry 50831 }


	iqudc30OutputPairs18OutputPair8RControl50847 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 8 R
					Control  cmdID= 50847 
					Use Routing  value= 0  
					Tone  value= 1  
					Silence  value= 2  "
		::= { iqudc30CmdEntry 50847 }


	iqudc30AudioShuffleCh2OutputPairs18StPair1 OBJECT-TYPE
		SYNTAX		RollCallString
		MAX-ACCESS		read-only
		STATUS			current
		DESCRIPTION
				"TYPE: - Display
				 PAGE: - Audio Shuffle-Ch2- Output Pairs 1-8 St
					Pair 1  cmdID= 50348  format=   "
		::= { iqudc30CmdEntry 50348 }


	iqudc30AudioShuffleCh2OutputPairs18StPair2 OBJECT-TYPE
		SYNTAX		RollCallString
		MAX-ACCESS		read-only
		STATUS			current
		DESCRIPTION
				"TYPE: - Display
				 PAGE: - Audio Shuffle-Ch2- Output Pairs 1-8 St
					Pair 2  cmdID= 50349  format=   "
		::= { iqudc30CmdEntry 50349 }


	iqudc30AudioShuffleCh2OutputPairs18StPair3 OBJECT-TYPE
		SYNTAX		RollCallString
		MAX-ACCESS		read-only
		STATUS			current
		DESCRIPTION
				"TYPE: - Display
				 PAGE: - Audio Shuffle-Ch2- Output Pairs 1-8 St
					Pair 3  cmdID= 50350  format=   "
		::= { iqudc30CmdEntry 50350 }


	iqudc30AudioShuffleCh2OutputPairs18StPair4 OBJECT-TYPE
		SYNTAX		RollCallString
		MAX-ACCESS		read-only
		STATUS			current
		DESCRIPTION
				"TYPE: - Display
				 PAGE: - Audio Shuffle-Ch2- Output Pairs 1-8 St
					Pair 4  cmdID= 50351  format=   "
		::= { iqudc30CmdEntry 50351 }


	iqudc30AudioShuffleCh2OutputPairs18StPair5 OBJECT-TYPE
		SYNTAX		RollCallString
		MAX-ACCESS		read-only
		STATUS			current
		DESCRIPTION
				"TYPE: - Display
				 PAGE: - Audio Shuffle-Ch2- Output Pairs 1-8 St
					Pair 5  cmdID= 50352  format=   "
		::= { iqudc30CmdEntry 50352 }


	iqudc30AudioShuffleCh2OutputPairs18StPair6 OBJECT-TYPE
		SYNTAX		RollCallString
		MAX-ACCESS		read-only
		STATUS			current
		DESCRIPTION
				"TYPE: - Display
				 PAGE: - Audio Shuffle-Ch2- Output Pairs 1-8 St
					Pair 6  cmdID= 50353  format=   "
		::= { iqudc30CmdEntry 50353 }


	iqudc30AudioShuffleCh2OutputPairs18StPair7 OBJECT-TYPE
		SYNTAX		RollCallString
		MAX-ACCESS		read-only
		STATUS			current
		DESCRIPTION
				"TYPE: - Display
				 PAGE: - Audio Shuffle-Ch2- Output Pairs 1-8 St
					Pair 7  cmdID= 50354  format=   "
		::= { iqudc30CmdEntry 50354 }


	iqudc30AudioShuffleCh2OutputPairs18StPair8 OBJECT-TYPE
		SYNTAX		RollCallString
		MAX-ACCESS		read-only
		STATUS			current
		DESCRIPTION
				"TYPE: - Display
				 PAGE: - Audio Shuffle-Ch2- Output Pairs 1-8 St
					Pair 8  cmdID= 50355  format=   "
		::= { iqudc30CmdEntry 50355 }


	iqudc30MenuAudioShuffleCh2NewDisplay OBJECT-TYPE
		SYNTAX		RollCallString
		MAX-ACCESS		read-only
		STATUS			current
		DESCRIPTION
				"TYPE: - Display
				 PAGE: - Audio Shuffle-Ch2
					New Display  cmdID= 44457  format=   "
		::= { iqudc30CmdEntry 44457 }


	iqudc30AudioControlCh1GainPair1L OBJECT-TYPE
		SYNTAX		INTEGER
		MAX-ACCESS		read-write
		STATUS			current
		DESCRIPTION
				"TYPE: - Number
				 PAGE: - Audio Control-Ch1
					Pair 1 L  cmdID= 50228  min= -180  max= 180  step= 1  format= %0.1fdB  div_scale= 10 
					Min = -18.0dB  Max = 18.0dB  Step = 0.1dB "
		::= { iqudc30CmdEntry 50228 }


	iqudc30AudioControlCh1GainPair1R OBJECT-TYPE
		SYNTAX		INTEGER
		MAX-ACCESS		read-write
		STATUS			current
		DESCRIPTION
				"TYPE: - Number
				 PAGE: - Audio Control-Ch1
					Pair 1 R  cmdID= 50229  min= -180  max= 180  step= 1  format= %0.1fdB  div_scale= 10 
					Min = -18.0dB  Max = 18.0dB  Step = 0.1dB "
		::= { iqudc30CmdEntry 50229 }


	iqudc30AudioControlCh1GainPair2L OBJECT-TYPE
		SYNTAX		INTEGER
		MAX-ACCESS		read-write
		STATUS			current
		DESCRIPTION
				"TYPE: - Number
				 PAGE: - Audio Control-Ch1
					Pair 2 L  cmdID= 50202  min= -180  max= 180  step= 1  format= %0.1fdB  div_scale= 10 
					Min = -18.0dB  Max = 18.0dB  Step = 0.1dB "
		::= { iqudc30CmdEntry 50202 }


	iqudc30AudioControlCh1GainPair2R OBJECT-TYPE
		SYNTAX		INTEGER
		MAX-ACCESS		read-write
		STATUS			current
		DESCRIPTION
				"TYPE: - Number
				 PAGE: - Audio Control-Ch1
					Pair 2 R  cmdID= 50231  min= -180  max= 180  step= 1  format= %0.1fdB  div_scale= 10 
					Min = -18.0dB  Max = 18.0dB  Step = 0.1dB "
		::= { iqudc30CmdEntry 50231 }


	iqudc30AudioControlCh1GainPair3L OBJECT-TYPE
		SYNTAX		INTEGER
		MAX-ACCESS		read-write
		STATUS			current
		DESCRIPTION
				"TYPE: - Number
				 PAGE: - Audio Control-Ch1
					Pair 3 L  cmdID= 50204  min= -180  max= 180  step= 1  format= %0.1fdB  div_scale= 10 
					Min = -18.0dB  Max = 18.0dB  Step = 0.1dB "
		::= { iqudc30CmdEntry 50204 }


	iqudc30AudioControlCh1GainPair3R OBJECT-TYPE
		SYNTAX		INTEGER
		MAX-ACCESS		read-write
		STATUS			current
		DESCRIPTION
				"TYPE: - Number
				 PAGE: - Audio Control-Ch1
					Pair 3 R  cmdID= 50205  min= -180  max= 180  step= 1  format= %0.1fdB  div_scale= 10 
					Min = -18.0dB  Max = 18.0dB  Step = 0.1dB "
		::= { iqudc30CmdEntry 50205 }


	iqudc30AudioControlCh1GainPair4L OBJECT-TYPE
		SYNTAX		INTEGER
		MAX-ACCESS		read-write
		STATUS			current
		DESCRIPTION
				"TYPE: - Number
				 PAGE: - Audio Control-Ch1
					Pair 4 L  cmdID= 50206  min= -180  max= 180  step= 1  format= %0.1fdB  div_scale= 10 
					Min = -18.0dB  Max = 18.0dB  Step = 0.1dB "
		::= { iqudc30CmdEntry 50206 }


	iqudc30AudioControlCh1GainPair4R OBJECT-TYPE
		SYNTAX		INTEGER
		MAX-ACCESS		read-write
		STATUS			current
		DESCRIPTION
				"TYPE: - Number
				 PAGE: - Audio Control-Ch1
					Pair 4 R  cmdID= 50235  min= -180  max= 180  step= 1  format= %0.1fdB  div_scale= 10 
					Min = -18.0dB  Max = 18.0dB  Step = 0.1dB "
		::= { iqudc30CmdEntry 50235 }


	iqudc30AudioControlCh1GainPair5L OBJECT-TYPE
		SYNTAX		INTEGER
		MAX-ACCESS		read-write
		STATUS			current
		DESCRIPTION
				"TYPE: - Number
				 PAGE: - Audio Control-Ch1
					Pair 5 L  cmdID= 50208  min= -180  max= 180  step= 1  format= %0.1fdB  div_scale= 10 
					Min = -18.0dB  Max = 18.0dB  Step = 0.1dB "
		::= { iqudc30CmdEntry 50208 }


	iqudc30AudioControlCh1GainPair5R OBJECT-TYPE
		SYNTAX		INTEGER
		MAX-ACCESS		read-write
		STATUS			current
		DESCRIPTION
				"TYPE: - Number
				 PAGE: - Audio Control-Ch1
					Pair 5 R  cmdID= 50209  min= -180  max= 180  step= 1  format= %0.1fdB  div_scale= 10 
					Min = -18.0dB  Max = 18.0dB  Step = 0.1dB "
		::= { iqudc30CmdEntry 50209 }


	iqudc30AudioControlCh1GainPair6L OBJECT-TYPE
		SYNTAX		INTEGER
		MAX-ACCESS		read-write
		STATUS			current
		DESCRIPTION
				"TYPE: - Number
				 PAGE: - Audio Control-Ch1
					Pair 6 L  cmdID= 50210  min= -180  max= 180  step= 1  format= %0.1fdB  div_scale= 10 
					Min = -18.0dB  Max = 18.0dB  Step = 0.1dB "
		::= { iqudc30CmdEntry 50210 }


	iqudc30AudioControlCh1GainPair6R OBJECT-TYPE
		SYNTAX		INTEGER
		MAX-ACCESS		read-write
		STATUS			current
		DESCRIPTION
				"TYPE: - Number
				 PAGE: - Audio Control-Ch1
					Pair 6 R  cmdID= 50211  min= -180  max= 180  step= 1  format= %0.1fdB  div_scale= 10 
					Min = -18.0dB  Max = 18.0dB  Step = 0.1dB "
		::= { iqudc30CmdEntry 50211 }


	iqudc30AudioControlCh1GainPair7L OBJECT-TYPE
		SYNTAX		INTEGER
		MAX-ACCESS		read-write
		STATUS			current
		DESCRIPTION
				"TYPE: - Number
				 PAGE: - Audio Control-Ch1
					Pair 7 L  cmdID= 50238  min= -180  max= 180  step= 1  format= %0.1fdB  div_scale= 10 
					Min = -18.0dB  Max = 18.0dB  Step = 0.1dB "
		::= { iqudc30CmdEntry 50238 }


	iqudc30AudioControlCh1GainPair7R OBJECT-TYPE
		SYNTAX		INTEGER
		MAX-ACCESS		read-write
		STATUS			current
		DESCRIPTION
				"TYPE: - Number
				 PAGE: - Audio Control-Ch1
					Pair 7 R  cmdID= 50239  min= -180  max= 180  step= 1  format= %0.1fdB  div_scale= 10 
					Min = -18.0dB  Max = 18.0dB  Step = 0.1dB "
		::= { iqudc30CmdEntry 50239 }


	iqudc30AudioControlCh1GainPair8L OBJECT-TYPE
		SYNTAX		INTEGER
		MAX-ACCESS		read-write
		STATUS			current
		DESCRIPTION
				"TYPE: - Number
				 PAGE: - Audio Control-Ch1
					Pair 8 L  cmdID= 50240  min= -180  max= 180  step= 1  format= %0.1fdB  div_scale= 10 
					Min = -18.0dB  Max = 18.0dB  Step = 0.1dB "
		::= { iqudc30CmdEntry 50240 }


	iqudc30AudioControlCh1GainPair8R OBJECT-TYPE
		SYNTAX		INTEGER
		MAX-ACCESS		read-write
		STATUS			current
		DESCRIPTION
				"TYPE: - Number
				 PAGE: - Audio Control-Ch1
					Pair 8 R  cmdID= 50241  min= -180  max= 180  step= 1  format= %0.1fdB  div_scale= 10 
					Min = -18.0dB  Max = 18.0dB  Step = 0.1dB "
		::= { iqudc30CmdEntry 50241 }


	iqudc30MenuAudioControlCh1ToneFrequency OBJECT-TYPE
		SYNTAX		INTEGER
		MAX-ACCESS		read-write
		STATUS			current
		DESCRIPTION
				"TYPE: - Number
				 PAGE: - Audio Control-Ch1
					Tone Frequency  cmdID= 50500  min= 100  max= 10000  step= 100  format= %0.1f KHz  div_scale= 1000 
					Min = 0.1 KHz  Max = 10.0 KHz  Step = 0.1 KHz "
		::= { iqudc30CmdEntry 50500 }


	iqudc30MenuAudioControlCh1DolbyEAlignmentO OBJECT-TYPE
		SYNTAX		INTEGER
		MAX-ACCESS		read-write
		STATUS			current
		DESCRIPTION
				"TYPE: - Number
				 PAGE: - Audio Control-Ch1
					Dolby E Alignment O  cmdID= 50502  min= -10  max= 10  step= 1  format= %0.0f Lines  div_scale= 1 
					Min = -10 Lines  Max = 10 Lines  Step = 1 Lines "
		::= { iqudc30CmdEntry 50502 }


	iqudc30DelayGlobalDelayPairOPair150319 OBJECT-TYPE
		SYNTAX		INTEGER
		MAX-ACCESS		read-write
		STATUS			current
		DESCRIPTION
				"TYPE: - Number
				 PAGE: - Audio Control-Ch1
					Pair 1  cmdID= 50319  min= -40  max= 200  step= 1  format= %0.0f ms  div_scale= 1 
					Min = -40 ms  Max = 200 ms  Step = 1 ms "
		::= { iqudc30CmdEntry 50319 }


	iqudc30DelayGlobalDelayPairOPair1Total50327 OBJECT-TYPE
		SYNTAX		RollCallString
		MAX-ACCESS		read-only
		STATUS			current
		DESCRIPTION
				"TYPE: - Display
				 PAGE: - Audio Control-Ch1
					Pair 1 Total  cmdID= 50327  format=   "
		::= { iqudc30CmdEntry 50327 }


	iqudc30DelayGlobalDelayPairOPair250320 OBJECT-TYPE
		SYNTAX		INTEGER
		MAX-ACCESS		read-write
		STATUS			current
		DESCRIPTION
				"TYPE: - Number
				 PAGE: - Audio Control-Ch1
					Pair 2  cmdID= 50320  min= -40  max= 200  step= 1  format= %0.0f ms  div_scale= 1 
					Min = -40 ms  Max = 200 ms  Step = 1 ms "
		::= { iqudc30CmdEntry 50320 }


	iqudc30DelayGlobalDelayPairOPair2Total50328 OBJECT-TYPE
		SYNTAX		RollCallString
		MAX-ACCESS		read-only
		STATUS			current
		DESCRIPTION
				"TYPE: - Display
				 PAGE: - Audio Control-Ch1
					Pair 2 Total  cmdID= 50328  format=   "
		::= { iqudc30CmdEntry 50328 }


	iqudc30DelayGlobalDelayPairOPair350321 OBJECT-TYPE
		SYNTAX		INTEGER
		MAX-ACCESS		read-write
		STATUS			current
		DESCRIPTION
				"TYPE: - Number
				 PAGE: - Audio Control-Ch1
					Pair 3  cmdID= 50321  min= -40  max= 200  step= 1  format= %0.0f ms  div_scale= 1 
					Min = -40 ms  Max = 200 ms  Step = 1 ms "
		::= { iqudc30CmdEntry 50321 }


	iqudc30DelayGlobalDelayPairOPair3Total50329 OBJECT-TYPE
		SYNTAX		RollCallString
		MAX-ACCESS		read-only
		STATUS			current
		DESCRIPTION
				"TYPE: - Display
				 PAGE: - Audio Control-Ch1
					Pair 3 Total  cmdID= 50329  format=   "
		::= { iqudc30CmdEntry 50329 }


	iqudc30DelayGlobalDelayPairOPair450322 OBJECT-TYPE
		SYNTAX		INTEGER
		MAX-ACCESS		read-write
		STATUS			current
		DESCRIPTION
				"TYPE: - Number
				 PAGE: - Audio Control-Ch1
					Pair 4  cmdID= 50322  min= -40  max= 200  step= 1  format= %0.0f ms  div_scale= 1 
					Min = -40 ms  Max = 200 ms  Step = 1 ms "
		::= { iqudc30CmdEntry 50322 }


	iqudc30DelayGlobalDelayPairOPair4Total50330 OBJECT-TYPE
		SYNTAX		RollCallString
		MAX-ACCESS		read-only
		STATUS			current
		DESCRIPTION
				"TYPE: - Display
				 PAGE: - Audio Control-Ch1
					Pair 4 Total  cmdID= 50330  format=   "
		::= { iqudc30CmdEntry 50330 }


	iqudc30DelayGlobalDelayPairOPair550323 OBJECT-TYPE
		SYNTAX		INTEGER
		MAX-ACCESS		read-write
		STATUS			current
		DESCRIPTION
				"TYPE: - Number
				 PAGE: - Audio Control-Ch1
					Pair 5  cmdID= 50323  min= -40  max= 200  step= 1  format= %0.0f ms  div_scale= 1 
					Min = -40 ms  Max = 200 ms  Step = 1 ms "
		::= { iqudc30CmdEntry 50323 }


	iqudc30DelayGlobalDelayPairOPair5Total50331 OBJECT-TYPE
		SYNTAX		RollCallString
		MAX-ACCESS		read-only
		STATUS			current
		DESCRIPTION
				"TYPE: - Display
				 PAGE: - Audio Control-Ch1
					Pair 5 Total  cmdID= 50331  format=   "
		::= { iqudc30CmdEntry 50331 }


	iqudc30DelayGlobalDelayPairOPair650324 OBJECT-TYPE
		SYNTAX		INTEGER
		MAX-ACCESS		read-write
		STATUS			current
		DESCRIPTION
				"TYPE: - Number
				 PAGE: - Audio Control-Ch1
					Pair 6  cmdID= 50324  min= -40  max= 200  step= 1  format= %0.0f ms  div_scale= 1 
					Min = -40 ms  Max = 200 ms  Step = 1 ms "
		::= { iqudc30CmdEntry 50324 }


	iqudc30DelayGlobalDelayPairOPair6Total50332 OBJECT-TYPE
		SYNTAX		RollCallString
		MAX-ACCESS		read-only
		STATUS			current
		DESCRIPTION
				"TYPE: - Display
				 PAGE: - Audio Control-Ch1
					Pair 6 Total  cmdID= 50332  format=   "
		::= { iqudc30CmdEntry 50332 }


	iqudc30DelayGlobalDelayPairOPair750325 OBJECT-TYPE
		SYNTAX		INTEGER
		MAX-ACCESS		read-write
		STATUS			current
		DESCRIPTION
				"TYPE: - Number
				 PAGE: - Audio Control-Ch1
					Pair 7  cmdID= 50325  min= -40  max= 200  step= 1  format= %0.0f ms  div_scale= 1 
					Min = -40 ms  Max = 200 ms  Step = 1 ms "
		::= { iqudc30CmdEntry 50325 }


	iqudc30DelayGlobalDelayPairOPair7Total50333 OBJECT-TYPE
		SYNTAX		RollCallString
		MAX-ACCESS		read-only
		STATUS			current
		DESCRIPTION
				"TYPE: - Display
				 PAGE: - Audio Control-Ch1
					Pair 7 Total  cmdID= 50333  format=   "
		::= { iqudc30CmdEntry 50333 }


	iqudc30DelayGlobalDelayPairOPair850326 OBJECT-TYPE
		SYNTAX		INTEGER
		MAX-ACCESS		read-write
		STATUS			current
		DESCRIPTION
				"TYPE: - Number
				 PAGE: - Audio Control-Ch1
					Pair 8  cmdID= 50326  min= -40  max= 200  step= 1  format= %0.0f ms  div_scale= 1 
					Min = -40 ms  Max = 200 ms  Step = 1 ms "
		::= { iqudc30CmdEntry 50326 }


	iqudc30DelayGlobalDelayPairOPair8Total50334 OBJECT-TYPE
		SYNTAX		RollCallString
		MAX-ACCESS		read-only
		STATUS			current
		DESCRIPTION
				"TYPE: - Display
				 PAGE: - Audio Control-Ch1
					Pair 8 Total  cmdID= 50334  format=   "
		::= { iqudc30CmdEntry 50334 }


	iqudc30AudioControlCh1GlobalDelayAudio OBJECT-TYPE
		SYNTAX		INTEGER
		MAX-ACCESS		read-write
		STATUS			current
		DESCRIPTION
				"TYPE: - Number
				 PAGE: - Audio Control-Ch1
					Audio  cmdID= 50316  min= -40  max= 200  step= 1  format= %0.0f ms  div_scale= 1 
					Min = -40 ms  Max = 200 ms  Step = 1 ms "
		::= { iqudc30CmdEntry 50316 }


	iqudc30AudioControlCh1GlobalDelayAudioTotal OBJECT-TYPE
		SYNTAX		RollCallString
		MAX-ACCESS		read-only
		STATUS			current
		DESCRIPTION
				"TYPE: - Display
				 PAGE: - Audio Control-Ch1
					Audio Total  cmdID= 50301  format=   "
		::= { iqudc30CmdEntry 50301 }


	iqudc30AudioControlCh1GlobalDelayVideoTotal OBJECT-TYPE
		SYNTAX		RollCallString
		MAX-ACCESS		read-only
		STATUS			current
		DESCRIPTION
				"TYPE: - Display
				 PAGE: - Audio Control-Ch1
					Video Total  cmdID= 50302  format=   "
		::= { iqudc30CmdEntry 50302 }


	iqudc30MenuAudioControlCh1NewDisplay OBJECT-TYPE
		SYNTAX		RollCallString
		MAX-ACCESS		read-only
		STATUS			current
		DESCRIPTION
				"TYPE: - Display
				 PAGE: - Audio Control-Ch1
					New Display  cmdID= 44462  format=   "
		::= { iqudc30CmdEntry 44462 }


	iqudc30AudioControlCh2GainPair1L OBJECT-TYPE
		SYNTAX		INTEGER
		MAX-ACCESS		read-write
		STATUS			current
		DESCRIPTION
				"TYPE: - Number
				 PAGE: - Audio Control-Ch2
					Pair 1 L  cmdID= 50300  min= -180  max= 180  step= 1  format= %0.1fdB  div_scale= 10 
					Min = -18.0dB  Max = 18.0dB  Step = 0.1dB "
		::= { iqudc30CmdEntry 50300 }


	iqudc30AudioControlCh2GainPair1R OBJECT-TYPE
		SYNTAX		INTEGER
		MAX-ACCESS		read-write
		STATUS			current
		DESCRIPTION
				"TYPE: - Number
				 PAGE: - Audio Control-Ch2
					Pair 1 R  cmdID= 50317  min= -180  max= 180  step= 1  format= %0.1fdB  div_scale= 10 
					Min = -18.0dB  Max = 18.0dB  Step = 0.1dB "
		::= { iqudc30CmdEntry 50317 }


	iqudc30AudioControlCh2GainPair2L OBJECT-TYPE
		SYNTAX		INTEGER
		MAX-ACCESS		read-write
		STATUS			current
		DESCRIPTION
				"TYPE: - Number
				 PAGE: - Audio Control-Ch2
					Pair 2 L  cmdID= 50318  min= -180  max= 180  step= 1  format= %0.1fdB  div_scale= 10 
					Min = -18.0dB  Max = 18.0dB  Step = 0.1dB "
		::= { iqudc30CmdEntry 50318 }


	iqudc30AudioControlCh2GainPair2R OBJECT-TYPE
		SYNTAX		INTEGER
		MAX-ACCESS		read-write
		STATUS			current
		DESCRIPTION
				"TYPE: - Number
				 PAGE: - Audio Control-Ch2
					Pair 2 R  cmdID= 50303  min= -180  max= 180  step= 1  format= %0.1fdB  div_scale= 10 
					Min = -18.0dB  Max = 18.0dB  Step = 0.1dB "
		::= { iqudc30CmdEntry 50303 }


	iqudc30AudioControlCh2GainPair3L OBJECT-TYPE
		SYNTAX		INTEGER
		MAX-ACCESS		read-write
		STATUS			current
		DESCRIPTION
				"TYPE: - Number
				 PAGE: - Audio Control-Ch2
					Pair 3 L  cmdID= 50304  min= -180  max= 180  step= 1  format= %0.1fdB  div_scale= 10 
					Min = -18.0dB  Max = 18.0dB  Step = 0.1dB "
		::= { iqudc30CmdEntry 50304 }


	iqudc30AudioControlCh2GainPair3R OBJECT-TYPE
		SYNTAX		INTEGER
		MAX-ACCESS		read-write
		STATUS			current
		DESCRIPTION
				"TYPE: - Number
				 PAGE: - Audio Control-Ch2
					Pair 3 R  cmdID= 50305  min= -180  max= 180  step= 1  format= %0.1fdB  div_scale= 10 
					Min = -18.0dB  Max = 18.0dB  Step = 0.1dB "
		::= { iqudc30CmdEntry 50305 }


	iqudc30AudioControlCh2GainPair4L OBJECT-TYPE
		SYNTAX		INTEGER
		MAX-ACCESS		read-write
		STATUS			current
		DESCRIPTION
				"TYPE: - Number
				 PAGE: - Audio Control-Ch2
					Pair 4 L  cmdID= 50306  min= -180  max= 180  step= 1  format= %0.1fdB  div_scale= 10 
					Min = -18.0dB  Max = 18.0dB  Step = 0.1dB "
		::= { iqudc30CmdEntry 50306 }


	iqudc30AudioControlCh2GainPair4R OBJECT-TYPE
		SYNTAX		INTEGER
		MAX-ACCESS		read-write
		STATUS			current
		DESCRIPTION
				"TYPE: - Number
				 PAGE: - Audio Control-Ch2
					Pair 4 R  cmdID= 50307  min= -180  max= 180  step= 1  format= %0.1fdB  div_scale= 10 
					Min = -18.0dB  Max = 18.0dB  Step = 0.1dB "
		::= { iqudc30CmdEntry 50307 }


	iqudc30AudioControlCh2GainPair5L OBJECT-TYPE
		SYNTAX		INTEGER
		MAX-ACCESS		read-write
		STATUS			current
		DESCRIPTION
				"TYPE: - Number
				 PAGE: - Audio Control-Ch2
					Pair 5 L  cmdID= 50308  min= -180  max= 180  step= 1  format= %0.1fdB  div_scale= 10 
					Min = -18.0dB  Max = 18.0dB  Step = 0.1dB "
		::= { iqudc30CmdEntry 50308 }


	iqudc30AudioControlCh2GainPair5R OBJECT-TYPE
		SYNTAX		INTEGER
		MAX-ACCESS		read-write
		STATUS			current
		DESCRIPTION
				"TYPE: - Number
				 PAGE: - Audio Control-Ch2
					Pair 5 R  cmdID= 50309  min= -180  max= 180  step= 1  format= %0.1fdB  div_scale= 10 
					Min = -18.0dB  Max = 18.0dB  Step = 0.1dB "
		::= { iqudc30CmdEntry 50309 }


	iqudc30AudioControlCh2GainPair6L OBJECT-TYPE
		SYNTAX		INTEGER
		MAX-ACCESS		read-write
		STATUS			current
		DESCRIPTION
				"TYPE: - Number
				 PAGE: - Audio Control-Ch2
					Pair 6 L  cmdID= 50310  min= -180  max= 180  step= 1  format= %0.1fdB  div_scale= 10 
					Min = -18.0dB  Max = 18.0dB  Step = 0.1dB "
		::= { iqudc30CmdEntry 50310 }


	iqudc30AudioControlCh2GainPair6R OBJECT-TYPE
		SYNTAX		INTEGER
		MAX-ACCESS		read-write
		STATUS			current
		DESCRIPTION
				"TYPE: - Number
				 PAGE: - Audio Control-Ch2
					Pair 6 R  cmdID= 50311  min= -180  max= 180  step= 1  format= %0.1fdB  div_scale= 10 
					Min = -18.0dB  Max = 18.0dB  Step = 0.1dB "
		::= { iqudc30CmdEntry 50311 }


	iqudc30AudioControlCh2GainPair7L OBJECT-TYPE
		SYNTAX		INTEGER
		MAX-ACCESS		read-write
		STATUS			current
		DESCRIPTION
				"TYPE: - Number
				 PAGE: - Audio Control-Ch2
					Pair 7 L  cmdID= 50312  min= -180  max= 180  step= 1  format= %0.1fdB  div_scale= 10 
					Min = -18.0dB  Max = 18.0dB  Step = 0.1dB "
		::= { iqudc30CmdEntry 50312 }


	iqudc30AudioControlCh2GainPair7R OBJECT-TYPE
		SYNTAX		INTEGER
		MAX-ACCESS		read-write
		STATUS			current
		DESCRIPTION
				"TYPE: - Number
				 PAGE: - Audio Control-Ch2
					Pair 7 R  cmdID= 50313  min= -180  max= 180  step= 1  format= %0.1fdB  div_scale= 10 
					Min = -18.0dB  Max = 18.0dB  Step = 0.1dB "
		::= { iqudc30CmdEntry 50313 }


	iqudc30AudioControlCh2GainPair8L OBJECT-TYPE
		SYNTAX		INTEGER
		MAX-ACCESS		read-write
		STATUS			current
		DESCRIPTION
				"TYPE: - Number
				 PAGE: - Audio Control-Ch2
					Pair 8 L  cmdID= 50314  min= -180  max= 180  step= 1  format= %0.1fdB  div_scale= 10 
					Min = -18.0dB  Max = 18.0dB  Step = 0.1dB "
		::= { iqudc30CmdEntry 50314 }


	iqudc30AudioControlCh2GainPair8R OBJECT-TYPE
		SYNTAX		INTEGER
		MAX-ACCESS		read-write
		STATUS			current
		DESCRIPTION
				"TYPE: - Number
				 PAGE: - Audio Control-Ch2
					Pair 8 R  cmdID= 50315  min= -180  max= 180  step= 1  format= %0.1fdB  div_scale= 10 
					Min = -18.0dB  Max = 18.0dB  Step = 0.1dB "
		::= { iqudc30CmdEntry 50315 }


	iqudc30MenuAudioControlCh2ToneFrequency OBJECT-TYPE
		SYNTAX		INTEGER
		MAX-ACCESS		read-write
		STATUS			current
		DESCRIPTION
				"TYPE: - Number
				 PAGE: - Audio Control-Ch2
					Tone Frequency  cmdID= 50600  min= 100  max= 10000  step= 100  format= %0.1f KHz  div_scale= 1000 
					Min = 0.1 KHz  Max = 10.0 KHz  Step = 0.1 KHz "
		::= { iqudc30CmdEntry 50600 }


	iqudc30MenuAudioControlCh2DolbyEAlignmentO OBJECT-TYPE
		SYNTAX		INTEGER
		MAX-ACCESS		read-write
		STATUS			current
		DESCRIPTION
				"TYPE: - Number
				 PAGE: - Audio Control-Ch2
					Dolby E Alignment O  cmdID= 50504  min= -10  max= 10  step= 1  format= %0.0f Lines  div_scale= 1 
					Min = -10 Lines  Max = 10 Lines  Step = 1 Lines "
		::= { iqudc30CmdEntry 50504 }


	iqudc30DelayGlobalDelayPairOPair150505 OBJECT-TYPE
		SYNTAX		INTEGER
		MAX-ACCESS		read-write
		STATUS			current
		DESCRIPTION
				"TYPE: - Number
				 PAGE: - Audio Control-Ch2
					Pair 1  cmdID= 50505  min= -40  max= 200  step= 1  format= %0.0f ms  div_scale= 1 
					Min = -40 ms  Max = 200 ms  Step = 1 ms "
		::= { iqudc30CmdEntry 50505 }


	iqudc30DelayGlobalDelayPairOPair1Total50513 OBJECT-TYPE
		SYNTAX		RollCallString
		MAX-ACCESS		read-only
		STATUS			current
		DESCRIPTION
				"TYPE: - Display
				 PAGE: - Audio Control-Ch2
					Pair 1 Total  cmdID= 50513  format=   "
		::= { iqudc30CmdEntry 50513 }


	iqudc30DelayGlobalDelayPairOPair250506 OBJECT-TYPE
		SYNTAX		INTEGER
		MAX-ACCESS		read-write
		STATUS			current
		DESCRIPTION
				"TYPE: - Number
				 PAGE: - Audio Control-Ch2
					Pair 2  cmdID= 50506  min= -40  max= 200  step= 1  format= %0.0f ms  div_scale= 1 
					Min = -40 ms  Max = 200 ms  Step = 1 ms "
		::= { iqudc30CmdEntry 50506 }


	iqudc30DelayGlobalDelayPairOPair2Total50514 OBJECT-TYPE
		SYNTAX		RollCallString
		MAX-ACCESS		read-only
		STATUS			current
		DESCRIPTION
				"TYPE: - Display
				 PAGE: - Audio Control-Ch2
					Pair 2 Total  cmdID= 50514  format=   "
		::= { iqudc30CmdEntry 50514 }


	iqudc30DelayGlobalDelayPairOPair350507 OBJECT-TYPE
		SYNTAX		INTEGER
		MAX-ACCESS		read-write
		STATUS			current
		DESCRIPTION
				"TYPE: - Number
				 PAGE: - Audio Control-Ch2
					Pair 3  cmdID= 50507  min= -40  max= 200  step= 1  format= %0.0f ms  div_scale= 1 
					Min = -40 ms  Max = 200 ms  Step = 1 ms "
		::= { iqudc30CmdEntry 50507 }


	iqudc30DelayGlobalDelayPairOPair3Total50515 OBJECT-TYPE
		SYNTAX		RollCallString
		MAX-ACCESS		read-only
		STATUS			current
		DESCRIPTION
				"TYPE: - Display
				 PAGE: - Audio Control-Ch2
					Pair 3 Total  cmdID= 50515  format=   "
		::= { iqudc30CmdEntry 50515 }


	iqudc30DelayGlobalDelayPairOPair450508 OBJECT-TYPE
		SYNTAX		INTEGER
		MAX-ACCESS		read-write
		STATUS			current
		DESCRIPTION
				"TYPE: - Number
				 PAGE: - Audio Control-Ch2
					Pair 4  cmdID= 50508  min= -40  max= 200  step= 1  format= %0.0f ms  div_scale= 1 
					Min = -40 ms  Max = 200 ms  Step = 1 ms "
		::= { iqudc30CmdEntry 50508 }


	iqudc30DelayGlobalDelayPairOPair4Total50516 OBJECT-TYPE
		SYNTAX		RollCallString
		MAX-ACCESS		read-only
		STATUS			current
		DESCRIPTION
				"TYPE: - Display
				 PAGE: - Audio Control-Ch2
					Pair 4 Total  cmdID= 50516  format=   "
		::= { iqudc30CmdEntry 50516 }


	iqudc30DelayGlobalDelayPairOPair550509 OBJECT-TYPE
		SYNTAX		INTEGER
		MAX-ACCESS		read-write
		STATUS			current
		DESCRIPTION
				"TYPE: - Number
				 PAGE: - Audio Control-Ch2
					Pair 5  cmdID= 50509  min= -40  max= 200  step= 1  format= %0.0f ms  div_scale= 1 
					Min = -40 ms  Max = 200 ms  Step = 1 ms "
		::= { iqudc30CmdEntry 50509 }


	iqudc30DelayGlobalDelayPairOPair5Total50517 OBJECT-TYPE
		SYNTAX		RollCallString
		MAX-ACCESS		read-only
		STATUS			current
		DESCRIPTION
				"TYPE: - Display
				 PAGE: - Audio Control-Ch2
					Pair 5 Total  cmdID= 50517  format=   "
		::= { iqudc30CmdEntry 50517 }


	iqudc30DelayGlobalDelayPairOPair650510 OBJECT-TYPE
		SYNTAX		INTEGER
		MAX-ACCESS		read-write
		STATUS			current
		DESCRIPTION
				"TYPE: - Number
				 PAGE: - Audio Control-Ch2
					Pair 6  cmdID= 50510  min= -40  max= 200  step= 1  format= %0.0f ms  div_scale= 1 
					Min = -40 ms  Max = 200 ms  Step = 1 ms "
		::= { iqudc30CmdEntry 50510 }


	iqudc30DelayGlobalDelayPairOPair6Total50518 OBJECT-TYPE
		SYNTAX		RollCallString
		MAX-ACCESS		read-only
		STATUS			current
		DESCRIPTION
				"TYPE: - Display
				 PAGE: - Audio Control-Ch2
					Pair 6 Total  cmdID= 50518  format=   "
		::= { iqudc30CmdEntry 50518 }


	iqudc30DelayGlobalDelayPairOPair750511 OBJECT-TYPE
		SYNTAX		INTEGER
		MAX-ACCESS		read-write
		STATUS			current
		DESCRIPTION
				"TYPE: - Number
				 PAGE: - Audio Control-Ch2
					Pair 7  cmdID= 50511  min= -40  max= 200  step= 1  format= %0.0f ms  div_scale= 1 
					Min = -40 ms  Max = 200 ms  Step = 1 ms "
		::= { iqudc30CmdEntry 50511 }


	iqudc30DelayGlobalDelayPairOPair7Total50519 OBJECT-TYPE
		SYNTAX		RollCallString
		MAX-ACCESS		read-only
		STATUS			current
		DESCRIPTION
				"TYPE: - Display
				 PAGE: - Audio Control-Ch2
					Pair 7 Total  cmdID= 50519  format=   "
		::= { iqudc30CmdEntry 50519 }


	iqudc30DelayGlobalDelayPairOPair850512 OBJECT-TYPE
		SYNTAX		INTEGER
		MAX-ACCESS		read-write
		STATUS			current
		DESCRIPTION
				"TYPE: - Number
				 PAGE: - Audio Control-Ch2
					Pair 8  cmdID= 50512  min= -40  max= 200  step= 1  format= %0.0f ms  div_scale= 1 
					Min = -40 ms  Max = 200 ms  Step = 1 ms "
		::= { iqudc30CmdEntry 50512 }


	iqudc30DelayGlobalDelayPairOPair8Total50520 OBJECT-TYPE
		SYNTAX		RollCallString
		MAX-ACCESS		read-only
		STATUS			current
		DESCRIPTION
				"TYPE: - Display
				 PAGE: - Audio Control-Ch2
					Pair 8 Total  cmdID= 50520  format=   "
		::= { iqudc30CmdEntry 50520 }


	iqudc30AudioControlCh2GlobalDelay OBJECT-TYPE
		SYNTAX		INTEGER
		MAX-ACCESS		read-write
		STATUS			current
		DESCRIPTION
				"TYPE: - Number
				 PAGE: - Audio Control-Ch2
					Global  cmdID= 50400  min= -40  max= 200  step= 1  format= %0.0f ms  div_scale= 1 
					Min = -40 ms  Max = 200 ms  Step = 1 ms "
		::= { iqudc30CmdEntry 50400 }


	iqudc30AudioControlCh2GlobalDelayGlobalTotal OBJECT-TYPE
		SYNTAX		RollCallString
		MAX-ACCESS		read-only
		STATUS			current
		DESCRIPTION
				"TYPE: - Display
				 PAGE: - Audio Control-Ch2
					Global Total  cmdID= 50401  format=   "
		::= { iqudc30CmdEntry 50401 }


	iqudc30AudioControlCh2GlobalDelayVideoTotal OBJECT-TYPE
		SYNTAX		RollCallString
		MAX-ACCESS		read-only
		STATUS			current
		DESCRIPTION
				"TYPE: - Display
				 PAGE: - Audio Control-Ch2
					Video Total  cmdID= 50402  format=   "
		::= { iqudc30CmdEntry 50402 }


	iqudc30MenuAudioControlCh2NewDisplay OBJECT-TYPE
		SYNTAX		RollCallString
		MAX-ACCESS		read-only
		STATUS			current
		DESCRIPTION
				"TYPE: - Display
				 PAGE: - Audio Control-Ch2
					New Display  cmdID= 44458  format=   "
		::= { iqudc30CmdEntry 44458 }


	iqudc30AudioIOAESAESOutput14AES1 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 1  cmdID= 40400 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40400 }


	iqudc30MenuAudioIOAESAES2 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 2  cmdID= 40401 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40401 }


	iqudc30MenuAudioIOAESAES3 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 3  cmdID= 40402 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40402 }


	iqudc30MenuAudioIOAESAES4 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 4  cmdID= 40403 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40403 }


	iqudc30AudioIOAESAESOutput58AES5 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 5  cmdID= 40404 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40404 }


	iqudc30MenuAudioIOAESAES6 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 6  cmdID= 40405 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40405 }


	iqudc30MenuAudioIOAESAES7 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 7  cmdID= 40406 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40406 }


	iqudc30MenuAudioIOAESAES8 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 8  cmdID= 40407 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc30CmdEntry 40407 }


	iqudc30MenuAudioIOAESNewDisplay OBJECT-TYPE
		SYNTAX		RollCallString
		MAX-ACCESS		read-only
		STATUS			current
		DESCRIPTION
				"TYPE: - Display
				 PAGE: - Audio I/O AES
					New Display  cmdID= 40005  format=   "
		::= { iqudc30CmdEntry 40005 }


	iqudc30AudioIOAnalogAnalogOutput12Analog1 OBJECT-TYPE
		SYNTAX		INTEGER {
							val-Ch-1-Pair-1(0),
							val-Ch-1-Pair-2(1),
							val-Ch-1-Pair-3(2),
							val-Ch-1-Pair-4(3),
							val-Ch-1-Pair-5(4),
							val-Ch-1-Pair-6(5),
							val-Ch-1-Pair-7(6),
							val-Ch-1-Pair-8(7),
							val-Ch-2-Pair-1(8),
							val-Ch-2-Pair-2(9),
							val-Ch-2-Pair-3(10),
							val-Ch-2-Pair-4(11),
							val-Ch-2-Pair-5(12),
							val-Ch-2-Pair-6(13),
							val-Ch-2-Pair-7(14),
							val-Ch-2-Pair-8(15)
							}
		MAX-ACCESS		read-write
		STATUS			current
		DESCRIPTION
				"TYPE: - RadiobuttonList
				 PAGE: - Audio I/O Analog
					Analog 1  cmdID= 40410 
					Ch 1 Pair 1  value= 0  
					Ch 1 Pair 2  value= 1  
					Ch 1 Pair 3  value= 2  
					Ch 1 Pair 4  value= 3  
					Ch 1 Pair 5  value= 4  
					Ch 1 Pair 6  value= 5  
					Ch 1 Pair 7  value= 6  
					Ch 1 Pair 8  value= 7  
					Ch 2 Pair 1  value= 8  
					Ch 2 Pair 2  value= 9  
					Ch 2 Pair 3  value= 10  
					Ch 2 Pair 4  value= 11  
					Ch 2 Pair 5  value= 12  
					Ch 2 Pair 6  value= 13  
					Ch 2 Pair 7  value= 14  
					Ch 2 Pair 8  value= 15  "
		::= { iqudc30CmdEntry 40410 }


	iqudc30MenuAudioIOAnalogAnalog2 OBJECT-TYPE
		SYNTAX		INTEGER {
							val-Ch-1-Pair-1(0),
							val-Ch-1-Pair-2(1),
							val-Ch-1-Pair-3(2),
							val-Ch-1-Pair-4(3),
							val-Ch-1-Pair-5(4),
							val-Ch-1-Pair-6(5),
							val-Ch-1-Pair-7(6),
							val-Ch-1-Pair-8(7),
							val-Ch-2-Pair-1(8),
							val-Ch-2-Pair-2(9),
							val-Ch-2-Pair-3(10),
							val-Ch-2-Pair-4(11),
							val-Ch-2-Pair-5(12),
							val-Ch-2-Pair-6(13),
							val-Ch-2-Pair-7(14),
							val-Ch-2-Pair-8(15)
							}
		MAX-ACCESS		read-write
		STATUS			current
		DESCRIPTION
				"TYPE: - RadiobuttonList
				 PAGE: - Audio I/O Analog
					Analog 2  cmdID= 40411 
					Ch 1 Pair 1  value= 0  
					Ch 1 Pair 2  value= 1  
					Ch 1 Pair 3  value= 2  
					Ch 1 Pair 4  value= 3  
					Ch 1 Pair 5  value= 4  
					Ch 1 Pair 6  value= 5  
					Ch 1 Pair 7  value= 6  
					Ch 1 Pair 8  value= 7  
					Ch 2 Pair 1  value= 8  
					Ch 2 Pair 2  value= 9  
					Ch 2 Pair 3  value= 10  
					Ch 2 Pair 4  value= 11  
					Ch 2 Pair 5  value= 12  
					Ch 2 Pair 6  value= 13  
					Ch 2 Pair 7  value= 14  
					Ch 2 Pair 8  value= 15  "
		::= { iqudc30CmdEntry 40411 }


	iqudc30InputAnalogInADCHeadrPair1 OBJECT-TYPE
		SYNTAX		INTEGER
		MAX-ACCESS		read-write
		STATUS			current
		DESCRIPTION
				"TYPE: - Number
				 PAGE: - Audio I/O Analog
					Pair 1  cmdID= 40000  min= 24  max= 48  step= 1  format= %d  div_scale= 2 
					Min = 12  Max = 24  Step = 0 "
		::= { iqudc30CmdEntry 40000 }


	iqudc30InputAnalogInADCHeadrPair2 OBJECT-TYPE
		SYNTAX		INTEGER
		MAX-ACCESS		read-write
		STATUS			current
		DESCRIPTION
				"TYPE: - Number
				 PAGE: - Audio I/O Analog
					Pair 2  cmdID= 40001  min= 24  max= 48  step= 1  format= %d  div_scale= 2 
					Min = 12  Max = 24  Step = 0 "
		::= { iqudc30CmdEntry 40001 }


	iqudc30OutputAnalogOutDACLevePair1 OBJECT-TYPE
		SYNTAX		INTEGER
		MAX-ACCESS		read-write
		STATUS			current
		DESCRIPTION
				"TYPE: - Number
				 PAGE: - Audio I/O Analog
					Pair 1  cmdID= 40200  min= 24  max= 48  step= 1  format= %d  div_scale= 2 
					Min = 12  Max = 24  Step = 0 "
		::= { iqudc30CmdEntry 40200 }


	iqudc30OutputAnalogOutDACLevePair2 OBJECT-TYPE
		SYNTAX		INTEGER
		MAX-ACCESS		read-write
		STATUS			current
		DESCRIPTION
				"TYPE: - Number
				 PAGE: - Audio I/O Analog
					Pair 2  cmdID= 40201  min= 24  max= 48  step= 1  format= %d  div_scale= 2 
					Min = 12  Max = 24  Step = 0 "
		::= { iqudc30CmdEntry 40201 }


	iqudc30MenuAudioIOAnalogNewDisplay OBJECT-TYPE
		SYNTAX		RollCallString
		MAX-ACCESS		read-only
		STATUS			current
		DESCRIPTION
				"TYPE: - Display
				 PAGE: - Audio I/O Analog
					New Display  cmdID= 40004  format=   "
		::= { iqudc30CmdEntry 40004 }


	iqudc30DolbySetupDolbyCh1Mode OBJECT-TYPE
		SYNTAX		INTEGER {
							val-Decode(0),
							val-Encode(1),
							val-Transcode(2)
							}
		MAX-ACCESS		read-write
		STATUS			current
		DESCRIPTION
				"TYPE: - RadiobuttonList
				 PAGE: - Dolby Setup
					Mode  cmdID= 40529 
					Decode  value= 0  
					Encode  value= 1  
					Transcode  value= 2  "
		::= { iqudc30CmdEntry 40529 }


	iqudc30DolbySetupDolbyCh1DolbyEDelayCompen OBJECT-TYPE
		SYNTAX		INTEGER {
							val-Early-Early(0),
							val-Early-Normal(1),
							val-Early-Late(2),
							val-Normal-Normal(3),
							val-Normal-Late(4),
							val-Late-Late(5)
							}
		MAX-ACCESS		read-write
		STATUS			current
		DESCRIPTION
				"TYPE: - RadiobuttonList
				 PAGE: - Dolby Setup
					DolbyE Delay Compen  cmdID= 40507 
					Early > Early  value= 0  
					Early > Normal  value= 1  
					Early > Late  value= 2  
					Normal > Normal  value= 3  
					Normal > Late  value= 4  
					Late > Late  value= 5  "
		::= { iqudc30CmdEntry 40507 }


	iqudc30DolbySetupDolbyCh1MetadataSource OBJECT-TYPE
		SYNTAX		INTEGER {
							val-Dolby-Decoder(0),
							val-SMPTE-2020(1)
							}
		MAX-ACCESS		read-write
		STATUS			current
		DESCRIPTION
				"TYPE: - RadiobuttonList
				 PAGE: - Dolby Setup
					Metadata Source  cmdID= 40506 
					Dolby Decoder  value= 0  
					SMPTE 2020  value= 1  "
		::= { iqudc30CmdEntry 40506 }


	iqudc30DolbyCh1SMPTE2020OutputOutputLine OBJECT-TYPE
		SYNTAX		INTEGER
		MAX-ACCESS		read-write
		STATUS			current
		DESCRIPTION
				"TYPE: - Number
				 PAGE: - Dolby Setup
					Output Line  cmdID= 40510  min= 8  max= 20  step= 1  format= %0.0f  div_scale= 1 
					Min = 8  Max = 20  Step = 1 "
		::= { iqudc30CmdEntry 40510 }


	iqudc30DolbyCh1SMPTE2020OutputOutputEnable OBJECT-TYPE
		SYNTAX		INTEGER { disable(0), enable(1) }
		MAX-ACCESS		read-write
		STATUS			current
		DESCRIPTION
				"TYPE: - Checkbox
				 PAGE: - Dolby Setup
					Output Enable  cmdID= 40509 "
		::= { iqudc30CmdEntry 40509 }


	iqudc30DolbySetupDolbyCh1DecoderSource OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Decoder Source  cmdID= 40500 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc30CmdEntry 40500 }


	iqudc30MenuDolbySetupEncoderSource1 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 1  cmdID= 40520 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc30CmdEntry 40520 }


	iqudc30MenuDolbySetupEncoderSource2 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 2  cmdID= 40521 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc30CmdEntry 40521 }


	iqudc30MenuDolbySetupEncoderSource3 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 3  cmdID= 40522 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc30CmdEntry 40522 }


	iqudc30MenuDolbySetupEncoderSource4 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 4  cmdID= 40523 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc30CmdEntry 40523 }


	iqudc30MenuDolbySetupEncoderFormat OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Format  cmdID= 40524 
					1  value= 0  
					2  value= 1  
					3  value= 2  
					4  value= 3  
					5  value= 4  
					6  value= 5  
					7  value= 6  
					8  value= 7  "
		::= { iqudc30CmdEntry 40524 }


	iqudc30MenuDolbySetupEncoderFormatED OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Format E D  cmdID= 40525 
					1  value= 0  
					2  value= 1  
					3  value= 2  
					4  value= 3  
					5  value= 4  
					6  value= 5  
					7  value= 6  
					8  value= 7  "
		::= { iqudc30CmdEntry 40525 }


	iqudc30MenuDolbySetupEncoderRate OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Rate  cmdID= 40526 
					1  value= 0  
					2  value= 1  
					3  value= 2  
					4  value= 3  
					5  value= 4  
					6  value= 5  
					7  value= 6  
					8  value= 7  "
		::= { iqudc30CmdEntry 40526 }


	iqudc30MenuDolbySetupEncoderBitDepth OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Bit Depth  cmdID= 40527 
					1  value= 0  
					2  value= 1  
					3  value= 2  
					4  value= 3  
					5  value= 4  
					6  value= 5  
					7  value= 6  
					8  value= 7  "
		::= { iqudc30CmdEntry 40527 }


	iqudc30MenuDolbySetupEncoderConfig OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Config  cmdID= 40528 
					1  value= 0  
					2  value= 1  
					3  value= 2  
					4  value= 3  
					5  value= 4  
					6  value= 5  
					7  value= 6  
					8  value= 7  "
		::= { iqudc30CmdEntry 40528 }


	iqudc30MenuDolbySetupInputStatus OBJECT-TYPE
		SYNTAX		RollCallString
		MAX-ACCESS		read-only
		STATUS			current
		DESCRIPTION
				"TYPE: - Display
				 PAGE: - Dolby Setup
					Input Status  cmdID= 40501  format=   "
		::= { iqudc30CmdEntry 40501 }


	iqudc30MenuDolbySetupDecoderRate OBJECT-TYPE
		SYNTAX		RollCallString
		MAX-ACCESS		read-only
		STATUS			current
		DESCRIPTION
				"TYPE: - Display
				 PAGE: - Dolby Setup
					Decoder Rate  cmdID= 40503  format=   "
		::= { iqudc30CmdEntry 40503 }


	iqudc30MenuDolbySetupDecoderFormat OBJECT-TYPE
		SYNTAX		RollCallString
		MAX-ACCESS		read-only
		STATUS			current
		DESCRIPTION
				"TYPE: - Display
				 PAGE: - Dolby Setup
					Decoder Format  cmdID= 40502  format=   "
		::= { iqudc30CmdEntry 40502 }


	iqudc30MenuDolbySetupDecoderVersion OBJECT-TYPE
		SYNTAX		RollCallString
		MAX-ACCESS		read-only
		STATUS			current
		DESCRIPTION
				"TYPE: - Display
				 PAGE: - Dolby Setup
					Decoder Version  cmdID= 40504  format=   "
		::= { iqudc30CmdEntry 40504 }


	iqudc30MenuDolbySetupEncoderVersion OBJECT-TYPE
		SYNTAX		RollCallString
		MAX-ACCESS		read-only
		STATUS			current
		DESCRIPTION
				"TYPE: - Display
				 PAGE: - Dolby Setup
					Encoder Version  cmdID= 40508  format=   "
		::= { iqudc30CmdEntry 40508 }


	iqudc30MenuDolbySetupNewDisplay OBJECT-TYPE
		SYNTAX		RollCallString
		MAX-ACCESS		read-only
		STATUS			current
		DESCRIPTION
				"TYPE: - Display
				 PAGE: - Dolby Setup
					New Display  cmdID= 44467  format=   "
		::= { iqudc30CmdEntry 44467 }


	iqudc30MenuGenlockSourceCh12 OBJECT-TYPE
		SYNTAX		INTEGER {
							val-Module-Reference(0),
							val-Chassis-Reference-A(1),
							val-Chassis-Reference-B(2),
							val-Ch-1-Input(3),
							val-Ch-2-Input(4),
							val-Free-Run(5)
							}
		MAX-ACCESS		read-write
		STATUS			current
		DESCRIPTION
				"TYPE: - RadiobuttonList
				 PAGE: - Genlock
					Source Ch 1 & 2  cmdID= 30000 
					Module Reference  value= 0  
					Chassis Reference A  value= 1  
					Chassis Reference B  value= 2  
					Ch 1 Input  value= 3  
					Ch 2 Input  value= 4  
					Free Run  value= 5  "
		::= { iqudc30CmdEntry 30000 }


	iqudc30GenlockTimingCh1VerticalTiming OBJECT-TYPE
		SYNTAX		INTEGER
		MAX-ACCESS		read-write
		STATUS			current
		DESCRIPTION
				"TYPE: - Number
				 PAGE: - Genlock
					Vertical Timing  cmdID= 30010  min= -1125  max= 1125  step= 1  format= %0.0f lines  div_scale= 1 
					Min = -1125 lines  Max = 1125 lines  Step = 1 lines "
		::= { iqudc30CmdEntry 30010 }


	iqudc30GenlockTimingCh1HorizontalTiming OBJECT-TYPE
		SYNTAX		INTEGER
		MAX-ACCESS		read-write
		STATUS			current
		DESCRIPTION
				"TYPE: - Number
				 PAGE: - Genlock
					Horizontal Timing  cmdID= 30011  min= -2640  max= 2640  step= 1  format= %0.0f pixels  div_scale= 1 
					Min = -2640 pixels  Max = 2640 pixels  Step = 1 pixels "
		::= { iqudc30CmdEntry 30011 }


	iqudc30GenlockTimingCh1Status OBJECT-TYPE
		SYNTAX		RollCallString
		MAX-ACCESS		read-only
		STATUS			current
		DESCRIPTION
				"TYPE: - Display
				 PAGE: - Genlock
					Status  cmdID= 61006  format=   "
		::= { iqudc30CmdEntry 61006 }


	iqudc30GenlockTimingCh2VerticalTiming OBJECT-TYPE
		SYNTAX		INTEGER
		MAX-ACCESS		read-write
		STATUS			current
		DESCRIPTION
				"TYPE: - Number
				 PAGE: - Genlock
					Vertical Timing  cmdID= 30012  min= -1125  max= 1125  step= 1  format= %0.0f lines  div_scale= 1 
					Min = -1125 lines  Max = 1125 lines  Step = 1 lines "
		::= { iqudc30CmdEntry 30012 }


	iqudc30GenlockTimingCh2HorizontalTiming OBJECT-TYPE
		SYNTAX		INTEGER
		MAX-ACCESS		read-write
		STATUS			current
		DESCRIPTION
				"TYPE: - Number
				 PAGE: - Genlock
					Horizontal Timing  cmdID= 30013  min= -2640  max= 2640  step= 1  format= %0.0f pixels  div_scale= 1 
					Min = -2640 pixels  Max = 2640 pixels  Step = 1 pixels "
		::= { iqudc30CmdEntry 30013 }


	iqudc30GenlockTimingCh2Status OBJECT-TYPE
		SYNTAX		RollCallString
		MAX-ACCESS		read-only
		STATUS			current
		DESCRIPTION
				"TYPE: - Display
				 PAGE: - Genlock
					Status  cmdID= 61007  format=   "
		::= { iqudc30CmdEntry 61007 }


	iqudc30MenuTimecodeCh1SourceHD OBJECT-TYPE
		SYNTAX		INTEGER {
							val-LTC(0),
							val-VITC(1)
							}
		MAX-ACCESS		read-write
		STATUS			current
		DESCRIPTION
				"TYPE: - RadiobuttonList
				 PAGE: - Timecode-Ch1
					Source (HD)  cmdID= 60100 
					LTC  value= 0  
					VITC  value= 1  "
		::= { iqudc30CmdEntry 60100 }


	iqudc30MenuTimecodeCh1SourceSD OBJECT-TYPE
		SYNTAX		INTEGER {
							val-VITC(0),
							val-ATC-LTC(1),
							val-ATC-VITC(2)
							}
		MAX-ACCESS		read-write
		STATUS			current
		DESCRIPTION
				"TYPE: - RadiobuttonList
				 PAGE: - Timecode-Ch1
					Source (SD)  cmdID= 60101 
					VITC  value= 0  
					ATC LTC  value= 1  
					ATC VITC  value= 2  "
		::= { iqudc30CmdEntry 60101 }


	iqudc30MenuTimecodeCh1Status OBJECT-TYPE
		SYNTAX		RollCallString
		MAX-ACCESS		read-only
		STATUS			current
		DESCRIPTION
				"TYPE: - Display
				 PAGE: - Timecode-Ch1
					Status  cmdID= 60112  format=   "
		::= { iqudc30CmdEntry 60112 }


	iqudc30MenuTimecodeCh1Mode OBJECT-TYPE
		SYNTAX		INTEGER {
							val-Follow-Input(0),
							val-Generate(1)
							}
		MAX-ACCESS		read-write
		STATUS			current
		DESCRIPTION
				"TYPE: - RadiobuttonList
				 PAGE: - Timecode-Ch1
					Mode  cmdID= 60102 
					Follow Input  value= 0  
					Generate  value= 1  "
		::= { iqudc30CmdEntry 60102 }


	iqudc30MenuTimecodeCh1OnTimecodeLoss OBJECT-TYPE
		SYNTAX		INTEGER {
							val-Freeze(0),
							val-Free-Run(1)
							}
		MAX-ACCESS		read-write
		STATUS			current
		DESCRIPTION
				"TYPE: - RadiobuttonList
				 PAGE: - Timecode-Ch1
					On Timecode Loss  cmdID= 60107 
					Freeze  value= 0  
					Free Run  value= 1  "
		::= { iqudc30CmdEntry 60107 }


	iqudc30MenuTimecodeCh1TimecodeEntry OBJECT-TYPE
		SYNTAX		RollCallString
		MAX-ACCESS		read-write
		STATUS			current
		DESCRIPTION
				"TYPE: - Editstring
				 PAGE: - Timecode-Ch1
					Timecode Entry  cmdID= 60110  "
		::= { iqudc30CmdEntry 60110 }


	iqudc30MenuTimecodeCh1TimecodeLoad OBJECT-TYPE
		SYNTAX		INTEGER { noAction(0),val-Timecode-Load(1) }
		MAX-ACCESS		read-write
		STATUS			current
		DESCRIPTION
				"TYPE: - Button
				 PAGE: - Timecode-Ch1
					Timecode Load  cmdID= 60113  value= 1  "
		::= { iqudc30CmdEntry 60113 }


	iqudc30MenuTimecodeCh1NondropFrame OBJECT-TYPE
		SYNTAX		INTEGER { disable(0), enable(1) }
		MAX-ACCESS		read-write
		STATUS			current
		DESCRIPTION
				"TYPE: - Checkbox
				 PAGE: - Timecode-Ch1
					Non-drop Frame  cmdID= 60109 "
		::= { iqudc30CmdEntry 60109 }


	iqudc30MenuTimecodeCh1VITCEnable OBJECT-TYPE
		SYNTAX		INTEGER { disable(0), enable(1) }
		MAX-ACCESS		read-write
		STATUS			current
		DESCRIPTION
				"TYPE: - Checkbox
				 PAGE: - Timecode-Ch1
					VITC Enable  cmdID= 60111 "
		::= { iqudc30CmdEntry 60111 }


	iqudc30MenuTimecodeCh1OutputLine525 OBJECT-TYPE
		SYNTAX		INTEGER
		MAX-ACCESS		read-write
		STATUS			current
		DESCRIPTION
				"TYPE: - Number
				 PAGE: - Timecode-Ch1
					Output Line (525)  cmdID= 60103  min= 11  max= 17  step= 1  format= %0.0f  div_scale= 1 
					Min = 11  Max = 17  Step = 1 "
		::= { iqudc30CmdEntry 60103 }


	iqudc30MenuTimecodeCh1OutputLine625 OBJECT-TYPE
		SYNTAX		INTEGER
		MAX-ACCESS		read-write
		STATUS			current
		DESCRIPTION
				"TYPE: - Number
				 PAGE: - Timecode-Ch1
					Output Line (625)  cmdID= 60104  min= 7  max= 20  step= 1  format= %0.0f  div_scale= 1 
					Min = 7  Max = 20  Step = 1 "
		::= { iqudc30CmdEntry 60104 }


	iqudc30MenuTimecodeCh1NewDisplay OBJECT-TYPE
		SYNTAX		RollCallString
		MAX-ACCESS		read-only
		STATUS			current
		DESCRIPTION
				"TYPE: - Display
				 PAGE: - Timecode-Ch1
					New Display  cmdID= 44465  format=   "
		::= { iqudc30CmdEntry 44465 }


	iqudc30MenuTimecodeCh2SourceHD OBJECT-TYPE
		SYNTAX		INTEGER {
							val-LTC(0),
							val-VITC(1)
							}
		MAX-ACCESS		read-write
		STATUS			current
		DESCRIPTION
				"TYPE: - RadiobuttonList
				 PAGE: - Timecode-Ch2
					Source (HD)  cmdID= 60214 
					LTC  value= 0  
					VITC  value= 1  "
		::= { iqudc30CmdEntry 60214 }


	iqudc30MenuTimecodeCh2SourceSD OBJECT-TYPE
		SYNTAX		INTEGER {
							val-VITC(0),
							val-ATC-LTC(1),
							val-ATC-VITC(2)
							}
		MAX-ACCESS		read-write
		STATUS			current
		DESCRIPTION
				"TYPE: - RadiobuttonList
				 PAGE: - Timecode-Ch2
					Source (SD)  cmdID= 60215 
					VITC  value= 0  
					ATC LTC  value= 1  
					ATC VITC  value= 2  "
		::= { iqudc30CmdEntry 60215 }


	iqudc30MenuTimecodeCh2Status OBJECT-TYPE
		SYNTAX		RollCallString
		MAX-ACCESS		read-only
		STATUS			current
		DESCRIPTION
				"TYPE: - Display
				 PAGE: - Timecode-Ch2
					Status  cmdID= 60212  format=   "
		::= { iqudc30CmdEntry 60212 }


	iqudc30MenuTimecodeCh2Mode OBJECT-TYPE
		SYNTAX		INTEGER {
							val-Follow-Input(0),
							val-Generate(1)
							}
		MAX-ACCESS		read-write
		STATUS			current
		DESCRIPTION
				"TYPE: - RadiobuttonList
				 PAGE: - Timecode-Ch2
					Mode  cmdID= 60202 
					Follow Input  value= 0  
					Generate  value= 1  "
		::= { iqudc30CmdEntry 60202 }


	iqudc30MenuTimecodeCh2OnTimecodeLoss OBJECT-TYPE
		SYNTAX		INTEGER {
							val-Freeze(0),
							val-Free-Run(1)
							}
		MAX-ACCESS		read-write
		STATUS			current
		DESCRIPTION
				"TYPE: - RadiobuttonList
				 PAGE: - Timecode-Ch2
					On Timecode Loss  cmdID= 60207 
					Freeze  value= 0  
					Free Run  value= 1  "
		::= { iqudc30CmdEntry 60207 }


	iqudc30MenuTimecodeCh2TimecodeEntry OBJECT-TYPE
		SYNTAX		RollCallString
		MAX-ACCESS		read-write
		STATUS			current
		DESCRIPTION
				"TYPE: - Editstring
				 PAGE: - Timecode-Ch2
					Timecode Entry  cmdID= 60210  "
		::= { iqudc30CmdEntry 60210 }


	iqudc30MenuTimecodeCh2TimecodeLoad OBJECT-TYPE
		SYNTAX		INTEGER { noAction(0),val-Timecode-Load(1) }
		MAX-ACCESS		read-write
		STATUS			current
		DESCRIPTION
				"TYPE: - Button
				 PAGE: - Timecode-Ch2
					Timecode Load  cmdID= 60213  value= 1  "
		::= { iqudc30CmdEntry 60213 }


	iqudc30MenuTimecodeCh2NondropFrame OBJECT-TYPE
		SYNTAX		INTEGER { disable(0), enable(1) }
		MAX-ACCESS		read-write
		STATUS			current
		DESCRIPTION
				"TYPE: - Checkbox
				 PAGE: - Timecode-Ch2
					Non-drop Frame  cmdID= 60220 "
		::= { iqudc30CmdEntry 60220 }


	iqudc30MenuTimecodeCh2VITCEnable OBJECT-TYPE
		SYNTAX		INTEGER { disable(0), enable(1) }
		MAX-ACCESS		read-write
		STATUS			current
		DESCRIPTION
				"TYPE: - Checkbox
				 PAGE: - Timecode-Ch2
					VITC Enable  cmdID= 60211 "
		::= { iqudc30CmdEntry 60211 }


	iqudc30MenuTimecodeCh2OutputLine525 OBJECT-TYPE
		SYNTAX		INTEGER
		MAX-ACCESS		read-write
		STATUS			current
		DESCRIPTION
				"TYPE: - Number
				 PAGE: - Timecode-Ch2
					Output Line (525)  cmdID= 60203  min= 11  max= 17  step= 1  format= %0.0f  div_scale= 1 
					Min = 11  Max = 17  Step = 1 "
		::= { iqudc30CmdEntry 60203 }


	iqudc30MenuTimecodeCh2OutputLine625 OBJECT-TYPE
		SYNTAX		INTEGER
		MAX-ACCESS		read-write
		STATUS			current
		DESCRIPTION
				"TYPE: - Number
				 PAGE: - Timecode-Ch2
					Output Line (625)  cmdID= 60204  min= 7  max= 20  step= 1  format= %0.0f  div_scale= 1 
					Min = 7  Max = 20  Step = 1 "
		::= { iqudc30CmdEntry 60204 }


	iqudc30MenuTimecodeCh2NewDisplay OBJECT-TYPE
		SYNTAX		RollCallString
		MAX-ACCESS		read-only
		STATUS			current
		DESCRIPTION
				"TYPE: - Display
				 PAGE: - Timecode-Ch2
					New Display  cmdID= 44451  format=   "
		::= { iqudc30CmdEntry 44451 }


	iqudc30MetadataCh1ClosedCaptionsStatus OBJECT-TYPE
		SYNTAX		RollCallString
		MAX-ACCESS		read-only
		STATUS			current
		DESCRIPTION
				"TYPE: - Display
				 PAGE: - Metadata-Ch1
					Status  cmdID= 60208  format=   "
		::= { iqudc30CmdEntry 60208 }


	iqudc30MetadataCh1ClosedCaptionsCEA608OutputEnab OBJECT-TYPE
		SYNTAX		INTEGER {
							val-Off(0),
							val-On(1)
							}
		MAX-ACCESS		read-write
		STATUS			current
		DESCRIPTION
				"TYPE: - RadiobuttonList
				 PAGE: - Metadata-Ch1
					CEA-608 Output Enab  cmdID= 60200 
					Off  value= 0  
					On  value= 1  "
		::= { iqudc30CmdEntry 60200 }


	iqudc30MenuMetadataCh1CEA708OutputEnab OBJECT-TYPE
		SYNTAX		INTEGER {
							val-Off(0),
							val-On(1)
							}
		MAX-ACCESS		read-write
		STATUS			current
		DESCRIPTION
				"TYPE: - RadiobuttonList
				 PAGE: - Metadata-Ch1
					CEA-708 Output Enab  cmdID= 60201 
					Off  value= 0  
					On  value= 1  "
		::= { iqudc30CmdEntry 60201 }


	iqudc30MenuMetadataCh1CEA708OutputLine OBJECT-TYPE
		SYNTAX		INTEGER
		MAX-ACCESS		read-write
		STATUS			current
		DESCRIPTION
				"TYPE: - Number
				 PAGE: - Metadata-Ch1
					CEA-708 Output Line  cmdID= 60216  min= 8  max= 20  step= 1  format= %0.0f  div_scale= 1 
					Min = 8  Max = 20  Step = 1 "
		::= { iqudc30CmdEntry 60216 }


	iqudc30MetadataCh1TeletextStatus OBJECT-TYPE
		SYNTAX		RollCallString
		MAX-ACCESS		read-only
		STATUS			current
		DESCRIPTION
				"TYPE: - Display
				 PAGE: - Metadata-Ch1
					Status  cmdID= 60209  format=   "
		::= { iqudc30CmdEntry 60209 }


	iqudc30MetadataCh1TeletextWSTInputLine OBJECT-TYPE
		SYNTAX		INTEGER
		MAX-ACCESS		read-write
		STATUS			current
		DESCRIPTION
				"TYPE: - Number
				 PAGE: - Metadata-Ch1
					WST Input Line  cmdID= 60217  min= 7  max= 22  step= 1  format= %0.0f  div_scale= 1 
					Min = 7  Max = 22  Step = 1 "
		::= { iqudc30CmdEntry 60217 }


	iqudc30MetadataCh1TeletextWSTOutputEnable OBJECT-TYPE
		SYNTAX		INTEGER {
							val-Off(0),
							val-On(1)
							}
		MAX-ACCESS		read-write
		STATUS			current
		DESCRIPTION
				"TYPE: - RadiobuttonList
				 PAGE: - Metadata-Ch1
					WST Output Enable  cmdID= 60218 
					Off  value= 0  
					On  value= 1  "
		::= { iqudc30CmdEntry 60218 }


	iqudc30MenuMetadataCh1 OBJECT-TYPE
		SYNTAX		INTEGER
		MAX-ACCESS		read-write
		STATUS			current
		DESCRIPTION
				"TYPE: - Number
				 PAGE: - Metadata-Ch1
					RDD-08 Input Line  cmdID= 60206  min= 8  max= 20  step= 1  format= %0.0f  div_scale= 1 
					RDD-08 Input Line  cmdID= 60206  min= 8  max= 20  step= 1  format= %0.0f  div_scale= 1 
					Min = 8  Max = 20  Step = 1 "
		::= { iqudc30CmdEntry 60206 }


	iqudc30MenuMetadataCh1RDD08OutputEnabl OBJECT-TYPE
		SYNTAX		INTEGER {
							val-Off(0),
							val-On(1)
							}
		MAX-ACCESS		read-write
		STATUS			current
		DESCRIPTION
				"TYPE: - RadiobuttonList
				 PAGE: - Metadata-Ch1
					RDD-08 Output Enabl  cmdID= 60205 
					Off  value= 0  
					On  value= 1  "
		::= { iqudc30CmdEntry 60205 }


	iqudc30MenuMetadataCh1RDD08OutputLine OBJECT-TYPE
		SYNTAX		INTEGER
		MAX-ACCESS		read-write
		STATUS			current
		DESCRIPTION
				"TYPE: - Number
				 PAGE: - Metadata-Ch1
					RDD-08 Output Line  cmdID= 60219  min= 8  max= 20  step= 1  format= %0.0f  div_scale= 1 
					Min = 8  Max = 20  Step = 1 "
		::= { iqudc30CmdEntry 60219 }


	iqudc30MenuMetadataCh1NewDisplay OBJECT-TYPE
		SYNTAX		RollCallString
		MAX-ACCESS		read-only
		STATUS			current
		DESCRIPTION
				"TYPE: - Display
				 PAGE: - Metadata-Ch1
					New Display  cmdID= 44466  format=   "
		::= { iqudc30CmdEntry 44466 }


	iqudc30MetadataCh2ClosedCaptionsStatus OBJECT-TYPE
		SYNTAX		RollCallString
		MAX-ACCESS		read-only
		STATUS			current
		DESCRIPTION
				"TYPE: - Display
				 PAGE: - Metadata-Ch2
					Status  cmdID= 60308  format=   "
		::= { iqudc30CmdEntry 60308 }


	iqudc30MetadataCh2ClosedCaptionsCEA608OutputEnab OBJECT-TYPE
		SYNTAX		INTEGER {
							val-Off(0),
							val-On(1)
							}
		MAX-ACCESS		read-write
		STATUS			current
		DESCRIPTION
				"TYPE: - RadiobuttonList
				 PAGE: - Metadata-Ch2
					CEA-608 Output Enab  cmdID= 60300 
					Off  value= 0  
					On  value= 1  "
		::= { iqudc30CmdEntry 60300 }


	iqudc30MenuMetadataCh2CEA708OutputEnab OBJECT-TYPE
		SYNTAX		INTEGER {
							val-Off(0),
							val-On(1)
							}
		MAX-ACCESS		read-write
		STATUS			current
		DESCRIPTION
				"TYPE: - RadiobuttonList
				 PAGE: - Metadata-Ch2
					CEA-708 Output Enab  cmdID= 60301 
					Off  value= 0  
					On  value= 1  "
		::= { iqudc30CmdEntry 60301 }


	iqudc30MenuMetadataCh2CEA708OutputLine OBJECT-TYPE
		SYNTAX		INTEGER
		MAX-ACCESS		read-write
		STATUS			current
		DESCRIPTION
				"TYPE: - Number
				 PAGE: - Metadata-Ch2
					CEA-708 Output Line  cmdID= 60302  min= 8  max= 20  step= 1  format= %0.0f  div_scale= 1 
					Min = 8  Max = 20  Step = 1 "
		::= { iqudc30CmdEntry 60302 }


	iqudc30MetadataCh2TeletextStatus OBJECT-TYPE
		SYNTAX		RollCallString
		MAX-ACCESS		read-only
		STATUS			current
		DESCRIPTION
				"TYPE: - Display
				 PAGE: - Metadata-Ch2
					Status  cmdID= 60309  format=   "
		::= { iqudc30CmdEntry 60309 }


	iqudc30MetadataCh2TeletextWSTInputLine OBJECT-TYPE
		SYNTAX		INTEGER
		MAX-ACCESS		read-write
		STATUS			current
		DESCRIPTION
				"TYPE: - Number
				 PAGE: - Metadata-Ch2
					WST Input Line  cmdID= 60303  min= 7  max= 22  step= 1  format= %0.0f  div_scale= 1 
					Min = 7  Max = 22  Step = 1 "
		::= { iqudc30CmdEntry 60303 }


	iqudc30MetadataCh2TeletextWSTOutputEnable OBJECT-TYPE
		SYNTAX		INTEGER {
							val-Off(0),
							val-On(1)
							}
		MAX-ACCESS		read-write
		STATUS			current
		DESCRIPTION
				"TYPE: - RadiobuttonList
				 PAGE: - Metadata-Ch2
					WST Output Enable  cmdID= 60304 
					Off  value= 0  
					On  value= 1  "
		::= { iqudc30CmdEntry 60304 }


	iqudc30MenuMetadataCh2 OBJECT-TYPE
		SYNTAX		INTEGER
		MAX-ACCESS		read-write
		STATUS			current
		DESCRIPTION
				"TYPE: - Number
				 PAGE: - Metadata-Ch2
					RDD-08 Input Line  cmdID= 60306  min= 8  max= 20  step= 1  format= %0.0f  div_scale= 1 
					RDD-08 Input Line  cmdID= 60306  min= 8  max= 20  step= 1  format= %0.0f  div_scale= 1 
					Min = 8  Max = 20  Step = 1 "
		::= { iqudc30CmdEntry 60306 }


	iqudc30MenuMetadataCh2RDD08OutputEnabl OBJECT-TYPE
		SYNTAX		INTEGER {
							val-Off(0),
							val-On(1)
							}
		MAX-ACCESS		read-write
		STATUS			current
		DESCRIPTION
				"TYPE: - RadiobuttonList
				 PAGE: - Metadata-Ch2
					RDD-08 Output Enabl  cmdID= 60305 
					Off  value= 0  
					On  value= 1  "
		::= { iqudc30CmdEntry 60305 }


	iqudc30MenuMetadataCh2RDD08OutputLine OBJECT-TYPE
		SYNTAX		INTEGER
		MAX-ACCESS		read-write
		STATUS			current
		DESCRIPTION
				"TYPE: - Number
				 PAGE: - Metadata-Ch2
					RDD-08 Output Line  cmdID= 60307  min= 8  max= 20  step= 1  format= %0.0f  div_scale= 1 
					Min = 8  Max = 20  Step = 1 "
		::= { iqudc30CmdEntry 60307 }


	iqudc30MenuMetadataCh2NewDisplay OBJECT-TYPE
		SYNTAX		RollCallString
		MAX-ACCESS		read-only
		STATUS			current
		DESCRIPTION
				"TYPE: - Display
				 PAGE: - Metadata-Ch2
					New Display  cmdID= 44452  format=   "
		::= { iqudc30CmdEntry 44452 }


	iqudc30GPIOGPI1GPIO1Mode OBJECT-TYPE
		SYNTAX		INTEGER {
							val-Unused(0),
							val-Input-GPI1(1),
							val-Output-GPO1(2)
							}
		MAX-ACCESS		read-write
		STATUS			current
		DESCRIPTION
				"TYPE: - RadiobuttonList
				 PAGE: - GPIO
					GPI/O 1 Mode  cmdID= 40600 
					Unused  value= 0  
					Input (GPI1)  value= 1  
					Output (GPO1)  value= 2  "
		::= { iqudc30CmdEntry 40600 }


	iqudc30MenuGPIOGPI1ipSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5),
							val-User-Memory-1(6),
							val-User-Memory-2(7),
							val-User-Memory-3(8),
							val-User-Memory-4(9),
							val-User-Memory-5(10),
							val-User-Memory-6(11),
							val-User-Memory-7(12),
							val-User-Memory-8(13),
							val-User-Memory-9(14),
							val-User-Memory-10(15),
							val-User-Memory-11(16),
							val-User-Memory-12(17),
							val-User-Memory-13(18),
							val-User-Memory-14(19),
							val-User-Memory-15(20),
							val-User-Memory-16(21)
							}
		MAX-ACCESS		read-write
		STATUS			current
		DESCRIPTION
				"TYPE: - RadiobuttonList
				 PAGE: - GPIO
					GPI 1-i/p Select  cmdID= 40602 
					Unused  value= 255  
					Freeze Ch1  value= 0  
					Black Ch1  value= 1  
					Pattern Ch1  value= 2  
					Freeze Ch2  value= 3  
					Black Ch2  value= 4  
					Pattern Ch2  value= 5  
					User Memory 1  value= 6  
					User Memory 2  value= 7  
					User Memory 3  value= 8  
					User Memory 4  value= 9  
					User Memory 5  value= 10  
					User Memory 6  value= 11  
					User Memory 7  value= 12  
					User Memory 8  value= 13  
					User Memory 9  value= 14  
					User Memory 10  value= 15  
					User Memory 11  value= 16  
					User Memory 12  value= 17  
					User Memory 13  value= 18  
					User Memory 14  value= 19  
					User Memory 15  value= 20  
					User Memory 16  value= 21  "
		::= { iqudc30CmdEntry 40602 }


	iqudc30MenuGPIOGPO1opSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5)
							}
		MAX-ACCESS		read-write
		STATUS			current
		DESCRIPTION
				"TYPE: - RadiobuttonList
				 PAGE: - GPIO
					GPO 1-o/p Select  cmdID= 40603 
					Unused  value= 255  
					Freeze Ch1  value= 0  
					Black Ch1  value= 1  
					Pattern Ch1  value= 2  
					Freeze Ch2  value= 3  
					Black Ch2  value= 4  
					Pattern Ch2  value= 5  "
		::= { iqudc30CmdEntry 40603 }


	iqudc30GPIOGPI2GPIO2Mode OBJECT-TYPE
		SYNTAX		INTEGER {
							val-Unused(0),
							val-Input-GPI2(1),
							val-Output-GPO2(2)
							}
		MAX-ACCESS		read-write
		STATUS			current
		DESCRIPTION
				"TYPE: - RadiobuttonList
				 PAGE: - GPIO
					GPI/O 2 Mode  cmdID= 40601 
					Unused  value= 0  
					Input (GPI2)  value= 1  
					Output (GPO2)  value= 2  "
		::= { iqudc30CmdEntry 40601 }


	iqudc30MenuGPIOGPI2ipSelect OBJECT-TYPE
		SYNTAX		INTEGER {
							val-Unused(255),
							val-Freeze-Ch1(0),
							val-Black-Ch-1(1),
							val-Pattern-Ch1(2),
							val-Freeze-Ch2(3),
							val-Black-Ch-2(4),
							val-Pattern-Ch2(5),
							val-User-Memory-1(6),
							val-User-Memory-2(7),
							val-User-Memory-3(8),
							val-User-Memory-4(9),
							val-User-Memory-5(10),
							val-User-Memory-6(11),
							val-User-Memory-7(12),
							val-User-Memory-8(13),
							val-User-Memory-9(14),
							val-User-Memory-10(15),
							val-User-Memory-11(16),
							val-User-Memory-12(17),
							val-User-Memory-13(18),
							val-User-Memory-14(19),
							val-User-Memory-15(20),
							val-User-Memory-16(21)
							}
		MAX-ACCESS		read-write
		STATUS			current
		DESCRIPTION
				"TYPE: - RadiobuttonList
				 PAGE: - GPIO
					GPI 2-i/p Select  cmdID= 40604 
					Unused  value= 255  
					Freeze Ch1  value= 0  
					Black Ch 1  value= 1  
					Pattern Ch1  value= 2  
					Freeze Ch2  value= 3  
					Black Ch 2  value= 4  
					Pattern Ch2  value= 5  
					User Memory 1  value= 6  
					User Memory 2  value= 7  
					User Memory 3  value= 8  
					User Memory 4  value= 9  
					User Memory 5  value= 10  
					User Memory 6  value= 11  
					User Memory 7  value= 12  
					User Memory 8  value= 13  
					User Memory 9  value= 14  
					User Memory 10  value= 15  
					User Memory 11  value= 16  
					User Memory 12  value= 17  
					User Memory 13  value= 18  
					User Memory 14  value= 19  
					User Memory 15  value= 20  
					User Memory 16  value= 21  "
		::= { iqudc30CmdEntry 40604 }


	iqudc30MenuGPIOGPO2opSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5)
							}
		MAX-ACCESS		read-write
		STATUS			current
		DESCRIPTION
				"TYPE: - RadiobuttonList
				 PAGE: - GPIO
					GPO 2-o/p Select  cmdID= 40605 
					Unused  value= 255  
					Freeze Ch1  value= 0  
					Black Ch1  value= 1  
					Pattern Ch1  value= 2  
					Freeze Ch2  value= 3  
					Black Ch2  value= 4  
					Pattern Ch2  value= 5  "
		::= { iqudc30CmdEntry 40605 }


	iqudc30MenuGPIONewDisplay OBJECT-TYPE
		SYNTAX		RollCallString
		MAX-ACCESS		read-only
		STATUS			current
		DESCRIPTION
				"TYPE: - Display
				 PAGE: - GPIO
					New Display  cmdID= 44453  format=   "
		::= { iqudc30CmdEntry 44453 }


	iqudc30MenuRollCallUnitName OBJECT-TYPE
		SYNTAX		RollCallString
		MAX-ACCESS		read-write
		STATUS			current
		DESCRIPTION
				"TYPE: - Editstring
				 PAGE: - RollCall
					Unit Name  cmdID= 51101  "
		::= { iqudc30CmdEntry 51101 }


	iqudc30MenuRollCallIPSharePort OBJECT-TYPE
		SYNTAX		INTEGER
		MAX-ACCESS		read-write
		STATUS			current
		DESCRIPTION
				"TYPE: - Number
				 PAGE: - RollCall
					IP Share Port  cmdID= 51105  min= 1024  max= 65535  step= 1  format= %d  div_scale= 1 
					Min = 1024  Max = -1  Step = 1 "
		::= { iqudc30CmdEntry 51105 }


	iqudc30MenuRollCallIPBridgingPort OBJECT-TYPE
		SYNTAX		INTEGER
		MAX-ACCESS		read-write
		STATUS			current
		DESCRIPTION
				"TYPE: - Number
				 PAGE: - RollCall
					IP Bridging Port  cmdID= 51106  min= 1024  max= 65535  step= 1  format= %d  div_scale= 1 
					Min = 1024  Max = -1  Step = 1 "
		::= { iqudc30CmdEntry 51106 }


	iqudc30MenuMemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Recall Memory  cmdID= 55002 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc30CmdEntry 55002 }


	iqudc30MenuMemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Sel Memory  cmdID= 55000 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc30CmdEntry 55000 }


	iqudc30MenuMemoriesSaveMemory OBJECT-TYPE
		SYNTAX		INTEGER { noAction(0),val-Save-Memory(1) }
		MAX-ACCESS		read-write
		STATUS			current
		DESCRIPTION
				"TYPE: - Button
				 PAGE: - Memories
					Save Memory  cmdID= 55001  value= 1  "
		::= { iqudc30CmdEntry 55001 }


	iqudc30MenuMemoriesClearMemory OBJECT-TYPE
		SYNTAX		INTEGER { noAction(0),val-Clear-Memory(1) }
		MAX-ACCESS		read-write
		STATUS			current
		DESCRIPTION
				"TYPE: - Button
				 PAGE: - Memories
					Clear Memory  cmdID= 55005  value= 1  "
		::= { iqudc30CmdEntry 55005 }


	iqudc30MemoriesMemoryNameChangeName OBJECT-TYPE
		SYNTAX		RollCallString
		MAX-ACCESS		read-write
		STATUS			current
		DESCRIPTION
				"TYPE: - Editstring
				 PAGE: - Memories
					Change Name  cmdID= 55003  "
		::= { iqudc30CmdEntry 55003 }


	iqudc30MenuMemoriesLastDisplayMemory OBJECT-TYPE
		SYNTAX		RollCallString
		MAX-ACCESS		read-only
		STATUS			current
		DESCRIPTION
				"TYPE: - Display
				 PAGE: - Memories
					Last Display Memory  cmdID= 55004  format=   "
		::= { iqudc30CmdEntry 55004 }


	iqudc30MenuRollTrackDisableAll OBJECT-TYPE
		SYNTAX		INTEGER { disable(0), enable(1) }
		MAX-ACCESS		read-write
		STATUS			current
		DESCRIPTION
				"TYPE: - Checkbox
				 PAGE: - RollTrack
					Disable All  cmdID= 60312 "
		::= { iqudc30CmdEntry 60312 }


	iqudc30MenuRollTrackIndex OBJECT-TYPE
		SYNTAX		INTEGER
		MAX-ACCESS		read-write
		STATUS			current
		DESCRIPTION
				"TYPE: - BarGraph
				 PAGE: - RollTrack
					Index  cmdID= 60313  min= 1  max= 50   step= 1  format= %0.0f  div_scale= 1 
					Min = 1  Max = 50  Step = 1 "
		::= { iqudc30CmdEntry 60313 }


	iqudc30MenuRollTrackSource OBJECT-TYPE
		SYNTAX		INTEGER {
							val-Unused(-1),
							val-Input-Present-Ch1(0),
							val-Input-Loss-Ch1(1),
							val-Reference-OK(2),
							val-Reference-Lost(3),
							val-Input-Present-Ch2(4),
							val-Input-Loss-Ch2(5)
							}
		MAX-ACCESS		read-write
		STATUS			current
		DESCRIPTION
				"TYPE: - RadiobuttonList
				 PAGE: - RollTrack
					Source  cmdID= 60315 
					Unused  value= -1  
					Input Present Ch1  value= 0  
					Input Loss Ch1  value= 1  
					Reference OK  value= 2  
					Reference Lost  value= 3  
					Input Present Ch2  value= 4  
					Input Loss Ch2  value= 5  "
		::= { iqudc30CmdEntry 60315 }


	iqudc30MenuRollTrackAddress OBJECT-TYPE
		SYNTAX		RollCallString
		MAX-ACCESS		read-write
		STATUS			current
		DESCRIPTION
				"TYPE: - Editstring
				 PAGE: - RollTrack
					Address  cmdID= 60317  "
		::= { iqudc30CmdEntry 60317 }


	iqudc30MenuRollTrackCommand OBJECT-TYPE
		SYNTAX		RollCallString
		MAX-ACCESS		read-write
		STATUS			current
		DESCRIPTION
				"TYPE: - Editstring
				 PAGE: - RollTrack
					Command  cmdID= 60318  "
		::= { iqudc30CmdEntry 60318 }


	iqudc30MenuRollTrackStatus OBJECT-TYPE
		SYNTAX		RollCallString
		MAX-ACCESS		read-only
		STATUS			current
		DESCRIPTION
				"TYPE: - Display
				 PAGE: - RollTrack
					Status  cmdID= 60316  format=   "
		::= { iqudc30CmdEntry 60316 }


	iqudc30MenuRollTrackSending OBJECT-TYPE
		SYNTAX		RollCallString
		MAX-ACCESS		read-only
		STATUS			current
		DESCRIPTION
				"TYPE: - Display
				 PAGE: - RollTrack
					Sending  cmdID= 60314  format=   "
		::= { iqudc30CmdEntry 60314 }


	iqudc30MenuMiscLoggingSerialNumberEnabl OBJECT-TYPE
		SYNTAX		INTEGER { disable(0), enable(1) }
		MAX-ACCESS		read-write
		STATUS			current
		DESCRIPTION
				"TYPE: - Checkbox
				 PAGE: - Misc. Logging
					Serial Number Enabl  cmdID= 62000 "
		::= { iqudc30CmdEntry 62000 }


	iqudc30MenuMiscLoggingSerialNumberStatu OBJECT-TYPE
		SYNTAX		RollCallString
		MAX-ACCESS		read-only
		STATUS			current
		DESCRIPTION
				"TYPE: - Display
				 PAGE: - Misc. Logging
					Serial Number Statu  cmdID= 62001  format=   "
		::= { iqudc30CmdEntry 62001 }


	iqudc30MenuMiscLoggingUpTimeEnable OBJECT-TYPE
		SYNTAX		INTEGER { disable(0), enable(1) }
		MAX-ACCESS		read-write
		STATUS			current
		DESCRIPTION
				"TYPE: - Checkbox
				 PAGE: - Misc. Logging
					Up Time Enable  cmdID= 62004 "
		::= { iqudc30CmdEntry 62004 }


	iqudc30MenuMiscLoggingUpTimeStatus OBJECT-TYPE
		SYNTAX		RollCallString
		MAX-ACCESS		read-only
		STATUS			current
		DESCRIPTION
				"TYPE: - Display
				 PAGE: - Misc. Logging
					Up Time Status  cmdID= 62005  format=   "
		::= { iqudc30CmdEntry 62005 }


	iqudc30MenuMiscLoggingPowerUsageStateE OBJECT-TYPE
		SYNTAX		INTEGER { disable(0), enable(1) }
		MAX-ACCESS		read-write
		STATUS			current
		DESCRIPTION
				"TYPE: - Checkbox
				 PAGE: - Misc. Logging
					Power Usage State E  cmdID= 62006 "
		::= { iqudc30CmdEntry 62006 }


	iqudc30MenuMiscLoggingPowerUsageStateS OBJECT-TYPE
		SYNTAX		RollCallString
		MAX-ACCESS		read-only
		STATUS			current
		DESCRIPTION
				"TYPE: - Display
				 PAGE: - Misc. Logging
					Power Usage State S  cmdID= 62007  format=   "
		::= { iqudc30CmdEntry 62007 }


	iqudc30MenuMiscLoggingBuild62011 OBJECT-TYPE
		SYNTAX		INTEGER { disable(0), enable(1) }
		MAX-ACCESS		read-write
		STATUS			current
		DESCRIPTION
				"TYPE: - Checkbox
				 PAGE: - Misc. Logging
					Build  cmdID= 62011 "
		::= { iqudc30CmdEntry 62011 }


	iqudc30MenuMiscLoggingBuild62010 OBJECT-TYPE
		SYNTAX		RollCallString
		MAX-ACCESS		read-only
		STATUS			current
		DESCRIPTION
				"TYPE: - Display
				 PAGE: - Misc. Logging
					Build  cmdID= 62010  format=   "
		::= { iqudc30CmdEntry 62010 }


	iqudc30MenuMiscLoggingAESOutput14Place OBJECT-TYPE
		SYNTAX		RollCallString
		MAX-ACCESS		read-only
		STATUS			current
		DESCRIPTION
				"TYPE: - Display
				 PAGE: - Misc. Logging
					AES Output1-4 Place  cmdID= 61009  format=   "
		::= { iqudc30CmdEntry 61009 }


	iqudc30MenuMiscLoggingAESOutput58Place OBJECT-TYPE
		SYNTAX		RollCallString
		MAX-ACCESS		read-only
		STATUS			current
		DESCRIPTION
				"TYPE: - Display
				 PAGE: - Misc. Logging
					AES Output5-8 Place  cmdID= 61010  format=   "
		::= { iqudc30CmdEntry 61010 }


	iqudc30MenuMiscLoggingInputADCPlacehold OBJECT-TYPE
		SYNTAX		RollCallString
		MAX-ACCESS		read-only
		STATUS			current
		DESCRIPTION
				"TYPE: - Display
				 PAGE: - Misc. Logging
					Input ADC Placehold  cmdID= 61011  format=   "
		::= { iqudc30CmdEntry 61011 }


	iqudc30MenuMiscLoggingSourceCh1Ch2Pl OBJECT-TYPE
		SYNTAX		RollCallString
		MAX-ACCESS		read-only
		STATUS			current
		DESCRIPTION
				"TYPE: - Display
				 PAGE: - Misc. Logging
					Source Ch1 & Ch2 Pl  cmdID= 61012  format=   "
		::= { iqudc30CmdEntry 61012 }


	iqudc30MenuMiscLoggingCVBSDecoderPlaceh OBJECT-TYPE
		SYNTAX		RollCallString
		MAX-ACCESS		read-only
		STATUS			current
		DESCRIPTION
				"TYPE: - Display
				 PAGE: - Misc. Logging
					CVBS Decoder Placeh  cmdID= 20500  format=   "
		::= { iqudc30CmdEntry 20500 }


	iqudc30MenuVideoInputLoggingInput1Type62100 OBJECT-TYPE
		SYNTAX		INTEGER { disable(0), enable(1) }
		MAX-ACCESS		read-write
		STATUS			current
		DESCRIPTION
				"TYPE: - Checkbox
				 PAGE: - Video Input Logging
					Input 1 Type  cmdID= 62100 "
		::= { iqudc30CmdEntry 62100 }


	iqudc30MenuVideoInputLoggingInput1Type62101 OBJECT-TYPE
		SYNTAX		RollCallString
		MAX-ACCESS		read-only
		STATUS			current
		DESCRIPTION
				"TYPE: - Display
				 PAGE: - Video Input Logging
					Input 1 Type=  cmdID= 62101  format=   "
		::= { iqudc30CmdEntry 62101 }


	iqudc30MenuVideoInputLoggingInput1State62102 OBJECT-TYPE
		SYNTAX		INTEGER { disable(0), enable(1) }
		MAX-ACCESS		read-write
		STATUS			current
		DESCRIPTION
				"TYPE: - Checkbox
				 PAGE: - Video Input Logging
					Input 1 State  cmdID= 62102 "
		::= { iqudc30CmdEntry 62102 }


	iqudc30MenuVideoInputLoggingInput1State62103 OBJECT-TYPE
		SYNTAX		RollCallString
		MAX-ACCESS		read-only
		STATUS			current
		DESCRIPTION
				"TYPE: - Display
				 PAGE: - Video Input Logging
					Input 1 State=  cmdID= 62103  format=   "
		::= { iqudc30CmdEntry 62103 }


	iqudc30MenuVideoInputLoggingInput1Std62104 OBJECT-TYPE
		SYNTAX		INTEGER { disable(0), enable(1) }
		MAX-ACCESS		read-write
		STATUS			current
		DESCRIPTION
				"TYPE: - Checkbox
				 PAGE: - Video Input Logging
					Input 1 Std.  cmdID= 62104 "
		::= { iqudc30CmdEntry 62104 }


	iqudc30MenuVideoInputLoggingInput1Std62105 OBJECT-TYPE
		SYNTAX		RollCallString
		MAX-ACCESS		read-only
		STATUS			current
		DESCRIPTION
				"TYPE: - Display
				 PAGE: - Video Input Logging
					Input 1 Std.=  cmdID= 62105  format=   "
		::= { iqudc30CmdEntry 62105 }


	iqudc30MenuVideoInputLoggingInput2Type62200 OBJECT-TYPE
		SYNTAX		INTEGER { disable(0), enable(1) }
		MAX-ACCESS		read-write
		STATUS			current
		DESCRIPTION
				"TYPE: - Checkbox
				 PAGE: - Video Input Logging
					Input 2 Type  cmdID= 62200 "
		::= { iqudc30CmdEntry 62200 }


	iqudc30MenuVideoInputLoggingInput2Type62201 OBJECT-TYPE
		SYNTAX		RollCallString
		MAX-ACCESS		read-only
		STATUS			current
		DESCRIPTION
				"TYPE: - Display
				 PAGE: - Video Input Logging
					Input 2 Type=  cmdID= 62201  format=   "
		::= { iqudc30CmdEntry 62201 }


	iqudc30MenuVideoInputLoggingInput2State62202 OBJECT-TYPE
		SYNTAX		INTEGER { disable(0), enable(1) }
		MAX-ACCESS		read-write
		STATUS			current
		DESCRIPTION
				"TYPE: - Checkbox
				 PAGE: - Video Input Logging
					Input 2 State  cmdID= 62202 "
		::= { iqudc30CmdEntry 62202 }


	iqudc30MenuVideoInputLoggingInput2State62203 OBJECT-TYPE
		SYNTAX		RollCallString
		MAX-ACCESS		read-only
		STATUS			current
		DESCRIPTION
				"TYPE: - Display
				 PAGE: - Video Input Logging
					Input 2 State=  cmdID= 62203  format=   "
		::= { iqudc30CmdEntry 62203 }


	iqudc30MenuVideoInputLoggingInput2Std62204 OBJECT-TYPE
		SYNTAX		INTEGER { disable(0), enable(1) }
		MAX-ACCESS		read-write
		STATUS			current
		DESCRIPTION
				"TYPE: - Checkbox
				 PAGE: - Video Input Logging
					Input 2 Std.  cmdID= 62204 "
		::= { iqudc30CmdEntry 62204 }


	iqudc30MenuVideoInputLoggingInput2Std62205 OBJECT-TYPE
		SYNTAX		RollCallString
		MAX-ACCESS		read-only
		STATUS			current
		DESCRIPTION
				"TYPE: - Display
				 PAGE: - Video Input Logging
					Input 2 Std.=  cmdID= 62205  format=   "
		::= { iqudc30CmdEntry 62205 }


	iqudc30MenuVideoInputLoggingInput3Type62300 OBJECT-TYPE
		SYNTAX		INTEGER { disable(0), enable(1) }
		MAX-ACCESS		read-write
		STATUS			current
		DESCRIPTION
				"TYPE: - Checkbox
				 PAGE: - Video Input Logging
					Input 3 Type  cmdID= 62300 "
		::= { iqudc30CmdEntry 62300 }


	iqudc30MenuVideoInputLoggingInput3Type62301 OBJECT-TYPE
		SYNTAX		RollCallString
		MAX-ACCESS		read-only
		STATUS			current
		DESCRIPTION
				"TYPE: - Display
				 PAGE: - Video Input Logging
					Input 3 Type=  cmdID= 62301  format=   "
		::= { iqudc30CmdEntry 62301 }


	iqudc30MenuVideoInputLoggingInput3State62302 OBJECT-TYPE
		SYNTAX		INTEGER { disable(0), enable(1) }
		MAX-ACCESS		read-write
		STATUS			current
		DESCRIPTION
				"TYPE: - Checkbox
				 PAGE: - Video Input Logging
					Input 3 State  cmdID= 62302 "
		::= { iqudc30CmdEntry 62302 }


	iqudc30MenuVideoInputLoggingInput3State62303 OBJECT-TYPE
		SYNTAX		RollCallString
		MAX-ACCESS		read-only
		STATUS			current
		DESCRIPTION
				"TYPE: - Display
				 PAGE: - Video Input Logging
					Input 3 State=  cmdID= 62303  format=   "
		::= { iqudc30CmdEntry 62303 }


	iqudc30MenuVideoInputLoggingInput3Std62304 OBJECT-TYPE
		SYNTAX		INTEGER { disable(0), enable(1) }
		MAX-ACCESS		read-write
		STATUS			current
		DESCRIPTION
				"TYPE: - Checkbox
				 PAGE: - Video Input Logging
					Input 3 Std.  cmdID= 62304 "
		::= { iqudc30CmdEntry 62304 }


	iqudc30MenuVideoInputLoggingInput3Std62305 OBJECT-TYPE
		SYNTAX		RollCallString
		MAX-ACCESS		read-only
		STATUS			current
		DESCRIPTION
				"TYPE: - Display
				 PAGE: - Video Input Logging
					Input 3 Std.=  cmdID= 62305  format=   "
		::= { iqudc30CmdEntry 62305 }


	iqudc30MenuVideoInputLoggingInput4Type62400 OBJECT-TYPE
		SYNTAX		INTEGER { disable(0), enable(1) }
		MAX-ACCESS		read-write
		STATUS			current
		DESCRIPTION
				"TYPE: - Checkbox
				 PAGE: - Video Input Logging
					Input 4 Type  cmdID= 62400 "
		::= { iqudc30CmdEntry 62400 }


	iqudc30MenuVideoInputLoggingInput4Type62401 OBJECT-TYPE
		SYNTAX		RollCallString
		MAX-ACCESS		read-only
		STATUS			current
		DESCRIPTION
				"TYPE: - Display
				 PAGE: - Video Input Logging
					Input 4 Type=  cmdID= 62401  format=   "
		::= { iqudc30CmdEntry 62401 }


	iqudc30MenuVideoInputLoggingInput4State62402 OBJECT-TYPE
		SYNTAX		INTEGER { disable(0), enable(1) }
		MAX-ACCESS		read-write
		STATUS			current
		DESCRIPTION
				"TYPE: - Checkbox
				 PAGE: - Video Input Logging
					Input 4 State  cmdID= 62402 "
		::= { iqudc30CmdEntry 62402 }


	iqudc30MenuVideoInputLoggingInput4State62403 OBJECT-TYPE
		SYNTAX		RollCallString
		MAX-ACCESS		read-only
		STATUS			current
		DESCRIPTION
				"TYPE: - Display
				 PAGE: - Video Input Logging
					Input 4 State=  cmdID= 62403  format=   "
		::= { iqudc30CmdEntry 62403 }


	iqudc30MenuVideoInputLoggingInput4Std62404 OBJECT-TYPE
		SYNTAX		INTEGER { disable(0), enable(1) }
		MAX-ACCESS		read-write
		STATUS			current
		DESCRIPTION
				"TYPE: - Checkbox
				 PAGE: - Video Input Logging
					Input 4 Std.  cmdID= 62404 "
		::= { iqudc30CmdEntry 62404 }


	iqudc30MenuVideoInputLoggingInput4Std62405 OBJECT-TYPE
		SYNTAX		RollCallString
		MAX-ACCESS		read-only
		STATUS			current
		DESCRIPTION
				"TYPE: - Display
				 PAGE: - Video Input Logging
					Input 4 Std.=  cmdID= 62405  format=   "
		::= { iqudc30CmdEntry 62405 }


	iqudc30MenuVideoInputLoggingInput5Type62500 OBJECT-TYPE
		SYNTAX		INTEGER { disable(0), enable(1) }
		MAX-ACCESS		read-write
		STATUS			current
		DESCRIPTION
				"TYPE: - Checkbox
				 PAGE: - Video Input Logging
					Input 5 Type  cmdID= 62500 "
		::= { iqudc30CmdEntry 62500 }


	iqudc30MenuVideoInputLoggingInput5Type62501 OBJECT-TYPE
		SYNTAX		RollCallString
		MAX-ACCESS		read-only
		STATUS			current
		DESCRIPTION
				"TYPE: - Display
				 PAGE: - Video Input Logging
					Input 5 Type=  cmdID= 62501  format=   "
		::= { iqudc30CmdEntry 62501 }


	iqudc30MenuVideoInputLoggingInput5State62502 OBJECT-TYPE
		SYNTAX		INTEGER { disable(0), enable(1) }
		MAX-ACCESS		read-write
		STATUS			current
		DESCRIPTION
				"TYPE: - Checkbox
				 PAGE: - Video Input Logging
					Input 5 State  cmdID= 62502 "
		::= { iqudc30CmdEntry 62502 }


	iqudc30MenuVideoInputLoggingInput5State62503 OBJECT-TYPE
		SYNTAX		RollCallString
		MAX-ACCESS		read-only
		STATUS			current
		DESCRIPTION
				"TYPE: - Display
				 PAGE: - Video Input Logging
					Input 5 State=  cmdID= 62503  format=   "
		::= { iqudc30CmdEntry 62503 }


	iqudc30MenuVideoInputLoggingInput5Std62504 OBJECT-TYPE
		SYNTAX		INTEGER { disable(0), enable(1) }
		MAX-ACCESS		read-write
		STATUS			current
		DESCRIPTION
				"TYPE: - Checkbox
				 PAGE: - Video Input Logging
					Input 5 Std.  cmdID= 62504 "
		::= { iqudc30CmdEntry 62504 }


	iqudc30MenuVideoInputLoggingInput5Std62505 OBJECT-TYPE
		SYNTAX		RollCallString
		MAX-ACCESS		read-only
		STATUS			current
		DESCRIPTION
				"TYPE: - Display
				 PAGE: - Video Input Logging
					Input 5 Std.=  cmdID= 62505  format=   "
		::= { iqudc30CmdEntry 62505 }


	iqudc30MenuOutputLoggingOutput1Type62600 OBJECT-TYPE
		SYNTAX		INTEGER { disable(0), enable(1) }
		MAX-ACCESS		read-write
		STATUS			current
		DESCRIPTION
				"TYPE: - Checkbox
				 PAGE: - Output Logging
					Output 1 Type  cmdID= 62600 "
		::= { iqudc30CmdEntry 62600 }


	iqudc30MenuOutputLoggingOutput1Type62601 OBJECT-TYPE
		SYNTAX		RollCallString
		MAX-ACCESS		read-only
		STATUS			current
		DESCRIPTION
				"TYPE: - Display
				 PAGE: - Output Logging
					Output 1 Type=  cmdID= 62601  format=   "
		::= { iqudc30CmdEntry 62601 }


	iqudc30MenuOutputLoggingOutput1State62602 OBJECT-TYPE
		SYNTAX		INTEGER { disable(0), enable(1) }
		MAX-ACCESS		read-write
		STATUS			current
		DESCRIPTION
				"TYPE: - Checkbox
				 PAGE: - Output Logging
					Output 1 State  cmdID= 62602 "
		::= { iqudc30CmdEntry 62602 }


	iqudc30MenuOutputLoggingOutput1State62603 OBJECT-TYPE
		SYNTAX		RollCallString
		MAX-ACCESS		read-only
		STATUS			current
		DESCRIPTION
				"TYPE: - Display
				 PAGE: - Output Logging
					Output 1 State=  cmdID= 62603  format=   "
		::= { iqudc30CmdEntry 62603 }


	iqudc30MenuOutputLoggingOutput1Std62604 OBJECT-TYPE
		SYNTAX		INTEGER { disable(0), enable(1) }
		MAX-ACCESS		read-write
		STATUS			current
		DESCRIPTION
				"TYPE: - Checkbox
				 PAGE: - Output Logging
					Output 1 Std.  cmdID= 62604 "
		::= { iqudc30CmdEntry 62604 }


	iqudc30MenuOutputLoggingOutput1Std62605 OBJECT-TYPE
		SYNTAX		RollCallString
		MAX-ACCESS		read-only
		STATUS			current
		DESCRIPTION
				"TYPE: - Display
				 PAGE: - Output Logging
					Output 1 Std.=  cmdID= 62605  format=   "
		::= { iqudc30CmdEntry 62605 }


	iqudc30MenuOutputLoggingOutput2Type62612 OBJECT-TYPE
		SYNTAX		INTEGER { disable(0), enable(1) }
		MAX-ACCESS		read-write
		STATUS			current
		DESCRIPTION
				"TYPE: - Checkbox
				 PAGE: - Output Logging
					Output 2 Type  cmdID= 62612 "
		::= { iqudc30CmdEntry 62612 }


	iqudc30MenuOutputLoggingOutput2Type62613 OBJECT-TYPE
		SYNTAX		RollCallString
		MAX-ACCESS		read-only
		STATUS			current
		DESCRIPTION
				"TYPE: - Display
				 PAGE: - Output Logging
					Output 2 Type=  cmdID= 62613  format=   "
		::= { iqudc30CmdEntry 62613 }


	iqudc30MenuOutputLoggingOutput2State62614 OBJECT-TYPE
		SYNTAX		INTEGER { disable(0), enable(1) }
		MAX-ACCESS		read-write
		STATUS			current
		DESCRIPTION
				"TYPE: - Checkbox
				 PAGE: - Output Logging
					Output 2 State  cmdID= 62614 "
		::= { iqudc30CmdEntry 62614 }


	iqudc30MenuOutputLoggingOutput2State62615 OBJECT-TYPE
		SYNTAX		RollCallString
		MAX-ACCESS		read-only
		STATUS			current
		DESCRIPTION
				"TYPE: - Display
				 PAGE: - Output Logging
					Output 2 State=  cmdID= 62615  format=   "
		::= { iqudc30CmdEntry 62615 }


	iqudc30MenuOutputLoggingOutput2Std62616 OBJECT-TYPE
		SYNTAX		INTEGER { disable(0), enable(1) }
		MAX-ACCESS		read-write
		STATUS			current
		DESCRIPTION
				"TYPE: - Checkbox
				 PAGE: - Output Logging
					Output 2 Std.  cmdID= 62616 "
		::= { iqudc30CmdEntry 62616 }


	iqudc30MenuOutputLoggingOutput2Std62617 OBJECT-TYPE
		SYNTAX		RollCallString
		MAX-ACCESS		read-only
		STATUS			current
		DESCRIPTION
				"TYPE: - Display
				 PAGE: - Output Logging
					Output 2 Std.=  cmdID= 62617  format=   "
		::= { iqudc30CmdEntry 62617 }


	iqudc30MenuOPAudioStateCh1OutputEmbPair1s62620 OBJECT-TYPE
		SYNTAX		INTEGER { disable(0), enable(1) }
		MAX-ACCESS		read-write
		STATUS			current
		DESCRIPTION
				"TYPE: - Checkbox
				 PAGE: - O/P Audio State Ch1
					Output Emb.Pair 1 s  cmdID= 62620 "
		::= { iqudc30CmdEntry 62620 }


	iqudc30MenuOPAudioStateCh1OutputEmbPair1s62621 OBJECT-TYPE
		SYNTAX		RollCallString
		MAX-ACCESS		read-only
		STATUS			current
		DESCRIPTION
				"TYPE: - Display
				 PAGE: - O/P Audio State Ch1
					Output Emb.Pair 1 s  cmdID= 62621  format=   "
		::= { iqudc30CmdEntry 62621 }


	iqudc30MenuOPAudioStateCh1OutputEmbPair2s62622 OBJECT-TYPE
		SYNTAX		INTEGER { disable(0), enable(1) }
		MAX-ACCESS		read-write
		STATUS			current
		DESCRIPTION
				"TYPE: - Checkbox
				 PAGE: - O/P Audio State Ch1
					Output Emb.Pair 2 s  cmdID= 62622 "
		::= { iqudc30CmdEntry 62622 }


	iqudc30MenuOPAudioStateCh1OutputEmbPair2s62623 OBJECT-TYPE
		SYNTAX		RollCallString
		MAX-ACCESS		read-only
		STATUS			current
		DESCRIPTION
				"TYPE: - Display
				 PAGE: - O/P Audio State Ch1
					Output Emb.Pair 2 s  cmdID= 62623  format=   "
		::= { iqudc30CmdEntry 62623 }


	iqudc30MenuOPAudioStateCh1OutputEmbPair3s62624 OBJECT-TYPE
		SYNTAX		INTEGER { disable(0), enable(1) }
		MAX-ACCESS		read-write
		STATUS			current
		DESCRIPTION
				"TYPE: - Checkbox
				 PAGE: - O/P Audio State Ch1
					Output Emb.Pair 3 s  cmdID= 62624 "
		::= { iqudc30CmdEntry 62624 }


	iqudc30MenuOPAudioStateCh1OutputEmbPair3s62625 OBJECT-TYPE
		SYNTAX		RollCallString
		MAX-ACCESS		read-only
		STATUS			current
		DESCRIPTION
				"TYPE: - Display
				 PAGE: - O/P Audio State Ch1
					Output Emb.Pair 3 s  cmdID= 62625  format=   "
		::= { iqudc30CmdEntry 62625 }


	iqudc30MenuOPAudioStateCh1OutputEmbPair4s62626 OBJECT-TYPE
		SYNTAX		INTEGER { disable(0), enable(1) }
		MAX-ACCESS		read-write
		STATUS			current
		DESCRIPTION
				"TYPE: - Checkbox
				 PAGE: - O/P Audio State Ch1
					Output Emb.Pair 4 s  cmdID= 62626 "
		::= { iqudc30CmdEntry 62626 }


	iqudc30MenuOPAudioStateCh1OutputEmbPair4s62627 OBJECT-TYPE
		SYNTAX		RollCallString
		MAX-ACCESS		read-only
		STATUS			current
		DESCRIPTION
				"TYPE: - Display
				 PAGE: - O/P Audio State Ch1
					Output Emb.Pair 4 s  cmdID= 62627  format=   "
		::= { iqudc30CmdEntry 62627 }


	iqudc30MenuOPAudioStateCh1OutputEmbPair5s62628 OBJECT-TYPE
		SYNTAX		INTEGER { disable(0), enable(1) }
		MAX-ACCESS		read-write
		STATUS			current
		DESCRIPTION
				"TYPE: - Checkbox
				 PAGE: - O/P Audio State Ch1
					Output Emb.Pair 5 s  cmdID= 62628 "
		::= { iqudc30CmdEntry 62628 }


	iqudc30MenuOPAudioStateCh1OutputEmbPair5s62629 OBJECT-TYPE
		SYNTAX		RollCallString
		MAX-ACCESS		read-only
		STATUS			current
		DESCRIPTION
				"TYPE: - Display
				 PAGE: - O/P Audio State Ch1
					Output Emb.Pair 5 s  cmdID= 62629  format=   "
		::= { iqudc30CmdEntry 62629 }


	iqudc30MenuOPAudioStateCh1OutputEmbPair6s62630 OBJECT-TYPE
		SYNTAX		INTEGER { disable(0), enable(1) }
		MAX-ACCESS		read-write
		STATUS			current
		DESCRIPTION
				"TYPE: - Checkbox
				 PAGE: - O/P Audio State Ch1
					Output Emb.Pair 6 s  cmdID= 62630 "
		::= { iqudc30CmdEntry 62630 }


	iqudc30MenuOPAudioStateCh1OutputEmbPair6s62631 OBJECT-TYPE
		SYNTAX		RollCallString
		MAX-ACCESS		read-only
		STATUS			current
		DESCRIPTION
				"TYPE: - Display
				 PAGE: - O/P Audio State Ch1
					Output Emb.Pair 6 s  cmdID= 62631  format=   "
		::= { iqudc30CmdEntry 62631 }


	iqudc30MenuOPAudioStateCh1OutputEmbPair7s62632 OBJECT-TYPE
		SYNTAX		INTEGER { disable(0), enable(1) }
		MAX-ACCESS		read-write
		STATUS			current
		DESCRIPTION
				"TYPE: - Checkbox
				 PAGE: - O/P Audio State Ch1
					Output Emb.Pair 7 s  cmdID= 62632 "
		::= { iqudc30CmdEntry 62632 }


	iqudc30MenuOPAudioStateCh1OutputEmbPair7s62633 OBJECT-TYPE
		SYNTAX		RollCallString
		MAX-ACCESS		read-only
		STATUS			current
		DESCRIPTION
				"TYPE: - Display
				 PAGE: - O/P Audio State Ch1
					Output Emb.Pair 7 s  cmdID= 62633  format=   "
		::= { iqudc30CmdEntry 62633 }


	iqudc30MenuOPAudioStateCh1OutputEmbPair8s62634 OBJECT-TYPE
		SYNTAX		INTEGER { disable(0), enable(1) }
		MAX-ACCESS		read-write
		STATUS			current
		DESCRIPTION
				"TYPE: - Checkbox
				 PAGE: - O/P Audio State Ch1
					Output Emb.Pair 8 s  cmdID= 62634 "
		::= { iqudc30CmdEntry 62634 }


	iqudc30MenuOPAudioStateCh1OutputEmbPair8s62635 OBJECT-TYPE
		SYNTAX		RollCallString
		MAX-ACCESS		read-only
		STATUS			current
		DESCRIPTION
				"TYPE: - Display
				 PAGE: - O/P Audio State Ch1
					Output Emb.Pair 8 s  cmdID= 62635  format=   "
		::= { iqudc30CmdEntry 62635 }


	iqudc30MenuOPAudioStateCh2OutputEmbPair1s62636 OBJECT-TYPE
		SYNTAX		INTEGER { disable(0), enable(1) }
		MAX-ACCESS		read-write
		STATUS			current
		DESCRIPTION
				"TYPE: - Checkbox
				 PAGE: - O/P Audio State Ch2
					Output Emb.Pair 1 s  cmdID= 62636 "
		::= { iqudc30CmdEntry 62636 }


	iqudc30MenuOPAudioStateCh2OutputEmbPair1s62637 OBJECT-TYPE
		SYNTAX		RollCallString
		MAX-ACCESS		read-only
		STATUS			current
		DESCRIPTION
				"TYPE: - Display
				 PAGE: - O/P Audio State Ch2
					Output Emb.Pair 1 s  cmdID= 62637  format=   "
		::= { iqudc30CmdEntry 62637 }


	iqudc30MenuOPAudioStateCh2OutputEmbPair2s62638 OBJECT-TYPE
		SYNTAX		INTEGER { disable(0), enable(1) }
		MAX-ACCESS		read-write
		STATUS			current
		DESCRIPTION
				"TYPE: - Checkbox
				 PAGE: - O/P Audio State Ch2
					Output Emb.Pair 2 s  cmdID= 62638 "
		::= { iqudc30CmdEntry 62638 }


	iqudc30MenuOPAudioStateCh2OutputEmbPair2s62639 OBJECT-TYPE
		SYNTAX		RollCallString
		MAX-ACCESS		read-only
		STATUS			current
		DESCRIPTION
				"TYPE: - Display
				 PAGE: - O/P Audio State Ch2
					Output Emb.Pair 2 s  cmdID= 62639  format=   "
		::= { iqudc30CmdEntry 62639 }


	iqudc30MenuOPAudioStateCh2OutputEmbPair3s62640 OBJECT-TYPE
		SYNTAX		INTEGER { disable(0), enable(1) }
		MAX-ACCESS		read-write
		STATUS			current
		DESCRIPTION
				"TYPE: - Checkbox
				 PAGE: - O/P Audio State Ch2
					Output Emb.Pair 3 s  cmdID= 62640 "
		::= { iqudc30CmdEntry 62640 }


	iqudc30MenuOPAudioStateCh2OutputEmbPair3s62641 OBJECT-TYPE
		SYNTAX		RollCallString
		MAX-ACCESS		read-only
		STATUS			current
		DESCRIPTION
				"TYPE: - Display
				 PAGE: - O/P Audio State Ch2
					Output Emb.Pair 3 s  cmdID= 62641  format=   "
		::= { iqudc30CmdEntry 62641 }


	iqudc30MenuOPAudioStateCh2OutputEmbPair4s62642 OBJECT-TYPE
		SYNTAX		INTEGER { disable(0), enable(1) }
		MAX-ACCESS		read-write
		STATUS			current
		DESCRIPTION
				"TYPE: - Checkbox
				 PAGE: - O/P Audio State Ch2
					Output Emb.Pair 4 s  cmdID= 62642 "
		::= { iqudc30CmdEntry 62642 }


	iqudc30MenuOPAudioStateCh2OutputEmbPair4s62643 OBJECT-TYPE
		SYNTAX		RollCallString
		MAX-ACCESS		read-only
		STATUS			current
		DESCRIPTION
				"TYPE: - Display
				 PAGE: - O/P Audio State Ch2
					Output Emb.Pair 4 s  cmdID= 62643  format=   "
		::= { iqudc30CmdEntry 62643 }


	iqudc30MenuOPAudioStateCh2OutputEmbPair5s62644 OBJECT-TYPE
		SYNTAX		INTEGER { disable(0), enable(1) }
		MAX-ACCESS		read-write
		STATUS			current
		DESCRIPTION
				"TYPE: - Checkbox
				 PAGE: - O/P Audio State Ch2
					Output Emb.Pair 5 s  cmdID= 62644 "
		::= { iqudc30CmdEntry 62644 }


	iqudc30MenuOPAudioStateCh2OutputEmbPair5s62645 OBJECT-TYPE
		SYNTAX		RollCallString
		MAX-ACCESS		read-only
		STATUS			current
		DESCRIPTION
				"TYPE: - Display
				 PAGE: - O/P Audio State Ch2
					Output Emb.Pair 5 s  cmdID= 62645  format=   "
		::= { iqudc30CmdEntry 62645 }


	iqudc30MenuOPAudioStateCh2OutputEmbPair6s62646 OBJECT-TYPE
		SYNTAX		INTEGER { disable(0), enable(1) }
		MAX-ACCESS		read-write
		STATUS			current
		DESCRIPTION
				"TYPE: - Checkbox
				 PAGE: - O/P Audio State Ch2
					Output Emb.Pair 6 s  cmdID= 62646 "
		::= { iqudc30CmdEntry 62646 }


	iqudc30MenuOPAudioStateCh2OutputEmbPair6s62647 OBJECT-TYPE
		SYNTAX		RollCallString
		MAX-ACCESS		read-only
		STATUS			current
		DESCRIPTION
				"TYPE: - Display
				 PAGE: - O/P Audio State Ch2
					Output Emb.Pair 6 s  cmdID= 62647  format=   "
		::= { iqudc30CmdEntry 62647 }


	iqudc30MenuOPAudioStateCh2OutputEmbPair7s62648 OBJECT-TYPE
		SYNTAX		INTEGER { disable(0), enable(1) }
		MAX-ACCESS		read-write
		STATUS			current
		DESCRIPTION
				"TYPE: - Checkbox
				 PAGE: - O/P Audio State Ch2
					Output Emb.Pair 7 s  cmdID= 62648 "
		::= { iqudc30CmdEntry 62648 }


	iqudc30MenuOPAudioStateCh2OutputEmbPair7s62649 OBJECT-TYPE
		SYNTAX		RollCallString
		MAX-ACCESS		read-only
		STATUS			current
		DESCRIPTION
				"TYPE: - Display
				 PAGE: - O/P Audio State Ch2
					Output Emb.Pair 7 s  cmdID= 62649  format=   "
		::= { iqudc30CmdEntry 62649 }


	iqudc30MenuOPAudioStateCh2OutputEmbPair8s62650 OBJECT-TYPE
		SYNTAX		INTEGER { disable(0), enable(1) }
		MAX-ACCESS		read-write
		STATUS			current
		DESCRIPTION
				"TYPE: - Checkbox
				 PAGE: - O/P Audio State Ch2
					Output Emb.Pair 8 s  cmdID= 62650 "
		::= { iqudc30CmdEntry 62650 }


	iqudc30MenuOPAudioStateCh2OutputEmbPair8s62651 OBJECT-TYPE
		SYNTAX		RollCallString
		MAX-ACCESS		read-only
		STATUS			current
		DESCRIPTION
				"TYPE: - Display
				 PAGE: - O/P Audio State Ch2
					Output Emb.Pair 8 s  cmdID= 62651  format=   "
		::= { iqudc30CmdEntry 62651 }


	iqudc30MenuOPAudioStateCh2NewDisplay OBJECT-TYPE
		SYNTAX		RollCallString
		MAX-ACCESS		read-only
		STATUS			current
		DESCRIPTION
				"TYPE: - Display
				 PAGE: - O/P Audio State Ch2
					New Display  cmdID= 62652  format=   "
		::= { iqudc30CmdEntry 62652 }


	iqudc30MenuOPAudioTypeCh1OutputEmbPair1t62653 OBJECT-TYPE
		SYNTAX		INTEGER { disable(0), enable(1) }
		MAX-ACCESS		read-write
		STATUS			current
		DESCRIPTION
				"TYPE: - Checkbox
				 PAGE: - O/P Audio Type Ch1 
					Output Emb.Pair 1 t  cmdID= 62653 "
		::= { iqudc30CmdEntry 62653 }


	iqudc30MenuOPAudioTypeCh1OutputEmbPair1t62654 OBJECT-TYPE
		SYNTAX		RollCallString
		MAX-ACCESS		read-only
		STATUS			current
		DESCRIPTION
				"TYPE: - Display
				 PAGE: - O/P Audio Type Ch1 
					Output Emb.Pair 1 t  cmdID= 62654  format=   "
		::= { iqudc30CmdEntry 62654 }


	iqudc30MenuOPAudioTypeCh1OutputEmbPair2t OBJECT-TYPE
		SYNTAX		INTEGER { disable(0), enable(1) }
		MAX-ACCESS		read-write
		STATUS			current
		DESCRIPTION
				"TYPE: - Checkbox
				 PAGE: - O/P Audio Type Ch1 
					Output Emb.Pair 2 t  cmdID= 62655 "
		::= { iqudc30CmdEntry 62655 }


	iqudc30MenuOPAudioTypeCh1OutputEmbPair2s OBJECT-TYPE
		SYNTAX		RollCallString
		MAX-ACCESS		read-only
		STATUS			current
		DESCRIPTION
				"TYPE: - Display
				 PAGE: - O/P Audio Type Ch1 
					Output Emb.Pair 2 s  cmdID= 62656  format=   "
		::= { iqudc30CmdEntry 62656 }


	iqudc30MenuOPAudioTypeCh1OutputEmbPair3t62657 OBJECT-TYPE
		SYNTAX		INTEGER { disable(0), enable(1) }
		MAX-ACCESS		read-write
		STATUS			current
		DESCRIPTION
				"TYPE: - Checkbox
				 PAGE: - O/P Audio Type Ch1 
					Output Emb.Pair 3 t  cmdID= 62657 "
		::= { iqudc30CmdEntry 62657 }


	iqudc30MenuOPAudioTypeCh1OutputEmbPair3t62658 OBJECT-TYPE
		SYNTAX		RollCallString
		MAX-ACCESS		read-only
		STATUS			current
		DESCRIPTION
				"TYPE: - Display
				 PAGE: - O/P Audio Type Ch1 
					Output Emb.Pair 3 t  cmdID= 62658  format=   "
		::= { iqudc30CmdEntry 62658 }


	iqudc30MenuOPAudioTypeCh1OutputEmbPair4t62659 OBJECT-TYPE
		SYNTAX		INTEGER { disable(0), enable(1) }
		MAX-ACCESS		read-write
		STATUS			current
		DESCRIPTION
				"TYPE: - Checkbox
				 PAGE: - O/P Audio Type Ch1 
					Output Emb.Pair 4 t  cmdID= 62659 "
		::= { iqudc30CmdEntry 62659 }


	iqudc30MenuOPAudioTypeCh1OutputEmbPair4t62660 OBJECT-TYPE
		SYNTAX		RollCallString
		MAX-ACCESS		read-only
		STATUS			current
		DESCRIPTION
				"TYPE: - Display
				 PAGE: - O/P Audio Type Ch1 
					Output Emb.Pair 4 t  cmdID= 62660  format=   "
		::= { iqudc30CmdEntry 62660 }


	iqudc30MenuOPAudioTypeCh1OutputEmbPair5t62661 OBJECT-TYPE
		SYNTAX		INTEGER { disable(0), enable(1) }
		MAX-ACCESS		read-write
		STATUS			current
		DESCRIPTION
				"TYPE: - Checkbox
				 PAGE: - O/P Audio Type Ch1 
					Output Emb.Pair 5 t  cmdID= 62661 "
		::= { iqudc30CmdEntry 62661 }


	iqudc30MenuOPAudioTypeCh1OutputEmbPair5t62662 OBJECT-TYPE
		SYNTAX		RollCallString
		MAX-ACCESS		read-only
		STATUS			current
		DESCRIPTION
				"TYPE: - Display
				 PAGE: - O/P Audio Type Ch1 
					Output Emb.Pair 5 t  cmdID= 62662  format=   "
		::= { iqudc30CmdEntry 62662 }


	iqudc30MenuOPAudioTypeCh1OutputEmbPair6t62663 OBJECT-TYPE
		SYNTAX		INTEGER { disable(0), enable(1) }
		MAX-ACCESS		read-write
		STATUS			current
		DESCRIPTION
				"TYPE: - Checkbox
				 PAGE: - O/P Audio Type Ch1 
					Output Emb.Pair 6 t  cmdID= 62663 "
		::= { iqudc30CmdEntry 62663 }


	iqudc30MenuOPAudioTypeCh1OutputEmbPair6t62664 OBJECT-TYPE
		SYNTAX		RollCallString
		MAX-ACCESS		read-only
		STATUS			current
		DESCRIPTION
				"TYPE: - Display
				 PAGE: - O/P Audio Type Ch1 
					Output Emb.Pair 6 t  cmdID= 62664  format=   "
		::= { iqudc30CmdEntry 62664 }


	iqudc30MenuOPAudioTypeCh1OutputEmbPair7t62665 OBJECT-TYPE
		SYNTAX		INTEGER { disable(0), enable(1) }
		MAX-ACCESS		read-write
		STATUS			current
		DESCRIPTION
				"TYPE: - Checkbox
				 PAGE: - O/P Audio Type Ch1 
					Output Emb.Pair 7 t  cmdID= 62665 "
		::= { iqudc30CmdEntry 62665 }


	iqudc30MenuOPAudioTypeCh1OutputEmbPair7t62666 OBJECT-TYPE
		SYNTAX		RollCallString
		MAX-ACCESS		read-only
		STATUS			current
		DESCRIPTION
				"TYPE: - Display
				 PAGE: - O/P Audio Type Ch1 
					Output Emb.Pair 7 t  cmdID= 62666  format=   "
		::= { iqudc30CmdEntry 62666 }


	iqudc30MenuOPAudioTypeCh1OutputEmbPair8t62667 OBJECT-TYPE
		SYNTAX		INTEGER { disable(0), enable(1) }
		MAX-ACCESS		read-write
		STATUS			current
		DESCRIPTION
				"TYPE: - Checkbox
				 PAGE: - O/P Audio Type Ch1 
					Output Emb.Pair 8 t  cmdID= 62667 "
		::= { iqudc30CmdEntry 62667 }


	iqudc30MenuOPAudioTypeCh1OutputEmbPair8t62668 OBJECT-TYPE
		SYNTAX		RollCallString
		MAX-ACCESS		read-only
		STATUS			current
		DESCRIPTION
				"TYPE: - Display
				 PAGE: - O/P Audio Type Ch1 
					Output Emb.Pair 8 t  cmdID= 62668  format=   "
		::= { iqudc30CmdEntry 62668 }


	iqudc30MenuOPAudioTypeCh2OutputEmbPair1t62669 OBJECT-TYPE
		SYNTAX		INTEGER { disable(0), enable(1) }
		MAX-ACCESS		read-write
		STATUS			current
		DESCRIPTION
				"TYPE: - Checkbox
				 PAGE: - O/P Audio Type Ch2 
					Output Emb.Pair 1 t  cmdID= 62669 "
		::= { iqudc30CmdEntry 62669 }


	iqudc30MenuOPAudioTypeCh2OutputEmbPair1t62670 OBJECT-TYPE
		SYNTAX		RollCallString
		MAX-ACCESS		read-only
		STATUS			current
		DESCRIPTION
				"TYPE: - Display
				 PAGE: - O/P Audio Type Ch2 
					Output Emb.Pair 1 t  cmdID= 62670  format=   "
		::= { iqudc30CmdEntry 62670 }


	iqudc30MenuOPAudioTypeCh2OutputEmbPair2t62671 OBJECT-TYPE
		SYNTAX		INTEGER { disable(0), enable(1) }
		MAX-ACCESS		read-write
		STATUS			current
		DESCRIPTION
				"TYPE: - Checkbox
				 PAGE: - O/P Audio Type Ch2 
					Output Emb.Pair 2 t  cmdID= 62671 "
		::= { iqudc30CmdEntry 62671 }


	iqudc30MenuOPAudioTypeCh2OutputEmbPair2t62672 OBJECT-TYPE
		SYNTAX		RollCallString
		MAX-ACCESS		read-only
		STATUS			current
		DESCRIPTION
				"TYPE: - Display
				 PAGE: - O/P Audio Type Ch2 
					Output Emb.Pair 2 t  cmdID= 62672  format=   "
		::= { iqudc30CmdEntry 62672 }


	iqudc30MenuOPAudioTypeCh2OutputEmbPair3t62673 OBJECT-TYPE
		SYNTAX		INTEGER { disable(0), enable(1) }
		MAX-ACCESS		read-write
		STATUS			current
		DESCRIPTION
				"TYPE: - Checkbox
				 PAGE: - O/P Audio Type Ch2 
					Output Emb.Pair 3 t  cmdID= 62673 "
		::= { iqudc30CmdEntry 62673 }


	iqudc30MenuOPAudioTypeCh2OutputEmbPair3t62674 OBJECT-TYPE
		SYNTAX		RollCallString
		MAX-ACCESS		read-only
		STATUS			current
		DESCRIPTION
				"TYPE: - Display
				 PAGE: - O/P Audio Type Ch2 
					Output Emb.Pair 3 t  cmdID= 62674  format=   "
		::= { iqudc30CmdEntry 62674 }


	iqudc30MenuOPAudioTypeCh2OutputEmbPair4t62675 OBJECT-TYPE
		SYNTAX		INTEGER { disable(0), enable(1) }
		MAX-ACCESS		read-write
		STATUS			current
		DESCRIPTION
				"TYPE: - Checkbox
				 PAGE: - O/P Audio Type Ch2 
					Output Emb.Pair 4 t  cmdID= 62675 "
		::= { iqudc30CmdEntry 62675 }


	iqudc30MenuOPAudioTypeCh2OutputEmbPair4t62676 OBJECT-TYPE
		SYNTAX		RollCallString
		MAX-ACCESS		read-only
		STATUS			current
		DESCRIPTION
				"TYPE: - Display
				 PAGE: - O/P Audio Type Ch2 
					Output Emb.Pair 4 t  cmdID= 62676  format=   "
		::= { iqudc30CmdEntry 62676 }


	iqudc30MenuOPAudioTypeCh2OutputEmbPair5t62677 OBJECT-TYPE
		SYNTAX		INTEGER { disable(0), enable(1) }
		MAX-ACCESS		read-write
		STATUS			current
		DESCRIPTION
				"TYPE: - Checkbox
				 PAGE: - O/P Audio Type Ch2 
					Output Emb.Pair 5 t  cmdID= 62677 "
		::= { iqudc30CmdEntry 62677 }


	iqudc30MenuOPAudioTypeCh2OutputEmbPair5t62678 OBJECT-TYPE
		SYNTAX		RollCallString
		MAX-ACCESS		read-only
		STATUS			current
		DESCRIPTION
				"TYPE: - Display
				 PAGE: - O/P Audio Type Ch2 
					Output Emb.Pair 5 t  cmdID= 62678  format=   "
		::= { iqudc30CmdEntry 62678 }


	iqudc30MenuOPAudioTypeCh2OutputEmbPair6t62679 OBJECT-TYPE
		SYNTAX		INTEGER { disable(0), enable(1) }
		MAX-ACCESS		read-write
		STATUS			current
		DESCRIPTION
				"TYPE: - Checkbox
				 PAGE: - O/P Audio Type Ch2 
					Output Emb.Pair 6 t  cmdID= 62679 "
		::= { iqudc30CmdEntry 62679 }


	iqudc30MenuOPAudioTypeCh2OutputEmbPair6t62680 OBJECT-TYPE
		SYNTAX		RollCallString
		MAX-ACCESS		read-only
		STATUS			current
		DESCRIPTION
				"TYPE: - Display
				 PAGE: - O/P Audio Type Ch2 
					Output Emb.Pair 6 t  cmdID= 62680  format=   "
		::= { iqudc30CmdEntry 62680 }


	iqudc30MenuOPAudioTypeCh2OutputEmbPair7t62681 OBJECT-TYPE
		SYNTAX		INTEGER { disable(0), enable(1) }
		MAX-ACCESS		read-write
		STATUS			current
		DESCRIPTION
				"TYPE: - Checkbox
				 PAGE: - O/P Audio Type Ch2 
					Output Emb.Pair 7 t  cmdID= 62681 "
		::= { iqudc30CmdEntry 62681 }


	iqudc30MenuOPAudioTypeCh2OutputEmbPair7t62682 OBJECT-TYPE
		SYNTAX		RollCallString
		MAX-ACCESS		read-only
		STATUS			current
		DESCRIPTION
				"TYPE: - Display
				 PAGE: - O/P Audio Type Ch2 
					Output Emb.Pair 7 t  cmdID= 62682  format=   "
		::= { iqudc30CmdEntry 62682 }


	iqudc30MenuOPAudioTypeCh2OutputEmbPair8t62683 OBJECT-TYPE
		SYNTAX		INTEGER { disable(0), enable(1) }
		MAX-ACCESS		read-write
		STATUS			current
		DESCRIPTION
				"TYPE: - Checkbox
				 PAGE: - O/P Audio Type Ch2 
					Output Emb.Pair 8 t  cmdID= 62683 "
		::= { iqudc30CmdEntry 62683 }


	iqudc30MenuOPAudioTypeCh2OutputEmbPair8t62684 OBJECT-TYPE
		SYNTAX		RollCallString
		MAX-ACCESS		read-only
		STATUS			current
		DESCRIPTION
				"TYPE: - Display
				 PAGE: - O/P Audio Type Ch2 
					Output Emb.Pair 8 t  cmdID= 62684  format=   "
		::= { iqudc30CmdEntry 62684 }


	iqudc30MenuOPAudioTypeCh2NewDisplay OBJECT-TYPE
		SYNTAX		RollCallString
		MAX-ACCESS		read-only
		STATUS			current
		DESCRIPTION
				"TYPE: - Display
				 PAGE: - O/P Audio Type Ch2 
					New Display  cmdID= 62685  format=   "
		::= { iqudc30CmdEntry 62685 }


	iqudc30MenuSetupSoftwareVersion OBJECT-TYPE
		SYNTAX		RollCallString
		MAX-ACCESS		read-only
		STATUS			current
		DESCRIPTION
				"TYPE: - Display
				 PAGE: - Setup
					Software Version  cmdID= 2  format=   "
		::= { iqudc30CmdEntry 2 }


	iqudc30MenuSetupSerialNumber OBJECT-TYPE
		SYNTAX		RollCallString
		MAX-ACCESS		read-only
		STATUS			current
		DESCRIPTION
				"TYPE: - Display
				 PAGE: - Setup
					Serial Number  cmdID= 1  format=   "
		::= { iqudc30CmdEntry 1 }


	iqudc30MenuSetupNumberOfChannels OBJECT-TYPE
		SYNTAX		RollCallString
		MAX-ACCESS		read-only
		STATUS			current
		DESCRIPTION
				"TYPE: - Display
				 PAGE: - Setup
					Number Of Channels  cmdID= 44456  format=   "
		::= { iqudc30CmdEntry 44456 }


	iqudc30MenuSetupFrameSlotNumber OBJECT-TYPE
		SYNTAX		RollCallString
		MAX-ACCESS		read-only
		STATUS			current
		DESCRIPTION
				"TYPE: - Display
				 PAGE: - Setup
					Frame Slot Number  cmdID= 44455  format=   "
		::= { iqudc30CmdEntry 44455 }


	iqudc30MenuSetupRearId OBJECT-TYPE
		SYNTAX		RollCallString
		MAX-ACCESS		read-only
		STATUS			current
		DESCRIPTION
				"TYPE: - Display
				 PAGE: - Setup
					Rear Id  cmdID= 44444  format=   "
		::= { iqudc30CmdEntry 44444 }


	iqudc30MenuSetupFanSpeed OBJECT-TYPE
		SYNTAX		RollCallString
		MAX-ACCESS		read-only
		STATUS			current
		DESCRIPTION
				"TYPE: - Display
				 PAGE: - Setup
					Fan Speed  cmdID= 61003  format=   "
		::= { iqudc30CmdEntry 61003 }


	iqudc30MenuSetupIQOPTMNR OBJECT-TYPE
		SYNTAX		RollCallString
		MAX-ACCESS		read-only
		STATUS			current
		DESCRIPTION
				"TYPE: - Display
				 PAGE: - Setup
					IQOPTM-NR  cmdID= 62687  format=   "
		::= { iqudc30CmdEntry 62687 }


	iqudc30MenuSetupIQOPTMSBK OBJECT-TYPE
		SYNTAX		RollCallString
		MAX-ACCESS		read-only
		STATUS			current
		DESCRIPTION
				"TYPE: - Display
				 PAGE: - Setup
					IQOPTM-SBK  cmdID= 62688  format=   "
		::= { iqudc30CmdEntry 62688 }


	iqudc30MenuSetupIQOPTMLFR OBJECT-TYPE
		SYNTAX		RollCallString
		MAX-ACCESS		read-only
		STATUS			current
		DESCRIPTION
				"TYPE: - Display
				 PAGE: - Setup
					IQOPTM-LFR  cmdID= 62691  format=   "
		::= { iqudc30CmdEntry 62691 }


	iqudc30MenuSetupIQOPTMLOG OBJECT-TYPE
		SYNTAX		RollCallString
		MAX-ACCESS		read-only
		STATUS			current
		DESCRIPTION
				"TYPE: - Display
				 PAGE: - Setup
					IQOPTM-LOG  cmdID= 62692  format=   "
		::= { iqudc30CmdEntry 62692 }


	iqudc30MenuSetupIQOPTMLC OBJECT-TYPE
		SYNTAX		RollCallString
		MAX-ACCESS		read-only
		STATUS			current
		DESCRIPTION
				"TYPE: - Display
				 PAGE: - Setup
					IQOPTM-LC  cmdID= 62693  format=   "
		::= { iqudc30CmdEntry 62693 }


	iqudc30MenuSetupIQOPTMDBD OBJECT-TYPE
		SYNTAX		RollCallString
		MAX-ACCESS		read-only
		STATUS			current
		DESCRIPTION
				"TYPE: - Display
				 PAGE: - Setup
					IQOPTM-DBD  cmdID= 62694  format=   "
		::= { iqudc30CmdEntry 62694 }


	iqudc30MenuSetupIQOPTMDBEE OBJECT-TYPE
		SYNTAX		RollCallString
		MAX-ACCESS		read-only
		STATUS			current
		DESCRIPTION
				"TYPE: - Display
				 PAGE: - Setup
					IQOPTM-DBE-E  cmdID= 62695  format=   "
		::= { iqudc30CmdEntry 62695 }


	iqudc30MenuSetupIQOPTMDBED OBJECT-TYPE
		SYNTAX		RollCallString
		MAX-ACCESS		read-only
		STATUS			current
		DESCRIPTION
				"TYPE: - Display
				 PAGE: - Setup
					IQOPTM-DBE-D  cmdID= 62696  format=   "
		::= { iqudc30CmdEntry 62696 }


	iqudc30MenuSetupIQOPTMLOUDJ OBJECT-TYPE
		SYNTAX		RollCallString
		MAX-ACCESS		read-only
		STATUS			current
		DESCRIPTION
				"TYPE: - Display
				 PAGE: - Setup
					IQOPTM-LOUD-J  cmdID= 62697  format=   "
		::= { iqudc30CmdEntry 62697 }


	iqudc30MenuSetupIQOPTMLOUDMC OBJECT-TYPE
		SYNTAX		RollCallString
		MAX-ACCESS		read-only
		STATUS			current
		DESCRIPTION
				"TYPE: - Display
				 PAGE: - Setup
					IQOPTM-LOUD-MC  cmdID= 62698  format=   "
		::= { iqudc30CmdEntry 62698 }


	iqudc30MenuSetupBuild OBJECT-TYPE
		SYNTAX		RollCallString
		MAX-ACCESS		read-only
		STATUS			current
		DESCRIPTION
				"TYPE: - Display
				 PAGE: - Setup
					Build  cmdID= 62689  format=   "
		::= { iqudc30CmdEntry 62689 }


	iqudc30MenuSetupLicencedOptionsH OBJECT-TYPE
		SYNTAX		RollCallString
		MAX-ACCESS		read-only
		STATUS			current
		DESCRIPTION
				"TYPE: - Display
				 PAGE: - Setup
					Licenced Options (H  cmdID= 62690  format=   "
		::= { iqudc30CmdEntry 62690 }


	iqudc30MenuSetupFactoryDefaults OBJECT-TYPE
		SYNTAX		INTEGER { noAction(0),val-Factory-Defaults(1) }
		MAX-ACCESS		read-write
		STATUS			current
		DESCRIPTION
				"TYPE: - Button
				 PAGE: - Setup
					Factory Defaults  cmdID= 55555  value= 1  "
		::= { iqudc30CmdEntry 55555 }


	iqudc30MenuSetupDefaultSettings OBJECT-TYPE
		SYNTAX		INTEGER { noAction(0),val-Default-Settings(1) }
		MAX-ACCESS		read-write
		STATUS			current
		DESCRIPTION
				"TYPE: - Button
				 PAGE: - Setup
					Default Settings  cmdID= 55054  value= 1  "
		::= { iqudc30CmdEntry 55054 }


	iqudc30MenuSetupRestart OBJECT-TYPE
		SYNTAX		INTEGER { noAction(0),val-Restart(1) }
		MAX-ACCESS		read-write
		STATUS			current
		DESCRIPTION
				"TYPE: - Button
				 PAGE: - Setup
					Restart  cmdID= 4  value= 1  "
		::= { iqudc30CmdEntry 4 }


	iqudc30MenuSetupUpgradeStartHide OBJECT-TYPE
		SYNTAX		INTEGER { noAction(0),val-Upgrade-Start-Hide(1) }
		MAX-ACCESS		read-write
		STATUS			current
		DESCRIPTION
				"TYPE: - Button
				 PAGE: - Setup
					Upgrade Start (Hide  cmdID= 5  value= 1  "
		::= { iqudc30CmdEntry 5 }


	iqudc30MenuSetupUpgradeFinishHid OBJECT-TYPE
		SYNTAX		INTEGER { noAction(0),val-Upgrade-Finish-Hid(1) }
		MAX-ACCESS		read-write
		STATUS			current
		DESCRIPTION
				"TYPE: - Button
				 PAGE: - Setup
					Upgrade Finish (Hid  cmdID= 6  value= 1  "
		::= { iqudc30CmdEntry 6 }


	iqudc30MenuDisplaymenu OBJECT-TYPE
		SYNTAX		INTEGER {
							val-Video-Input(0),
							val-Video-Output(1),
							val-Audio(2),
							val-Metadata(3),
							val-Reference(4)
							}
		MAX-ACCESS		read-write
		STATUS			current
		DESCRIPTION
				"TYPE: - RadiobuttonList
				 PAGE: - Displaymenu
					Display  cmdID= 62686 
					Video Input  value= 0  
					Video Output  value= 1  
					Audio  value= 2  
					Metadata  value= 3  
					Reference  value= 4  "
		::= { iqudc30CmdEntry 62686 }


	iqudc30MenuPlaceholderCh1ScrollingCaptionG OBJECT-TYPE
		SYNTAX		RollCallString
		MAX-ACCESS		read-only
		STATUS			current
		DESCRIPTION
				"TYPE: - Display
				 PAGE: - Placeholder-Ch1
					Scrolling Caption G  cmdID= 44459  format=   "
		::= { iqudc30CmdEntry 44459 }


	iqudc30MenuPlaceholderCh1SFPOutputRouting OBJECT-TYPE
		SYNTAX		RollCallString
		MAX-ACCESS		read-only
		STATUS			current
		DESCRIPTION
				"TYPE: - Display
				 PAGE: - Placeholder-Ch1
					SFP Output Routing   cmdID= 20515  format=   "
		::= { iqudc30CmdEntry 20515 }


	iqudc30MenuPlaceholderCh1CVBSEncoderPlaceh OBJECT-TYPE
		SYNTAX		RollCallString
		MAX-ACCESS		read-only
		STATUS			current
		DESCRIPTION
				"TYPE: - Display
				 PAGE: - Placeholder-Ch1
					CVBS Encoder Placeh  cmdID= 20507  format=   "
		::= { iqudc30CmdEntry 20507 }


	iqudc30MenuPlaceholderCh1NonlinearEnhancer OBJECT-TYPE
		SYNTAX		RollCallString
		MAX-ACCESS		read-only
		STATUS			current
		DESCRIPTION
				"TYPE: - Display
				 PAGE: - Placeholder-Ch1
					Nonlinear Enhancer   cmdID= 64120  format=   "
		::= { iqudc30CmdEntry 64120 }


	iqudc30MenuPlaceholderCh1ConversionAperture OBJECT-TYPE
		SYNTAX		RollCallString
		MAX-ACCESS		read-only
		STATUS			current
		DESCRIPTION
				"TYPE: - Display
				 PAGE: - Placeholder-Ch1
					Conversion Aperture  cmdID= 64121  format=   "
		::= { iqudc30CmdEntry 64121 }


	iqudc30MenuPlaceholderCh1NoiseReducerPlace OBJECT-TYPE
		SYNTAX		RollCallString
		MAX-ACCESS		read-only
		STATUS			current
		DESCRIPTION
				"TYPE: - Display
				 PAGE: - Placeholder-Ch1
					Noise Reducer Place  cmdID= 64102  format=   "
		::= { iqudc30CmdEntry 64102 }


	iqudc30MenuPlaceholderCh1UpConversionPlace OBJECT-TYPE
		SYNTAX		RollCallString
		MAX-ACCESS		read-only
		STATUS			current
		DESCRIPTION
				"TYPE: - Display
				 PAGE: - Placeholder-Ch1
					Up Conversion Place  cmdID= 64103  format=   "
		::= { iqudc30CmdEntry 64103 }


	iqudc30MenuPlaceholderCh1GenlockTimingPlac OBJECT-TYPE
		SYNTAX		RollCallString
		MAX-ACCESS		read-only
		STATUS			current
		DESCRIPTION
				"TYPE: - Display
				 PAGE: - Placeholder-Ch1
					Genlock Timing Plac  cmdID= 64201  format=   "
		::= { iqudc30CmdEntry 64201 }


	iqudc30MenuPlaceholderCh1FanSpeedPlacehold OBJECT-TYPE
		SYNTAX		RollCallString
		MAX-ACCESS		read-only
		STATUS			current
		DESCRIPTION
				"TYPE: - Display
				 PAGE: - Placeholder-Ch1
					Fan Speed Placehold  cmdID= 61002  format=   "
		::= { iqudc30CmdEntry 61002 }


	iqudc30MenuPlaceholderCh2InputSourcePlaceh OBJECT-TYPE
		SYNTAX		RollCallString
		MAX-ACCESS		read-only
		STATUS			current
		DESCRIPTION
				"TYPE: - Display
				 PAGE: - Placeholder-Ch2
					Input Source Placeh  cmdID= 44445  format=   "
		::= { iqudc30CmdEntry 44445 }


	iqudc30MenuPlaceholderCh2ScrollingCaptionG OBJECT-TYPE
		SYNTAX		RollCallString
		MAX-ACCESS		read-only
		STATUS			current
		DESCRIPTION
				"TYPE: - Display
				 PAGE: - Placeholder-Ch2
					Scrolling Caption G  cmdID= 44460  format=   "
		::= { iqudc30CmdEntry 44460 }


	iqudc30MenuPlaceholderCh2SFPOutputRouting OBJECT-TYPE
		SYNTAX		RollCallString
		MAX-ACCESS		read-only
		STATUS			current
		DESCRIPTION
				"TYPE: - Display
				 PAGE: - Placeholder-Ch2
					SFP Output Routing   cmdID= 20518  format=   "
		::= { iqudc30CmdEntry 20518 }


	iqudc30MenuPlaceholderCh2CVBSEncoderPlaceh OBJECT-TYPE
		SYNTAX		RollCallString
		MAX-ACCESS		read-only
		STATUS			current
		DESCRIPTION
				"TYPE: - Display
				 PAGE: - Placeholder-Ch2
					CVBS Encoder Placeh  cmdID= 20511  format=   "
		::= { iqudc30CmdEntry 20511 }


	iqudc30MenuPlaceholderCh2NonlinearEnhancer OBJECT-TYPE
		SYNTAX		RollCallString
		MAX-ACCESS		read-only
		STATUS			current
		DESCRIPTION
				"TYPE: - Display
				 PAGE: - Placeholder-Ch2
					Nonlinear Enhancer   cmdID= 64122  format=   "
		::= { iqudc30CmdEntry 64122 }


	iqudc30MenuPlaceholderCh2ConversionAperture OBJECT-TYPE
		SYNTAX		RollCallString
		MAX-ACCESS		read-only
		STATUS			current
		DESCRIPTION
				"TYPE: - Display
				 PAGE: - Placeholder-Ch2
					Conversion Aperture  cmdID= 64123  format=   "
		::= { iqudc30CmdEntry 64123 }


	iqudc30MenuPlaceholderCh2NoiseReducerPlace OBJECT-TYPE
		SYNTAX		RollCallString
		MAX-ACCESS		read-only
		STATUS			current
		DESCRIPTION
				"TYPE: - Display
				 PAGE: - Placeholder-Ch2
					Noise Reducer Place  cmdID= 64202  format=   "
		::= { iqudc30CmdEntry 64202 }


	iqudc30MenuPlaceholderCh2UpConversionPlace OBJECT-TYPE
		SYNTAX		RollCallString
		MAX-ACCESS		read-only
		STATUS			current
		DESCRIPTION
				"TYPE: - Display
				 PAGE: - Placeholder-Ch2
					Up Conversion Place  cmdID= 64203  format=   "
		::= { iqudc30CmdEntry 64203 }


	iqudc30MenuPlaceholderCh2GenlockTimingPlac OBJECT-TYPE
		SYNTAX		RollCallString
		MAX-ACCESS		read-only
		STATUS			current
		DESCRIPTION
				"TYPE: - Display
				 PAGE: - Placeholder-Ch2
					Genlock Timing Plac  cmdID= 64210  format=   "
		::= { iqudc30CmdEntry 64210 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 13130108
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 1
--				: 
-- Comments		: 
--
---------------------------------------------------------------------------------------------------
-- Header		: POWER_USAGE
--
-- MIB ref		: swCardEventLogSlotXX       .11.80.79.87.69.82.95.85.83.65.71.69
-- absolute OID	: 1.3.6.1.4.1.7995.2.6.1.1.XX.11.80.79.87.69.82.95.85.83.65.71.69
-- Vary			: YES
--
-- Value(s)		: 
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: 
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: 
--				: 
-- Comments		: 
--
---------------------------------------------------------------------------------------------------
-- Header		: INPUT_3_TYPE
--
-- MIB ref		: swCardEventLogSlotXX       .12.73.78.80.85.84.95.51.95.84.89.80.69
-- absolute OID	: 1.3.6.1.4.1.7995.2.6.1.1.XX.12.73.78.80.85.84.95.51.95.84.89.80.69
-- Vary			: YES
--
-- Value(s)		: 
--				: 
-- Comments		: 
--
---------------------------------------------------------------------------------------------------
-- Header		: INPUT_4_TYPE
--
-- MIB ref		: swCardEventLogSlotXX       .12.73.78.80.85.84.95.52.95.84.89.80.69
-- absolute OID	: 1.3.6.1.4.1.7995.2.6.1.1.XX.12.73.78.80.85.84.95.52.95.84.89.80.69
-- Vary			: YES
--
-- Value(s)		: 
--				: 
-- Comments		: 
--
---------------------------------------------------------------------------------------------------
-- Header		: INPUT_5_TYPE
--
-- MIB ref		: swCardEventLogSlotXX       .12.73.78.80.85.84.95.53.95.84.89.80.69
-- absolute OID	: 1.3.6.1.4.1.7995.2.6.1.1.XX.12.73.78.80.85.84.95.53.95.84.89.80.69
-- Vary			: YES
--
-- Value(s)		: 
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2014-01-15T09:36:17Z
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: 
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: 
--				: 
-- Comments		: 
--
---------------------------------------------------------------------------------------------------
-- Header		: INPUT_3_STATE
--
-- MIB ref		: swCardEventLogSlotXX       .13.73.78.80.85.84.95.51.95.83.84.65.84.69
-- absolute OID	: 1.3.6.1.4.1.7995.2.6.1.1.XX.13.73.78.80.85.84.95.51.95.83.84.65.84.69
-- Vary			: YES
--
-- Value(s)		: 
--				: 
-- Comments		: 
--
---------------------------------------------------------------------------------------------------
-- Header		: INPUT_4_STATE
--
-- MIB ref		: swCardEventLogSlotXX       .13.73.78.80.85.84.95.52.95.83.84.65.84.69
-- absolute OID	: 1.3.6.1.4.1.7995.2.6.1.1.XX.13.73.78.80.85.84.95.52.95.83.84.65.84.69
-- Vary			: YES
--
-- Value(s)		: 
--				: 
-- Comments		: 
--
---------------------------------------------------------------------------------------------------
-- Header		: INPUT_5_STATE
--
-- MIB ref		: swCardEventLogSlotXX       .13.73.78.80.85.84.95.53.95.83.84.65.84.69
-- absolute OID	: 1.3.6.1.4.1.7995.2.6.1.1.XX.13.73.78.80.85.84.95.53.95.83.84.65.84.69
-- Vary			: YES
--
-- Value(s)		: 
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 
--				: 
-- Comments		: 
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
-- Vary			: YES
--
-- Value(s)		: 
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: 
--				: 
-- Comments		: 
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
-- Vary			: YES
--
-- Value(s)		: 
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: 
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: 
--				: 
-- Comments		: 
--
---------------------------------------------------------------------------------------------------
-- Header		: INPUT_3_STANDARD
--
-- MIB ref		: swCardEventLogSlotXX       .16.73.78.80.85.84.95.51.95.83.84.65.78.68.65.82.68
-- absolute OID	: 1.3.6.1.4.1.7995.2.6.1.1.XX.16.73.78.80.85.84.95.51.95.83.84.65.78.68.65.82.68
-- Vary			: YES
--
-- Value(s)		: 
--				: 
-- Comments		: 
--
---------------------------------------------------------------------------------------------------
-- Header		: INPUT_4_STANDARD
--
-- MIB ref		: swCardEventLogSlotXX       .16.73.78.80.85.84.95.52.95.83.84.65.78.68.65.82.68
-- absolute OID	: 1.3.6.1.4.1.7995.2.6.1.1.XX.16.73.78.80.85.84.95.52.95.83.84.65.78.68.65.82.68
-- Vary			: YES
--
-- Value(s)		: 
--				: 
-- Comments		: 
--
---------------------------------------------------------------------------------------------------
-- Header		: INPUT_5_STANDARD
--
-- MIB ref		: swCardEventLogSlotXX       .16.73.78.80.85.84.95.53.95.83.84.65.78.68.65.82.68
-- absolute OID	: 1.3.6.1.4.1.7995.2.6.1.1.XX.16.73.78.80.85.84.95.53.95.83.84.65.78.68.65.82.68
-- Vary			: YES
--
-- Value(s)		: 
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 
--				: 
-- Comments		: 
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
-- Vary			: YES
--
-- Value(s)		: 
--				: 
-- Comments		: 
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: 
--				: 
-- Comments		: 
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: 
--				: 
-- Comments		: 
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: 
--				: 
-- Comments		: 
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: 
--				: 
-- Comments		: 
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: 
--				: 
-- Comments		: 
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: 
--				: 
-- Comments		: 
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: 
--				: 
-- Comments		: 
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: 
--				: 
-- Comments		: 
--
---------------------------------------------------------------------------------------------------
-- Header		: OUTPUT_2_EMBEDDED_AUDIO_1_TYPE
--
-- MIB ref		: swCardEventLogSlotXX       .30.79.85.84.80.85.84.95.50.95.69.77.66.69.68.68.69.68.95.65.85.68.73.79.95.49.95.84.89.80.69
-- absolute OID	: 1.3.6.1.4.1.7995.2.6.1.1.XX.30.79.85.84.80.85.84.95.50.95.69.77.66.69.68.68.69.68.95.65.85.68.73.79.95.49.95.84.89.80.69
-- Vary			: YES
--
-- Value(s)		: 
--				: 
-- Comments		: 
--
---------------------------------------------------------------------------------------------------
-- Header		: OUTPUT_2_EMBEDDED_AUDIO_2_TYPE
--
-- MIB ref		: swCardEventLogSlotXX       .30.79.85.84.80.85.84.95.50.95.69.77.66.69.68.68.69.68.95.65.85.68.73.79.95.50.95.84.89.80.69
-- absolute OID	: 1.3.6.1.4.1.7995.2.6.1.1.XX.30.79.85.84.80.85.84.95.50.95.69.77.66.69.68.68.69.68.95.65.85.68.73.79.95.50.95.84.89.80.69
-- Vary			: YES
--
-- Value(s)		: 
--				: 
-- Comments		: 
--
---------------------------------------------------------------------------------------------------
-- Header		: OUTPUT_2_EMBEDDED_AUDIO_3_TYPE
--
-- MIB ref		: swCardEventLogSlotXX       .30.79.85.84.80.85.84.95.50.95.69.77.66.69.68.68.69.68.95.65.85.68.73.79.95.51.95.84.89.80.69
-- absolute OID	: 1.3.6.1.4.1.7995.2.6.1.1.XX.30.79.85.84.80.85.84.95.50.95.69.77.66.69.68.68.69.68.95.65.85.68.73.79.95.51.95.84.89.80.69
-- Vary			: YES
--
-- Value(s)		: 
--				: 
-- Comments		: 
--
---------------------------------------------------------------------------------------------------
-- Header		: OUTPUT_2_EMBEDDED_AUDIO_4_TYPE
--
-- MIB ref		: swCardEventLogSlotXX       .30.79.85.84.80.85.84.95.50.95.69.77.66.69.68.68.69.68.95.65.85.68.73.79.95.52.95.84.89.80.69
-- absolute OID	: 1.3.6.1.4.1.7995.2.6.1.1.XX.30.79.85.84.80.85.84.95.50.95.69.77.66.69.68.68.69.68.95.65.85.68.73.79.95.52.95.84.89.80.69
-- Vary			: YES
--
-- Value(s)		: 
--				: 
-- Comments		: 
--
---------------------------------------------------------------------------------------------------
-- Header		: OUTPUT_2_EMBEDDED_AUDIO_5_TYPE
--
-- MIB ref		: swCardEventLogSlotXX       .30.79.85.84.80.85.84.95.50.95.69.77.66.69.68.68.69.68.95.65.85.68.73.79.95.53.95.84.89.80.69
-- absolute OID	: 1.3.6.1.4.1.7995.2.6.1.1.XX.30.79.85.84.80.85.84.95.50.95.69.77.66.69.68.68.69.68.95.65.85.68.73.79.95.53.95.84.89.80.69
-- Vary			: YES
--
-- Value(s)		: 
--				: 
-- Comments		: 
--
---------------------------------------------------------------------------------------------------
-- Header		: OUTPUT_2_EMBEDDED_AUDIO_6_TYPE
--
-- MIB ref		: swCardEventLogSlotXX       .30.79.85.84.80.85.84.95.50.95.69.77.66.69.68.68.69.68.95.65.85.68.73.79.95.54.95.84.89.80.69
-- absolute OID	: 1.3.6.1.4.1.7995.2.6.1.1.XX.30.79.85.84.80.85.84.95.50.95.69.77.66.69.68.68.69.68.95.65.85.68.73.79.95.54.95.84.89.80.69
-- Vary			: YES
--
-- Value(s)		: 
--				: 
-- Comments		: 
--
---------------------------------------------------------------------------------------------------
-- Header		: OUTPUT_2_EMBEDDED_AUDIO_7_TYPE
--
-- MIB ref		: swCardEventLogSlotXX       .30.79.85.84.80.85.84.95.50.95.69.77.66.69.68.68.69.68.95.65.85.68.73.79.95.55.95.84.89.80.69
-- absolute OID	: 1.3.6.1.4.1.7995.2.6.1.1.XX.30.79.85.84.80.85.84.95.50.95.69.77.66.69.68.68.69.68.95.65.85.68.73.79.95.55.95.84.89.80.69
-- Vary			: YES
--
-- Value(s)		: 
--				: 
-- Comments		: 
--
---------------------------------------------------------------------------------------------------
-- Header		: OUTPUT_2_EMBEDDED_AUDIO_8_TYPE
--
-- MIB ref		: swCardEventLogSlotXX       .30.79.85.84.80.85.84.95.50.95.69.77.66.69.68.68.69.68.95.65.85.68.73.79.95.56.95.84.89.80.69
-- absolute OID	: 1.3.6.1.4.1.7995.2.6.1.1.XX.30.79.85.84.80.85.84.95.50.95.69.77.66.69.68.68.69.68.95.65.85.68.73.79.95.56.95.84.89.80.69
-- Vary			: YES
--
-- Value(s)		: 
--				: 
-- Comments		: 
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: 
--				: 
-- Comments		: 
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: 
--				: 
-- Comments		: 
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: 
--				: 
-- Comments		: 
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: 
--				: 
-- Comments		: 
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: 
--				: 
-- Comments		: 
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: 
--				: 
-- Comments		: 
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: 
--				: 
-- Comments		: 
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: 
--				: 
-- Comments		: 
--
---------------------------------------------------------------------------------------------------
-- Header		: OUTPUT_2_EMBEDDED_AUDIO_1_STATE
--
-- MIB ref		: swCardEventLogSlotXX       .31.79.85.84.80.85.84.95.50.95.69.77.66.69.68.68.69.68.95.65.85.68.73.79.95.49.95.83.84.65.84.69
-- absolute OID	: 1.3.6.1.4.1.7995.2.6.1.1.XX.31.79.85.84.80.85.84.95.50.95.69.77.66.69.68.68.69.68.95.65.85.68.73.79.95.49.95.83.84.65.84.69
-- Vary			: YES
--
-- Value(s)		: 
--				: 
-- Comments		: 
--
---------------------------------------------------------------------------------------------------
-- Header		: OUTPUT_2_EMBEDDED_AUDIO_2_STATE
--
-- MIB ref		: swCardEventLogSlotXX       .31.79.85.84.80.85.84.95.50.95.69.77.66.69.68.68.69.68.95.65.85.68.73.79.95.50.95.83.84.65.84.69
-- absolute OID	: 1.3.6.1.4.1.7995.2.6.1.1.XX.31.79.85.84.80.85.84.95.50.95.69.77.66.69.68.68.69.68.95.65.85.68.73.79.95.50.95.83.84.65.84.69
-- Vary			: YES
--
-- Value(s)		: 
--				: 
-- Comments		: 
--
---------------------------------------------------------------------------------------------------
-- Header		: OUTPUT_2_EMBEDDED_AUDIO_3_STATE
--
-- MIB ref		: swCardEventLogSlotXX       .31.79.85.84.80.85.84.95.50.95.69.77.66.69.68.68.69.68.95.65.85.68.73.79.95.51.95.83.84.65.84.69
-- absolute OID	: 1.3.6.1.4.1.7995.2.6.1.1.XX.31.79.85.84.80.85.84.95.50.95.69.77.66.69.68.68.69.68.95.65.85.68.73.79.95.51.95.83.84.65.84.69
-- Vary			: YES
--
-- Value(s)		: 
--				: 
-- Comments		: 
--
---------------------------------------------------------------------------------------------------
-- Header		: OUTPUT_2_EMBEDDED_AUDIO_4_STATE
--
-- MIB ref		: swCardEventLogSlotXX       .31.79.85.84.80.85.84.95.50.95.69.77.66.69.68.68.69.68.95.65.85.68.73.79.95.52.95.83.84.65.84.69
-- absolute OID	: 1.3.6.1.4.1.7995.2.6.1.1.XX.31.79.85.84.80.85.84.95.50.95.69.77.66.69.68.68.69.68.95.65.85.68.73.79.95.52.95.83.84.65.84.69
-- Vary			: YES
--
-- Value(s)		: 
--				: 
-- Comments		: 
--
---------------------------------------------------------------------------------------------------
-- Header		: OUTPUT_2_EMBEDDED_AUDIO_5_STATE
--
-- MIB ref		: swCardEventLogSlotXX       .31.79.85.84.80.85.84.95.50.95.69.77.66.69.68.68.69.68.95.65.85.68.73.79.95.53.95.83.84.65.84.69
-- absolute OID	: 1.3.6.1.4.1.7995.2.6.1.1.XX.31.79.85.84.80.85.84.95.50.95.69.77.66.69.68.68.69.68.95.65.85.68.73.79.95.53.95.83.84.65.84.69
-- Vary			: YES
--
-- Value(s)		: 
--				: 
-- Comments		: 
--
---------------------------------------------------------------------------------------------------
-- Header		: OUTPUT_2_EMBEDDED_AUDIO_6_STATE
--
-- MIB ref		: swCardEventLogSlotXX       .31.79.85.84.80.85.84.95.50.95.69.77.66.69.68.68.69.68.95.65.85.68.73.79.95.54.95.83.84.65.84.69
-- absolute OID	: 1.3.6.1.4.1.7995.2.6.1.1.XX.31.79.85.84.80.85.84.95.50.95.69.77.66.69.68.68.69.68.95.65.85.68.73.79.95.54.95.83.84.65.84.69
-- Vary			: YES
--
-- Value(s)		: 
--				: 
-- Comments		: 
--
---------------------------------------------------------------------------------------------------
-- Header		: OUTPUT_2_EMBEDDED_AUDIO_7_STATE
--
-- MIB ref		: swCardEventLogSlotXX       .31.79.85.84.80.85.84.95.50.95.69.77.66.69.68.68.69.68.95.65.85.68.73.79.95.55.95.83.84.65.84.69
-- absolute OID	: 1.3.6.1.4.1.7995.2.6.1.1.XX.31.79.85.84.80.85.84.95.50.95.69.77.66.69.68.68.69.68.95.65.85.68.73.79.95.55.95.83.84.65.84.69
-- Vary			: YES
--
-- Value(s)		: 
--				: 
-- Comments		: 
--
---------------------------------------------------------------------------------------------------
-- Header		: OUTPUT_2_EMBEDDED_AUDIO_8_STATE
--
-- MIB ref		: swCardEventLogSlotXX       .31.79.85.84.80.85.84.95.50.95.69.77.66.69.68.68.69.68.95.65.85.68.73.79.95.56.95.83.84.65.84.69
-- absolute OID	: 1.3.6.1.4.1.7995.2.6.1.1.XX.31.79.85.84.80.85.84.95.50.95.69.77.66.69.68.68.69.68.95.65.85.68.73.79.95.56.95.83.84.65.84.69
-- Vary			: YES
--
-- Value(s)		: 
--				: 
-- Comments		: 
--
---------------------------------------------------------------------------------------------------
