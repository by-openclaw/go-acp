-- ************************************************************************************
--        Snell Card:IQUDC31
--        Module Id#:686
--       Command Set:6
--          Filename:SNELL-IQUDC31-CMD-MIB.mib
--            Author:N Hext
--              Date:15/01/2014
--              Time:09:52
--
-- Copyright (c) 2010 Snell Ltd
-- All rights reserved.
--
-- ************************************************************************************

SNELL-IQUDC31-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUDC31,
    moduleIQUDC31MIB
        FROM SNELL-WILCOX-PRODUCT-REG;

 moduleIQUDC31CmdMi MODULE-IDENTITY
    LAST-UPDATED "1401150952Z"
    ORGANIZATION "Snell Ltd"
    CONTACT-INFO
        "Primary Author:N Hext

         postal:    Southleigh Park House
                    Eastleigh Road
                    Havant, Hants
                    PO9 2PE
         phone:     +44 (0)23 92489000
         email:     snmp.support@snellgroup.com"
    DESCRIPTION
        "This file defines the Snell card, command set  translations."
    ::= { moduleIQUDC31MIB 1 }




--********************************************************************************
--*
--*  Snell Card:
--*  command set:
--*  list commands/menus:
--*
--******************************************************************************
	iqudc31CmdTable OBJECT-TYPE
		SYNTAX			SEQUENCE OF Iqudc31CmdEntry
		MAX-ACCESS		not-accessible
		STATUS			current
		DESCRIPTION
				"Note the instance of this table is relected in the command set Version"
		::= { moduleIQUDC31 1 }

	iqudc31CmdEntry OBJECT-TYPE
		SYNTAX		Iqudc31CmdEntry
		MAX-ACCESS		not-accessible
		STATUS			current
		DESCRIPTION
				"Entry in command table."
		INDEX	{ iqudc31SlotIndex }
		::= { iqudc31CmdTable 1 }

	Iqudc31CmdEntry ::=
		SEQUENCE {
			iqudc31SlotIndex
				Unsigned32,
			iqudc31InputInputSourceCh1InputSelect
				INTEGER,
			iqudc31InputSourceCh1StatusSDI1
				RollCallString,
			iqudc31InputSourceCh1StatusSDI2
				RollCallString,
			iqudc31InputSourceCh1StatusCVBS
				RollCallString,
			iqudc31InputSourceCh1StatusSFP1
				RollCallString,
			iqudc31InputSourceCh1StatusSFP2
				RollCallString,
			iqudc31InputSourceCh1StatusCurrentInputStand
				RollCallString,
			iqudc31InputInputSourceCh2InputSelect
				INTEGER,
			iqudc31InputSourceCh2StatusSDI1
				RollCallString,
			iqudc31InputSourceCh2StatusSDI2
				RollCallString,
			iqudc31InputSourceCh2StatusCVBS
				RollCallString,
			iqudc31InputSourceCh2StatusSFP1
				RollCallString,
			iqudc31InputSourceCh2StatusSFP2
				RollCallString,
			iqudc31InputSourceCh2StatusCurrentInputStand
				RollCallString,
			iqudc31CVBSDecoderSetupACC
				INTEGER,
			iqudc31CVBSDecoderSetupCTI
				INTEGER,
			iqudc31CVBSDecoderSetupPedestal
				INTEGER,
			iqudc31InputCVBSDecoderNTSCHue
				INTEGER,
			iqudc31CVBSDecoderCalibrationLumaGain
				INTEGER,
			iqudc31CVBSDecoderCalibrationSaveDecoder
				INTEGER,
			iqudc31OutputCh1OutputStandardStandard
				INTEGER,
			iqudc31MenuOutputCh1Format
				INTEGER,
			iqudc31MenuOutputCh1DefaultFieldRate
				INTEGER,
			iqudc31MenuOutputCh1CurrentOutputStan
				RollCallString,
			iqudc31OutputCh1ScrollingCaptionGCaptionEntry
				RollCallString,
			iqudc31OutputCh1ScrollingCaptionGCaptionScroll
				INTEGER,
			iqudc31OutputCh1ScrollingCaptionGCaptionEnable
				INTEGER,
			iqudc31MenuOutputCh1Freeze
				INTEGER,
			iqudc31MenuOutputCh1Legalizer
				INTEGER,
			iqudc31OutputCh1SFPOutputRoutingSFP1Source
				INTEGER,
			iqudc31MenuOutputCh1SFP2Source
				INTEGER,
			iqudc31MenuOutputCh1TestPatterns
				INTEGER,
			iqudc31CVBSEncoderASetupFormat
				INTEGER,
			iqudc31OutputCh1CalibrationDACGain
				INTEGER,
			iqudc31OutputCh1CalibrationSaveEncoder
				INTEGER,
			iqudc31OutputCh1BlankingEmbeddedAudio
				INTEGER,
			iqudc31MenuOutputCh1VAncillaryData
				INTEGER,
			iqudc31MenuOutputCh1SDHalfLine
				INTEGER,
			iqudc31OutputCh2OutputStandardStandard
				INTEGER,
			iqudc31MenuOutputCh2Format
				INTEGER,
			iqudc31MenuOutputCh2DefaultFieldRate
				INTEGER,
			iqudc31MenuOutputCh2CurrentOutputStan
				RollCallString,
			iqudc31OutputCh2ScrollingCaptionGCaptionEntry
				RollCallString,
			iqudc31OutputCh2ScrollingCaptionGCaptionScroll
				INTEGER,
			iqudc31OutputCh2ScrollingCaptionGCaptionEnable
				INTEGER,
			iqudc31MenuOutputCh2Freeze
				INTEGER,
			iqudc31MenuOutputCh2Legalizer
				INTEGER,
			iqudc31MenuOutputCh2TestPatterns
				INTEGER,
			iqudc31CVBSEncoderBSetupFormat
				INTEGER,
			iqudc31OutputCh2CalibrationDACGain
				INTEGER,
			iqudc31OutputCh2CalibrationSaveEncoder
				INTEGER,
			iqudc31OutputCh2BlankingEmbeddedAudio
				INTEGER,
			iqudc31MenuOutputCh2VAncillaryData
				INTEGER,
			iqudc31MenuOutputCh2SDHalfLine
				INTEGER,
			iqudc31MenuOutputCh2NewDisplay
				RollCallString,
			iqudc31VideoCh1ProcAmpEnable
				INTEGER,
			iqudc31VideoCh1ProcAmpContrast
				INTEGER,
			iqudc31VideoCh1ProcAmpSaturation
				INTEGER,
			iqudc31VideoCh1ProcAmpBlackLevel
				INTEGER,
			iqudc31VideoCh1ProcAmpGamma
				INTEGER,
			iqudc31VideoCh1ProcAmpYCOffset
				INTEGER,
			iqudc31VideoCh1NonlinearEnhancerEnable
				INTEGER,
			iqudc31VideoCh1NonlinearEnhancerLevel
				INTEGER,
			iqudc31VideoCh1NonlinearEnhancerMode
				INTEGER,
			iqudc31MenuVideoCh1FrequencyBand20052
				INTEGER,
			iqudc31MenuVideoCh1NoiseRejection
				INTEGER,
			iqudc31VideoCh1ConversionAperturePreset
				INTEGER,
			iqudc31ConversionApertureHorizontalSharpness30100
				INTEGER,
			iqudc31MenuVideoCh1Detail
				INTEGER,
			iqudc31VideoCh1VerticalLevel
				INTEGER,
			iqudc31MenuVideoCh1FrequencyBand20060
				INTEGER,
			iqudc31VideoCh1NoiseReductionEnable
				INTEGER,
			iqudc31NoiseReductionRecursiveLuma20005
				INTEGER,
			iqudc31NoiseReductionRecursiveChroma20001
				INTEGER,
			iqudc31NoiseReductionRecursiveMode20002
				INTEGER,
			iqudc31VideoCh1NoiseReductionThreshold
				INTEGER,
			iqudc31NoiseReductionSpatialLevel20011
				INTEGER,
			iqudc31NoiseReductionSpatialMode20010
				INTEGER,
			iqudc31MenuVideoCh1Threshold
				INTEGER,
			iqudc31MenuVideoCh1SplitScreen
				INTEGER,
			iqudc31VideoCh2ProcAmpEnable
				INTEGER,
			iqudc31VideoCh2ProcAmpContrast
				INTEGER,
			iqudc31VideoCh2ProcAmpSaturation
				INTEGER,
			iqudc31VideoCh2ProcAmpBlackLevel
				INTEGER,
			iqudc31VideoCh2ProcAmpGamma
				INTEGER,
			iqudc31VideoCh2ProcAmpYCOffset
				INTEGER,
			iqudc31VideoCh2NonlinearEnhancerEnable
				INTEGER,
			iqudc31VideoCh2NonlinearEnhancerLevel
				INTEGER,
			iqudc31VideoCh2NonlinearEnhancerMode
				INTEGER,
			iqudc31MenuVideoCh2FrequencyBand20152
				INTEGER,
			iqudc31MenuVideoCh2NoiseRejection
				INTEGER,
			iqudc31VideoCh2ConversionAperturePreset
				INTEGER,
			iqudc31ConversionApertureHorizontalSharpness30200
				INTEGER,
			iqudc31MenuVideoCh2Detail
				INTEGER,
			iqudc31VideoCh2VerticalLevel
				INTEGER,
			iqudc31MenuVideoCh2FrequencyBand20160
				INTEGER,
			iqudc31VideoCh2NoiseReductionEnable
				INTEGER,
			iqudc31NoiseReductionRecursiveLuma20105
				INTEGER,
			iqudc31NoiseReductionRecursiveChroma20101
				INTEGER,
			iqudc31NoiseReductionRecursiveMode20107
				INTEGER,
			iqudc31VideoCh2NoiseReductionThreshold
				INTEGER,
			iqudc31NoiseReductionSpatialLevel20111
				INTEGER,
			iqudc31NoiseReductionSpatialMode20110
				INTEGER,
			iqudc31MenuVideoCh2Threshold
				INTEGER,
			iqudc31MenuVideoCh2SplitScreen
				INTEGER,
			iqudc31MenuVideoCh2NewDisplay
				RollCallString,
			iqudc31ConvertCh1UpConversionCleanEdgeUpconver
				INTEGER,
			iqudc31ConvertCh1MotionProcessing
				INTEGER,
			iqudc31ConvertCh1MotionProcessingEnhancedMotion
				INTEGER,
			iqudc31ConvertCh1MotionProcessingStillProcess
				INTEGER,
			iqudc31ConvertCh1MotionProcessingEnhancedStill
				INTEGER,
			iqudc31ConvertCh1MotionProcessingInputispsf
				INTEGER,
			iqudc31ConvertCh1MotionProcessingEnhancedFilm
				INTEGER,
			iqudc31ConvertCh1InputCadenceFilmCadence
				INTEGER,
			iqudc31ConvertCh1InputCadence59Cadence
				INTEGER,
			iqudc31MenuConvertCh123Source30052
				INTEGER,
			iqudc31MenuConvertCh123StartHour30053
				INTEGER,
			iqudc31ConvertCh1OutputCadenceFilmCadence
				INTEGER,
			iqudc31ConvertCh1OutputCadence59Cadence
				INTEGER,
			iqudc31MenuConvertCh123Source30062
				INTEGER,
			iqudc31MenuConvertCh123StartHour30063
				INTEGER,
			iqudc31ConvertCh2UpConversionCleanEdgeUpconver
				INTEGER,
			iqudc31ConvertCh2MotionProcessing
				INTEGER,
			iqudc31ConvertCh2MotionProcessingEnhancedMotion
				INTEGER,
			iqudc31ConvertCh2MotionProcessingStillProcess
				INTEGER,
			iqudc31ConvertCh2MotionProcessingEnhancedStill
				INTEGER,
			iqudc31ConvertCh2MotionProcessingInputispsf
				INTEGER,
			iqudc31ConvertCh2MotionProcessingEnhancedFilm
				INTEGER,
			iqudc31ConvertCh2InputCadenceFilmCadence
				INTEGER,
			iqudc31ConvertCh2InputCadence59Cadence
				INTEGER,
			iqudc31MenuConvertCh223Source30152
				INTEGER,
			iqudc31MenuConvertCh223StartHour30153
				INTEGER,
			iqudc31ConvertCh2OutputCadenceFilmCadence
				INTEGER,
			iqudc31ConvertCh2OutputCadence59Cadence
				INTEGER,
			iqudc31MenuConvertCh223Source30162
				INTEGER,
			iqudc31MenuConvertCh223StartHour30163
				INTEGER,
			iqudc31MenuConvertCh2NewDisplay
				RollCallString,
			iqudc31MenuARCSidebarKeyerSyncMode40007
				INTEGER,
			iqudc31MenuARCSidebarKeyerAspectSignallingC40136
				INTEGER,
			iqudc31MenuARCSidebarKeyerSignallingDetected64020
				RollCallString,
			iqudc31ARCSidebarKeyerSidebarKeyingOuMode40017
				INTEGER,
			iqudc31MenuARCSidebarKeyerSidebarKeySource40018
				INTEGER,
			iqudc31ARCSidebarKeyerOutputCropPositioTop40013
				INTEGER,
			iqudc31ARCSidebarKeyerOutputCropPositioBottom40014
				INTEGER,
			iqudc31ARCSidebarKeyerOutputCropPositioLeft40015
				INTEGER,
			iqudc31ARCSidebarKeyerOutputCropPositioRight40016
				INTEGER,
			iqudc31ARCSidebarKeyerPostScalingControPostScalingEnable40003
				INTEGER,
			iqudc31ARCSidebarKeyerPostScalingControSize40008
				INTEGER,
			iqudc31ARCSidebarKeyerPostScalingControAspect40009
				INTEGER,
			iqudc31ARCSidebarKeyerPostScalingControPan40006
				INTEGER,
			iqudc31ARCSidebarKeyerPostScalingControTilt40002
				INTEGER,
			iqudc31ARCSidebarKeyerStandardPresetsWhSDInputis70240030
				INTEGER,
			iqudc31ARCSidebarKeyerStandardPresetsWhSDOutputis70240037
				INTEGER,
			iqudc31StandardPresetsWhSDCrossConversionSelectStdPreset40031
				INTEGER,
			iqudc31ARCSidebarKeyerUpConversionSelectStdPreset40033
				INTEGER,
			iqudc31ARCSidebarKeyerDownConversionSelectStdPreset40035
				INTEGER,
			iqudc31ScalingControlSDInputFormatifUseManualifUnkno40135
				INTEGER,
			iqudc31ScalingControlSDInputFormatif40010
				INTEGER,
			iqudc31ARCSidebarKeyerAspectSignallingCSDOutputFormat40011
				INTEGER,
			iqudc31ARCSidebarKeyerAspectSignallingCConversionScaling40012
				INTEGER,
			iqudc31AspectSignallingCSignallingConfigSource40100
				INTEGER,
			iqudc31SignallingConfigSMPTE2016Mode40130
				INTEGER,
			iqudc31AspectSignallingCSignallingConfigOutputLine625
				INTEGER,
			iqudc31AspectSignallingCSignallingConfigOutputLine525
				INTEGER,
			iqudc31AspectSignallingCSignallingConfigOutputLineHD40138
				INTEGER,
			iqudc31AspectSignallingCSignallingConfigOutputLineStatus40141
				RollCallString,
			iqudc31SignallingConfigVIMode40120
				INTEGER,
			iqudc31MenuARCSidebarKeyerOutputFormat40121
				INTEGER,
			iqudc31MenuARCSidebarKeyerVIPassData40122
				INTEGER,
			iqudc31ARCSidebarKeyerL23Mode40112
				INTEGER,
			iqudc31ARCSidebarKeyerL23OutputFormat40113
				INTEGER,
			iqudc31MenuARCSidebarKeyerInputLine40110
				INTEGER,
			iqudc31MenuARCSidebarKeyerOutputLine40111
				INTEGER,
			iqudc31MenuARCSidebarKeyerOutputLineStatus20166
				RollCallString,
			iqudc31ARCSidebarKeyerAFDUserBitsForceUserBitsVal20163
				INTEGER,
			iqudc31ARCSidebarKeyerAFDUserBitsUserBitsValue40137
				INTEGER,
			iqudc31ARCSidebarKeyerForceOutputSignalSMPTE201640133
				INTEGER,
			iqudc31MenuARCSidebarKeyerSMPTERP18640134
				INTEGER,
			iqudc31MenuARCSidebarKeyerAFD40131
				INTEGER,
			iqudc31MenuARCSidebarKeyerETSI40132
				INTEGER,
			iqudc31MenuARCSidebarKeyerSyncMode40107
				INTEGER,
			iqudc31MenuARCSidebarKeyerAspectSignallingC40236
				INTEGER,
			iqudc31MenuARCSidebarKeyerSignallingDetected64220
				RollCallString,
			iqudc31ARCSidebarKeyerSidebarKeyingOuMode40023
				INTEGER,
			iqudc31MenuARCSidebarKeyerSidebarKeySource40024
				INTEGER,
			iqudc31ARCSidebarKeyerOutputCropPositioTop40019
				INTEGER,
			iqudc31ARCSidebarKeyerOutputCropPositioBottom40020
				INTEGER,
			iqudc31ARCSidebarKeyerOutputCropPositioLeft40021
				INTEGER,
			iqudc31ARCSidebarKeyerOutputCropPositioRight40022
				INTEGER,
			iqudc31ARCSidebarKeyerPostScalingControPostScalingEnable40103
				INTEGER,
			iqudc31ARCSidebarKeyerPostScalingControSize40108
				INTEGER,
			iqudc31ARCSidebarKeyerPostScalingControAspect40109
				INTEGER,
			iqudc31ARCSidebarKeyerPostScalingControPan40106
				INTEGER,
			iqudc31ARCSidebarKeyerPostScalingControTilt40102
				INTEGER,
			iqudc31ARCSidebarKeyerStandardPresetsWhSDInputis70240040
				INTEGER,
			iqudc31ARCSidebarKeyerStandardPresetsWhSDOutputis70240047
				INTEGER,
			iqudc31StandardPresetsWhSDCrossConversionSelectStdPreset40041
				INTEGER,
			iqudc31ARCSidebarKeyerUpConversionSelectStdPreset40043
				INTEGER,
			iqudc31ARCSidebarKeyerDownConversionSelectStdPreset40045
				INTEGER,
			iqudc31ScalingControlSDInputFormatifUseManualifUnkno40235
				INTEGER,
			iqudc31ScalingControlSDInputFormatif40114
				INTEGER,
			iqudc31ARCSidebarKeyerAspectSignallingCSDOutputFormat40115
				INTEGER,
			iqudc31ARCSidebarKeyerAspectSignallingCConversionScaling40116
				INTEGER,
			iqudc31AspectSignallingCSignallingConfigSource40202
				INTEGER,
			iqudc31SignallingConfigSMPTE2016Mode40230
				INTEGER,
			iqudc31AspectSignallingCSignallingConfigOutputLinePAL
				INTEGER,
			iqudc31AspectSignallingCSignallingConfigOutputLineNTSC
				INTEGER,
			iqudc31AspectSignallingCSignallingConfigOutputLineHD40238
				INTEGER,
			iqudc31AspectSignallingCSignallingConfigOutputLineStatus40241
				RollCallString,
			iqudc31SignallingConfigVIMode40220
				INTEGER,
			iqudc31MenuARCSidebarKeyerOutputFormat40221
				INTEGER,
			iqudc31MenuARCSidebarKeyerVIPassData40222
				INTEGER,
			iqudc31ARCSidebarKeyerL23Mode40212
				INTEGER,
			iqudc31ARCSidebarKeyerL23OutputFormat40213
				INTEGER,
			iqudc31MenuARCSidebarKeyerInputLine40210
				INTEGER,
			iqudc31MenuARCSidebarKeyerOutputLine40211
				INTEGER,
			iqudc31MenuARCSidebarKeyerOutputLineStatus20176
				RollCallString,
			iqudc31ARCSidebarKeyerAFDUserBitsForceUserBitsVal20173
				INTEGER,
			iqudc31ARCSidebarKeyerAFDUserBitsUserBitsValue40237
				INTEGER,
			iqudc31ARCSidebarKeyerForceOutputSignalSMPTE201640233
				INTEGER,
			iqudc31MenuARCSidebarKeyerSMPTERP18640234
				INTEGER,
			iqudc31MenuARCSidebarKeyerAFD40231
				INTEGER,
			iqudc31MenuARCSidebarKeyerETSI40232
				INTEGER,
			iqudc31MenuARCSidebarKeyerNewDisplay
				RollCallString,
			iqudc31AudioRoutingCh1InputPairsStatusEmbedded1
				RollCallString,
			iqudc31AudioRoutingCh1InputPairsStatusEmbedded2
				RollCallString,
			iqudc31AudioRoutingCh1InputPairsStatusEmbedded3
				RollCallString,
			iqudc31AudioRoutingCh1InputPairsStatusEmbedded4
				RollCallString,
			iqudc31AudioRoutingCh1InputPairsStatusEmbedded5
				RollCallString,
			iqudc31AudioRoutingCh1InputPairsStatusEmbedded6
				RollCallString,
			iqudc31AudioRoutingCh1InputPairsStatusEmbedded7
				RollCallString,
			iqudc31AudioRoutingCh1InputPairsStatusEmbedded8
				RollCallString,
			iqudc31AudioRoutingCh1InputPairsStatusAES1
				RollCallString,
			iqudc31AudioRoutingCh1InputPairsStatusAES2
				RollCallString,
			iqudc31AudioRoutingCh1InputPairsStatusAES3
				RollCallString,
			iqudc31AudioRoutingCh1InputPairsStatusAES4
				RollCallString,
			iqudc31AudioRoutingCh1InputPairsStatusAES5
				RollCallString,
			iqudc31AudioRoutingCh1InputPairsStatusAES6
				RollCallString,
			iqudc31AudioRoutingCh1InputPairsStatusAES7
				RollCallString,
			iqudc31AudioRoutingCh1InputPairsStatusAES8
				RollCallString,
			iqudc31AudioRoutingCh1InputPairsStatusAnalog1
				RollCallString,
			iqudc31AudioRoutingCh1InputPairsStatusAnalog2
				RollCallString,
			iqudc31AudioRoutingCh1InputPairsStatusDolbyDecoder1
				RollCallString,
			iqudc31AudioRoutingCh1InputPairsStatusDolbyDecoder2
				RollCallString,
			iqudc31AudioRoutingCh1InputPairsStatusDolbyDecoder3
				RollCallString,
			iqudc31AudioRoutingCh1InputPairsStatusDolbyDecoder4
				RollCallString,
			iqudc31AudioRoutingCh1InputPairsStatusDolbyDownmix
				RollCallString,
			iqudc31AudioRoutingCh1InputPairsStatusDolbyEncoder
				RollCallString,
			iqudc31ProcessPairs18Pair1InputPairsSource
				INTEGER,
			iqudc31ProcessPairs18Pair2InputPairsSource
				INTEGER,
			iqudc31ProcessPairs18Pair3InputPairsSource
				INTEGER,
			iqudc31ProcessPairs18Pair4InputPairsSource
				INTEGER,
			iqudc31ProcessPairs18Pair5InputPairsSource
				INTEGER,
			iqudc31ProcessPairs18Pair6InputPairsSource
				INTEGER,
			iqudc31ProcessPairs18Pair7InputPairsSource
				INTEGER,
			iqudc31ProcessPairs18Pair8InputPairsSource
				INTEGER,
			iqudc31AudioRoutingCh1ProcessPairs18SPair1
				RollCallString,
			iqudc31AudioRoutingCh1ProcessPairs18SPair2
				RollCallString,
			iqudc31AudioRoutingCh1ProcessPairs18SPair3
				RollCallString,
			iqudc31AudioRoutingCh1ProcessPairs18SPair4
				RollCallString,
			iqudc31AudioRoutingCh1ProcessPairs18SPair5
				RollCallString,
			iqudc31AudioRoutingCh1ProcessPairs18SPair6
				RollCallString,
			iqudc31AudioRoutingCh1ProcessPairs18SPair7
				RollCallString,
			iqudc31AudioRoutingCh1ProcessPairs18SPair8
				RollCallString,
			iqudc31AudioRoutingCh2InputPairsStatusEmbedded1
				RollCallString,
			iqudc31AudioRoutingCh2InputPairsStatusEmbedded2
				RollCallString,
			iqudc31AudioRoutingCh2InputPairsStatusEmbedded3
				RollCallString,
			iqudc31AudioRoutingCh2InputPairsStatusEmbedded4
				RollCallString,
			iqudc31AudioRoutingCh2InputPairsStatusEmbedded5
				RollCallString,
			iqudc31AudioRoutingCh2InputPairsStatusEmbedded6
				RollCallString,
			iqudc31AudioRoutingCh2InputPairsStatusEmbedded7
				RollCallString,
			iqudc31AudioRoutingCh2InputPairsStatusEmbedded8
				RollCallString,
			iqudc31AudioRoutingCh2InputPairsStatusAES1
				RollCallString,
			iqudc31AudioRoutingCh2InputPairsStatusAES2
				RollCallString,
			iqudc31AudioRoutingCh2InputPairsStatusAES3
				RollCallString,
			iqudc31AudioRoutingCh2InputPairsStatusAES4
				RollCallString,
			iqudc31AudioRoutingCh2InputPairsStatusAES5
				RollCallString,
			iqudc31AudioRoutingCh2InputPairsStatusAES6
				RollCallString,
			iqudc31AudioRoutingCh2InputPairsStatusAES7
				RollCallString,
			iqudc31AudioRoutingCh2InputPairsStatusAES8
				RollCallString,
			iqudc31AudioRoutingCh2InputPairsStatusAnalog1
				RollCallString,
			iqudc31AudioRoutingCh2InputPairsStatusAnalog2
				RollCallString,
			iqudc31AudioRoutingCh2InputPairsStatusDolbyDecoder1
				RollCallString,
			iqudc31AudioRoutingCh2InputPairsStatusDolbyDecoder2
				RollCallString,
			iqudc31AudioRoutingCh2InputPairsStatusDolbyDecoder3
				RollCallString,
			iqudc31AudioRoutingCh2InputPairsStatusDolbyDecoder4
				RollCallString,
			iqudc31AudioRoutingCh2InputPairsStatusDolbyDownmix
				RollCallString,
			iqudc31AudioRoutingCh2InputPairsStatusDolbyEncoder
				RollCallString,
			iqudc31ProcessPairs18ProcessPair1InputPairsSource
				INTEGER,
			iqudc31ProcessPairs18ProcessPair2InputPairsSource
				INTEGER,
			iqudc31ProcessPairs18ProcessPair3InputPairsSource
				INTEGER,
			iqudc31ProcessPairs18ProcessPair4InputPairsSource
				INTEGER,
			iqudc31ProcessPairs18ProcessPair5InputPairsSource
				INTEGER,
			iqudc31ProcessPairs18ProcessPair6InputPairsSource
				INTEGER,
			iqudc31ProcessPairs18ProcessPair7InputPairsSource
				INTEGER,
			iqudc31ProcessPairs18ProcessPair8InputPairsSource
				INTEGER,
			iqudc31AudioRoutingCh2ProcessPairs18SPair1
				RollCallString,
			iqudc31AudioRoutingCh2ProcessPairs18SPair2
				RollCallString,
			iqudc31AudioRoutingCh2ProcessPairs18SPair3
				RollCallString,
			iqudc31AudioRoutingCh2ProcessPairs18SPair4
				RollCallString,
			iqudc31AudioRoutingCh2ProcessPairs18SPair5
				RollCallString,
			iqudc31AudioRoutingCh2ProcessPairs18SPair6
				RollCallString,
			iqudc31AudioRoutingCh2ProcessPairs18SPair7
				RollCallString,
			iqudc31AudioRoutingCh2ProcessPairs18SPair8
				RollCallString,
			iqudc31MenuAudioRoutingCh2NewDisplay
				RollCallString,
			iqudc31OutputPairs18OutputPair1LProcessPairsSourc52000
				INTEGER,
			iqudc31OutputPairs18OutputPair1LInvertPhase50700
				INTEGER,
			iqudc31OutputPairs18OutputPair1LControl50100
				INTEGER,
			iqudc31OutputPairs18OutputPair1RProcessPairsSourc52008
				INTEGER,
			iqudc31OutputPairs18OutputPair1RInvertPhase50708
				INTEGER,
			iqudc31OutputPairs18OutputPair1RControl50108
				INTEGER,
			iqudc31OutputPairs18OutputPair2LProcessPairsSourc52001
				INTEGER,
			iqudc31OutputPairs18OutputPair2LInvertPhase50701
				INTEGER,
			iqudc31OutputPairs18OutputPair2LControl50101
				INTEGER,
			iqudc31OutputPairs18OutputPair2RProcessPairsSourc52009
				INTEGER,
			iqudc31OutputPairs18OutputPair2RInvertPhase50709
				INTEGER,
			iqudc31OutputPairs18OutputPair2RControl50109
				INTEGER,
			iqudc31OutputPairs18OutputPair3LProcessPairsSourc52002
				INTEGER,
			iqudc31OutputPairs18OutputPair3LInvertPhase50702
				INTEGER,
			iqudc31OutputPairs18OutputPair3LControl50102
				INTEGER,
			iqudc31OutputPairs18OutputPair3RProcessPairsSourc52010
				INTEGER,
			iqudc31OutputPairs18OutputPair3RInvertPhase50710
				INTEGER,
			iqudc31OutputPairs18OutputPair3RControl50110
				INTEGER,
			iqudc31OutputPairs18OutputPair4LProcessPairsSourc52003
				INTEGER,
			iqudc31OutputPairs18OutputPair4LInvertPhase50703
				INTEGER,
			iqudc31OutputPairs18OutputPair4LControl50103
				INTEGER,
			iqudc31OutputPairs18OutputPair4RProcessPairsSourc52011
				INTEGER,
			iqudc31OutputPairs18OutputPair4RInvertPhase50711
				INTEGER,
			iqudc31OutputPairs18OutputPair4RControl50111
				INTEGER,
			iqudc31OutputPairs18OutputPair5LProcessPairsSourc52004
				INTEGER,
			iqudc31OutputPairs18OutputPair5LInvertPhase50704
				INTEGER,
			iqudc31OutputPairs18OutputPair5LControl50104
				INTEGER,
			iqudc31OutputPairs18OutputPair5RProcessPairsSourc52012
				INTEGER,
			iqudc31OutputPairs18OutputPair5RInvertPhase50712
				INTEGER,
			iqudc31OutputPairs18OutputPair5RControl50112
				INTEGER,
			iqudc31OutputPairs18OutputPair6LProcessPairsSourc52005
				INTEGER,
			iqudc31OutputPairs18OutputPair6LInvertPhase50705
				INTEGER,
			iqudc31OutputPairs18OutputPair6LControl50105
				INTEGER,
			iqudc31OutputPairs18OutputPair6RProcessPairsSourc52013
				INTEGER,
			iqudc31OutputPairs18OutputPair6RInvertPhase50713
				INTEGER,
			iqudc31OutputPairs18OutputPair6RControl50113
				INTEGER,
			iqudc31OutputPairs18OutputPair7LProcessPairsSourc52006
				INTEGER,
			iqudc31OutputPairs18OutputPair7LInvertPhase50706
				INTEGER,
			iqudc31OutputPairs18OutputPair7LControl50106
				INTEGER,
			iqudc31OutputPairs18OutputPair7RProcessPairsSourc52014
				INTEGER,
			iqudc31OutputPairs18OutputPair7RInvertPhase50714
				INTEGER,
			iqudc31OutputPairs18OutputPair7RControl50114
				INTEGER,
			iqudc31OutputPairs18OutputPair8LProcessPairsSourc52007
				INTEGER,
			iqudc31OutputPairs18OutputPair8LInvertPhase50707
				INTEGER,
			iqudc31OutputPairs18OutputPair8LControl50107
				INTEGER,
			iqudc31OutputPairs18OutputPair8RProcessPairsSourc52015
				INTEGER,
			iqudc31OutputPairs18OutputPair8RInvertPhase50715
				INTEGER,
			iqudc31OutputPairs18OutputPair8RControl50115
				INTEGER,
			iqudc31AudioShuffleCh1OutputPairs18StPair1
				RollCallString,
			iqudc31AudioShuffleCh1OutputPairs18StPair2
				RollCallString,
			iqudc31AudioShuffleCh1OutputPairs18StPair3
				RollCallString,
			iqudc31AudioShuffleCh1OutputPairs18StPair4
				RollCallString,
			iqudc31AudioShuffleCh1OutputPairs18StPair5
				RollCallString,
			iqudc31AudioShuffleCh1OutputPairs18StPair6
				RollCallString,
			iqudc31AudioShuffleCh1OutputPairs18StPair7
				RollCallString,
			iqudc31AudioShuffleCh1OutputPairs18StPair8
				RollCallString,
			iqudc31MenuAudioShuffleCh1NewDisplay
				RollCallString,
			iqudc31OutputPairs18OutputPair1LProcessPairsSourc50800
				INTEGER,
			iqudc31OutputPairs18OutputPair1LInvertPhase50816
				INTEGER,
			iqudc31OutputPairs18OutputPair1LControl50832
				INTEGER,
			iqudc31OutputPairs18OutputPair1RProcessPairsSourc50808
				INTEGER,
			iqudc31OutputPairs18OutputPair1RInvertPhase50824
				INTEGER,
			iqudc31OutputPairs18OutputPair1RControl50840
				INTEGER,
			iqudc31OutputPairs18OutputPair2LProcessPairsSourc50801
				INTEGER,
			iqudc31OutputPairs18OutputPair2LInvertPhase50817
				INTEGER,
			iqudc31OutputPairs18OutputPair2LControl50833
				INTEGER,
			iqudc31OutputPairs18OutputPair2RProcessPairsSourc50809
				INTEGER,
			iqudc31OutputPairs18OutputPair2RInvertPhase50825
				INTEGER,
			iqudc31OutputPairs18OutputPair2RControl50841
				INTEGER,
			iqudc31OutputPairs18OutputPair3LProcessPairsSourc50802
				INTEGER,
			iqudc31OutputPairs18OutputPair3LInvertPhase50818
				INTEGER,
			iqudc31OutputPairs18OutputPair3LControl50834
				INTEGER,
			iqudc31OutputPairs18OutputPair3RProcessPairsSourc50810
				INTEGER,
			iqudc31OutputPairs18OutputPair3RInvertPhase50826
				INTEGER,
			iqudc31OutputPairs18OutputPair3RControl50842
				INTEGER,
			iqudc31OutputPairs18OutputPair4LProcessPairsSourc50803
				INTEGER,
			iqudc31OutputPairs18OutputPair4LInvertPhase50819
				INTEGER,
			iqudc31OutputPairs18OutputPair4LControl50835
				INTEGER,
			iqudc31OutputPairs18OutputPair4RProcessPairsSourc50811
				INTEGER,
			iqudc31OutputPairs18OutputPair4RInvertPhase50827
				INTEGER,
			iqudc31OutputPairs18OutputPair4RControl50843
				INTEGER,
			iqudc31OutputPairs18OutputPair5LProcessPairsSourc50804
				INTEGER,
			iqudc31OutputPairs18OutputPair5LInvertPhase50820
				INTEGER,
			iqudc31OutputPairs18OutputPair5LControl50836
				INTEGER,
			iqudc31OutputPairs18OutputPair5RProcessPairsSourc50812
				INTEGER,
			iqudc31OutputPairs18OutputPair5RInvertPhase50828
				INTEGER,
			iqudc31OutputPairs18OutputPair5RControl50844
				INTEGER,
			iqudc31OutputPairs18OutputPair6LProcessPairsSourc50805
				INTEGER,
			iqudc31OutputPairs18OutputPair6LInvertPhase50821
				INTEGER,
			iqudc31OutputPairs18OutputPair6LControl50837
				INTEGER,
			iqudc31OutputPairs18OutputPair6RProcessPairsSourc50813
				INTEGER,
			iqudc31OutputPairs18OutputPair6RInvertPhase50829
				INTEGER,
			iqudc31OutputPairs18OutputPair6RControl50845
				INTEGER,
			iqudc31OutputPairs18OutputPair7LProcessPairsSourc50806
				INTEGER,
			iqudc31OutputPairs18OutputPair7LInvertPhase50822
				INTEGER,
			iqudc31OutputPairs18OutputPair7LControl50838
				INTEGER,
			iqudc31OutputPairs18OutputPair7RProcessPairsSourc50814
				INTEGER,
			iqudc31OutputPairs18OutputPair7RInvertPhase50830
				INTEGER,
			iqudc31OutputPairs18OutputPair7RControl50846
				INTEGER,
			iqudc31OutputPairs18OutputPair8LProcessPairsSourc50807
				INTEGER,
			iqudc31OutputPairs18OutputPair8LInvertPhase50823
				INTEGER,
			iqudc31OutputPairs18OutputPair8LControl50839
				INTEGER,
			iqudc31OutputPairs18OutputPair8RProcessPairsSourc50815
				INTEGER,
			iqudc31OutputPairs18OutputPair8RInvertPhase50831
				INTEGER,
			iqudc31OutputPairs18OutputPair8RControl50847
				INTEGER,
			iqudc31AudioShuffleCh2OutputPairs18StPair1
				RollCallString,
			iqudc31AudioShuffleCh2OutputPairs18StPair2
				RollCallString,
			iqudc31AudioShuffleCh2OutputPairs18StPair3
				RollCallString,
			iqudc31AudioShuffleCh2OutputPairs18StPair4
				RollCallString,
			iqudc31AudioShuffleCh2OutputPairs18StPair5
				RollCallString,
			iqudc31AudioShuffleCh2OutputPairs18StPair6
				RollCallString,
			iqudc31AudioShuffleCh2OutputPairs18StPair7
				RollCallString,
			iqudc31AudioShuffleCh2OutputPairs18StPair8
				RollCallString,
			iqudc31MenuAudioShuffleCh2NewDisplay
				RollCallString,
			iqudc31AudioControlCh1GainPair1L
				INTEGER,
			iqudc31AudioControlCh1GainPair1R
				INTEGER,
			iqudc31AudioControlCh1GainPair2L
				INTEGER,
			iqudc31AudioControlCh1GainPair2R
				INTEGER,
			iqudc31AudioControlCh1GainPair3L
				INTEGER,
			iqudc31AudioControlCh1GainPair3R
				INTEGER,
			iqudc31AudioControlCh1GainPair4L
				INTEGER,
			iqudc31AudioControlCh1GainPair4R
				INTEGER,
			iqudc31AudioControlCh1GainPair5L
				INTEGER,
			iqudc31AudioControlCh1GainPair5R
				INTEGER,
			iqudc31AudioControlCh1GainPair6L
				INTEGER,
			iqudc31AudioControlCh1GainPair6R
				INTEGER,
			iqudc31AudioControlCh1GainPair7L
				INTEGER,
			iqudc31AudioControlCh1GainPair7R
				INTEGER,
			iqudc31AudioControlCh1GainPair8L
				INTEGER,
			iqudc31AudioControlCh1GainPair8R
				INTEGER,
			iqudc31MenuAudioControlCh1ToneFrequency
				INTEGER,
			iqudc31MenuAudioControlCh1DolbyEAlignmentO
				INTEGER,
			iqudc31DelayGlobalDelayPairOPair150319
				INTEGER,
			iqudc31DelayGlobalDelayPairOPair1Total50327
				RollCallString,
			iqudc31DelayGlobalDelayPairOPair250320
				INTEGER,
			iqudc31DelayGlobalDelayPairOPair2Total50328
				RollCallString,
			iqudc31DelayGlobalDelayPairOPair350321
				INTEGER,
			iqudc31DelayGlobalDelayPairOPair3Total50329
				RollCallString,
			iqudc31DelayGlobalDelayPairOPair450322
				INTEGER,
			iqudc31DelayGlobalDelayPairOPair4Total50330
				RollCallString,
			iqudc31DelayGlobalDelayPairOPair550323
				INTEGER,
			iqudc31DelayGlobalDelayPairOPair5Total50331
				RollCallString,
			iqudc31DelayGlobalDelayPairOPair650324
				INTEGER,
			iqudc31DelayGlobalDelayPairOPair6Total50332
				RollCallString,
			iqudc31DelayGlobalDelayPairOPair750325
				INTEGER,
			iqudc31DelayGlobalDelayPairOPair7Total50333
				RollCallString,
			iqudc31DelayGlobalDelayPairOPair850326
				INTEGER,
			iqudc31DelayGlobalDelayPairOPair8Total50334
				RollCallString,
			iqudc31AudioControlCh1GlobalDelayAudio
				INTEGER,
			iqudc31AudioControlCh1GlobalDelayAudioTotal
				RollCallString,
			iqudc31AudioControlCh1GlobalDelayVideoTotal
				RollCallString,
			iqudc31MenuAudioControlCh1NewDisplay
				RollCallString,
			iqudc31AudioControlCh2GainPair1L
				INTEGER,
			iqudc31AudioControlCh2GainPair1R
				INTEGER,
			iqudc31AudioControlCh2GainPair2L
				INTEGER,
			iqudc31AudioControlCh2GainPair2R
				INTEGER,
			iqudc31AudioControlCh2GainPair3L
				INTEGER,
			iqudc31AudioControlCh2GainPair3R
				INTEGER,
			iqudc31AudioControlCh2GainPair4L
				INTEGER,
			iqudc31AudioControlCh2GainPair4R
				INTEGER,
			iqudc31AudioControlCh2GainPair5L
				INTEGER,
			iqudc31AudioControlCh2GainPair5R
				INTEGER,
			iqudc31AudioControlCh2GainPair6L
				INTEGER,
			iqudc31AudioControlCh2GainPair6R
				INTEGER,
			iqudc31AudioControlCh2GainPair7L
				INTEGER,
			iqudc31AudioControlCh2GainPair7R
				INTEGER,
			iqudc31AudioControlCh2GainPair8L
				INTEGER,
			iqudc31AudioControlCh2GainPair8R
				INTEGER,
			iqudc31MenuAudioControlCh2ToneFrequency
				INTEGER,
			iqudc31MenuAudioControlCh2DolbyEAlignmentO
				INTEGER,
			iqudc31DelayGlobalDelayPairOPair150505
				INTEGER,
			iqudc31DelayGlobalDelayPairOPair1Total50513
				RollCallString,
			iqudc31DelayGlobalDelayPairOPair250506
				INTEGER,
			iqudc31DelayGlobalDelayPairOPair2Total50514
				RollCallString,
			iqudc31DelayGlobalDelayPairOPair350507
				INTEGER,
			iqudc31DelayGlobalDelayPairOPair3Total50515
				RollCallString,
			iqudc31DelayGlobalDelayPairOPair450508
				INTEGER,
			iqudc31DelayGlobalDelayPairOPair4Total50516
				RollCallString,
			iqudc31DelayGlobalDelayPairOPair550509
				INTEGER,
			iqudc31DelayGlobalDelayPairOPair5Total50517
				RollCallString,
			iqudc31DelayGlobalDelayPairOPair650510
				INTEGER,
			iqudc31DelayGlobalDelayPairOPair6Total50518
				RollCallString,
			iqudc31DelayGlobalDelayPairOPair750511
				INTEGER,
			iqudc31DelayGlobalDelayPairOPair7Total50519
				RollCallString,
			iqudc31DelayGlobalDelayPairOPair850512
				INTEGER,
			iqudc31DelayGlobalDelayPairOPair8Total50520
				RollCallString,
			iqudc31AudioControlCh2GlobalDelay
				INTEGER,
			iqudc31AudioControlCh2GlobalDelayGlobalTotal
				RollCallString,
			iqudc31AudioControlCh2GlobalDelayVideoTotal
				RollCallString,
			iqudc31MenuAudioControlCh2NewDisplay
				RollCallString,
			iqudc31AudioIOAESAESOutput14AES1
				INTEGER,
			iqudc31MenuAudioIOAESAES2
				INTEGER,
			iqudc31MenuAudioIOAESAES3
				INTEGER,
			iqudc31MenuAudioIOAESAES4
				INTEGER,
			iqudc31AudioIOAESAESOutput58AES5
				INTEGER,
			iqudc31MenuAudioIOAESAES6
				INTEGER,
			iqudc31MenuAudioIOAESAES7
				INTEGER,
			iqudc31MenuAudioIOAESAES8
				INTEGER,
			iqudc31MenuAudioIOAESNewDisplay
				RollCallString,
			iqudc31AudioIOAnalogAnalogOutput12Analog1
				INTEGER,
			iqudc31MenuAudioIOAnalogAnalog2
				INTEGER,
			iqudc31InputAnalogInADCHeadrPair1
				INTEGER,
			iqudc31InputAnalogInADCHeadrPair2
				INTEGER,
			iqudc31OutputAnalogOutDACLevePair1
				INTEGER,
			iqudc31OutputAnalogOutDACLevePair2
				INTEGER,
			iqudc31MenuAudioIOAnalogNewDisplay
				RollCallString,
			iqudc31DolbySetupDolbyCh1Mode
				INTEGER,
			iqudc31DolbySetupDolbyCh1DolbyEDelayCompen
				INTEGER,
			iqudc31DolbySetupDolbyCh1MetadataSource
				INTEGER,
			iqudc31DolbyCh1SMPTE2020OutputOutputLine
				INTEGER,
			iqudc31DolbyCh1SMPTE2020OutputOutputEnable
				INTEGER,
			iqudc31DolbySetupDolbyCh1DecoderSource
				INTEGER,
			iqudc31MenuDolbySetupEncoderSource1
				INTEGER,
			iqudc31MenuDolbySetupEncoderSource2
				INTEGER,
			iqudc31MenuDolbySetupEncoderSource3
				INTEGER,
			iqudc31MenuDolbySetupEncoderSource4
				INTEGER,
			iqudc31MenuDolbySetupEncoderFormat
				INTEGER,
			iqudc31MenuDolbySetupEncoderFormatED
				INTEGER,
			iqudc31MenuDolbySetupEncoderRate
				INTEGER,
			iqudc31MenuDolbySetupEncoderBitDepth
				INTEGER,
			iqudc31MenuDolbySetupEncoderConfig
				INTEGER,
			iqudc31MenuDolbySetupInputStatus
				RollCallString,
			iqudc31MenuDolbySetupDecoderRate
				RollCallString,
			iqudc31MenuDolbySetupDecoderFormat
				RollCallString,
			iqudc31MenuDolbySetupDecoderVersion
				RollCallString,
			iqudc31MenuDolbySetupEncoderVersion
				RollCallString,
			iqudc31MenuDolbySetupNewDisplay
				RollCallString,
			iqudc31MenuGenlockSourceCh12
				INTEGER,
			iqudc31GenlockTimingCh1VerticalTiming
				INTEGER,
			iqudc31GenlockTimingCh1HorizontalTiming
				INTEGER,
			iqudc31GenlockTimingCh1Status
				RollCallString,
			iqudc31GenlockTimingCh2VerticalTiming
				INTEGER,
			iqudc31GenlockTimingCh2HorizontalTiming
				INTEGER,
			iqudc31GenlockTimingCh2Status
				RollCallString,
			iqudc31MenuTimecodeCh1SourceHD
				INTEGER,
			iqudc31MenuTimecodeCh1SourceSD
				INTEGER,
			iqudc31MenuTimecodeCh1Status
				RollCallString,
			iqudc31MenuTimecodeCh1Mode
				INTEGER,
			iqudc31MenuTimecodeCh1OnTimecodeLoss
				INTEGER,
			iqudc31MenuTimecodeCh1TimecodeEntry
				RollCallString,
			iqudc31MenuTimecodeCh1TimecodeLoad
				INTEGER,
			iqudc31MenuTimecodeCh1NondropFrame
				INTEGER,
			iqudc31MenuTimecodeCh1VITCEnable
				INTEGER,
			iqudc31MenuTimecodeCh1OutputLine525
				INTEGER,
			iqudc31MenuTimecodeCh1OutputLine625
				INTEGER,
			iqudc31MenuTimecodeCh1OutputLineStatus
				RollCallString,
			iqudc31MenuTimecodeCh1NewDisplay
				RollCallString,
			iqudc31MenuTimecodeCh2SourceHD
				INTEGER,
			iqudc31MenuTimecodeCh2SourceSD
				INTEGER,
			iqudc31MenuTimecodeCh2Status
				RollCallString,
			iqudc31MenuTimecodeCh2Mode
				INTEGER,
			iqudc31MenuTimecodeCh2OnTimecodeLoss
				INTEGER,
			iqudc31MenuTimecodeCh2TimecodeEntry
				RollCallString,
			iqudc31MenuTimecodeCh2TimecodeLoad
				INTEGER,
			iqudc31MenuTimecodeCh2NondropFrame
				INTEGER,
			iqudc31MenuTimecodeCh2VITCEnable
				INTEGER,
			iqudc31MenuTimecodeCh2OutputLine525
				INTEGER,
			iqudc31MenuTimecodeCh2OutputLine625
				INTEGER,
			iqudc31MenuTimecodeCh2OutputLineStatus
				RollCallString,
			iqudc31MenuTimecodeCh2NewDisplay
				RollCallString,
			iqudc31MetadataCh1ClosedCaptionsInputStatus
				RollCallString,
			iqudc31MetadataCh1ClosedCaptionsCEA608OutputEnab
				INTEGER,
			iqudc31MetadataCh1ClosedCaptionsCEA708OutputEnab
				INTEGER,
			iqudc31MenuMetadataCh1CEA708OutputLine60216
				INTEGER,
			iqudc31MenuMetadataCh1CEA708OutputLine60221
				RollCallString,
			iqudc31MetadataCh1TeletextTeletextPresentSt
				RollCallString,
			iqudc31MetadataCh1TeletextWSTInputLine
				INTEGER,
			iqudc31MetadataCh1TeletextWSTOutputEnable
				INTEGER,
			iqudc31MetadataCh1TeletextWSTOutputLine
				INTEGER,
			iqudc31MetadataCh1TeletextWSTOutputLineSta
				RollCallString,
			iqudc31MetadataCh1TeletextRDD08InputLine
				INTEGER,
			iqudc31MetadataCh1TeletextRDD08OutputEnabl
				INTEGER,
			iqudc31MenuMetadataCh1RDD08OutputLine60219
				INTEGER,
			iqudc31MenuMetadataCh1RDD08OutputLine20167
				RollCallString,
			iqudc31MenuMetadataCh1NewDisplay
				RollCallString,
			iqudc31MetadataCh2ClosedCaptionsInputStatus
				RollCallString,
			iqudc31MetadataCh2ClosedCaptionsCEA608OutputEnab
				INTEGER,
			iqudc31MetadataCh2ClosedCaptionsCEA708OutputEnab
				INTEGER,
			iqudc31MenuMetadataCh2CEA708OutputLine60302
				INTEGER,
			iqudc31MenuMetadataCh2CEA708OutputLine60222
				RollCallString,
			iqudc31MetadataCh2TeletextTeletextPresentSt
				RollCallString,
			iqudc31MetadataCh2TeletextWSTInputLine
				INTEGER,
			iqudc31MetadataCh2TeletextWSTOutputEnable
				INTEGER,
			iqudc31MetadataCh2TeletextWSTOutputLine
				INTEGER,
			iqudc31MetadataCh2TeletextWSTOutputLineSta
				RollCallString,
			iqudc31MetadataCh2TeletextRDD08InputLine
				INTEGER,
			iqudc31MetadataCh2TeletextRDD08OutputEnabl
				INTEGER,
			iqudc31MenuMetadataCh2RDD08OutputLine60307
				INTEGER,
			iqudc31MenuMetadataCh2RDD08OutputLine20177
				RollCallString,
			iqudc31MenuMetadataCh2NewDisplay
				RollCallString,
			iqudc31GPIOGPI1GPIO1Mode
				INTEGER,
			iqudc31MenuGPIOGPI1ipSelect
				INTEGER,
			iqudc31MenuGPIOGPO1opSelect
				INTEGER,
			iqudc31GPIOGPI2GPIO2Mode
				INTEGER,
			iqudc31MenuGPIOGPI2ipSelect
				INTEGER,
			iqudc31MenuGPIOGPO2opSelect
				INTEGER,
			iqudc31MenuGPIONewDisplay
				RollCallString,
			iqudc31MenuRollCallUnitName
				RollCallString,
			iqudc31MenuRollCallIPSharePort
				INTEGER,
			iqudc31MenuRollCallIPBridgingPort
				INTEGER,
			iqudc31MenuMemoriesRecallMemory
				INTEGER,
			iqudc31MenuMemoriesSelMemory
				INTEGER,
			iqudc31MenuMemoriesSaveMemory
				INTEGER,
			iqudc31MenuMemoriesClearMemory
				INTEGER,
			iqudc31MemoriesMemoryNameChangeName
				RollCallString,
			iqudc31MenuMemoriesLastDisplayMemory
				RollCallString,
			iqudc31MenuRollTrackDisableAll
				INTEGER,
			iqudc31MenuRollTrackIndex
				INTEGER,
			iqudc31MenuRollTrackSource
				INTEGER,
			iqudc31MenuRollTrackAddress
				RollCallString,
			iqudc31MenuRollTrackCommand
				RollCallString,
			iqudc31MenuRollTrackStatus
				RollCallString,
			iqudc31MenuRollTrackSending
				RollCallString,
			iqudc31MenuMiscLoggingSerialNumberEnabl
				INTEGER,
			iqudc31MenuMiscLoggingSerialNumberStatu
				RollCallString,
			iqudc31MenuMiscLoggingUpTimeEnable
				INTEGER,
			iqudc31MenuMiscLoggingUpTimeStatus
				RollCallString,
			iqudc31MenuMiscLoggingPowerUsageStateE
				INTEGER,
			iqudc31MenuMiscLoggingPowerUsageStateS
				RollCallString,
			iqudc31MenuMiscLoggingBuild62011
				INTEGER,
			iqudc31MenuMiscLoggingBuild62010
				RollCallString,
			iqudc31MenuMiscLoggingAESOutput14Place
				RollCallString,
			iqudc31MenuMiscLoggingAESOutput58Place
				RollCallString,
			iqudc31MenuMiscLoggingInputADCPlacehold
				RollCallString,
			iqudc31MenuMiscLoggingSourceCh1Ch2Pl
				RollCallString,
			iqudc31MenuMiscLoggingCVBSDecoderPlaceh
				RollCallString,
			iqudc31MenuMiscLoggingFanSpeedPlacehold
				RollCallString,
			iqudc31MenuVideoInputLoggingInput1Type62100
				INTEGER,
			iqudc31MenuVideoInputLoggingInput1Type62101
				RollCallString,
			iqudc31MenuVideoInputLoggingInput1State62102
				INTEGER,
			iqudc31MenuVideoInputLoggingInput1State62103
				RollCallString,
			iqudc31MenuVideoInputLoggingInput1Std62104
				INTEGER,
			iqudc31MenuVideoInputLoggingInput1Std62105
				RollCallString,
			iqudc31MenuVideoInputLoggingInput2Type62200
				INTEGER,
			iqudc31MenuVideoInputLoggingInput2Type62201
				RollCallString,
			iqudc31MenuVideoInputLoggingInput2State62202
				INTEGER,
			iqudc31MenuVideoInputLoggingInput2State62203
				RollCallString,
			iqudc31MenuVideoInputLoggingInput2Std62204
				INTEGER,
			iqudc31MenuVideoInputLoggingInput2Std62205
				RollCallString,
			iqudc31MenuVideoInputLoggingInput3Type62300
				INTEGER,
			iqudc31MenuVideoInputLoggingInput3Type62301
				RollCallString,
			iqudc31MenuVideoInputLoggingInput3State62302
				INTEGER,
			iqudc31MenuVideoInputLoggingInput3State62303
				RollCallString,
			iqudc31MenuVideoInputLoggingInput3Std62304
				INTEGER,
			iqudc31MenuVideoInputLoggingInput3Std62305
				RollCallString,
			iqudc31MenuVideoInputLoggingInput4Type62400
				INTEGER,
			iqudc31MenuVideoInputLoggingInput4Type62401
				RollCallString,
			iqudc31MenuVideoInputLoggingInput4State62402
				INTEGER,
			iqudc31MenuVideoInputLoggingInput4State62403
				RollCallString,
			iqudc31MenuVideoInputLoggingInput4Std62404
				INTEGER,
			iqudc31MenuVideoInputLoggingInput4Std62405
				RollCallString,
			iqudc31MenuVideoInputLoggingInput5Type62500
				INTEGER,
			iqudc31MenuVideoInputLoggingInput5Type62501
				RollCallString,
			iqudc31MenuVideoInputLoggingInput5State62502
				INTEGER,
			iqudc31MenuVideoInputLoggingInput5State62503
				RollCallString,
			iqudc31MenuVideoInputLoggingInput5Std62504
				INTEGER,
			iqudc31MenuVideoInputLoggingInput5Std62505
				RollCallString,
			iqudc31MenuOutputLoggingOutput1Type62600
				INTEGER,
			iqudc31MenuOutputLoggingOutput1Type62601
				RollCallString,
			iqudc31MenuOutputLoggingOutput1State62602
				INTEGER,
			iqudc31MenuOutputLoggingOutput1State62603
				RollCallString,
			iqudc31MenuOutputLoggingOutput1Std62604
				INTEGER,
			iqudc31MenuOutputLoggingOutput1Std62605
				RollCallString,
			iqudc31MenuOutputLoggingOutput2Type62612
				INTEGER,
			iqudc31MenuOutputLoggingOutput2Type62613
				RollCallString,
			iqudc31MenuOutputLoggingOutput2State62614
				INTEGER,
			iqudc31MenuOutputLoggingOutput2State62615
				RollCallString,
			iqudc31MenuOutputLoggingOutput2Std62616
				INTEGER,
			iqudc31MenuOutputLoggingOutput2Std62617
				RollCallString,
			iqudc31MenuOPAudioStateCh1OutputEmbPair1s62620
				INTEGER,
			iqudc31MenuOPAudioStateCh1OutputEmbPair1s62621
				RollCallString,
			iqudc31MenuOPAudioStateCh1OutputEmbPair2s62622
				INTEGER,
			iqudc31MenuOPAudioStateCh1OutputEmbPair2s62623
				RollCallString,
			iqudc31MenuOPAudioStateCh1OutputEmbPair3s62624
				INTEGER,
			iqudc31MenuOPAudioStateCh1OutputEmbPair3s62625
				RollCallString,
			iqudc31MenuOPAudioStateCh1OutputEmbPair4s62626
				INTEGER,
			iqudc31MenuOPAudioStateCh1OutputEmbPair4s62627
				RollCallString,
			iqudc31MenuOPAudioStateCh1OutputEmbPair5s62628
				INTEGER,
			iqudc31MenuOPAudioStateCh1OutputEmbPair5s62629
				RollCallString,
			iqudc31MenuOPAudioStateCh1OutputEmbPair6s62630
				INTEGER,
			iqudc31MenuOPAudioStateCh1OutputEmbPair6s62631
				RollCallString,
			iqudc31MenuOPAudioStateCh1OutputEmbPair7s62632
				INTEGER,
			iqudc31MenuOPAudioStateCh1OutputEmbPair7s62633
				RollCallString,
			iqudc31MenuOPAudioStateCh1OutputEmbPair8s62634
				INTEGER,
			iqudc31MenuOPAudioStateCh1OutputEmbPair8s62635
				RollCallString,
			iqudc31MenuOPAudioStateCh2OutputEmbPair1s62636
				INTEGER,
			iqudc31MenuOPAudioStateCh2OutputEmbPair1s62637
				RollCallString,
			iqudc31MenuOPAudioStateCh2OutputEmbPair2s62638
				INTEGER,
			iqudc31MenuOPAudioStateCh2OutputEmbPair2s62639
				RollCallString,
			iqudc31MenuOPAudioStateCh2OutputEmbPair3s62640
				INTEGER,
			iqudc31MenuOPAudioStateCh2OutputEmbPair3s62641
				RollCallString,
			iqudc31MenuOPAudioStateCh2OutputEmbPair4s62642
				INTEGER,
			iqudc31MenuOPAudioStateCh2OutputEmbPair4s62643
				RollCallString,
			iqudc31MenuOPAudioStateCh2OutputEmbPair5s62644
				INTEGER,
			iqudc31MenuOPAudioStateCh2OutputEmbPair5s62645
				RollCallString,
			iqudc31MenuOPAudioStateCh2OutputEmbPair6s62646
				INTEGER,
			iqudc31MenuOPAudioStateCh2OutputEmbPair6s62647
				RollCallString,
			iqudc31MenuOPAudioStateCh2OutputEmbPair7s62648
				INTEGER,
			iqudc31MenuOPAudioStateCh2OutputEmbPair7s62649
				RollCallString,
			iqudc31MenuOPAudioStateCh2OutputEmbPair8s62650
				INTEGER,
			iqudc31MenuOPAudioStateCh2OutputEmbPair8s62651
				RollCallString,
			iqudc31MenuOPAudioStateCh2NewDisplay
				RollCallString,
			iqudc31MenuOPAudioTypeCh1OutputEmbPair1t62653
				INTEGER,
			iqudc31MenuOPAudioTypeCh1OutputEmbPair1t62654
				RollCallString,
			iqudc31MenuOPAudioTypeCh1OutputEmbPair2t
				INTEGER,
			iqudc31MenuOPAudioTypeCh1OutputEmbPair2s
				RollCallString,
			iqudc31MenuOPAudioTypeCh1OutputEmbPair3t62657
				INTEGER,
			iqudc31MenuOPAudioTypeCh1OutputEmbPair3t62658
				RollCallString,
			iqudc31MenuOPAudioTypeCh1OutputEmbPair4t62659
				INTEGER,
			iqudc31MenuOPAudioTypeCh1OutputEmbPair4t62660
				RollCallString,
			iqudc31MenuOPAudioTypeCh1OutputEmbPair5t62661
				INTEGER,
			iqudc31MenuOPAudioTypeCh1OutputEmbPair5t62662
				RollCallString,
			iqudc31MenuOPAudioTypeCh1OutputEmbPair6t62663
				INTEGER,
			iqudc31MenuOPAudioTypeCh1OutputEmbPair6t62664
				RollCallString,
			iqudc31MenuOPAudioTypeCh1OutputEmbPair7t62665
				INTEGER,
			iqudc31MenuOPAudioTypeCh1OutputEmbPair7t62666
				RollCallString,
			iqudc31MenuOPAudioTypeCh1OutputEmbPair8t62667
				INTEGER,
			iqudc31MenuOPAudioTypeCh1OutputEmbPair8t62668
				RollCallString,
			iqudc31MenuOPAudioTypeCh2OutputEmbPair1t62669
				INTEGER,
			iqudc31MenuOPAudioTypeCh2OutputEmbPair1t62670
				RollCallString,
			iqudc31MenuOPAudioTypeCh2OutputEmbPair2t62671
				INTEGER,
			iqudc31MenuOPAudioTypeCh2OutputEmbPair2t62672
				RollCallString,
			iqudc31MenuOPAudioTypeCh2OutputEmbPair3t62673
				INTEGER,
			iqudc31MenuOPAudioTypeCh2OutputEmbPair3t62674
				RollCallString,
			iqudc31MenuOPAudioTypeCh2OutputEmbPair4t62675
				INTEGER,
			iqudc31MenuOPAudioTypeCh2OutputEmbPair4t62676
				RollCallString,
			iqudc31MenuOPAudioTypeCh2OutputEmbPair5t62677
				INTEGER,
			iqudc31MenuOPAudioTypeCh2OutputEmbPair5t62678
				RollCallString,
			iqudc31MenuOPAudioTypeCh2OutputEmbPair6t62679
				INTEGER,
			iqudc31MenuOPAudioTypeCh2OutputEmbPair6t62680
				RollCallString,
			iqudc31MenuOPAudioTypeCh2OutputEmbPair7t62681
				INTEGER,
			iqudc31MenuOPAudioTypeCh2OutputEmbPair7t62682
				RollCallString,
			iqudc31MenuOPAudioTypeCh2OutputEmbPair8t62683
				INTEGER,
			iqudc31MenuOPAudioTypeCh2OutputEmbPair8t62684
				RollCallString,
			iqudc31MenuOPAudioTypeCh2NewDisplay
				RollCallString,
			iqudc31MenuSetupSoftwareVersion
				RollCallString,
			iqudc31MenuSetupSerialNumber
				RollCallString,
			iqudc31MenuSetupNumberOfChannels
				RollCallString,
			iqudc31MenuSetupFrameSlotNumber
				RollCallString,
			iqudc31MenuSetupRearId
				RollCallString,
			iqudc31MenuSetupFanSpeed
				RollCallString,
			iqudc31MenuSetupIQOPTMNR
				RollCallString,
			iqudc31MenuSetupIQOPTMSBK
				RollCallString,
			iqudc31MenuSetupIQOPTMLFR
				RollCallString,
			iqudc31MenuSetupIQOPTMLOG
				RollCallString,
			iqudc31MenuSetupIQOPTMLC
				RollCallString,
			iqudc31MenuSetupIQOPTMDBD
				RollCallString,
			iqudc31MenuSetupIQOPTMDBEE
				RollCallString,
			iqudc31MenuSetupIQOPTMDBED
				RollCallString,
			iqudc31MenuSetupIQOPTMLOUDJ
				RollCallString,
			iqudc31MenuSetupIQOPTMLOUDMC
				RollCallString,
			iqudc31MenuSetupBuild
				RollCallString,
			iqudc31MenuSetupLicencedOptionsH
				RollCallString,
			iqudc31MenuSetupFactoryDefaults
				INTEGER,
			iqudc31MenuSetupDefaultSettings
				INTEGER,
			iqudc31MenuSetupRestart
				INTEGER,
			iqudc31MenuSetupUpgradeStartHide
				INTEGER,
			iqudc31MenuSetupUpgradeFinishHid
				INTEGER,
			iqudc31MenuDisplaymenu
				INTEGER,
			iqudc31MenuPlaceholderCh1ScrollingCaptionG
				RollCallString,
			iqudc31MenuPlaceholderCh1SFPOutputRouting
				RollCallString,
			iqudc31MenuPlaceholderCh1CVBSEncoderPlaceh
				RollCallString,
			iqudc31MenuPlaceholderCh1NonlinearEnhancer
				RollCallString,
			iqudc31MenuPlaceholderCh1ConversionAperture
				RollCallString,
			iqudc31MenuPlaceholderCh1NoiseReducerPlace
				RollCallString,
			iqudc31MenuPlaceholderCh1UpConversionPlace
				RollCallString,
			iqudc31MenuPlaceholderCh1GenlockTimingPlac
				RollCallString,
			iqudc31MenuPlaceholderCh1ClosedCaptions708
				RollCallString,
			iqudc31MenuPlaceholderCh2InputSourcePlaceh
				RollCallString,
			iqudc31MenuPlaceholderCh2ScrollingCaptionG
				RollCallString,
			iqudc31MenuPlaceholderCh2SFPOutputRouting
				RollCallString,
			iqudc31MenuPlaceholderCh2CVBSEncoderPlaceh
				RollCallString,
			iqudc31MenuPlaceholderCh2NonlinearEnhancer
				RollCallString,
			iqudc31MenuPlaceholderCh2ConversionAperture
				RollCallString,
			iqudc31MenuPlaceholderCh2NoiseReducerPlace
				RollCallString,
			iqudc31MenuPlaceholderCh2UpConversionPlace
				RollCallString,
			iqudc31MenuPlaceholderCh2GenlockTimingPlac
				RollCallString,
			iqudc31MenuPlaceholderCh2ClosedCaptions708
				RollCallString
		}

	iqudc31SlotIndex OBJECT-TYPE
		SYNTAX		Unsigned32
		MAX-ACCESS		not-accessible
		STATUS			current
		DESCRIPTION
				"The unique Index value for each slot.  Its value
					ranges between 1 and the value of slotNumber."
		::= { iqudc31CmdEntry 0 }


	iqudc31InputInputSourceCh1InputSelect OBJECT-TYPE
		SYNTAX		INTEGER {
							val-SDI-1(0),
							val-SDI-2(1),
							val-CVBS(2),
							val-SFP-1(3),
							val-SFP-2(4)
							}
		MAX-ACCESS		read-write
		STATUS			current
		DESCRIPTION
				"TYPE: - RadiobuttonList
				 PAGE: - Input- Input Source Ch 1
					Input Select  cmdID= 10006 
					SDI 1  value= 0  
					SDI 2  value= 1  
					CVBS  value= 2  
					SFP 1  value= 3  
					SFP 2  value= 4  "
		::= { iqudc31CmdEntry 10006 }


	iqudc31InputSourceCh1StatusSDI1 OBJECT-TYPE
		SYNTAX		RollCallString
		MAX-ACCESS		read-only
		STATUS			current
		DESCRIPTION
				"TYPE: - Display
				 PAGE: - Input- Input Source Ch 1
					SDI 1  cmdID= 63000  format=   "
		::= { iqudc31CmdEntry 63000 }


	iqudc31InputSourceCh1StatusSDI2 OBJECT-TYPE
		SYNTAX		RollCallString
		MAX-ACCESS		read-only
		STATUS			current
		DESCRIPTION
				"TYPE: - Display
				 PAGE: - Input- Input Source Ch 1
					SDI 2  cmdID= 63001  format=   "
		::= { iqudc31CmdEntry 63001 }


	iqudc31InputSourceCh1StatusCVBS OBJECT-TYPE
		SYNTAX		RollCallString
		MAX-ACCESS		read-only
		STATUS			current
		DESCRIPTION
				"TYPE: - Display
				 PAGE: - Input- Input Source Ch 1
					CVBS  cmdID= 63004  format=   "
		::= { iqudc31CmdEntry 63004 }


	iqudc31InputSourceCh1StatusSFP1 OBJECT-TYPE
		SYNTAX		RollCallString
		MAX-ACCESS		read-only
		STATUS			current
		DESCRIPTION
				"TYPE: - Display
				 PAGE: - Input- Input Source Ch 1
					SFP 1  cmdID= 63008  format=   "
		::= { iqudc31CmdEntry 63008 }


	iqudc31InputSourceCh1StatusSFP2 OBJECT-TYPE
		SYNTAX		RollCallString
		MAX-ACCESS		read-only
		STATUS			current
		DESCRIPTION
				"TYPE: - Display
				 PAGE: - Input- Input Source Ch 1
					SFP 2  cmdID= 63009  format=   "
		::= { iqudc31CmdEntry 63009 }


	iqudc31InputSourceCh1StatusCurrentInputStand OBJECT-TYPE
		SYNTAX		RollCallString
		MAX-ACCESS		read-only
		STATUS			current
		DESCRIPTION
				"TYPE: - Display
				 PAGE: - Input- Input Source Ch 1
					Current Input Stand  cmdID= 64010  format=   "
		::= { iqudc31CmdEntry 64010 }


	iqudc31InputInputSourceCh2InputSelect OBJECT-TYPE
		SYNTAX		INTEGER {
							val-SDI-1(0),
							val-SDI-2(1),
							val-CVBS(2),
							val-SFP-1(3),
							val-SFP-2(4)
							}
		MAX-ACCESS		read-write
		STATUS			current
		DESCRIPTION
				"TYPE: - RadiobuttonList
				 PAGE: - Input- Input Source Ch 2
					Input Select  cmdID= 10106 
					SDI 1  value= 0  
					SDI 2  value= 1  
					CVBS  value= 2  
					SFP 1  value= 3  
					SFP 2  value= 4  "
		::= { iqudc31CmdEntry 10106 }


	iqudc31InputSourceCh2StatusSDI1 OBJECT-TYPE
		SYNTAX		RollCallString
		MAX-ACCESS		read-only
		STATUS			current
		DESCRIPTION
				"TYPE: - Display
				 PAGE: - Input- Input Source Ch 2
					SDI 1  cmdID= 63100  format=   "
		::= { iqudc31CmdEntry 63100 }


	iqudc31InputSourceCh2StatusSDI2 OBJECT-TYPE
		SYNTAX		RollCallString
		MAX-ACCESS		read-only
		STATUS			current
		DESCRIPTION
				"TYPE: - Display
				 PAGE: - Input- Input Source Ch 2
					SDI 2  cmdID= 63101  format=   "
		::= { iqudc31CmdEntry 63101 }


	iqudc31InputSourceCh2StatusCVBS OBJECT-TYPE
		SYNTAX		RollCallString
		MAX-ACCESS		read-only
		STATUS			current
		DESCRIPTION
				"TYPE: - Display
				 PAGE: - Input- Input Source Ch 2
					CVBS  cmdID= 63104  format=   "
		::= { iqudc31CmdEntry 63104 }


	iqudc31InputSourceCh2StatusSFP1 OBJECT-TYPE
		SYNTAX		RollCallString
		MAX-ACCESS		read-only
		STATUS			current
		DESCRIPTION
				"TYPE: - Display
				 PAGE: - Input- Input Source Ch 2
					SFP 1  cmdID= 63108  format=   "
		::= { iqudc31CmdEntry 63108 }


	iqudc31InputSourceCh2StatusSFP2 OBJECT-TYPE
		SYNTAX		RollCallString
		MAX-ACCESS		read-only
		STATUS			current
		DESCRIPTION
				"TYPE: - Display
				 PAGE: - Input- Input Source Ch 2
					SFP 2  cmdID= 63109  format=   "
		::= { iqudc31CmdEntry 63109 }


	iqudc31InputSourceCh2StatusCurrentInputStand OBJECT-TYPE
		SYNTAX		RollCallString
		MAX-ACCESS		read-only
		STATUS			current
		DESCRIPTION
				"TYPE: - Display
				 PAGE: - Input- Input Source Ch 2
					Current Input Stand  cmdID= 64110  format=   "
		::= { iqudc31CmdEntry 64110 }


	iqudc31CVBSDecoderSetupACC OBJECT-TYPE
		SYNTAX		INTEGER { disable(0), enable(1) }
		MAX-ACCESS		read-write
		STATUS			current
		DESCRIPTION
				"TYPE: - Checkbox
				 PAGE: - Input- CVBS Decoder
					ACC  cmdID= 20501 "
		::= { iqudc31CmdEntry 20501 }


	iqudc31CVBSDecoderSetupCTI OBJECT-TYPE
		SYNTAX		INTEGER { disable(0), enable(1) }
		MAX-ACCESS		read-write
		STATUS			current
		DESCRIPTION
				"TYPE: - Checkbox
				 PAGE: - Input- CVBS Decoder
					CTI  cmdID= 20502 "
		::= { iqudc31CmdEntry 20502 }


	iqudc31CVBSDecoderSetupPedestal OBJECT-TYPE
		SYNTAX		INTEGER {
							val-Off(0),
							val-On(1)
							}
		MAX-ACCESS		read-write
		STATUS			current
		DESCRIPTION
				"TYPE: - RadiobuttonList
				 PAGE: - Input- CVBS Decoder
					Pedestal  cmdID= 20503 
					Off  value= 0  
					On  value= 1  "
		::= { iqudc31CmdEntry 20503 }


	iqudc31InputCVBSDecoderNTSCHue OBJECT-TYPE
		SYNTAX		INTEGER
		MAX-ACCESS		read-write
		STATUS			current
		DESCRIPTION
				"TYPE: - Number
				 PAGE: - Input- CVBS Decoder
					NTSC Hue  cmdID= 20504  min= -180  max= 180  step= 1  format= %d deg  div_scale= 1 
					Min = -180 deg  Max = 180 deg  Step = 1 deg "
		::= { iqudc31CmdEntry 20504 }


	iqudc31CVBSDecoderCalibrationLumaGain OBJECT-TYPE
		SYNTAX		INTEGER
		MAX-ACCESS		read-write
		STATUS			current
		DESCRIPTION
				"TYPE: - Number
				 PAGE: - Input- CVBS Decoder
					Luma Gain  cmdID= 20505  min= 0  max= 2047  step= 1  format= %d  div_scale= 1 
					Min = 0  Max = 2047  Step = 1 "
		::= { iqudc31CmdEntry 20505 }


	iqudc31CVBSDecoderCalibrationSaveDecoder OBJECT-TYPE
		SYNTAX		INTEGER { noAction(0),val-Save-Decoder(1) }
		MAX-ACCESS		read-write
		STATUS			current
		DESCRIPTION
				"TYPE: - Button
				 PAGE: - Input- CVBS Decoder
					Save Decoder  cmdID= 20506  value= 1  "
		::= { iqudc31CmdEntry 20506 }


	iqudc31OutputCh1OutputStandardStandard OBJECT-TYPE
		SYNTAX		INTEGER {
							val-625-50i(2),
							val-525-59i(3),
							val-720-23p(4),
							val-720-24p(5),
							val-720-25p(6),
							val-720-29p(7),
							val-720-50p(9),
							val-720-59p(10),
							val-1080-23p(12),
							val-1080-24p(13),
							val-1080-25p(14),
							val-1080-29p(15),
							val-1080-50i(17),
							val-1080-59i(18),
							val-1080-23psf(20),
							val-1080-24psf(21),
							val-1080-25psf(50),
							val-1080-29psf(51),
							val-1080-50p-A(22),
							val-1080-59p-A(23),
							val-1080-50p-B(25),
							val-1080-59p-B(26)
							}
		MAX-ACCESS		read-write
		STATUS			current
		DESCRIPTION
				"TYPE: - RadiobuttonList
				 PAGE: - Output-Ch1
					Standard  cmdID= 10100 
					625 50i  value= 2  
					525 59i  value= 3  
					720 23p  value= 4  
					720 24p  value= 5  
					720 25p  value= 6  
					720 29p  value= 7  
					720 50p  value= 9  
					720 59p  value= 10  
					1080 23p  value= 12  
					1080 24p  value= 13  
					1080 25p  value= 14  
					1080 29p  value= 15  
					1080 50i  value= 17  
					1080 59i  value= 18  
					1080 23psf  value= 20  
					1080 24psf  value= 21  
					1080 25psf  value= 50  
					1080 29psf  value= 51  
					1080 50p-A  value= 22  
					1080 59p-A  value= 23  
					1080 50p-B  value= 25  
					1080 59p-B  value= 26  "
		::= { iqudc31CmdEntry 10100 }


	iqudc31MenuOutputCh1Format OBJECT-TYPE
		SYNTAX		INTEGER {
							val-525-625(0),
							val-720p(1),
							val-1080i(2),
							val-1080p-A(3),
							val-1080p-B(4)
							}
		MAX-ACCESS		read-write
		STATUS			current
		DESCRIPTION
				"TYPE: - RadiobuttonList
				 PAGE: - Output-Ch1
					Format  cmdID= 10101 
					525/625  value= 0  
					720p  value= 1  
					1080i  value= 2  
					1080p-A  value= 3  
					1080p-B  value= 4  "
		::= { iqudc31CmdEntry 10101 }


	iqudc31MenuOutputCh1DefaultFieldRate OBJECT-TYPE
		SYNTAX		INTEGER {
							val-Last-Valid-Input(0),
							val-23-Hz(1),
							val-24-Hz(2),
							val-25-Hz(3),
							val-29-Hz(4),
							val-50-Hz(6),
							val-59-Hz(7)
							}
		MAX-ACCESS		read-write
		STATUS			current
		DESCRIPTION
				"TYPE: - RadiobuttonList
				 PAGE: - Output-Ch1
					Default Field Rate  cmdID= 10102 
					Last Valid Input  value= 0  
					23 Hz  value= 1  
					24 Hz  value= 2  
					25 Hz  value= 3  
					29 Hz  value= 4  
					50 Hz  value= 6  
					59 Hz  value= 7  "
		::= { iqudc31CmdEntry 10102 }


	iqudc31MenuOutputCh1CurrentOutputStan OBJECT-TYPE
		SYNTAX		RollCallString
		MAX-ACCESS		read-only
		STATUS			current
		DESCRIPTION
				"TYPE: - Display
				 PAGE: - Output-Ch1
					Current Output Stan  cmdID= 64011  format=   "
		::= { iqudc31CmdEntry 64011 }


	iqudc31OutputCh1ScrollingCaptionGCaptionEntry OBJECT-TYPE
		SYNTAX		RollCallString
		MAX-ACCESS		read-write
		STATUS			current
		DESCRIPTION
				"TYPE: - Editstring
				 PAGE: - Output-Ch1
					Caption Entry  cmdID= 10013  "
		::= { iqudc31CmdEntry 10013 }


	iqudc31OutputCh1ScrollingCaptionGCaptionScroll OBJECT-TYPE
		SYNTAX		INTEGER { disable(0), enable(1) }
		MAX-ACCESS		read-write
		STATUS			current
		DESCRIPTION
				"TYPE: - Checkbox
				 PAGE: - Output-Ch1
					Caption Scroll  cmdID= 10015 "
		::= { iqudc31CmdEntry 10015 }


	iqudc31OutputCh1ScrollingCaptionGCaptionEnable OBJECT-TYPE
		SYNTAX		INTEGER { disable(0), enable(1) }
		MAX-ACCESS		read-write
		STATUS			current
		DESCRIPTION
				"TYPE: - Checkbox
				 PAGE: - Output-Ch1
					Caption Enable  cmdID= 10014 "
		::= { iqudc31CmdEntry 10014 }


	iqudc31MenuOutputCh1Freeze OBJECT-TYPE
		SYNTAX		INTEGER { disable(0), enable(1) }
		MAX-ACCESS		read-write
		STATUS			current
		DESCRIPTION
				"TYPE: - Checkbox
				 PAGE: - Output-Ch1
					Freeze  cmdID= 20302 "
		::= { iqudc31CmdEntry 20302 }


	iqudc31MenuOutputCh1Legalizer OBJECT-TYPE
		SYNTAX		INTEGER { disable(0), enable(1) }
		MAX-ACCESS		read-write
		STATUS			current
		DESCRIPTION
				"TYPE: - Checkbox
				 PAGE: - Output-Ch1
					Legalizer  cmdID= 20205 "
		::= { iqudc31CmdEntry 20205 }


	iqudc31OutputCh1SFPOutputRoutingSFP1Source OBJECT-TYPE
		SYNTAX		INTEGER {
							val-Ch-1(0),
							val-Ch-2(1)
							}
		MAX-ACCESS		read-write
		STATUS			current
		DESCRIPTION
				"TYPE: - RadiobuttonList
				 PAGE: - Output-Ch1
					SFP 1 Source  cmdID= 20519 
					Ch 1  value= 0  
					Ch 2  value= 1  "
		::= { iqudc31CmdEntry 20519 }


	iqudc31MenuOutputCh1SFP2Source OBJECT-TYPE
		SYNTAX		INTEGER {
							val-Ch-1(0),
							val-Ch-2(1)
							}
		MAX-ACCESS		read-write
		STATUS			current
		DESCRIPTION
				"TYPE: - RadiobuttonList
				 PAGE: - Output-Ch1
					SFP 2 Source  cmdID= 20520 
					Ch 1  value= 0  
					Ch 2  value= 1  "
		::= { iqudc31CmdEntry 20520 }


	iqudc31MenuOutputCh1TestPatterns OBJECT-TYPE
		SYNTAX		INTEGER {
							val-Off(0),
							val-Black(1),
							val-Ramp(2),
							val-Bars(3)
							}
		MAX-ACCESS		read-write
		STATUS			current
		DESCRIPTION
				"TYPE: - RadiobuttonList
				 PAGE: - Output-Ch1
					Test Patterns  cmdID= 20301 
					Off  value= 0  
					Black  value= 1  
					Ramp  value= 2  
					Bars  value= 3  "
		::= { iqudc31CmdEntry 20301 }


	iqudc31CVBSEncoderASetupFormat OBJECT-TYPE
		SYNTAX		INTEGER {
							val-PAL-NTSC(0),
							val-PAL-N-PAL-M(1),
							val-PAL-NTSC-J(2)
							}
		MAX-ACCESS		read-write
		STATUS			current
		DESCRIPTION
				"TYPE: - RadiobuttonList
				 PAGE: - Output-Ch1
					Format  cmdID= 20508 
					PAL/NTSC  value= 0  
					PAL-N/PAL-M  value= 1  
					PAL/NTSC-J  value= 2  "
		::= { iqudc31CmdEntry 20508 }


	iqudc31OutputCh1CalibrationDACGain OBJECT-TYPE
		SYNTAX		INTEGER
		MAX-ACCESS		read-write
		STATUS			current
		DESCRIPTION
				"TYPE: - Number
				 PAGE: - Output-Ch1
					DAC Gain  cmdID= 20509  min= -64  max= 64  step= 1  format= %d  div_scale= 1 
					Min = -64  Max = 64  Step = 1 "
		::= { iqudc31CmdEntry 20509 }


	iqudc31OutputCh1CalibrationSaveEncoder OBJECT-TYPE
		SYNTAX		INTEGER { noAction(0),val-Save-Encoder(1) }
		MAX-ACCESS		read-write
		STATUS			current
		DESCRIPTION
				"TYPE: - Button
				 PAGE: - Output-Ch1
					Save Encoder  cmdID= 20510  value= 1  "
		::= { iqudc31CmdEntry 20510 }


	iqudc31OutputCh1BlankingEmbeddedAudio OBJECT-TYPE
		SYNTAX		INTEGER {
							val-Enable(0),
							val-Blank(1)
							}
		MAX-ACCESS		read-write
		STATUS			current
		DESCRIPTION
				"TYPE: - RadiobuttonList
				 PAGE: - Output-Ch1
					Embedded Audio  cmdID= 10010 
					Enable  value= 0  
					Blank  value= 1  "
		::= { iqudc31CmdEntry 10010 }


	iqudc31MenuOutputCh1VAncillaryData OBJECT-TYPE
		SYNTAX		INTEGER {
							val-Pass(0),
							val-Strip(1)
							}
		MAX-ACCESS		read-write
		STATUS			current
		DESCRIPTION
				"TYPE: - RadiobuttonList
				 PAGE: - Output-Ch1
					V Ancillary Data  cmdID= 10011 
					Pass  value= 0  
					Strip  value= 1  "
		::= { iqudc31CmdEntry 10011 }


	iqudc31MenuOutputCh1SDHalfLine OBJECT-TYPE
		SYNTAX		INTEGER {
							val-Pass(0),
							val-Blank(1)
							}
		MAX-ACCESS		read-write
		STATUS			current
		DESCRIPTION
				"TYPE: - RadiobuttonList
				 PAGE: - Output-Ch1
					SD Half Line  cmdID= 10012 
					Pass  value= 0  
					Blank  value= 1  "
		::= { iqudc31CmdEntry 10012 }


	iqudc31OutputCh2OutputStandardStandard OBJECT-TYPE
		SYNTAX		INTEGER {
							val-625-50i(2),
							val-525-59i(3),
							val-720-23p(4),
							val-720-24p(5),
							val-720-25p(6),
							val-720-29p(7),
							val-720-50p(9),
							val-720-59p(10),
							val-1080-23p(12),
							val-1080-24p(13),
							val-1080-25p(14),
							val-1080-29p(15),
							val-1080-50i(17),
							val-1080-59i(18),
							val-1080-23psf(20),
							val-1080-24psf(21),
							val-1080-25psf(50),
							val-1080-29psf(51),
							val-1080-50p-A(22),
							val-1080-59p-A(23),
							val-1080-50p-B(25),
							val-1080-59p-B(26)
							}
		MAX-ACCESS		read-write
		STATUS			current
		DESCRIPTION
				"TYPE: - RadiobuttonList
				 PAGE: - Output-Ch2
					Standard  cmdID= 10200 
					625 50i  value= 2  
					525 59i  value= 3  
					720 23p  value= 4  
					720 24p  value= 5  
					720 25p  value= 6  
					720 29p  value= 7  
					720 50p  value= 9  
					720 59p  value= 10  
					1080 23p  value= 12  
					1080 24p  value= 13  
					1080 25p  value= 14  
					1080 29p  value= 15  
					1080 50i  value= 17  
					1080 59i  value= 18  
					1080 23psf  value= 20  
					1080 24psf  value= 21  
					1080 25psf  value= 50  
					1080 29psf  value= 51  
					1080 50p-A  value= 22  
					1080 59p-A  value= 23  
					1080 50p-B  value= 25  
					1080 59p-B  value= 26  "
		::= { iqudc31CmdEntry 10200 }


	iqudc31MenuOutputCh2Format OBJECT-TYPE
		SYNTAX		INTEGER {
							val-525-625(0),
							val-720p(1),
							val-1080i(2),
							val-1080p-A(3),
							val-1080p-B(4)
							}
		MAX-ACCESS		read-write
		STATUS			current
		DESCRIPTION
				"TYPE: - RadiobuttonList
				 PAGE: - Output-Ch2
					Format  cmdID= 10201 
					525/625  value= 0  
					720p  value= 1  
					1080i  value= 2  
					1080p-A  value= 3  
					1080p-B  value= 4  "
		::= { iqudc31CmdEntry 10201 }


	iqudc31MenuOutputCh2DefaultFieldRate OBJECT-TYPE
		SYNTAX		INTEGER {
							val-Last-Valid-Input(0),
							val-23-Hz(1),
							val-24-Hz(2),
							val-25-Hz(3),
							val-29-Hz(4),
							val-50-Hz(6),
							val-59-Hz(7)
							}
		MAX-ACCESS		read-write
		STATUS			current
		DESCRIPTION
				"TYPE: - RadiobuttonList
				 PAGE: - Output-Ch2
					Default Field Rate  cmdID= 10202 
					Last Valid Input  value= 0  
					23 Hz  value= 1  
					24 Hz  value= 2  
					25 Hz  value= 3  
					29 Hz  value= 4  
					50 Hz  value= 6  
					59 Hz  value= 7  "
		::= { iqudc31CmdEntry 10202 }


	iqudc31MenuOutputCh2CurrentOutputStan OBJECT-TYPE
		SYNTAX		RollCallString
		MAX-ACCESS		read-only
		STATUS			current
		DESCRIPTION
				"TYPE: - Display
				 PAGE: - Output-Ch2
					Current Output Stan  cmdID= 64111  format=   "
		::= { iqudc31CmdEntry 64111 }


	iqudc31OutputCh2ScrollingCaptionGCaptionEntry OBJECT-TYPE
		SYNTAX		RollCallString
		MAX-ACCESS		read-write
		STATUS			current
		DESCRIPTION
				"TYPE: - Editstring
				 PAGE: - Output-Ch2
					Caption Entry  cmdID= 10113  "
		::= { iqudc31CmdEntry 10113 }


	iqudc31OutputCh2ScrollingCaptionGCaptionScroll OBJECT-TYPE
		SYNTAX		INTEGER { disable(0), enable(1) }
		MAX-ACCESS		read-write
		STATUS			current
		DESCRIPTION
				"TYPE: - Checkbox
				 PAGE: - Output-Ch2
					Caption Scroll  cmdID= 10115 "
		::= { iqudc31CmdEntry 10115 }


	iqudc31OutputCh2ScrollingCaptionGCaptionEnable OBJECT-TYPE
		SYNTAX		INTEGER { disable(0), enable(1) }
		MAX-ACCESS		read-write
		STATUS			current
		DESCRIPTION
				"TYPE: - Checkbox
				 PAGE: - Output-Ch2
					Caption Enable  cmdID= 10114 "
		::= { iqudc31CmdEntry 10114 }


	iqudc31MenuOutputCh2Freeze OBJECT-TYPE
		SYNTAX		INTEGER { disable(0), enable(1) }
		MAX-ACCESS		read-write
		STATUS			current
		DESCRIPTION
				"TYPE: - Checkbox
				 PAGE: - Output-Ch2
					Freeze  cmdID= 20400 "
		::= { iqudc31CmdEntry 20400 }


	iqudc31MenuOutputCh2Legalizer OBJECT-TYPE
		SYNTAX		INTEGER { disable(0), enable(1) }
		MAX-ACCESS		read-write
		STATUS			current
		DESCRIPTION
				"TYPE: - Checkbox
				 PAGE: - Output-Ch2
					Legalizer  cmdID= 20300 "
		::= { iqudc31CmdEntry 20300 }


	iqudc31MenuOutputCh2TestPatterns OBJECT-TYPE
		SYNTAX		INTEGER {
							val-Off(0),
							val-Black(1),
							val-Ramp(2),
							val-Bars(3)
							}
		MAX-ACCESS		read-write
		STATUS			current
		DESCRIPTION
				"TYPE: - RadiobuttonList
				 PAGE: - Output-Ch2
					Test Patterns  cmdID= 20401 
					Off  value= 0  
					Black  value= 1  
					Ramp  value= 2  
					Bars  value= 3  "
		::= { iqudc31CmdEntry 20401 }


	iqudc31CVBSEncoderBSetupFormat OBJECT-TYPE
		SYNTAX		INTEGER {
							val-PAL-NTSC(0),
							val-PAL-N-PAL-M(1),
							val-PAL-NTSC-J(2)
							}
		MAX-ACCESS		read-write
		STATUS			current
		DESCRIPTION
				"TYPE: - RadiobuttonList
				 PAGE: - Output-Ch2
					Format  cmdID= 20512 
					PAL/NTSC  value= 0  
					PAL-N/PAL-M  value= 1  
					PAL/NTSC-J  value= 2  "
		::= { iqudc31CmdEntry 20512 }


	iqudc31OutputCh2CalibrationDACGain OBJECT-TYPE
		SYNTAX		INTEGER
		MAX-ACCESS		read-write
		STATUS			current
		DESCRIPTION
				"TYPE: - Number
				 PAGE: - Output-Ch2
					DAC Gain  cmdID= 20513  min= -64  max= 64  step= 1  format= %d  div_scale= 1 
					Min = -64  Max = 64  Step = 1 "
		::= { iqudc31CmdEntry 20513 }


	iqudc31OutputCh2CalibrationSaveEncoder OBJECT-TYPE
		SYNTAX		INTEGER { noAction(0),val-Save-Encoder(1) }
		MAX-ACCESS		read-write
		STATUS			current
		DESCRIPTION
				"TYPE: - Button
				 PAGE: - Output-Ch2
					Save Encoder  cmdID= 20514  value= 1  "
		::= { iqudc31CmdEntry 20514 }


	iqudc31OutputCh2BlankingEmbeddedAudio OBJECT-TYPE
		SYNTAX		INTEGER {
							val-Enable(0),
							val-Blank(1)
							}
		MAX-ACCESS		read-write
		STATUS			current
		DESCRIPTION
				"TYPE: - RadiobuttonList
				 PAGE: - Output-Ch2
					Embedded Audio  cmdID= 10110 
					Enable  value= 0  
					Blank  value= 1  "
		::= { iqudc31CmdEntry 10110 }


	iqudc31MenuOutputCh2VAncillaryData OBJECT-TYPE
		SYNTAX		INTEGER {
							val-Pass(0),
							val-Strip(1)
							}
		MAX-ACCESS		read-write
		STATUS			current
		DESCRIPTION
				"TYPE: - RadiobuttonList
				 PAGE: - Output-Ch2
					V Ancillary Data  cmdID= 10111 
					Pass  value= 0  
					Strip  value= 1  "
		::= { iqudc31CmdEntry 10111 }


	iqudc31MenuOutputCh2SDHalfLine OBJECT-TYPE
		SYNTAX		INTEGER {
							val-Pass(0),
							val-Blank(1)
							}
		MAX-ACCESS		read-write
		STATUS			current
		DESCRIPTION
				"TYPE: - RadiobuttonList
				 PAGE: - Output-Ch2
					SD Half Line  cmdID= 10112 
					Pass  value= 0  
					Blank  value= 1  "
		::= { iqudc31CmdEntry 10112 }


	iqudc31MenuOutputCh2NewDisplay OBJECT-TYPE
		SYNTAX		RollCallString
		MAX-ACCESS		read-only
		STATUS			current
		DESCRIPTION
				"TYPE: - Display
				 PAGE: - Output-Ch2
					New Display  cmdID= 44446  format=   "
		::= { iqudc31CmdEntry 44446 }


	iqudc31VideoCh1ProcAmpEnable OBJECT-TYPE
		SYNTAX		INTEGER { disable(0), enable(1) }
		MAX-ACCESS		read-write
		STATUS			current
		DESCRIPTION
				"TYPE: - Checkbox
				 PAGE: - Video-Ch1
					Enable  cmdID= 20109 "
		::= { iqudc31CmdEntry 20109 }


	iqudc31VideoCh1ProcAmpContrast OBJECT-TYPE
		SYNTAX		INTEGER
		MAX-ACCESS		read-write
		STATUS			current
		DESCRIPTION
				"TYPE: - Number
				 PAGE: - Video-Ch1
					Contrast  cmdID= 20100  min= -60  max= 60  step= 2  format= %0.1fdB  div_scale= 10 
					Min = -6.0dB  Max = 6.0dB  Step = 0.2dB "
		::= { iqudc31CmdEntry 20100 }


	iqudc31VideoCh1ProcAmpSaturation OBJECT-TYPE
		SYNTAX		INTEGER
		MAX-ACCESS		read-write
		STATUS			current
		DESCRIPTION
				"TYPE: - Number
				 PAGE: - Video-Ch1
					Saturation  cmdID= 20106  min= -60  max= 60  step= 2  format= %0.1fdB  div_scale= 10 
					Min = -6.0dB  Max = 6.0dB  Step = 0.2dB "
		::= { iqudc31CmdEntry 20106 }


	iqudc31VideoCh1ProcAmpBlackLevel OBJECT-TYPE
		SYNTAX		INTEGER
		MAX-ACCESS		read-write
		STATUS			current
		DESCRIPTION
				"TYPE: - Number
				 PAGE: - Video-Ch1
					Black Level  cmdID= 20102  min= -1000  max= 1000  step= 8  format= %0.1fmV  div_scale= 10 
					Min = -100.0mV  Max = 100.0mV  Step = 0.8mV "
		::= { iqudc31CmdEntry 20102 }


	iqudc31VideoCh1ProcAmpGamma OBJECT-TYPE
		SYNTAX		INTEGER
		MAX-ACCESS		read-write
		STATUS			current
		DESCRIPTION
				"TYPE: - Number
				 PAGE: - Video-Ch1
					Gamma  cmdID= 20103  min= 4  max= 17  step= 1  format= %0.1f  div_scale= 10 
					Min = 0.4  Max = 1.7  Step = 0.1 "
		::= { iqudc31CmdEntry 20103 }


	iqudc31VideoCh1ProcAmpYCOffset OBJECT-TYPE
		SYNTAX		INTEGER
		MAX-ACCESS		read-write
		STATUS			current
		DESCRIPTION
				"TYPE: - Number
				 PAGE: - Video-Ch1
					YC Offset  cmdID= 20114  min= -20  max= 20  step= 2  format= %0.0f  div_scale= 1 
					Min = -20  Max = 20  Step = 2 "
		::= { iqudc31CmdEntry 20114 }


	iqudc31VideoCh1NonlinearEnhancerEnable OBJECT-TYPE
		SYNTAX		INTEGER { disable(0), enable(1) }
		MAX-ACCESS		read-write
		STATUS			current
		DESCRIPTION
				"TYPE: - Checkbox
				 PAGE: - Video-Ch1
					Enable  cmdID= 20050 "
		::= { iqudc31CmdEntry 20050 }


	iqudc31VideoCh1NonlinearEnhancerLevel OBJECT-TYPE
		SYNTAX		INTEGER
		MAX-ACCESS		read-write
		STATUS			current
		DESCRIPTION
				"TYPE: - Number
				 PAGE: - Video-Ch1
					Level  cmdID= 20053  min= 0  max= 192  step= 1  format= %0.0f  div_scale= 1 
					Min = 0  Max = 192  Step = 1 "
		::= { iqudc31CmdEntry 20053 }


	iqudc31VideoCh1NonlinearEnhancerMode OBJECT-TYPE
		SYNTAX		INTEGER {
							val-Low(0),
							val-Medium(1),
							val-High(2),
							val-Super(3),
							val-Manual(4)
							}
		MAX-ACCESS		read-write
		STATUS			current
		DESCRIPTION
				"TYPE: - RadiobuttonList
				 PAGE: - Video-Ch1
					Mode  cmdID= 20051 
					Low  value= 0  
					Medium  value= 1  
					High  value= 2  
					Super  value= 3  
					Manual  value= 4  "
		::= { iqudc31CmdEntry 20051 }


	iqudc31MenuVideoCh1FrequencyBand20052 OBJECT-TYPE
		SYNTAX		INTEGER {
							val-Low(0),
							val-Medium(1),
							val-High(2)
							}
		MAX-ACCESS		read-write
		STATUS			current
		DESCRIPTION
				"TYPE: - RadiobuttonList
				 PAGE: - Video-Ch1
					Frequency Band  cmdID= 20052 
					Low  value= 0  
					Medium  value= 1  
					High  value= 2  "
		::= { iqudc31CmdEntry 20052 }


	iqudc31MenuVideoCh1NoiseRejection OBJECT-TYPE
		SYNTAX		INTEGER
		MAX-ACCESS		read-write
		STATUS			current
		DESCRIPTION
				"TYPE: - Number
				 PAGE: - Video-Ch1
					Noise Rejection  cmdID= 20054  min= 0  max= 100  step= 1  format= %0.0f  div_scale= 1 
					Min = 0  Max = 100  Step = 1 "
		::= { iqudc31CmdEntry 20054 }


	iqudc31VideoCh1ConversionAperturePreset OBJECT-TYPE
		SYNTAX		INTEGER { noAction(0),val-Preset(1) }
		MAX-ACCESS		read-write
		STATUS			current
		DESCRIPTION
				"TYPE: - Button
				 PAGE: - Video-Ch1
					Preset  cmdID= 20162  value= 1  "
		::= { iqudc31CmdEntry 20162 }


	iqudc31ConversionApertureHorizontalSharpness30100 OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch1
					Sharpness  cmdID= 30100 
					Soft 2  value= 0  
					Soft 1  value= 1  
					Normal  value= 2  
					Sharp 1  value= 3  
					Sharp 2  value= 4  "
		::= { iqudc31CmdEntry 30100 }


	iqudc31MenuVideoCh1Detail OBJECT-TYPE
		SYNTAX		INTEGER {
							val-Low-2(0),
							val-Low-1(1),
							val-Normal(2),
							val-High-1(3),
							val-High-2(4)
							}
		MAX-ACCESS		read-write
		STATUS			current
		DESCRIPTION
				"TYPE: - RadiobuttonList
				 PAGE: - Video-Ch1
					Detail  cmdID= 30101 
					Low 2  value= 0  
					Low 1  value= 1  
					Normal  value= 2  
					High 1  value= 3  
					High 2  value= 4  "
		::= { iqudc31CmdEntry 30101 }


	iqudc31VideoCh1VerticalLevel OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch1
					Level  cmdID= 20061 
					Soft 2  value= 0  
					Soft 1  value= 1  
					Normal  value= 2  
					Sharp 1  value= 3  
					Sharp 2  value= 4  "
		::= { iqudc31CmdEntry 20061 }


	iqudc31MenuVideoCh1FrequencyBand20060 OBJECT-TYPE
		SYNTAX		INTEGER {
							val-Low(0),
							val-Medium(1),
							val-High(2)
							}
		MAX-ACCESS		read-write
		STATUS			current
		DESCRIPTION
				"TYPE: - RadiobuttonList
				 PAGE: - Video-Ch1
					Frequency Band  cmdID= 20060 
					Low  value= 0  
					Medium  value= 1  
					High  value= 2  "
		::= { iqudc31CmdEntry 20060 }


	iqudc31VideoCh1NoiseReductionEnable OBJECT-TYPE
		SYNTAX		INTEGER { disable(0), enable(1) }
		MAX-ACCESS		read-write
		STATUS			current
		DESCRIPTION
				"TYPE: - Checkbox
				 PAGE: - Video-Ch1
					Enable  cmdID= 20004 "
		::= { iqudc31CmdEntry 20004 }


	iqudc31NoiseReductionRecursiveLuma20005 OBJECT-TYPE
		SYNTAX		INTEGER
		MAX-ACCESS		read-write
		STATUS			current
		DESCRIPTION
				"TYPE: - Number
				 PAGE: - Video-Ch1
					Luma  cmdID= 20005  min= 0  max= 7  step= 1  format= %0.0f  div_scale= 1 
					Min = 0  Max = 7  Step = 1 "
		::= { iqudc31CmdEntry 20005 }


	iqudc31NoiseReductionRecursiveChroma20001 OBJECT-TYPE
		SYNTAX		INTEGER
		MAX-ACCESS		read-write
		STATUS			current
		DESCRIPTION
				"TYPE: - Number
				 PAGE: - Video-Ch1
					Chroma  cmdID= 20001  min= 0  max= 7  step= 1  format= %0.0f  div_scale= 1 
					Min = 0  Max = 7  Step = 1 "
		::= { iqudc31CmdEntry 20001 }


	iqudc31NoiseReductionRecursiveMode20002 OBJECT-TYPE
		SYNTAX		INTEGER {
							val-Auto(0),
							val-Manual(1)
							}
		MAX-ACCESS		read-write
		STATUS			current
		DESCRIPTION
				"TYPE: - RadiobuttonList
				 PAGE: - Video-Ch1
					Mode  cmdID= 20002 
					Auto  value= 0  
					Manual  value= 1  "
		::= { iqudc31CmdEntry 20002 }


	iqudc31VideoCh1NoiseReductionThreshold OBJECT-TYPE
		SYNTAX		INTEGER
		MAX-ACCESS		read-write
		STATUS			current
		DESCRIPTION
				"TYPE: - Number
				 PAGE: - Video-Ch1
					Threshold  cmdID= 20008  min= 0  max= 7  step= 1  format= %0.0f  div_scale= 1 
					Min = 0  Max = 7  Step = 1 "
		::= { iqudc31CmdEntry 20008 }


	iqudc31NoiseReductionSpatialLevel20011 OBJECT-TYPE
		SYNTAX		INTEGER
		MAX-ACCESS		read-write
		STATUS			current
		DESCRIPTION
				"TYPE: - Number
				 PAGE: - Video-Ch1
					Level  cmdID= 20011  min= 0  max= 7  step= 1  format= %0.0f  div_scale= 1 
					Min = 0  Max = 7  Step = 1 "
		::= { iqudc31CmdEntry 20011 }


	iqudc31NoiseReductionSpatialMode20010 OBJECT-TYPE
		SYNTAX		INTEGER {
							val-Auto(0),
							val-Manual(1)
							}
		MAX-ACCESS		read-write
		STATUS			current
		DESCRIPTION
				"TYPE: - RadiobuttonList
				 PAGE: - Video-Ch1
					Mode  cmdID= 20010 
					Auto  value= 0  
					Manual  value= 1  "
		::= { iqudc31CmdEntry 20010 }


	iqudc31MenuVideoCh1Threshold OBJECT-TYPE
		SYNTAX		INTEGER
		MAX-ACCESS		read-write
		STATUS			current
		DESCRIPTION
				"TYPE: - Number
				 PAGE: - Video-Ch1
					Threshold  cmdID= 20012  min= 1  max= 4  step= 1  format= %0.0f  div_scale= 1 
					Min = 1  Max = 4  Step = 1 "
		::= { iqudc31CmdEntry 20012 }


	iqudc31MenuVideoCh1SplitScreen OBJECT-TYPE
		SYNTAX		INTEGER { disable(0), enable(1) }
		MAX-ACCESS		read-write
		STATUS			current
		DESCRIPTION
				"TYPE: - Checkbox
				 PAGE: - Video-Ch1
					Split Screen  cmdID= 20013 "
		::= { iqudc31CmdEntry 20013 }


	iqudc31VideoCh2ProcAmpEnable OBJECT-TYPE
		SYNTAX		INTEGER { disable(0), enable(1) }
		MAX-ACCESS		read-write
		STATUS			current
		DESCRIPTION
				"TYPE: - Checkbox
				 PAGE: - Video-Ch2
					Enable  cmdID= 20204 "
		::= { iqudc31CmdEntry 20204 }


	iqudc31VideoCh2ProcAmpContrast OBJECT-TYPE
		SYNTAX		INTEGER
		MAX-ACCESS		read-write
		STATUS			current
		DESCRIPTION
				"TYPE: - Number
				 PAGE: - Video-Ch2
					Contrast  cmdID= 20200  min= -60  max= 60  step= 2  format= %0.1fdB  div_scale= 10 
					Min = -6.0dB  Max = 6.0dB  Step = 0.2dB "
		::= { iqudc31CmdEntry 20200 }


	iqudc31VideoCh2ProcAmpSaturation OBJECT-TYPE
		SYNTAX		INTEGER
		MAX-ACCESS		read-write
		STATUS			current
		DESCRIPTION
				"TYPE: - Number
				 PAGE: - Video-Ch2
					Saturation  cmdID= 20201  min= -60  max= 60  step= 2  format= %0.1fdB  div_scale= 10 
					Min = -6.0dB  Max = 6.0dB  Step = 0.2dB "
		::= { iqudc31CmdEntry 20201 }


	iqudc31VideoCh2ProcAmpBlackLevel OBJECT-TYPE
		SYNTAX		INTEGER
		MAX-ACCESS		read-write
		STATUS			current
		DESCRIPTION
				"TYPE: - Number
				 PAGE: - Video-Ch2
					Black Level  cmdID= 20202  min= -1000  max= 1000  step= 8  format= %0.1fmV  div_scale= 10 
					Min = -100.0mV  Max = 100.0mV  Step = 0.8mV "
		::= { iqudc31CmdEntry 20202 }


	iqudc31VideoCh2ProcAmpGamma OBJECT-TYPE
		SYNTAX		INTEGER
		MAX-ACCESS		read-write
		STATUS			current
		DESCRIPTION
				"TYPE: - Number
				 PAGE: - Video-Ch2
					Gamma  cmdID= 20203  min= 4  max= 17  step= 1  format= %0.1f  div_scale= 10 
					Min = 0.4  Max = 1.7  Step = 0.1 "
		::= { iqudc31CmdEntry 20203 }


	iqudc31VideoCh2ProcAmpYCOffset OBJECT-TYPE
		SYNTAX		INTEGER
		MAX-ACCESS		read-write
		STATUS			current
		DESCRIPTION
				"TYPE: - Number
				 PAGE: - Video-Ch2
					YC Offset  cmdID= 20214  min= -20  max= 20  step= 2  format= %0.0f  div_scale= 1 
					Min = -20  Max = 20  Step = 2 "
		::= { iqudc31CmdEntry 20214 }


	iqudc31VideoCh2NonlinearEnhancerEnable OBJECT-TYPE
		SYNTAX		INTEGER { disable(0), enable(1) }
		MAX-ACCESS		read-write
		STATUS			current
		DESCRIPTION
				"TYPE: - Checkbox
				 PAGE: - Video-Ch2
					Enable  cmdID= 20150 "
		::= { iqudc31CmdEntry 20150 }


	iqudc31VideoCh2NonlinearEnhancerLevel OBJECT-TYPE
		SYNTAX		INTEGER
		MAX-ACCESS		read-write
		STATUS			current
		DESCRIPTION
				"TYPE: - Number
				 PAGE: - Video-Ch2
					Level  cmdID= 20153  min= 0  max= 192  step= 1  format= %0.0f  div_scale= 1 
					Min = 0  Max = 192  Step = 1 "
		::= { iqudc31CmdEntry 20153 }


	iqudc31VideoCh2NonlinearEnhancerMode OBJECT-TYPE
		SYNTAX		INTEGER {
							val-Low(0),
							val-Medium(1),
							val-High(2),
							val-Super(3),
							val-Manual(4)
							}
		MAX-ACCESS		read-write
		STATUS			current
		DESCRIPTION
				"TYPE: - RadiobuttonList
				 PAGE: - Video-Ch2
					Mode  cmdID= 20151 
					Low  value= 0  
					Medium  value= 1  
					High  value= 2  
					Super  value= 3  
					Manual  value= 4  "
		::= { iqudc31CmdEntry 20151 }


	iqudc31MenuVideoCh2FrequencyBand20152 OBJECT-TYPE
		SYNTAX		INTEGER {
							val-Low(0),
							val-Medium(1),
							val-High(2)
							}
		MAX-ACCESS		read-write
		STATUS			current
		DESCRIPTION
				"TYPE: - RadiobuttonList
				 PAGE: - Video-Ch2
					Frequency Band  cmdID= 20152 
					Low  value= 0  
					Medium  value= 1  
					High  value= 2  "
		::= { iqudc31CmdEntry 20152 }


	iqudc31MenuVideoCh2NoiseRejection OBJECT-TYPE
		SYNTAX		INTEGER
		MAX-ACCESS		read-write
		STATUS			current
		DESCRIPTION
				"TYPE: - Number
				 PAGE: - Video-Ch2
					Noise Rejection  cmdID= 20154  min= 0  max= 100  step= 1  format= %0.0f  div_scale= 1 
					Min = 0  Max = 100  Step = 1 "
		::= { iqudc31CmdEntry 20154 }


	iqudc31VideoCh2ConversionAperturePreset OBJECT-TYPE
		SYNTAX		INTEGER { noAction(0),val-Preset(1) }
		MAX-ACCESS		read-write
		STATUS			current
		DESCRIPTION
				"TYPE: - Button
				 PAGE: - Video-Ch2
					Preset  cmdID= 20262  value= 1  "
		::= { iqudc31CmdEntry 20262 }


	iqudc31ConversionApertureHorizontalSharpness30200 OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch2
					Sharpness  cmdID= 30200 
					Soft 2  value= 0  
					Soft 1  value= 1  
					Normal  value= 2  
					Sharp 1  value= 3  
					Sharp 2  value= 4  "
		::= { iqudc31CmdEntry 30200 }


	iqudc31MenuVideoCh2Detail OBJECT-TYPE
		SYNTAX		INTEGER {
							val-Low-2(0),
							val-Low-1(1),
							val-Normal(2),
							val-High-1(3),
							val-High-2(4)
							}
		MAX-ACCESS		read-write
		STATUS			current
		DESCRIPTION
				"TYPE: - RadiobuttonList
				 PAGE: - Video-Ch2
					Detail  cmdID= 30201 
					Low 2  value= 0  
					Low 1  value= 1  
					Normal  value= 2  
					High 1  value= 3  
					High 2  value= 4  "
		::= { iqudc31CmdEntry 30201 }


	iqudc31VideoCh2VerticalLevel OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch2
					Level  cmdID= 20161 
					Soft 2  value= 0  
					Soft 1  value= 1  
					Normal  value= 2  
					Sharp 1  value= 3  
					Sharp 2  value= 4  "
		::= { iqudc31CmdEntry 20161 }


	iqudc31MenuVideoCh2FrequencyBand20160 OBJECT-TYPE
		SYNTAX		INTEGER {
							val-Low(0),
							val-Medium(1),
							val-High(2)
							}
		MAX-ACCESS		read-write
		STATUS			current
		DESCRIPTION
				"TYPE: - RadiobuttonList
				 PAGE: - Video-Ch2
					Frequency Band  cmdID= 20160 
					Low  value= 0  
					Medium  value= 1  
					High  value= 2  "
		::= { iqudc31CmdEntry 20160 }


	iqudc31VideoCh2NoiseReductionEnable OBJECT-TYPE
		SYNTAX		INTEGER { disable(0), enable(1) }
		MAX-ACCESS		read-write
		STATUS			current
		DESCRIPTION
				"TYPE: - Checkbox
				 PAGE: - Video-Ch2
					Enable  cmdID= 20104 "
		::= { iqudc31CmdEntry 20104 }


	iqudc31NoiseReductionRecursiveLuma20105 OBJECT-TYPE
		SYNTAX		INTEGER
		MAX-ACCESS		read-write
		STATUS			current
		DESCRIPTION
				"TYPE: - Number
				 PAGE: - Video-Ch2
					Luma  cmdID= 20105  min= 0  max= 7  step= 1  format= %0.0f  div_scale= 1 
					Min = 0  Max = 7  Step = 1 "
		::= { iqudc31CmdEntry 20105 }


	iqudc31NoiseReductionRecursiveChroma20101 OBJECT-TYPE
		SYNTAX		INTEGER
		MAX-ACCESS		read-write
		STATUS			current
		DESCRIPTION
				"TYPE: - Number
				 PAGE: - Video-Ch2
					Chroma  cmdID= 20101  min= 0  max= 7  step= 1  format= %0.0f  div_scale= 1 
					Min = 0  Max = 7  Step = 1 "
		::= { iqudc31CmdEntry 20101 }


	iqudc31NoiseReductionRecursiveMode20107 OBJECT-TYPE
		SYNTAX		INTEGER {
							val-Auto(0),
							val-Manual(1)
							}
		MAX-ACCESS		read-write
		STATUS			current
		DESCRIPTION
				"TYPE: - RadiobuttonList
				 PAGE: - Video-Ch2
					Mode  cmdID= 20107 
					Auto  value= 0  
					Manual  value= 1  "
		::= { iqudc31CmdEntry 20107 }


	iqudc31VideoCh2NoiseReductionThreshold OBJECT-TYPE
		SYNTAX		INTEGER
		MAX-ACCESS		read-write
		STATUS			current
		DESCRIPTION
				"TYPE: - Number
				 PAGE: - Video-Ch2
					Threshold  cmdID= 20108  min= 0  max= 7  step= 1  format= %0.0f  div_scale= 1 
					Min = 0  Max = 7  Step = 1 "
		::= { iqudc31CmdEntry 20108 }


	iqudc31NoiseReductionSpatialLevel20111 OBJECT-TYPE
		SYNTAX		INTEGER
		MAX-ACCESS		read-write
		STATUS			current
		DESCRIPTION
				"TYPE: - Number
				 PAGE: - Video-Ch2
					Level  cmdID= 20111  min= 0  max= 7  step= 1  format= %0.0f  div_scale= 1 
					Min = 0  Max = 7  Step = 1 "
		::= { iqudc31CmdEntry 20111 }


	iqudc31NoiseReductionSpatialMode20110 OBJECT-TYPE
		SYNTAX		INTEGER {
							val-Auto(0),
							val-Manual(1)
							}
		MAX-ACCESS		read-write
		STATUS			current
		DESCRIPTION
				"TYPE: - RadiobuttonList
				 PAGE: - Video-Ch2
					Mode  cmdID= 20110 
					Auto  value= 0  
					Manual  value= 1  "
		::= { iqudc31CmdEntry 20110 }


	iqudc31MenuVideoCh2Threshold OBJECT-TYPE
		SYNTAX		INTEGER
		MAX-ACCESS		read-write
		STATUS			current
		DESCRIPTION
				"TYPE: - Number
				 PAGE: - Video-Ch2
					Threshold  cmdID= 20112  min= 1  max= 4  step= 1  format= %0.0f  div_scale= 1 
					Min = 1  Max = 4  Step = 1 "
		::= { iqudc31CmdEntry 20112 }


	iqudc31MenuVideoCh2SplitScreen OBJECT-TYPE
		SYNTAX		INTEGER { disable(0), enable(1) }
		MAX-ACCESS		read-write
		STATUS			current
		DESCRIPTION
				"TYPE: - Checkbox
				 PAGE: - Video-Ch2
					Split Screen  cmdID= 20113 "
		::= { iqudc31CmdEntry 20113 }


	iqudc31MenuVideoCh2NewDisplay OBJECT-TYPE
		SYNTAX		RollCallString
		MAX-ACCESS		read-only
		STATUS			current
		DESCRIPTION
				"TYPE: - Display
				 PAGE: - Video-Ch2
					New Display  cmdID= 44447  format=   "
		::= { iqudc31CmdEntry 44447 }


	iqudc31ConvertCh1UpConversionCleanEdgeUpconver OBJECT-TYPE
		SYNTAX		INTEGER { disable(0), enable(1) }
		MAX-ACCESS		read-write
		STATUS			current
		DESCRIPTION
				"TYPE: - Checkbox
				 PAGE: - Convert-Ch1
					Clean Edge Upconver  cmdID= 30072 "
		::= { iqudc31CmdEntry 30072 }


	iqudc31ConvertCh1MotionProcessing OBJECT-TYPE
		SYNTAX		INTEGER { disable(0), enable(1) }
		MAX-ACCESS		read-write
		STATUS			current
		DESCRIPTION
				"TYPE: - Checkbox
				 PAGE: - Convert-Ch1
					Motion Process  cmdID= 30005 "
		::= { iqudc31CmdEntry 30005 }


	iqudc31ConvertCh1MotionProcessingEnhancedMotion OBJECT-TYPE
		SYNTAX		INTEGER { disable(0), enable(1) }
		MAX-ACCESS		read-write
		STATUS			current
		DESCRIPTION
				"TYPE: - Checkbox
				 PAGE: - Convert-Ch1
					Enhanced Motion  cmdID= 30002 "
		::= { iqudc31CmdEntry 30002 }


	iqudc31ConvertCh1MotionProcessingStillProcess OBJECT-TYPE
		SYNTAX		INTEGER { disable(0), enable(1) }
		MAX-ACCESS		read-write
		STATUS			current
		DESCRIPTION
				"TYPE: - Checkbox
				 PAGE: - Convert-Ch1
					Still Process  cmdID= 30003 "
		::= { iqudc31CmdEntry 30003 }


	iqudc31ConvertCh1MotionProcessingEnhancedStill OBJECT-TYPE
		SYNTAX		INTEGER { disable(0), enable(1) }
		MAX-ACCESS		read-write
		STATUS			current
		DESCRIPTION
				"TYPE: - Checkbox
				 PAGE: - Convert-Ch1
					Enhanced Still  cmdID= 30004 "
		::= { iqudc31CmdEntry 30004 }


	iqudc31ConvertCh1MotionProcessingInputispsf OBJECT-TYPE
		SYNTAX		INTEGER { disable(0), enable(1) }
		MAX-ACCESS		read-write
		STATUS			current
		DESCRIPTION
				"TYPE: - Checkbox
				 PAGE: - Convert-Ch1
					Input is psf  cmdID= 30071 "
		::= { iqudc31CmdEntry 30071 }


	iqudc31ConvertCh1MotionProcessingEnhancedFilm OBJECT-TYPE
		SYNTAX		INTEGER { disable(0), enable(1) }
		MAX-ACCESS		read-write
		STATUS			current
		DESCRIPTION
				"TYPE: - Checkbox
				 PAGE: - Convert-Ch1
					Enhanced Film  cmdID= 30070 "
		::= { iqudc31CmdEntry 30070 }


	iqudc31ConvertCh1InputCadenceFilmCadence OBJECT-TYPE
		SYNTAX		INTEGER { disable(0), enable(1) }
		MAX-ACCESS		read-write
		STATUS			current
		DESCRIPTION
				"TYPE: - Checkbox
				 PAGE: - Convert-Ch1
					Film Cadence  cmdID= 30050 "
		::= { iqudc31CmdEntry 30050 }


	iqudc31ConvertCh1InputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch1
					59 Cadence  cmdID= 30051 
					2:3  value= 0  
					2:2 (psf)  value= 1  "
		::= { iqudc31CmdEntry 30051 }


	iqudc31MenuConvertCh123Source30052 OBJECT-TYPE
		SYNTAX		INTEGER {
							val-Automatic(0),
							val-Input-Timecode(1)
							}
		MAX-ACCESS		read-write
		STATUS			current
		DESCRIPTION
				"TYPE: - RadiobuttonList
				 PAGE: - Convert-Ch1
					2:3 Source  cmdID= 30052 
					Automatic  value= 0  
					Input Timecode  value= 1  "
		::= { iqudc31CmdEntry 30052 }


	iqudc31MenuConvertCh123StartHour30053 OBJECT-TYPE
		SYNTAX		INTEGER
		MAX-ACCESS		read-write
		STATUS			current
		DESCRIPTION
				"TYPE: - Number
				 PAGE: - Convert-Ch1
					2:3 Start Hour  cmdID= 30053  min= 0  max= 23  step= 1  format= %0.0f  div_scale= 1 
					Min = 0  Max = 23  Step = 1 "
		::= { iqudc31CmdEntry 30053 }


	iqudc31ConvertCh1OutputCadenceFilmCadence OBJECT-TYPE
		SYNTAX		INTEGER { disable(0), enable(1) }
		MAX-ACCESS		read-write
		STATUS			current
		DESCRIPTION
				"TYPE: - Checkbox
				 PAGE: - Convert-Ch1
					Film Cadence  cmdID= 30060 "
		::= { iqudc31CmdEntry 30060 }


	iqudc31ConvertCh1OutputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch1
					59 Cadence  cmdID= 30061 
					2:3  value= 0  
					2:2 (psf)  value= 1  "
		::= { iqudc31CmdEntry 30061 }


	iqudc31MenuConvertCh123Source30062 OBJECT-TYPE
		SYNTAX		INTEGER {
							val-Free-Run(0),
							val-Output-Timecode(1)
							}
		MAX-ACCESS		read-write
		STATUS			current
		DESCRIPTION
				"TYPE: - RadiobuttonList
				 PAGE: - Convert-Ch1
					2:3 Source  cmdID= 30062 
					Free Run  value= 0  
					Output Timecode  value= 1  "
		::= { iqudc31CmdEntry 30062 }


	iqudc31MenuConvertCh123StartHour30063 OBJECT-TYPE
		SYNTAX		INTEGER
		MAX-ACCESS		read-write
		STATUS			current
		DESCRIPTION
				"TYPE: - Number
				 PAGE: - Convert-Ch1
					2:3 Start Hour  cmdID= 30063  min= 0  max= 23  step= 1  format= %0.0f  div_scale= 1 
					Min = 0  Max = 23  Step = 1 "
		::= { iqudc31CmdEntry 30063 }


	iqudc31ConvertCh2UpConversionCleanEdgeUpconver OBJECT-TYPE
		SYNTAX		INTEGER { disable(0), enable(1) }
		MAX-ACCESS		read-write
		STATUS			current
		DESCRIPTION
				"TYPE: - Checkbox
				 PAGE: - Convert-Ch2
					Clean Edge Upconver  cmdID= 30172 "
		::= { iqudc31CmdEntry 30172 }


	iqudc31ConvertCh2MotionProcessing OBJECT-TYPE
		SYNTAX		INTEGER { disable(0), enable(1) }
		MAX-ACCESS		read-write
		STATUS			current
		DESCRIPTION
				"TYPE: - Checkbox
				 PAGE: - Convert-Ch2
					Motion Process  cmdID= 30105 "
		::= { iqudc31CmdEntry 30105 }


	iqudc31ConvertCh2MotionProcessingEnhancedMotion OBJECT-TYPE
		SYNTAX		INTEGER { disable(0), enable(1) }
		MAX-ACCESS		read-write
		STATUS			current
		DESCRIPTION
				"TYPE: - Checkbox
				 PAGE: - Convert-Ch2
					Enhanced Motion  cmdID= 30102 "
		::= { iqudc31CmdEntry 30102 }


	iqudc31ConvertCh2MotionProcessingStillProcess OBJECT-TYPE
		SYNTAX		INTEGER { disable(0), enable(1) }
		MAX-ACCESS		read-write
		STATUS			current
		DESCRIPTION
				"TYPE: - Checkbox
				 PAGE: - Convert-Ch2
					Still Process  cmdID= 30103 "
		::= { iqudc31CmdEntry 30103 }


	iqudc31ConvertCh2MotionProcessingEnhancedStill OBJECT-TYPE
		SYNTAX		INTEGER { disable(0), enable(1) }
		MAX-ACCESS		read-write
		STATUS			current
		DESCRIPTION
				"TYPE: - Checkbox
				 PAGE: - Convert-Ch2
					Enhanced Still  cmdID= 30104 "
		::= { iqudc31CmdEntry 30104 }


	iqudc31ConvertCh2MotionProcessingInputispsf OBJECT-TYPE
		SYNTAX		INTEGER { disable(0), enable(1) }
		MAX-ACCESS		read-write
		STATUS			current
		DESCRIPTION
				"TYPE: - Checkbox
				 PAGE: - Convert-Ch2
					Input is psf  cmdID= 30171 "
		::= { iqudc31CmdEntry 30171 }


	iqudc31ConvertCh2MotionProcessingEnhancedFilm OBJECT-TYPE
		SYNTAX		INTEGER { disable(0), enable(1) }
		MAX-ACCESS		read-write
		STATUS			current
		DESCRIPTION
				"TYPE: - Checkbox
				 PAGE: - Convert-Ch2
					Enhanced Film  cmdID= 30170 "
		::= { iqudc31CmdEntry 30170 }


	iqudc31ConvertCh2InputCadenceFilmCadence OBJECT-TYPE
		SYNTAX		INTEGER { disable(0), enable(1) }
		MAX-ACCESS		read-write
		STATUS			current
		DESCRIPTION
				"TYPE: - Checkbox
				 PAGE: - Convert-Ch2
					Film Cadence  cmdID= 30150 "
		::= { iqudc31CmdEntry 30150 }


	iqudc31ConvertCh2InputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch2
					59 Cadence  cmdID= 30151 
					2:3  value= 0  
					2:2 (psf)  value= 1  "
		::= { iqudc31CmdEntry 30151 }


	iqudc31MenuConvertCh223Source30152 OBJECT-TYPE
		SYNTAX		INTEGER {
							val-Automatic(0),
							val-Input-Timecode(1)
							}
		MAX-ACCESS		read-write
		STATUS			current
		DESCRIPTION
				"TYPE: - RadiobuttonList
				 PAGE: - Convert-Ch2
					2:3 Source  cmdID= 30152 
					Automatic  value= 0  
					Input Timecode  value= 1  "
		::= { iqudc31CmdEntry 30152 }


	iqudc31MenuConvertCh223StartHour30153 OBJECT-TYPE
		SYNTAX		INTEGER
		MAX-ACCESS		read-write
		STATUS			current
		DESCRIPTION
				"TYPE: - Number
				 PAGE: - Convert-Ch2
					2:3 Start Hour  cmdID= 30153  min= 0  max= 23  step= 1  format= %0.0f  div_scale= 1 
					Min = 0  Max = 23  Step = 1 "
		::= { iqudc31CmdEntry 30153 }


	iqudc31ConvertCh2OutputCadenceFilmCadence OBJECT-TYPE
		SYNTAX		INTEGER { disable(0), enable(1) }
		MAX-ACCESS		read-write
		STATUS			current
		DESCRIPTION
				"TYPE: - Checkbox
				 PAGE: - Convert-Ch2
					Film Cadence  cmdID= 30160 "
		::= { iqudc31CmdEntry 30160 }


	iqudc31ConvertCh2OutputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch2
					59 Cadence  cmdID= 30161 
					2:3  value= 0  
					2:2 (psf)  value= 1  "
		::= { iqudc31CmdEntry 30161 }


	iqudc31MenuConvertCh223Source30162 OBJECT-TYPE
		SYNTAX		INTEGER {
							val-Free-Run(0),
							val-Output-Timecode(1)
							}
		MAX-ACCESS		read-write
		STATUS			current
		DESCRIPTION
				"TYPE: - RadiobuttonList
				 PAGE: - Convert-Ch2
					2:3 Source  cmdID= 30162 
					Free Run  value= 0  
					Output Timecode  value= 1  "
		::= { iqudc31CmdEntry 30162 }


	iqudc31MenuConvertCh223StartHour30163 OBJECT-TYPE
		SYNTAX		INTEGER
		MAX-ACCESS		read-write
		STATUS			current
		DESCRIPTION
				"TYPE: - Number
				 PAGE: - Convert-Ch2
					2:3 Start Hour  cmdID= 30163  min= 0  max= 23  step= 1  format= %0.0f  div_scale= 1 
					Min = 0  Max = 23  Step = 1 "
		::= { iqudc31CmdEntry 30163 }


	iqudc31MenuConvertCh2NewDisplay OBJECT-TYPE
		SYNTAX		RollCallString
		MAX-ACCESS		read-only
		STATUS			current
		DESCRIPTION
				"TYPE: - Display
				 PAGE: - Convert-Ch2
					New Display  cmdID= 44448  format=   "
		::= { iqudc31CmdEntry 44448 }


	iqudc31MenuARCSidebarKeyerSyncMode40007 OBJECT-TYPE
		SYNTAX		INTEGER { disable(0), enable(1) }
		MAX-ACCESS		read-write
		STATUS			current
		DESCRIPTION
				"TYPE: - Checkbox
				 PAGE: - ARC & Sidebar Keyer
					Sync Mode  cmdID= 40007 "
		::= { iqudc31CmdEntry 40007 }


	iqudc31MenuARCSidebarKeyerAspectSignallingC40136 OBJECT-TYPE
		SYNTAX		INTEGER { disable(0), enable(1) }
		MAX-ACCESS		read-write
		STATUS			current
		DESCRIPTION
				"TYPE: - Checkbox
				 PAGE: - ARC & Sidebar Keyer
					Aspect Signalling C  cmdID= 40136 "
		::= { iqudc31CmdEntry 40136 }


	iqudc31MenuARCSidebarKeyerSignallingDetected64020 OBJECT-TYPE
		SYNTAX		RollCallString
		MAX-ACCESS		read-only
		STATUS			current
		DESCRIPTION
				"TYPE: - Display
				 PAGE: - ARC & Sidebar Keyer
					Signalling Detected  cmdID= 64020  format=   "
		::= { iqudc31CmdEntry 64020 }


	iqudc31ARCSidebarKeyerSidebarKeyingOuMode40017 OBJECT-TYPE
		SYNTAX		INTEGER {
							val-Off(0),
							val-Output-Crop(1),
							val-Sidebar-Key(2)
							}
		MAX-ACCESS		read-write
		STATUS			current
		DESCRIPTION
				"TYPE: - RadiobuttonList
				 PAGE: - ARC & Sidebar Keyer
					Mode  cmdID= 40017 
					Off  value= 0  
					Output Crop  value= 1  
					Sidebar Key  value= 2  "
		::= { iqudc31CmdEntry 40017 }


	iqudc31MenuARCSidebarKeyerSidebarKeySource40018 OBJECT-TYPE
		SYNTAX		INTEGER {
							val-SDI-1(0),
							val-SDI-2(1),
							val-CVBS(2),
							val-SFP-1(3),
							val-SFP-2(4),
							val-Ch-2-Output(20)
							}
		MAX-ACCESS		read-write
		STATUS			current
		DESCRIPTION
				"TYPE: - RadiobuttonList
				 PAGE: - ARC & Sidebar Keyer
					Sidebar Key Source  cmdID= 40018 
					SDI 1  value= 0  
					SDI 2  value= 1  
					CVBS  value= 2  
					SFP 1  value= 3  
					SFP 2  value= 4  
					Ch 2 Output  value= 20  "
		::= { iqudc31CmdEntry 40018 }


	iqudc31ARCSidebarKeyerOutputCropPositioTop40013 OBJECT-TYPE
		SYNTAX		INTEGER
		MAX-ACCESS		read-write
		STATUS			current
		DESCRIPTION
				"TYPE: - Number
				 PAGE: - ARC & Sidebar Keyer
					Top  cmdID= 40013  min= 0  max= 99  step= 1  format= %0.0f%%  div_scale= 1 
					Min = 0%  Max = 99%  Step = 1% "
		::= { iqudc31CmdEntry 40013 }


	iqudc31ARCSidebarKeyerOutputCropPositioBottom40014 OBJECT-TYPE
		SYNTAX		INTEGER
		MAX-ACCESS		read-write
		STATUS			current
		DESCRIPTION
				"TYPE: - Number
				 PAGE: - ARC & Sidebar Keyer
					Bottom  cmdID= 40014  min= 0  max= 99  step= 1  format= %0.0f%%  div_scale= 1 
					Min = 0%  Max = 99%  Step = 1% "
		::= { iqudc31CmdEntry 40014 }


	iqudc31ARCSidebarKeyerOutputCropPositioLeft40015 OBJECT-TYPE
		SYNTAX		INTEGER
		MAX-ACCESS		read-write
		STATUS			current
		DESCRIPTION
				"TYPE: - Number
				 PAGE: - ARC & Sidebar Keyer
					Left  cmdID= 40015  min= 0  max= 99  step= 1  format= %0.0f%%  div_scale= 1 
					Min = 0%  Max = 99%  Step = 1% "
		::= { iqudc31CmdEntry 40015 }


	iqudc31ARCSidebarKeyerOutputCropPositioRight40016 OBJECT-TYPE
		SYNTAX		INTEGER
		MAX-ACCESS		read-write
		STATUS			current
		DESCRIPTION
				"TYPE: - Number
				 PAGE: - ARC & Sidebar Keyer
					Right  cmdID= 40016  min= 0  max= 99  step= 1  format= %0.0f%%  div_scale= 1 
					Min = 0%  Max = 99%  Step = 1% "
		::= { iqudc31CmdEntry 40016 }


	iqudc31ARCSidebarKeyerPostScalingControPostScalingEnable40003 OBJECT-TYPE
		SYNTAX		INTEGER { disable(0), enable(1) }
		MAX-ACCESS		read-write
		STATUS			current
		DESCRIPTION
				"TYPE: - Checkbox
				 PAGE: - ARC & Sidebar Keyer
					Post Scaling Enable  cmdID= 40003 "
		::= { iqudc31CmdEntry 40003 }


	iqudc31ARCSidebarKeyerPostScalingControSize40008 OBJECT-TYPE
		SYNTAX		INTEGER
		MAX-ACCESS		read-write
		STATUS			current
		DESCRIPTION
				"TYPE: - Number
				 PAGE: - ARC & Sidebar Keyer
					Size  cmdID= 40008  min= 80  max= 120  step= 1  format= %0.0f%%  div_scale= 1 
					Min = 80%  Max = 120%  Step = 1% "
		::= { iqudc31CmdEntry 40008 }


	iqudc31ARCSidebarKeyerPostScalingControAspect40009 OBJECT-TYPE
		SYNTAX		INTEGER
		MAX-ACCESS		read-write
		STATUS			current
		DESCRIPTION
				"TYPE: - Number
				 PAGE: - ARC & Sidebar Keyer
					Aspect  cmdID= 40009  min= 70  max= 150  step= 1  format= %0.0f%%  div_scale= 1 
					Min = 70%  Max = 150%  Step = 1% "
		::= { iqudc31CmdEntry 40009 }


	iqudc31ARCSidebarKeyerPostScalingControPan40006 OBJECT-TYPE
		SYNTAX		INTEGER
		MAX-ACCESS		read-write
		STATUS			current
		DESCRIPTION
				"TYPE: - Number
				 PAGE: - ARC & Sidebar Keyer
					Pan  cmdID= 40006  min= -50  max= 50  step= 1  format= %0.0f%  div_scale= 1 
					Min = -50 Max = 50 Step = 1"
		::= { iqudc31CmdEntry 40006 }


	iqudc31ARCSidebarKeyerPostScalingControTilt40002 OBJECT-TYPE
		SYNTAX		INTEGER
		MAX-ACCESS		read-write
		STATUS			current
		DESCRIPTION
				"TYPE: - Number
				 PAGE: - ARC & Sidebar Keyer
					Tilt  cmdID= 40002  min= -50  max= 50  step= 1  format= %0.0f%  div_scale= 1 
					Min = -50 Max = 50 Step = 1"
		::= { iqudc31CmdEntry 40002 }


	iqudc31ARCSidebarKeyerStandardPresetsWhSDInputis70240030 OBJECT-TYPE
		SYNTAX		INTEGER { disable(0), enable(1) }
		MAX-ACCESS		read-write
		STATUS			current
		DESCRIPTION
				"TYPE: - Checkbox
				 PAGE: - ARC & Sidebar Keyer
					SD Input is 702  cmdID= 40030 "
		::= { iqudc31CmdEntry 40030 }


	iqudc31ARCSidebarKeyerStandardPresetsWhSDOutputis70240037 OBJECT-TYPE
		SYNTAX		INTEGER { disable(0), enable(1) }
		MAX-ACCESS		read-write
		STATUS			current
		DESCRIPTION
				"TYPE: - Checkbox
				 PAGE: - ARC & Sidebar Keyer
					SD Output is 702  cmdID= 40037 "
		::= { iqudc31CmdEntry 40037 }


	iqudc31StandardPresetsWhSDCrossConversionSelectStdPreset40031 OBJECT-TYPE
		SYNTAX		INTEGER {
							val-None(0),
							val-16-9-LB-4-3-H-Cr(1),
							val-16-9-LB-16-9-Ana(2),
							val-16-9-LB-14-9-LB(3),
							val-16-9-Ana-4-3-H-Cr(4),
							val-16-9-Ana-16-9-LB(5),
							val-16-9-Ana-14-9-LB(6)
							}
		MAX-ACCESS		read-write
		STATUS			current
		DESCRIPTION
				"TYPE: - RadiobuttonList
				 PAGE: - ARC & Sidebar Keyer
					Select Std Preset  cmdID= 40031 
					None  value= 0  
					16:9 LB > 4:3 H-Cr  value= 1  
					16:9 LB > 16:9 Ana  value= 2  
					16:9 LB > 14:9 LB  value= 3  
					16:9 Ana > 4:3 H-Cr  value= 4  
					16:9 Ana > 16:9 LB  value= 5  
					16:9 Ana > 14:9 LB  value= 6  "
		::= { iqudc31CmdEntry 40031 }


	iqudc31ARCSidebarKeyerUpConversionSelectStdPreset40033 OBJECT-TYPE
		SYNTAX		INTEGER {
							val-4-3-16-9-V-Cr(0),
							val-4-3-4-3-PB(1),
							val-16-9-LB-16-9(2),
							val-16-9-Ana-16-9(3),
							val-14-9-LB-14-9-PB(4)
							}
		MAX-ACCESS		read-write
		STATUS			current
		DESCRIPTION
				"TYPE: - RadiobuttonList
				 PAGE: - ARC & Sidebar Keyer
					Select Std Preset  cmdID= 40033 
					4:3 > 16:9 V-Cr  value= 0  
					4:3 > 4:3 PB  value= 1  
					16:9 LB > 16:9  value= 2  
					16:9 Ana > 16:9  value= 3  
					14:9 LB > 14:9 PB  value= 4  "
		::= { iqudc31CmdEntry 40033 }


	iqudc31ARCSidebarKeyerDownConversionSelectStdPreset40035 OBJECT-TYPE
		SYNTAX		INTEGER {
							val-16-9-4-3-H-Cr(0),
							val-16-9-16-9-LB(1),
							val-16-9-16-9-Ana(2),
							val-4-3-PB-4-3(3),
							val-14-9-PB-14-9-LB(4)
							}
		MAX-ACCESS		read-write
		STATUS			current
		DESCRIPTION
				"TYPE: - RadiobuttonList
				 PAGE: - ARC & Sidebar Keyer
					Select Std Preset  cmdID= 40035 
					16:9 > 4:3 H-Cr  value= 0  
					16:9 > 16:9 LB  value= 1  
					16:9 > 16:9 Ana  value= 2  
					4:3 PB > 4:3  value= 3  
					14:9 PB > 14:9 LB  value= 4  "
		::= { iqudc31CmdEntry 40035 }


	iqudc31ScalingControlSDInputFormatifUseManualifUnkno40135 OBJECT-TYPE
		SYNTAX		INTEGER { disable(0), enable(1) }
		MAX-ACCESS		read-write
		STATUS			current
		DESCRIPTION
				"TYPE: - Checkbox
				 PAGE: - ARC & Sidebar Keyer
					Use Manual if Unkno  cmdID= 40135 "
		::= { iqudc31CmdEntry 40135 }


	iqudc31ScalingControlSDInputFormatif40010 OBJECT-TYPE
		SYNTAX		INTEGER {
							val-Normal(0),
							val-Anamorphic(1),
							val-Letterbox(2)
							}
		MAX-ACCESS		read-write
		STATUS			current
		DESCRIPTION
				"TYPE: - RadiobuttonList
				 PAGE: - ARC & Sidebar Keyer
					SD Input Format  cmdID= 40010 
					Normal  value= 0  
					Anamorphic  value= 1  
					Letterbox  value= 2  "
		::= { iqudc31CmdEntry 40010 }


	iqudc31ARCSidebarKeyerAspectSignallingCSDOutputFormat40011 OBJECT-TYPE
		SYNTAX		INTEGER {
							val-Normal(0),
							val-Anamorphic(1)
							}
		MAX-ACCESS		read-write
		STATUS			current
		DESCRIPTION
				"TYPE: - RadiobuttonList
				 PAGE: - ARC & Sidebar Keyer
					SD Output Format  cmdID= 40011 
					Normal  value= 0  
					Anamorphic  value= 1  "
		::= { iqudc31CmdEntry 40011 }


	iqudc31ARCSidebarKeyerAspectSignallingCConversionScaling40012 OBJECT-TYPE
		SYNTAX		INTEGER {
							val-Fit-to-Height(0),
							val-Fit-to-Width(1),
							val-14-9(2)
							}
		MAX-ACCESS		read-write
		STATUS			current
		DESCRIPTION
				"TYPE: - RadiobuttonList
				 PAGE: - ARC & Sidebar Keyer
					Conversion Scaling  cmdID= 40012 
					Fit to Height  value= 0  
					Fit to Width  value= 1  
					14:9  value= 2  "
		::= { iqudc31CmdEntry 40012 }


	iqudc31AspectSignallingCSignallingConfigSource40100 OBJECT-TYPE
		SYNTAX		INTEGER {
							val-SMPTE-2016(0),
							val-L23-ETSI(1),
							val-L23-AFD(2),
							val-VI-SMPTE(3),
							val-VI-AFD(4)
							}
		MAX-ACCESS		read-write
		STATUS			current
		DESCRIPTION
				"TYPE: - RadiobuttonList
				 PAGE: - ARC & Sidebar Keyer
					Source  cmdID= 40100 
					SMPTE 2016  value= 0  
					L23 ETSI  value= 1  
					L23 AFD  value= 2  
					VI SMPTE  value= 3  
					VI AFD  value= 4  "
		::= { iqudc31CmdEntry 40100 }


	iqudc31SignallingConfigSMPTE2016Mode40130 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40130 
					Auto  value= 0  
					Pass  value= 1  
					Force  value= 2  
					Delete  value= 3  "
		::= { iqudc31CmdEntry 40130 }


	iqudc31AspectSignallingCSignallingConfigOutputLine625 OBJECT-TYPE
		SYNTAX		INTEGER
		MAX-ACCESS		read-write
		STATUS			current
		DESCRIPTION
				"TYPE: - Number
				 PAGE: - ARC & Sidebar Keyer
					Output Line 625  cmdID= 40139  min= 7  max= 22  step= 1  format= %0.0f  div_scale= 1 
					Min = 7  Max = 22  Step = 1 "
		::= { iqudc31CmdEntry 40139 }


	iqudc31AspectSignallingCSignallingConfigOutputLine525 OBJECT-TYPE
		SYNTAX		INTEGER
		MAX-ACCESS		read-write
		STATUS			current
		DESCRIPTION
				"TYPE: - Number
				 PAGE: - ARC & Sidebar Keyer
					Output Line 525  cmdID= 40140  min= 11  max= 19  step= 1  format= %0.0f  div_scale= 1 
					Min = 11  Max = 19  Step = 1 "
		::= { iqudc31CmdEntry 40140 }


	iqudc31AspectSignallingCSignallingConfigOutputLineHD40138 OBJECT-TYPE
		SYNTAX		INTEGER
		MAX-ACCESS		read-write
		STATUS			current
		DESCRIPTION
				"TYPE: - Number
				 PAGE: - ARC & Sidebar Keyer
					Output Line HD  cmdID= 40138  min= 9  max= 20  step= 1  format= %0.0f  div_scale= 1 
					Min = 9  Max = 20  Step = 1 "
		::= { iqudc31CmdEntry 40138 }


	iqudc31AspectSignallingCSignallingConfigOutputLineStatus40141 OBJECT-TYPE
		SYNTAX		RollCallString
		MAX-ACCESS		read-only
		STATUS			current
		DESCRIPTION
				"TYPE: - Display
				 PAGE: - ARC & Sidebar Keyer
					Output Line Status  cmdID= 40141  format=   "
		::= { iqudc31CmdEntry 40141 }


	iqudc31SignallingConfigVIMode40120 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40120 
					Auto  value= 0  
					Pass  value= 1  
					Force  value= 2  
					Delete  value= 3  "
		::= { iqudc31CmdEntry 40120 }


	iqudc31MenuARCSidebarKeyerOutputFormat40121 OBJECT-TYPE
		SYNTAX		INTEGER {
							val-SMPTE(0),
							val-AFD(1)
							}
		MAX-ACCESS		read-write
		STATUS			current
		DESCRIPTION
				"TYPE: - RadiobuttonList
				 PAGE: - ARC & Sidebar Keyer
					Output Format  cmdID= 40121 
					SMPTE  value= 0  
					AFD  value= 1  "
		::= { iqudc31CmdEntry 40121 }


	iqudc31MenuARCSidebarKeyerVIPassData40122 OBJECT-TYPE
		SYNTAX		INTEGER { disable(0), enable(1) }
		MAX-ACCESS		read-write
		STATUS			current
		DESCRIPTION
				"TYPE: - Checkbox
				 PAGE: - ARC & Sidebar Keyer
					VI Pass Data  cmdID= 40122 "
		::= { iqudc31CmdEntry 40122 }


	iqudc31ARCSidebarKeyerL23Mode40112 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40112 
					Auto  value= 0  
					Pass  value= 1  
					Force  value= 2  
					Delete  value= 3  "
		::= { iqudc31CmdEntry 40112 }


	iqudc31ARCSidebarKeyerL23OutputFormat40113 OBJECT-TYPE
		SYNTAX		INTEGER {
							val-ETSI(0),
							val-AFD(1)
							}
		MAX-ACCESS		read-write
		STATUS			current
		DESCRIPTION
				"TYPE: - RadiobuttonList
				 PAGE: - ARC & Sidebar Keyer
					Output Format  cmdID= 40113 
					ETSI  value= 0  
					AFD  value= 1  "
		::= { iqudc31CmdEntry 40113 }


	iqudc31MenuARCSidebarKeyerInputLine40110 OBJECT-TYPE
		SYNTAX		INTEGER
		MAX-ACCESS		read-write
		STATUS			current
		DESCRIPTION
				"TYPE: - Number
				 PAGE: - ARC & Sidebar Keyer
					Input Line  cmdID= 40110  min= 10  max= 23  step= 1  format= %0.0f  div_scale= 1 
					Min = 10  Max = 23  Step = 1 "
		::= { iqudc31CmdEntry 40110 }


	iqudc31MenuARCSidebarKeyerOutputLine40111 OBJECT-TYPE
		SYNTAX		INTEGER
		MAX-ACCESS		read-write
		STATUS			current
		DESCRIPTION
				"TYPE: - Number
				 PAGE: - ARC & Sidebar Keyer
					Output Line  cmdID= 40111  min= 10  max= 23  step= 1  format= %0.0f  div_scale= 1 
					Min = 10  Max = 23  Step = 1 "
		::= { iqudc31CmdEntry 40111 }


	iqudc31MenuARCSidebarKeyerOutputLineStatus20166 OBJECT-TYPE
		SYNTAX		RollCallString
		MAX-ACCESS		read-only
		STATUS			current
		DESCRIPTION
				"TYPE: - Display
				 PAGE: - ARC & Sidebar Keyer
					Output Line Status  cmdID= 20166  format=   "
		::= { iqudc31CmdEntry 20166 }


	iqudc31ARCSidebarKeyerAFDUserBitsForceUserBitsVal20163 OBJECT-TYPE
		SYNTAX		INTEGER { disable(0), enable(1) }
		MAX-ACCESS		read-write
		STATUS			current
		DESCRIPTION
				"TYPE: - Checkbox
				 PAGE: - ARC & Sidebar Keyer
					Force User Bits Val  cmdID= 20163 "
		::= { iqudc31CmdEntry 20163 }


	iqudc31ARCSidebarKeyerAFDUserBitsUserBitsValue40137 OBJECT-TYPE
		SYNTAX		INTEGER
		MAX-ACCESS		read-write
		STATUS			current
		DESCRIPTION
				"TYPE: - Number
				 PAGE: - ARC & Sidebar Keyer
					User Bits Value  cmdID= 40137  min= 0  max= 15  step= 1  format= %0.0f  div_scale= 1 
					Min = 0  Max = 15  Step = 1 "
		::= { iqudc31CmdEntry 40137 }


	iqudc31ARCSidebarKeyerForceOutputSignalSMPTE201640133 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-4-3-AFD-8(8),
							val-4-3-AFD-9(9),
							val-4-3-AFD-10(10),
							val-4-3-AFD-11(11),
							val-4-3-AFD-12(12),
							val-4-3-AFD-13(13),
							val-4-3-AFD-14(14),
							val-4-3-AFD-15(15),
							val-16-9-AFD-0(16),
							val-16-9-AFD-1(17),
							val-16-9-AFD-2(18),
							val-16-9-AFD-3(19),
							val-16-9-AFD-4(20),
							val-16-9-AFD-5(21),
							val-16-9-AFD-6(22),
							val-16-9-AFD-7(23),
							val-16-9-AFD-8(24),
							val-16-9-AFD-9(25),
							val-16-9-AFD-10(26),
							val-16-9-AFD-11(27),
							val-16-9-AFD-12(28),
							val-16-9-AFD-13(29),
							val-16-9-AFD-14(30),
							val-16-9-AFD-15(31)
							}
		MAX-ACCESS		read-write
		STATUS			current
		DESCRIPTION
				"TYPE: - RadiobuttonList
				 PAGE: - ARC & Sidebar Keyer
					SMPTE 2016  cmdID= 40133 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					4:3 AFD 8  value= 8  
					4:3 AFD 9  value= 9  
					4:3 AFD 10  value= 10  
					4:3 AFD 11  value= 11  
					4:3 AFD 12  value= 12  
					4:3 AFD 13  value= 13  
					4:3 AFD 14  value= 14  
					4:3 AFD 15  value= 15  
					16:9 AFD 0  value= 16  
					16:9 AFD 1  value= 17  
					16:9 AFD 2  value= 18  
					16:9 AFD 3  value= 19  
					16:9 AFD 4  value= 20  
					16:9 AFD 5  value= 21  
					16:9 AFD 6  value= 22  
					16:9 AFD 7  value= 23  
					16:9 AFD 8  value= 24  
					16:9 AFD 9  value= 25  
					16:9 AFD 10  value= 26  
					16:9 AFD 11  value= 27  
					16:9 AFD 12  value= 28  
					16:9 AFD 13  value= 29  
					16:9 AFD 14  value= 30  
					16:9 AFD 15  value= 31  "
		::= { iqudc31CmdEntry 40133 }


	iqudc31MenuARCSidebarKeyerSMPTERP18640134 OBJECT-TYPE
		SYNTAX		INTEGER {
							val-4-3(0),
							val-16-9(1)
							}
		MAX-ACCESS		read-write
		STATUS			current
		DESCRIPTION
				"TYPE: - RadiobuttonList
				 PAGE: - ARC & Sidebar Keyer
					SMPTE RP186  cmdID= 40134 
					4:3  value= 0  
					16:9  value= 1  "
		::= { iqudc31CmdEntry 40134 }


	iqudc31MenuARCSidebarKeyerAFD40131 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-16-9-AFD-0(8),
							val-16-9-AFD-1(9),
							val-16-9-AFD-2(10),
							val-16-9-AFD-3(11),
							val-16-9-AFD-4(12),
							val-16-9-AFD-5(13),
							val-16-9-AFD-6(14),
							val-16-9-AFD-7(15)
							}
		MAX-ACCESS		read-write
		STATUS			current
		DESCRIPTION
				"TYPE: - RadiobuttonList
				 PAGE: - ARC & Sidebar Keyer
					AFD  cmdID= 40131 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					16:9 AFD 0  value= 8  
					16:9 AFD 1  value= 9  
					16:9 AFD 2  value= 10  
					16:9 AFD 3  value= 11  
					16:9 AFD 4  value= 12  
					16:9 AFD 5  value= 13  
					16:9 AFD 6  value= 14  
					16:9 AFD 7  value= 15  "
		::= { iqudc31CmdEntry 40131 }


	iqudc31MenuARCSidebarKeyerETSI40132 OBJECT-TYPE
		SYNTAX		INTEGER {
							val-4-3-FF(0),
							val-14-9-Centre(1),
							val-14-9-Top(2),
							val-16-9-Centre(3),
							val-16-9-Top(4),
							val-grt-16-9-Centre(5),
							val-4-3-SP-14-9(6),
							val-16-9-FF(7)
							}
		MAX-ACCESS		read-write
		STATUS			current
		DESCRIPTION
				"TYPE: - RadiobuttonList
				 PAGE: - ARC & Sidebar Keyer
					ETSI  cmdID= 40132 
					4:3 FF  value= 0  
					14:9 Centre  value= 1  
					14:9 Top  value= 2  
					16:9 Centre  value= 3  
					16:9 Top  value= 4  
					>16:9 Centre  value= 5  
					4:3 SP 14:9  value= 6  
					16:9 FF  value= 7  "
		::= { iqudc31CmdEntry 40132 }


	iqudc31MenuARCSidebarKeyerSyncMode40107 OBJECT-TYPE
		SYNTAX		INTEGER { disable(0), enable(1) }
		MAX-ACCESS		read-write
		STATUS			current
		DESCRIPTION
				"TYPE: - Checkbox
				 PAGE: - ARC & Sidebar Keyer
					Sync Mode  cmdID= 40107 "
		::= { iqudc31CmdEntry 40107 }


	iqudc31MenuARCSidebarKeyerAspectSignallingC40236 OBJECT-TYPE
		SYNTAX		INTEGER { disable(0), enable(1) }
		MAX-ACCESS		read-write
		STATUS			current
		DESCRIPTION
				"TYPE: - Checkbox
				 PAGE: - ARC & Sidebar Keyer
					Aspect Signalling C  cmdID= 40236 "
		::= { iqudc31CmdEntry 40236 }


	iqudc31MenuARCSidebarKeyerSignallingDetected64220 OBJECT-TYPE
		SYNTAX		RollCallString
		MAX-ACCESS		read-only
		STATUS			current
		DESCRIPTION
				"TYPE: - Display
				 PAGE: - ARC & Sidebar Keyer
					Signalling Detected  cmdID= 64220  format=   "
		::= { iqudc31CmdEntry 64220 }


	iqudc31ARCSidebarKeyerSidebarKeyingOuMode40023 OBJECT-TYPE
		SYNTAX		INTEGER {
							val-Off(0),
							val-Output-Crop(1),
							val-Sidebar-Key(2)
							}
		MAX-ACCESS		read-write
		STATUS			current
		DESCRIPTION
				"TYPE: - RadiobuttonList
				 PAGE: - ARC & Sidebar Keyer
					Mode  cmdID= 40023 
					Off  value= 0  
					Output Crop  value= 1  
					Sidebar Key  value= 2  "
		::= { iqudc31CmdEntry 40023 }


	iqudc31MenuARCSidebarKeyerSidebarKeySource40024 OBJECT-TYPE
		SYNTAX		INTEGER {
							val-SDI-1(0),
							val-SDI-2(1),
							val-CVBS(2),
							val-SFP-1(3),
							val-SFP-2(4),
							val-Ch-1-Output(20)
							}
		MAX-ACCESS		read-write
		STATUS			current
		DESCRIPTION
				"TYPE: - RadiobuttonList
				 PAGE: - ARC & Sidebar Keyer
					Sidebar Key Source  cmdID= 40024 
					SDI 1  value= 0  
					SDI 2  value= 1  
					CVBS  value= 2  
					SFP 1  value= 3  
					SFP 2  value= 4  
					Ch 1 Output  value= 20  "
		::= { iqudc31CmdEntry 40024 }


	iqudc31ARCSidebarKeyerOutputCropPositioTop40019 OBJECT-TYPE
		SYNTAX		INTEGER
		MAX-ACCESS		read-write
		STATUS			current
		DESCRIPTION
				"TYPE: - Number
				 PAGE: - ARC & Sidebar Keyer
					Top  cmdID= 40019  min= 0  max= 99  step= 1  format= %0.0f%%  div_scale= 1 
					Min = 0%  Max = 99%  Step = 1% "
		::= { iqudc31CmdEntry 40019 }


	iqudc31ARCSidebarKeyerOutputCropPositioBottom40020 OBJECT-TYPE
		SYNTAX		INTEGER
		MAX-ACCESS		read-write
		STATUS			current
		DESCRIPTION
				"TYPE: - Number
				 PAGE: - ARC & Sidebar Keyer
					Bottom  cmdID= 40020  min= 0  max= 99  step= 1  format= %0.0f%%  div_scale= 1 
					Min = 0%  Max = 99%  Step = 1% "
		::= { iqudc31CmdEntry 40020 }


	iqudc31ARCSidebarKeyerOutputCropPositioLeft40021 OBJECT-TYPE
		SYNTAX		INTEGER
		MAX-ACCESS		read-write
		STATUS			current
		DESCRIPTION
				"TYPE: - Number
				 PAGE: - ARC & Sidebar Keyer
					Left  cmdID= 40021  min= 0  max= 99  step= 1  format= %0.0f%%  div_scale= 1 
					Min = 0%  Max = 99%  Step = 1% "
		::= { iqudc31CmdEntry 40021 }


	iqudc31ARCSidebarKeyerOutputCropPositioRight40022 OBJECT-TYPE
		SYNTAX		INTEGER
		MAX-ACCESS		read-write
		STATUS			current
		DESCRIPTION
				"TYPE: - Number
				 PAGE: - ARC & Sidebar Keyer
					Right  cmdID= 40022  min= 0  max= 99  step= 1  format= %0.0f%%  div_scale= 1 
					Min = 0%  Max = 99%  Step = 1% "
		::= { iqudc31CmdEntry 40022 }


	iqudc31ARCSidebarKeyerPostScalingControPostScalingEnable40103 OBJECT-TYPE
		SYNTAX		INTEGER { disable(0), enable(1) }
		MAX-ACCESS		read-write
		STATUS			current
		DESCRIPTION
				"TYPE: - Checkbox
				 PAGE: - ARC & Sidebar Keyer
					Post Scaling Enable  cmdID= 40103 "
		::= { iqudc31CmdEntry 40103 }


	iqudc31ARCSidebarKeyerPostScalingControSize40108 OBJECT-TYPE
		SYNTAX		INTEGER
		MAX-ACCESS		read-write
		STATUS			current
		DESCRIPTION
				"TYPE: - Number
				 PAGE: - ARC & Sidebar Keyer
					Size  cmdID= 40108  min= 80  max= 120  step= 1  format= %0.0f%%  div_scale= 1 
					Min = 80%  Max = 120%  Step = 1% "
		::= { iqudc31CmdEntry 40108 }


	iqudc31ARCSidebarKeyerPostScalingControAspect40109 OBJECT-TYPE
		SYNTAX		INTEGER
		MAX-ACCESS		read-write
		STATUS			current
		DESCRIPTION
				"TYPE: - Number
				 PAGE: - ARC & Sidebar Keyer
					Aspect  cmdID= 40109  min= 70  max= 150  step= 1  format= %0.0f%%  div_scale= 1 
					Min = 70%  Max = 150%  Step = 1% "
		::= { iqudc31CmdEntry 40109 }


	iqudc31ARCSidebarKeyerPostScalingControPan40106 OBJECT-TYPE
		SYNTAX		INTEGER
		MAX-ACCESS		read-write
		STATUS			current
		DESCRIPTION
				"TYPE: - Number
				 PAGE: - ARC & Sidebar Keyer
					Pan  cmdID= 40106  min= -50  max= 50  step= 1  format= %0.0f%  div_scale= 1 
					Min = -50 Max = 50 Step = 1"
		::= { iqudc31CmdEntry 40106 }


	iqudc31ARCSidebarKeyerPostScalingControTilt40102 OBJECT-TYPE
		SYNTAX		INTEGER
		MAX-ACCESS		read-write
		STATUS			current
		DESCRIPTION
				"TYPE: - Number
				 PAGE: - ARC & Sidebar Keyer
					Tilt  cmdID= 40102  min= -50  max= 50  step= 1  format= %0.0f%  div_scale= 1 
					Min = -50 Max = 50 Step = 1"
		::= { iqudc31CmdEntry 40102 }


	iqudc31ARCSidebarKeyerStandardPresetsWhSDInputis70240040 OBJECT-TYPE
		SYNTAX		INTEGER { disable(0), enable(1) }
		MAX-ACCESS		read-write
		STATUS			current
		DESCRIPTION
				"TYPE: - Checkbox
				 PAGE: - ARC & Sidebar Keyer
					SD Input is 702  cmdID= 40040 "
		::= { iqudc31CmdEntry 40040 }


	iqudc31ARCSidebarKeyerStandardPresetsWhSDOutputis70240047 OBJECT-TYPE
		SYNTAX		INTEGER { disable(0), enable(1) }
		MAX-ACCESS		read-write
		STATUS			current
		DESCRIPTION
				"TYPE: - Checkbox
				 PAGE: - ARC & Sidebar Keyer
					SD Output is 702  cmdID= 40047 "
		::= { iqudc31CmdEntry 40047 }


	iqudc31StandardPresetsWhSDCrossConversionSelectStdPreset40041 OBJECT-TYPE
		SYNTAX		INTEGER {
							val-None(0),
							val-16-9-LB-4-3-H-Cr(1),
							val-16-9-LB-16-9-Ana(2),
							val-16-9-LB-14-9-LB(3),
							val-16-9-Ana-4-3-H-Cr(4),
							val-16-9-Ana-16-9-LB(5),
							val-16-9-Ana-14-9-LB(6)
							}
		MAX-ACCESS		read-write
		STATUS			current
		DESCRIPTION
				"TYPE: - RadiobuttonList
				 PAGE: - ARC & Sidebar Keyer
					Select Std Preset  cmdID= 40041 
					None  value= 0  
					16:9 LB > 4:3 H-Cr  value= 1  
					16:9 LB > 16:9 Ana  value= 2  
					16:9 LB > 14:9 LB  value= 3  
					16:9 Ana > 4:3 H-Cr  value= 4  
					16:9 Ana > 16:9 LB  value= 5  
					16:9 Ana > 14:9 LB  value= 6  "
		::= { iqudc31CmdEntry 40041 }


	iqudc31ARCSidebarKeyerUpConversionSelectStdPreset40043 OBJECT-TYPE
		SYNTAX		INTEGER {
							val-4-3-16-9-V-Cr(0),
							val-4-3-4-3-PB(1),
							val-16-9-LB-16-9(2),
							val-16-9-Ana-16-9(3),
							val-14-9-LB-14-9-PB(4)
							}
		MAX-ACCESS		read-write
		STATUS			current
		DESCRIPTION
				"TYPE: - RadiobuttonList
				 PAGE: - ARC & Sidebar Keyer
					Select Std Preset  cmdID= 40043 
					4:3 > 16:9 V-Cr  value= 0  
					4:3 > 4:3 PB  value= 1  
					16:9 LB > 16:9  value= 2  
					16:9 Ana > 16:9  value= 3  
					14:9 LB > 14:9 PB  value= 4  "
		::= { iqudc31CmdEntry 40043 }


	iqudc31ARCSidebarKeyerDownConversionSelectStdPreset40045 OBJECT-TYPE
		SYNTAX		INTEGER {
							val-16-9-4-3-H-Cr(0),
							val-16-9-16-9-LB(1),
							val-16-9-16-9-Ana(2),
							val-4-3-PB-4-3(3),
							val-14-9-PB-14-9-LB(4)
							}
		MAX-ACCESS		read-write
		STATUS			current
		DESCRIPTION
				"TYPE: - RadiobuttonList
				 PAGE: - ARC & Sidebar Keyer
					Select Std Preset  cmdID= 40045 
					16:9 > 4:3 H-Cr  value= 0  
					16:9 > 16:9 LB  value= 1  
					16:9 > 16:9 Ana  value= 2  
					4:3 PB > 4:3  value= 3  
					14:9 PB > 14:9 LB  value= 4  "
		::= { iqudc31CmdEntry 40045 }


	iqudc31ScalingControlSDInputFormatifUseManualifUnkno40235 OBJECT-TYPE
		SYNTAX		INTEGER { disable(0), enable(1) }
		MAX-ACCESS		read-write
		STATUS			current
		DESCRIPTION
				"TYPE: - Checkbox
				 PAGE: - ARC & Sidebar Keyer
					Use Manual if Unkno  cmdID= 40235 "
		::= { iqudc31CmdEntry 40235 }


	iqudc31ScalingControlSDInputFormatif40114 OBJECT-TYPE
		SYNTAX		INTEGER {
							val-Normal(0),
							val-Anamorphic(1),
							val-Letterbox(2)
							}
		MAX-ACCESS		read-write
		STATUS			current
		DESCRIPTION
				"TYPE: - RadiobuttonList
				 PAGE: - ARC & Sidebar Keyer
					SD Input Format  cmdID= 40114 
					Normal  value= 0  
					Anamorphic  value= 1  
					Letterbox  value= 2  "
		::= { iqudc31CmdEntry 40114 }


	iqudc31ARCSidebarKeyerAspectSignallingCSDOutputFormat40115 OBJECT-TYPE
		SYNTAX		INTEGER {
							val-Normal(0),
							val-Anamorphic(1)
							}
		MAX-ACCESS		read-write
		STATUS			current
		DESCRIPTION
				"TYPE: - RadiobuttonList
				 PAGE: - ARC & Sidebar Keyer
					SD Output Format  cmdID= 40115 
					Normal  value= 0  
					Anamorphic  value= 1  "
		::= { iqudc31CmdEntry 40115 }


	iqudc31ARCSidebarKeyerAspectSignallingCConversionScaling40116 OBJECT-TYPE
		SYNTAX		INTEGER {
							val-Fit-to-Height(0),
							val-Fit-to-Width(1),
							val-14-9(2)
							}
		MAX-ACCESS		read-write
		STATUS			current
		DESCRIPTION
				"TYPE: - RadiobuttonList
				 PAGE: - ARC & Sidebar Keyer
					Conversion Scaling  cmdID= 40116 
					Fit to Height  value= 0  
					Fit to Width  value= 1  
					14:9  value= 2  "
		::= { iqudc31CmdEntry 40116 }


	iqudc31AspectSignallingCSignallingConfigSource40202 OBJECT-TYPE
		SYNTAX		INTEGER {
							val-SMPTE-2016(0),
							val-L23-ETSI(1),
							val-L23-AFD(2),
							val-VI-SMPTE(3),
							val-VI-AFD(4)
							}
		MAX-ACCESS		read-write
		STATUS			current
		DESCRIPTION
				"TYPE: - RadiobuttonList
				 PAGE: - ARC & Sidebar Keyer
					Source  cmdID= 40202 
					SMPTE 2016  value= 0  
					L23 ETSI  value= 1  
					L23 AFD  value= 2  
					VI SMPTE  value= 3  
					VI AFD  value= 4  "
		::= { iqudc31CmdEntry 40202 }


	iqudc31SignallingConfigSMPTE2016Mode40230 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40230 
					Auto  value= 0  
					Pass  value= 1  
					Force  value= 2  
					Delete  value= 3  "
		::= { iqudc31CmdEntry 40230 }


	iqudc31AspectSignallingCSignallingConfigOutputLinePAL OBJECT-TYPE
		SYNTAX		INTEGER
		MAX-ACCESS		read-write
		STATUS			current
		DESCRIPTION
				"TYPE: - Number
				 PAGE: - ARC & Sidebar Keyer
					Output Line PAL  cmdID= 40239  min= 7  max= 22  step= 1  format= %0.0f  div_scale= 1 
					Min = 7  Max = 22  Step = 1 "
		::= { iqudc31CmdEntry 40239 }


	iqudc31AspectSignallingCSignallingConfigOutputLineNTSC OBJECT-TYPE
		SYNTAX		INTEGER
		MAX-ACCESS		read-write
		STATUS			current
		DESCRIPTION
				"TYPE: - Number
				 PAGE: - ARC & Sidebar Keyer
					Output Line NTSC  cmdID= 40240  min= 11  max= 19  step= 1  format= %0.0f  div_scale= 1 
					Min = 11  Max = 19  Step = 1 "
		::= { iqudc31CmdEntry 40240 }


	iqudc31AspectSignallingCSignallingConfigOutputLineHD40238 OBJECT-TYPE
		SYNTAX		INTEGER
		MAX-ACCESS		read-write
		STATUS			current
		DESCRIPTION
				"TYPE: - Number
				 PAGE: - ARC & Sidebar Keyer
					Output Line HD  cmdID= 40238  min= 9  max= 20  step= 1  format= %0.0f  div_scale= 1 
					Min = 9  Max = 20  Step = 1 "
		::= { iqudc31CmdEntry 40238 }


	iqudc31AspectSignallingCSignallingConfigOutputLineStatus40241 OBJECT-TYPE
		SYNTAX		RollCallString
		MAX-ACCESS		read-only
		STATUS			current
		DESCRIPTION
				"TYPE: - Display
				 PAGE: - ARC & Sidebar Keyer
					Output Line Status  cmdID= 40241  format=   "
		::= { iqudc31CmdEntry 40241 }


	iqudc31SignallingConfigVIMode40220 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40220 
					Auto  value= 0  
					Pass  value= 1  
					Force  value= 2  
					Delete  value= 3  "
		::= { iqudc31CmdEntry 40220 }


	iqudc31MenuARCSidebarKeyerOutputFormat40221 OBJECT-TYPE
		SYNTAX		INTEGER {
							val-SMPTE(0),
							val-AFD(1)
							}
		MAX-ACCESS		read-write
		STATUS			current
		DESCRIPTION
				"TYPE: - RadiobuttonList
				 PAGE: - ARC & Sidebar Keyer
					Output Format  cmdID= 40221 
					SMPTE  value= 0  
					AFD  value= 1  "
		::= { iqudc31CmdEntry 40221 }


	iqudc31MenuARCSidebarKeyerVIPassData40222 OBJECT-TYPE
		SYNTAX		INTEGER { disable(0), enable(1) }
		MAX-ACCESS		read-write
		STATUS			current
		DESCRIPTION
				"TYPE: - Checkbox
				 PAGE: - ARC & Sidebar Keyer
					VI Pass Data  cmdID= 40222 "
		::= { iqudc31CmdEntry 40222 }


	iqudc31ARCSidebarKeyerL23Mode40212 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer
					Mode  cmdID= 40212 
					Auto  value= 0  
					Pass  value= 1  
					Force  value= 2  
					Delete  value= 3  "
		::= { iqudc31CmdEntry 40212 }


	iqudc31ARCSidebarKeyerL23OutputFormat40213 OBJECT-TYPE
		SYNTAX		INTEGER {
							val-ETSI(0),
							val-AFD(1)
							}
		MAX-ACCESS		read-write
		STATUS			current
		DESCRIPTION
				"TYPE: - RadiobuttonList
				 PAGE: - ARC & Sidebar Keyer
					Output Format  cmdID= 40213 
					ETSI  value= 0  
					AFD  value= 1  "
		::= { iqudc31CmdEntry 40213 }


	iqudc31MenuARCSidebarKeyerInputLine40210 OBJECT-TYPE
		SYNTAX		INTEGER
		MAX-ACCESS		read-write
		STATUS			current
		DESCRIPTION
				"TYPE: - Number
				 PAGE: - ARC & Sidebar Keyer
					Input Line  cmdID= 40210  min= 10  max= 23  step= 1  format= %0.0f  div_scale= 1 
					Min = 10  Max = 23  Step = 1 "
		::= { iqudc31CmdEntry 40210 }


	iqudc31MenuARCSidebarKeyerOutputLine40211 OBJECT-TYPE
		SYNTAX		INTEGER
		MAX-ACCESS		read-write
		STATUS			current
		DESCRIPTION
				"TYPE: - Number
				 PAGE: - ARC & Sidebar Keyer
					Output Line  cmdID= 40211  min= 10  max= 23  step= 1  format= %0.0f  div_scale= 1 
					Min = 10  Max = 23  Step = 1 "
		::= { iqudc31CmdEntry 40211 }


	iqudc31MenuARCSidebarKeyerOutputLineStatus20176 OBJECT-TYPE
		SYNTAX		RollCallString
		MAX-ACCESS		read-only
		STATUS			current
		DESCRIPTION
				"TYPE: - Display
				 PAGE: - ARC & Sidebar Keyer
					Output Line Status  cmdID= 20176  format=   "
		::= { iqudc31CmdEntry 20176 }


	iqudc31ARCSidebarKeyerAFDUserBitsForceUserBitsVal20173 OBJECT-TYPE
		SYNTAX		INTEGER { disable(0), enable(1) }
		MAX-ACCESS		read-write
		STATUS			current
		DESCRIPTION
				"TYPE: - Checkbox
				 PAGE: - ARC & Sidebar Keyer
					Force User Bits Val  cmdID= 20173 "
		::= { iqudc31CmdEntry 20173 }


	iqudc31ARCSidebarKeyerAFDUserBitsUserBitsValue40237 OBJECT-TYPE
		SYNTAX		INTEGER
		MAX-ACCESS		read-write
		STATUS			current
		DESCRIPTION
				"TYPE: - Number
				 PAGE: - ARC & Sidebar Keyer
					User Bits Value  cmdID= 40237  min= 0  max= 15  step= 1  format= %0.0f  div_scale= 1 
					Min = 0  Max = 15  Step = 1 "
		::= { iqudc31CmdEntry 40237 }


	iqudc31ARCSidebarKeyerForceOutputSignalSMPTE201640233 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-4-3-AFD-8(8),
							val-4-3-AFD-9(9),
							val-4-3-AFD-10(10),
							val-4-3-AFD-11(11),
							val-4-3-AFD-12(12),
							val-4-3-AFD-13(13),
							val-4-3-AFD-14(14),
							val-4-3-AFD-15(15),
							val-16-9-AFD-0(16),
							val-16-9-AFD-1(17),
							val-16-9-AFD-2(18),
							val-16-9-AFD-3(19),
							val-16-9-AFD-4(20),
							val-16-9-AFD-5(21),
							val-16-9-AFD-6(22),
							val-16-9-AFD-7(23),
							val-16-9-AFD-8(24),
							val-16-9-AFD-9(25),
							val-16-9-AFD-10(26),
							val-16-9-AFD-11(27),
							val-16-9-AFD-12(28),
							val-16-9-AFD-13(29),
							val-16-9-AFD-14(30),
							val-16-9-AFD-15(31)
							}
		MAX-ACCESS		read-write
		STATUS			current
		DESCRIPTION
				"TYPE: - RadiobuttonList
				 PAGE: - ARC & Sidebar Keyer
					SMPTE 2016  cmdID= 40233 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					4:3 AFD 8  value= 8  
					4:3 AFD 9  value= 9  
					4:3 AFD 10  value= 10  
					4:3 AFD 11  value= 11  
					4:3 AFD 12  value= 12  
					4:3 AFD 13  value= 13  
					4:3 AFD 14  value= 14  
					4:3 AFD 15  value= 15  
					16:9 AFD 0  value= 16  
					16:9 AFD 1  value= 17  
					16:9 AFD 2  value= 18  
					16:9 AFD 3  value= 19  
					16:9 AFD 4  value= 20  
					16:9 AFD 5  value= 21  
					16:9 AFD 6  value= 22  
					16:9 AFD 7  value= 23  
					16:9 AFD 8  value= 24  
					16:9 AFD 9  value= 25  
					16:9 AFD 10  value= 26  
					16:9 AFD 11  value= 27  
					16:9 AFD 12  value= 28  
					16:9 AFD 13  value= 29  
					16:9 AFD 14  value= 30  
					16:9 AFD 15  value= 31  "
		::= { iqudc31CmdEntry 40233 }


	iqudc31MenuARCSidebarKeyerSMPTERP18640234 OBJECT-TYPE
		SYNTAX		INTEGER {
							val-4-3(0),
							val-16-9(1)
							}
		MAX-ACCESS		read-write
		STATUS			current
		DESCRIPTION
				"TYPE: - RadiobuttonList
				 PAGE: - ARC & Sidebar Keyer
					SMPTE RP186  cmdID= 40234 
					4:3  value= 0  
					16:9  value= 1  "
		::= { iqudc31CmdEntry 40234 }


	iqudc31MenuARCSidebarKeyerAFD40231 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-16-9-AFD-0(8),
							val-16-9-AFD-1(9),
							val-16-9-AFD-2(10),
							val-16-9-AFD-3(11),
							val-16-9-AFD-4(12),
							val-16-9-AFD-5(13),
							val-16-9-AFD-6(14),
							val-16-9-AFD-7(15)
							}
		MAX-ACCESS		read-write
		STATUS			current
		DESCRIPTION
				"TYPE: - RadiobuttonList
				 PAGE: - ARC & Sidebar Keyer
					AFD  cmdID= 40231 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					16:9 AFD 0  value= 8  
					16:9 AFD 1  value= 9  
					16:9 AFD 2  value= 10  
					16:9 AFD 3  value= 11  
					16:9 AFD 4  value= 12  
					16:9 AFD 5  value= 13  
					16:9 AFD 6  value= 14  
					16:9 AFD 7  value= 15  "
		::= { iqudc31CmdEntry 40231 }


	iqudc31MenuARCSidebarKeyerETSI40232 OBJECT-TYPE
		SYNTAX		INTEGER {
							val-4-3-FF(0),
							val-14-9-Centre(1),
							val-14-9-Top(2),
							val-16-9-Centre(3),
							val-16-9-Top(4),
							val-grt-16-9-Centre(5),
							val-4-3-SP-14-9(6),
							val-16-9-FF(7)
							}
		MAX-ACCESS		read-write
		STATUS			current
		DESCRIPTION
				"TYPE: - RadiobuttonList
				 PAGE: - ARC & Sidebar Keyer
					ETSI  cmdID= 40232 
					4:3 FF  value= 0  
					14:9 Centre  value= 1  
					14:9 Top  value= 2  
					16:9 Centre  value= 3  
					16:9 Top  value= 4  
					>16:9 Centre  value= 5  
					4:3 SP 14:9  value= 6  
					16:9 FF  value= 7  "
		::= { iqudc31CmdEntry 40232 }


	iqudc31MenuARCSidebarKeyerNewDisplay OBJECT-TYPE
		SYNTAX		RollCallString
		MAX-ACCESS		read-only
		STATUS			current
		DESCRIPTION
				"TYPE: - Display
				 PAGE: - ARC & Sidebar Keyer
					New Display  cmdID= 44449  format=   "
		::= { iqudc31CmdEntry 44449 }


	iqudc31AudioRoutingCh1InputPairsStatusEmbedded1 OBJECT-TYPE
		SYNTAX		RollCallString
		MAX-ACCESS		read-only
		STATUS			current
		DESCRIPTION
				"TYPE: - Display
				 PAGE: - Audio Routing-Ch1
					Embedded 1  cmdID= 63112  format=   "
		::= { iqudc31CmdEntry 63112 }


	iqudc31AudioRoutingCh1InputPairsStatusEmbedded2 OBJECT-TYPE
		SYNTAX		RollCallString
		MAX-ACCESS		read-only
		STATUS			current
		DESCRIPTION
				"TYPE: - Display
				 PAGE: - Audio Routing-Ch1
					Embedded 2  cmdID= 63113  format=   "
		::= { iqudc31CmdEntry 63113 }


	iqudc31AudioRoutingCh1InputPairsStatusEmbedded3 OBJECT-TYPE
		SYNTAX		RollCallString
		MAX-ACCESS		read-only
		STATUS			current
		DESCRIPTION
				"TYPE: - Display
				 PAGE: - Audio Routing-Ch1
					Embedded 3  cmdID= 63102  format=   "
		::= { iqudc31CmdEntry 63102 }


	iqudc31AudioRoutingCh1InputPairsStatusEmbedded4 OBJECT-TYPE
		SYNTAX		RollCallString
		MAX-ACCESS		read-only
		STATUS			current
		DESCRIPTION
				"TYPE: - Display
				 PAGE: - Audio Routing-Ch1
					Embedded 4  cmdID= 63103  format=   "
		::= { iqudc31CmdEntry 63103 }


	iqudc31AudioRoutingCh1InputPairsStatusEmbedded5 OBJECT-TYPE
		SYNTAX		RollCallString
		MAX-ACCESS		read-only
		STATUS			current
		DESCRIPTION
				"TYPE: - Display
				 PAGE: - Audio Routing-Ch1
					Embedded 5  cmdID= 63114  format=   "
		::= { iqudc31CmdEntry 63114 }


	iqudc31AudioRoutingCh1InputPairsStatusEmbedded6 OBJECT-TYPE
		SYNTAX		RollCallString
		MAX-ACCESS		read-only
		STATUS			current
		DESCRIPTION
				"TYPE: - Display
				 PAGE: - Audio Routing-Ch1
					Embedded 6  cmdID= 63105  format=   "
		::= { iqudc31CmdEntry 63105 }


	iqudc31AudioRoutingCh1InputPairsStatusEmbedded7 OBJECT-TYPE
		SYNTAX		RollCallString
		MAX-ACCESS		read-only
		STATUS			current
		DESCRIPTION
				"TYPE: - Display
				 PAGE: - Audio Routing-Ch1
					Embedded 7  cmdID= 63106  format=   "
		::= { iqudc31CmdEntry 63106 }


	iqudc31AudioRoutingCh1InputPairsStatusEmbedded8 OBJECT-TYPE
		SYNTAX		RollCallString
		MAX-ACCESS		read-only
		STATUS			current
		DESCRIPTION
				"TYPE: - Display
				 PAGE: - Audio Routing-Ch1
					Embedded 8  cmdID= 63107  format=   "
		::= { iqudc31CmdEntry 63107 }


	iqudc31AudioRoutingCh1InputPairsStatusAES1 OBJECT-TYPE
		SYNTAX		RollCallString
		MAX-ACCESS		read-only
		STATUS			current
		DESCRIPTION
				"TYPE: - Display
				 PAGE: - Audio Routing-Ch1
					AES 1  cmdID= 63120  format=   "
		::= { iqudc31CmdEntry 63120 }


	iqudc31AudioRoutingCh1InputPairsStatusAES2 OBJECT-TYPE
		SYNTAX		RollCallString
		MAX-ACCESS		read-only
		STATUS			current
		DESCRIPTION
				"TYPE: - Display
				 PAGE: - Audio Routing-Ch1
					AES 2  cmdID= 63121  format=   "
		::= { iqudc31CmdEntry 63121 }


	iqudc31AudioRoutingCh1InputPairsStatusAES3 OBJECT-TYPE
		SYNTAX		RollCallString
		MAX-ACCESS		read-only
		STATUS			current
		DESCRIPTION
				"TYPE: - Display
				 PAGE: - Audio Routing-Ch1
					AES 3  cmdID= 63123  format=   "
		::= { iqudc31CmdEntry 63123 }


	iqudc31AudioRoutingCh1InputPairsStatusAES4 OBJECT-TYPE
		SYNTAX		RollCallString
		MAX-ACCESS		read-only
		STATUS			current
		DESCRIPTION
				"TYPE: - Display
				 PAGE: - Audio Routing-Ch1
					AES 4  cmdID= 63124  format=   "
		::= { iqudc31CmdEntry 63124 }


	iqudc31AudioRoutingCh1InputPairsStatusAES5 OBJECT-TYPE
		SYNTAX		RollCallString
		MAX-ACCESS		read-only
		STATUS			current
		DESCRIPTION
				"TYPE: - Display
				 PAGE: - Audio Routing-Ch1
					AES 5  cmdID= 63125  format=   "
		::= { iqudc31CmdEntry 63125 }


	iqudc31AudioRoutingCh1InputPairsStatusAES6 OBJECT-TYPE
		SYNTAX		RollCallString
		MAX-ACCESS		read-only
		STATUS			current
		DESCRIPTION
				"TYPE: - Display
				 PAGE: - Audio Routing-Ch1
					AES 6  cmdID= 63126  format=   "
		::= { iqudc31CmdEntry 63126 }


	iqudc31AudioRoutingCh1InputPairsStatusAES7 OBJECT-TYPE
		SYNTAX		RollCallString
		MAX-ACCESS		read-only
		STATUS			current
		DESCRIPTION
				"TYPE: - Display
				 PAGE: - Audio Routing-Ch1
					AES 7  cmdID= 63127  format=   "
		::= { iqudc31CmdEntry 63127 }


	iqudc31AudioRoutingCh1InputPairsStatusAES8 OBJECT-TYPE
		SYNTAX		RollCallString
		MAX-ACCESS		read-only
		STATUS			current
		DESCRIPTION
				"TYPE: - Display
				 PAGE: - Audio Routing-Ch1
					AES 8  cmdID= 63128  format=   "
		::= { iqudc31CmdEntry 63128 }


	iqudc31AudioRoutingCh1InputPairsStatusAnalog1 OBJECT-TYPE
		SYNTAX		RollCallString
		MAX-ACCESS		read-only
		STATUS			current
		DESCRIPTION
				"TYPE: - Display
				 PAGE: - Audio Routing-Ch1
					Analog 1  cmdID= 63129  format=   "
		::= { iqudc31CmdEntry 63129 }


	iqudc31AudioRoutingCh1InputPairsStatusAnalog2 OBJECT-TYPE
		SYNTAX		RollCallString
		MAX-ACCESS		read-only
		STATUS			current
		DESCRIPTION
				"TYPE: - Display
				 PAGE: - Audio Routing-Ch1
					Analog 2  cmdID= 63130  format=   "
		::= { iqudc31CmdEntry 63130 }


	iqudc31AudioRoutingCh1InputPairsStatusDolbyDecoder1 OBJECT-TYPE
		SYNTAX		RollCallString
		MAX-ACCESS		read-only
		STATUS			current
		DESCRIPTION
				"TYPE: - Display
				 PAGE: - Audio Routing-Ch1
					Dolby Decoder 1  cmdID= 63131  format=   "
		::= { iqudc31CmdEntry 63131 }


	iqudc31AudioRoutingCh1InputPairsStatusDolbyDecoder2 OBJECT-TYPE
		SYNTAX		RollCallString
		MAX-ACCESS		read-only
		STATUS			current
		DESCRIPTION
				"TYPE: - Display
				 PAGE: - Audio Routing-Ch1
					Dolby Decoder 2  cmdID= 63132  format=   "
		::= { iqudc31CmdEntry 63132 }


	iqudc31AudioRoutingCh1InputPairsStatusDolbyDecoder3 OBJECT-TYPE
		SYNTAX		RollCallString
		MAX-ACCESS		read-only
		STATUS			current
		DESCRIPTION
				"TYPE: - Display
				 PAGE: - Audio Routing-Ch1
					Dolby Decoder 3  cmdID= 63133  format=   "
		::= { iqudc31CmdEntry 63133 }


	iqudc31AudioRoutingCh1InputPairsStatusDolbyDecoder4 OBJECT-TYPE
		SYNTAX		RollCallString
		MAX-ACCESS		read-only
		STATUS			current
		DESCRIPTION
				"TYPE: - Display
				 PAGE: - Audio Routing-Ch1
					Dolby Decoder 4  cmdID= 63134  format=   "
		::= { iqudc31CmdEntry 63134 }


	iqudc31AudioRoutingCh1InputPairsStatusDolbyDownmix OBJECT-TYPE
		SYNTAX		RollCallString
		MAX-ACCESS		read-only
		STATUS			current
		DESCRIPTION
				"TYPE: - Display
				 PAGE: - Audio Routing-Ch1
					Dolby Downmix  cmdID= 63135  format=   "
		::= { iqudc31CmdEntry 63135 }


	iqudc31AudioRoutingCh1InputPairsStatusDolbyEncoder OBJECT-TYPE
		SYNTAX		RollCallString
		MAX-ACCESS		read-only
		STATUS			current
		DESCRIPTION
				"TYPE: - Display
				 PAGE: - Audio Routing-Ch1
					Dolby Encoder  cmdID= 63136  format=   "
		::= { iqudc31CmdEntry 63136 }


	iqudc31ProcessPairs18Pair1InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 1
					Input Pairs Source  cmdID= 50005 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50005 }


	iqudc31ProcessPairs18Pair2InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 2
					Input Pairs Source  cmdID= 50007 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50007 }


	iqudc31ProcessPairs18Pair3InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 3
					Input Pairs Source  cmdID= 50004 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50004 }


	iqudc31ProcessPairs18Pair4InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 4
					Input Pairs Source  cmdID= 50006 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50006 }


	iqudc31ProcessPairs18Pair5InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 5
					Input Pairs Source  cmdID= 50008 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50008 }


	iqudc31ProcessPairs18Pair6InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 6
					Input Pairs Source  cmdID= 50010 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50010 }


	iqudc31ProcessPairs18Pair7InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 7
					Input Pairs Source  cmdID= 50012 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50012 }


	iqudc31ProcessPairs18Pair8InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 8
					Input Pairs Source  cmdID= 50017 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50017 }


	iqudc31AudioRoutingCh1ProcessPairs18SPair1 OBJECT-TYPE
		SYNTAX		RollCallString
		MAX-ACCESS		read-only
		STATUS			current
		DESCRIPTION
				"TYPE: - Display
				 PAGE: - Audio Routing-Ch1- Process Pairs 1-8 S
					Pair 1  cmdID= 63137  format=   "
		::= { iqudc31CmdEntry 63137 }


	iqudc31AudioRoutingCh1ProcessPairs18SPair2 OBJECT-TYPE
		SYNTAX		RollCallString
		MAX-ACCESS		read-only
		STATUS			current
		DESCRIPTION
				"TYPE: - Display
				 PAGE: - Audio Routing-Ch1- Process Pairs 1-8 S
					Pair 2  cmdID= 63138  format=   "
		::= { iqudc31CmdEntry 63138 }


	iqudc31AudioRoutingCh1ProcessPairs18SPair3 OBJECT-TYPE
		SYNTAX		RollCallString
		MAX-ACCESS		read-only
		STATUS			current
		DESCRIPTION
				"TYPE: - Display
				 PAGE: - Audio Routing-Ch1- Process Pairs 1-8 S
					Pair 3  cmdID= 63139  format=   "
		::= { iqudc31CmdEntry 63139 }


	iqudc31AudioRoutingCh1ProcessPairs18SPair4 OBJECT-TYPE
		SYNTAX		RollCallString
		MAX-ACCESS		read-only
		STATUS			current
		DESCRIPTION
				"TYPE: - Display
				 PAGE: - Audio Routing-Ch1- Process Pairs 1-8 S
					Pair 4  cmdID= 63140  format=   "
		::= { iqudc31CmdEntry 63140 }


	iqudc31AudioRoutingCh1ProcessPairs18SPair5 OBJECT-TYPE
		SYNTAX		RollCallString
		MAX-ACCESS		read-only
		STATUS			current
		DESCRIPTION
				"TYPE: - Display
				 PAGE: - Audio Routing-Ch1- Process Pairs 1-8 S
					Pair 5  cmdID= 63141  format=   "
		::= { iqudc31CmdEntry 63141 }


	iqudc31AudioRoutingCh1ProcessPairs18SPair6 OBJECT-TYPE
		SYNTAX		RollCallString
		MAX-ACCESS		read-only
		STATUS			current
		DESCRIPTION
				"TYPE: - Display
				 PAGE: - Audio Routing-Ch1- Process Pairs 1-8 S
					Pair 6  cmdID= 63142  format=   "
		::= { iqudc31CmdEntry 63142 }


	iqudc31AudioRoutingCh1ProcessPairs18SPair7 OBJECT-TYPE
		SYNTAX		RollCallString
		MAX-ACCESS		read-only
		STATUS			current
		DESCRIPTION
				"TYPE: - Display
				 PAGE: - Audio Routing-Ch1- Process Pairs 1-8 S
					Pair 7  cmdID= 63143  format=   "
		::= { iqudc31CmdEntry 63143 }


	iqudc31AudioRoutingCh1ProcessPairs18SPair8 OBJECT-TYPE
		SYNTAX		RollCallString
		MAX-ACCESS		read-only
		STATUS			current
		DESCRIPTION
				"TYPE: - Display
				 PAGE: - Audio Routing-Ch1- Process Pairs 1-8 S
					Pair 8  cmdID= 63144  format=   "
		::= { iqudc31CmdEntry 63144 }


	iqudc31AudioRoutingCh2InputPairsStatusEmbedded1 OBJECT-TYPE
		SYNTAX		RollCallString
		MAX-ACCESS		read-only
		STATUS			current
		DESCRIPTION
				"TYPE: - Display
				 PAGE: - Audio Routing-Ch2
					Embedded 1  cmdID= 63200  format=   "
		::= { iqudc31CmdEntry 63200 }


	iqudc31AudioRoutingCh2InputPairsStatusEmbedded2 OBJECT-TYPE
		SYNTAX		RollCallString
		MAX-ACCESS		read-only
		STATUS			current
		DESCRIPTION
				"TYPE: - Display
				 PAGE: - Audio Routing-Ch2
					Embedded 2  cmdID= 63201  format=   "
		::= { iqudc31CmdEntry 63201 }


	iqudc31AudioRoutingCh2InputPairsStatusEmbedded3 OBJECT-TYPE
		SYNTAX		RollCallString
		MAX-ACCESS		read-only
		STATUS			current
		DESCRIPTION
				"TYPE: - Display
				 PAGE: - Audio Routing-Ch2
					Embedded 3  cmdID= 63202  format=   "
		::= { iqudc31CmdEntry 63202 }


	iqudc31AudioRoutingCh2InputPairsStatusEmbedded4 OBJECT-TYPE
		SYNTAX		RollCallString
		MAX-ACCESS		read-only
		STATUS			current
		DESCRIPTION
				"TYPE: - Display
				 PAGE: - Audio Routing-Ch2
					Embedded 4  cmdID= 63203  format=   "
		::= { iqudc31CmdEntry 63203 }


	iqudc31AudioRoutingCh2InputPairsStatusEmbedded5 OBJECT-TYPE
		SYNTAX		RollCallString
		MAX-ACCESS		read-only
		STATUS			current
		DESCRIPTION
				"TYPE: - Display
				 PAGE: - Audio Routing-Ch2
					Embedded 5  cmdID= 63204  format=   "
		::= { iqudc31CmdEntry 63204 }


	iqudc31AudioRoutingCh2InputPairsStatusEmbedded6 OBJECT-TYPE
		SYNTAX		RollCallString
		MAX-ACCESS		read-only
		STATUS			current
		DESCRIPTION
				"TYPE: - Display
				 PAGE: - Audio Routing-Ch2
					Embedded 6  cmdID= 63205  format=   "
		::= { iqudc31CmdEntry 63205 }


	iqudc31AudioRoutingCh2InputPairsStatusEmbedded7 OBJECT-TYPE
		SYNTAX		RollCallString
		MAX-ACCESS		read-only
		STATUS			current
		DESCRIPTION
				"TYPE: - Display
				 PAGE: - Audio Routing-Ch2
					Embedded 7  cmdID= 63206  format=   "
		::= { iqudc31CmdEntry 63206 }


	iqudc31AudioRoutingCh2InputPairsStatusEmbedded8 OBJECT-TYPE
		SYNTAX		RollCallString
		MAX-ACCESS		read-only
		STATUS			current
		DESCRIPTION
				"TYPE: - Display
				 PAGE: - Audio Routing-Ch2
					Embedded 8  cmdID= 63207  format=   "
		::= { iqudc31CmdEntry 63207 }


	iqudc31AudioRoutingCh2InputPairsStatusAES1 OBJECT-TYPE
		SYNTAX		RollCallString
		MAX-ACCESS		read-only
		STATUS			current
		DESCRIPTION
				"TYPE: - Display
				 PAGE: - Audio Routing-Ch2
					AES 1  cmdID= 63220  format=   "
		::= { iqudc31CmdEntry 63220 }


	iqudc31AudioRoutingCh2InputPairsStatusAES2 OBJECT-TYPE
		SYNTAX		RollCallString
		MAX-ACCESS		read-only
		STATUS			current
		DESCRIPTION
				"TYPE: - Display
				 PAGE: - Audio Routing-Ch2
					AES 2  cmdID= 63221  format=   "
		::= { iqudc31CmdEntry 63221 }


	iqudc31AudioRoutingCh2InputPairsStatusAES3 OBJECT-TYPE
		SYNTAX		RollCallString
		MAX-ACCESS		read-only
		STATUS			current
		DESCRIPTION
				"TYPE: - Display
				 PAGE: - Audio Routing-Ch2
					AES 3  cmdID= 63223  format=   "
		::= { iqudc31CmdEntry 63223 }


	iqudc31AudioRoutingCh2InputPairsStatusAES4 OBJECT-TYPE
		SYNTAX		RollCallString
		MAX-ACCESS		read-only
		STATUS			current
		DESCRIPTION
				"TYPE: - Display
				 PAGE: - Audio Routing-Ch2
					AES 4  cmdID= 63224  format=   "
		::= { iqudc31CmdEntry 63224 }


	iqudc31AudioRoutingCh2InputPairsStatusAES5 OBJECT-TYPE
		SYNTAX		RollCallString
		MAX-ACCESS		read-only
		STATUS			current
		DESCRIPTION
				"TYPE: - Display
				 PAGE: - Audio Routing-Ch2
					AES 5  cmdID= 63225  format=   "
		::= { iqudc31CmdEntry 63225 }


	iqudc31AudioRoutingCh2InputPairsStatusAES6 OBJECT-TYPE
		SYNTAX		RollCallString
		MAX-ACCESS		read-only
		STATUS			current
		DESCRIPTION
				"TYPE: - Display
				 PAGE: - Audio Routing-Ch2
					AES 6  cmdID= 63226  format=   "
		::= { iqudc31CmdEntry 63226 }


	iqudc31AudioRoutingCh2InputPairsStatusAES7 OBJECT-TYPE
		SYNTAX		RollCallString
		MAX-ACCESS		read-only
		STATUS			current
		DESCRIPTION
				"TYPE: - Display
				 PAGE: - Audio Routing-Ch2
					AES 7  cmdID= 63227  format=   "
		::= { iqudc31CmdEntry 63227 }


	iqudc31AudioRoutingCh2InputPairsStatusAES8 OBJECT-TYPE
		SYNTAX		RollCallString
		MAX-ACCESS		read-only
		STATUS			current
		DESCRIPTION
				"TYPE: - Display
				 PAGE: - Audio Routing-Ch2
					AES 8  cmdID= 63228  format=   "
		::= { iqudc31CmdEntry 63228 }


	iqudc31AudioRoutingCh2InputPairsStatusAnalog1 OBJECT-TYPE
		SYNTAX		RollCallString
		MAX-ACCESS		read-only
		STATUS			current
		DESCRIPTION
				"TYPE: - Display
				 PAGE: - Audio Routing-Ch2
					Analog 1  cmdID= 63229  format=   "
		::= { iqudc31CmdEntry 63229 }


	iqudc31AudioRoutingCh2InputPairsStatusAnalog2 OBJECT-TYPE
		SYNTAX		RollCallString
		MAX-ACCESS		read-only
		STATUS			current
		DESCRIPTION
				"TYPE: - Display
				 PAGE: - Audio Routing-Ch2
					Analog 2  cmdID= 63236  format=   "
		::= { iqudc31CmdEntry 63236 }


	iqudc31AudioRoutingCh2InputPairsStatusDolbyDecoder1 OBJECT-TYPE
		SYNTAX		RollCallString
		MAX-ACCESS		read-only
		STATUS			current
		DESCRIPTION
				"TYPE: - Display
				 PAGE: - Audio Routing-Ch2
					Dolby Decoder 1  cmdID= 63230  format=   "
		::= { iqudc31CmdEntry 63230 }


	iqudc31AudioRoutingCh2InputPairsStatusDolbyDecoder2 OBJECT-TYPE
		SYNTAX		RollCallString
		MAX-ACCESS		read-only
		STATUS			current
		DESCRIPTION
				"TYPE: - Display
				 PAGE: - Audio Routing-Ch2
					Dolby Decoder 2  cmdID= 63231  format=   "
		::= { iqudc31CmdEntry 63231 }


	iqudc31AudioRoutingCh2InputPairsStatusDolbyDecoder3 OBJECT-TYPE
		SYNTAX		RollCallString
		MAX-ACCESS		read-only
		STATUS			current
		DESCRIPTION
				"TYPE: - Display
				 PAGE: - Audio Routing-Ch2
					Dolby Decoder 3  cmdID= 63232  format=   "
		::= { iqudc31CmdEntry 63232 }


	iqudc31AudioRoutingCh2InputPairsStatusDolbyDecoder4 OBJECT-TYPE
		SYNTAX		RollCallString
		MAX-ACCESS		read-only
		STATUS			current
		DESCRIPTION
				"TYPE: - Display
				 PAGE: - Audio Routing-Ch2
					Dolby Decoder 4  cmdID= 63233  format=   "
		::= { iqudc31CmdEntry 63233 }


	iqudc31AudioRoutingCh2InputPairsStatusDolbyDownmix OBJECT-TYPE
		SYNTAX		RollCallString
		MAX-ACCESS		read-only
		STATUS			current
		DESCRIPTION
				"TYPE: - Display
				 PAGE: - Audio Routing-Ch2
					Dolby Downmix  cmdID= 63234  format=   "
		::= { iqudc31CmdEntry 63234 }


	iqudc31AudioRoutingCh2InputPairsStatusDolbyEncoder OBJECT-TYPE
		SYNTAX		RollCallString
		MAX-ACCESS		read-only
		STATUS			current
		DESCRIPTION
				"TYPE: - Display
				 PAGE: - Audio Routing-Ch2
					Dolby Encoder  cmdID= 63235  format=   "
		::= { iqudc31CmdEntry 63235 }


	iqudc31ProcessPairs18ProcessPair1InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 1
					Input Pairs Source  cmdID= 50242 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50242 }


	iqudc31ProcessPairs18ProcessPair2InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 2
					Input Pairs Source  cmdID= 50243 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50243 }


	iqudc31ProcessPairs18ProcessPair3InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 3
					Input Pairs Source  cmdID= 50244 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50244 }


	iqudc31ProcessPairs18ProcessPair4InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 4
					Input Pairs Source  cmdID= 50245 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50245 }


	iqudc31ProcessPairs18ProcessPair5InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 5
					Input Pairs Source  cmdID= 50246 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50246 }


	iqudc31ProcessPairs18ProcessPair6InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 6
					Input Pairs Source  cmdID= 50247 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50247 }


	iqudc31ProcessPairs18ProcessPair7InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 7
					Input Pairs Source  cmdID= 50248 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50248 }


	iqudc31ProcessPairs18ProcessPair8InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 8
					Input Pairs Source  cmdID= 50249 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc31CmdEntry 50249 }


	iqudc31AudioRoutingCh2ProcessPairs18SPair1 OBJECT-TYPE
		SYNTAX		RollCallString
		MAX-ACCESS		read-only
		STATUS			current
		DESCRIPTION
				"TYPE: - Display
				 PAGE: - Audio Routing-Ch2- Process Pairs 1-8 S
					Pair 1  cmdID= 63145  format=   "
		::= { iqudc31CmdEntry 63145 }


	iqudc31AudioRoutingCh2ProcessPairs18SPair2 OBJECT-TYPE
		SYNTAX		RollCallString
		MAX-ACCESS		read-only
		STATUS			current
		DESCRIPTION
				"TYPE: - Display
				 PAGE: - Audio Routing-Ch2- Process Pairs 1-8 S
					Pair 2  cmdID= 63146  format=   "
		::= { iqudc31CmdEntry 63146 }


	iqudc31AudioRoutingCh2ProcessPairs18SPair3 OBJECT-TYPE
		SYNTAX		RollCallString
		MAX-ACCESS		read-only
		STATUS			current
		DESCRIPTION
				"TYPE: - Display
				 PAGE: - Audio Routing-Ch2- Process Pairs 1-8 S
					Pair 3  cmdID= 63147  format=   "
		::= { iqudc31CmdEntry 63147 }


	iqudc31AudioRoutingCh2ProcessPairs18SPair4 OBJECT-TYPE
		SYNTAX		RollCallString
		MAX-ACCESS		read-only
		STATUS			current
		DESCRIPTION
				"TYPE: - Display
				 PAGE: - Audio Routing-Ch2- Process Pairs 1-8 S
					Pair 4  cmdID= 63148  format=   "
		::= { iqudc31CmdEntry 63148 }


	iqudc31AudioRoutingCh2ProcessPairs18SPair5 OBJECT-TYPE
		SYNTAX		RollCallString
		MAX-ACCESS		read-only
		STATUS			current
		DESCRIPTION
				"TYPE: - Display
				 PAGE: - Audio Routing-Ch2- Process Pairs 1-8 S
					Pair 5  cmdID= 63149  format=   "
		::= { iqudc31CmdEntry 63149 }


	iqudc31AudioRoutingCh2ProcessPairs18SPair6 OBJECT-TYPE
		SYNTAX		RollCallString
		MAX-ACCESS		read-only
		STATUS			current
		DESCRIPTION
				"TYPE: - Display
				 PAGE: - Audio Routing-Ch2- Process Pairs 1-8 S
					Pair 6  cmdID= 63150  format=   "
		::= { iqudc31CmdEntry 63150 }


	iqudc31AudioRoutingCh2ProcessPairs18SPair7 OBJECT-TYPE
		SYNTAX		RollCallString
		MAX-ACCESS		read-only
		STATUS			current
		DESCRIPTION
				"TYPE: - Display
				 PAGE: - Audio Routing-Ch2- Process Pairs 1-8 S
					Pair 7  cmdID= 63151  format=   "
		::= { iqudc31CmdEntry 63151 }


	iqudc31AudioRoutingCh2ProcessPairs18SPair8 OBJECT-TYPE
		SYNTAX		RollCallString
		MAX-ACCESS		read-only
		STATUS			current
		DESCRIPTION
				"TYPE: - Display
				 PAGE: - Audio Routing-Ch2- Process Pairs 1-8 S
					Pair 8  cmdID= 63152  format=   "
		::= { iqudc31CmdEntry 63152 }


	iqudc31MenuAudioRoutingCh2NewDisplay OBJECT-TYPE
		SYNTAX		RollCallString
		MAX-ACCESS		read-only
		STATUS			current
		DESCRIPTION
				"TYPE: - Display
				 PAGE: - Audio Routing-Ch2
					New Display  cmdID= 44450  format=   "
		::= { iqudc31CmdEntry 44450 }


	iqudc31OutputPairs18OutputPair1LProcessPairsSourc52000 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 1 L
					Process Pairs Sourc  cmdID= 52000 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52000 }


	iqudc31OutputPairs18OutputPair1LInvertPhase50700 OBJECT-TYPE
		SYNTAX		INTEGER { disable(0), enable(1) }
		MAX-ACCESS		read-write
		STATUS			current
		DESCRIPTION
				"TYPE: - Checkbox
				 PAGE: - Audio Shuffle-Ch1- Output Pairs 1-8- Output Pair 1 L
					Invert Phase  cmdID= 50700 "
		::= { iqudc31CmdEntry 50700 }


	iqudc31OutputPairs18OutputPair1LControl50100 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 1 L
					Control  cmdID= 50100 
					Use Routing  value= 0  
					Tone  value= 1  
					Silence  value= 2  "
		::= { iqudc31CmdEntry 50100 }


	iqudc31OutputPairs18OutputPair1RProcessPairsSourc52008 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 1 R
					Process Pairs Sourc  cmdID= 52008 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52008 }


	iqudc31OutputPairs18OutputPair1RInvertPhase50708 OBJECT-TYPE
		SYNTAX		INTEGER { disable(0), enable(1) }
		MAX-ACCESS		read-write
		STATUS			current
		DESCRIPTION
				"TYPE: - Checkbox
				 PAGE: - Audio Shuffle-Ch1- Output Pairs 1-8- Output Pair 1 R
					Invert Phase  cmdID= 50708 "
		::= { iqudc31CmdEntry 50708 }


	iqudc31OutputPairs18OutputPair1RControl50108 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 1 R
					Control  cmdID= 50108 
					Use Routing  value= 0  
					Tone  value= 1  
					Silence  value= 2  "
		::= { iqudc31CmdEntry 50108 }


	iqudc31OutputPairs18OutputPair2LProcessPairsSourc52001 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 2 L
					Process Pairs Sourc  cmdID= 52001 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52001 }


	iqudc31OutputPairs18OutputPair2LInvertPhase50701 OBJECT-TYPE
		SYNTAX		INTEGER { disable(0), enable(1) }
		MAX-ACCESS		read-write
		STATUS			current
		DESCRIPTION
				"TYPE: - Checkbox
				 PAGE: - Audio Shuffle-Ch1- Output Pairs 1-8- Output Pair 2 L
					Invert Phase  cmdID= 50701 "
		::= { iqudc31CmdEntry 50701 }


	iqudc31OutputPairs18OutputPair2LControl50101 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 2 L
					Control  cmdID= 50101 
					Use Routing  value= 0  
					Tone  value= 1  
					Silence  value= 2  "
		::= { iqudc31CmdEntry 50101 }


	iqudc31OutputPairs18OutputPair2RProcessPairsSourc52009 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 2 R
					Process Pairs Sourc  cmdID= 52009 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52009 }


	iqudc31OutputPairs18OutputPair2RInvertPhase50709 OBJECT-TYPE
		SYNTAX		INTEGER { disable(0), enable(1) }
		MAX-ACCESS		read-write
		STATUS			current
		DESCRIPTION
				"TYPE: - Checkbox
				 PAGE: - Audio Shuffle-Ch1- Output Pairs 1-8- Output Pair 2 R
					Invert Phase  cmdID= 50709 "
		::= { iqudc31CmdEntry 50709 }


	iqudc31OutputPairs18OutputPair2RControl50109 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 2 R
					Control  cmdID= 50109 
					Use Routing  value= 0  
					Tone  value= 1  
					Silence  value= 2  "
		::= { iqudc31CmdEntry 50109 }


	iqudc31OutputPairs18OutputPair3LProcessPairsSourc52002 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 3 L
					Process Pairs Sourc  cmdID= 52002 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52002 }


	iqudc31OutputPairs18OutputPair3LInvertPhase50702 OBJECT-TYPE
		SYNTAX		INTEGER { disable(0), enable(1) }
		MAX-ACCESS		read-write
		STATUS			current
		DESCRIPTION
				"TYPE: - Checkbox
				 PAGE: - Audio Shuffle-Ch1- Output Pairs 1-8- Output Pair 3 L
					Invert Phase  cmdID= 50702 "
		::= { iqudc31CmdEntry 50702 }


	iqudc31OutputPairs18OutputPair3LControl50102 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 3 L
					Control  cmdID= 50102 
					Use Routing  value= 0  
					Tone  value= 1  
					Silence  value= 2  "
		::= { iqudc31CmdEntry 50102 }


	iqudc31OutputPairs18OutputPair3RProcessPairsSourc52010 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 3 R
					Process Pairs Sourc  cmdID= 52010 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52010 }


	iqudc31OutputPairs18OutputPair3RInvertPhase50710 OBJECT-TYPE
		SYNTAX		INTEGER { disable(0), enable(1) }
		MAX-ACCESS		read-write
		STATUS			current
		DESCRIPTION
				"TYPE: - Checkbox
				 PAGE: - Audio Shuffle-Ch1- Output Pairs 1-8- Output Pair 3 R
					Invert Phase  cmdID= 50710 "
		::= { iqudc31CmdEntry 50710 }


	iqudc31OutputPairs18OutputPair3RControl50110 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 3 R
					Control  cmdID= 50110 
					Use Routing  value= 0  
					Tone  value= 1  
					Silence  value= 2  "
		::= { iqudc31CmdEntry 50110 }


	iqudc31OutputPairs18OutputPair4LProcessPairsSourc52003 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 4 L
					Process Pairs Sourc  cmdID= 52003 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52003 }


	iqudc31OutputPairs18OutputPair4LInvertPhase50703 OBJECT-TYPE
		SYNTAX		INTEGER { disable(0), enable(1) }
		MAX-ACCESS		read-write
		STATUS			current
		DESCRIPTION
				"TYPE: - Checkbox
				 PAGE: - Audio Shuffle-Ch1- Output Pairs 1-8- Output Pair 4 L
					Invert Phase  cmdID= 50703 "
		::= { iqudc31CmdEntry 50703 }


	iqudc31OutputPairs18OutputPair4LControl50103 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 4 L
					Control  cmdID= 50103 
					Use Routing  value= 0  
					Tone  value= 1  
					Silence  value= 2  "
		::= { iqudc31CmdEntry 50103 }


	iqudc31OutputPairs18OutputPair4RProcessPairsSourc52011 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 4 R
					Process Pairs Sourc  cmdID= 52011 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52011 }


	iqudc31OutputPairs18OutputPair4RInvertPhase50711 OBJECT-TYPE
		SYNTAX		INTEGER { disable(0), enable(1) }
		MAX-ACCESS		read-write
		STATUS			current
		DESCRIPTION
				"TYPE: - Checkbox
				 PAGE: - Audio Shuffle-Ch1- Output Pairs 1-8- Output Pair 4 R
					Invert Phase  cmdID= 50711 "
		::= { iqudc31CmdEntry 50711 }


	iqudc31OutputPairs18OutputPair4RControl50111 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 4 R
					Control  cmdID= 50111 
					Use Routing  value= 0  
					Tone  value= 1  
					Silence  value= 2  "
		::= { iqudc31CmdEntry 50111 }


	iqudc31OutputPairs18OutputPair5LProcessPairsSourc52004 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 5 L
					Process Pairs Sourc  cmdID= 52004 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52004 }


	iqudc31OutputPairs18OutputPair5LInvertPhase50704 OBJECT-TYPE
		SYNTAX		INTEGER { disable(0), enable(1) }
		MAX-ACCESS		read-write
		STATUS			current
		DESCRIPTION
				"TYPE: - Checkbox
				 PAGE: - Audio Shuffle-Ch1- Output Pairs 1-8- Output Pair 5 L
					Invert Phase  cmdID= 50704 "
		::= { iqudc31CmdEntry 50704 }


	iqudc31OutputPairs18OutputPair5LControl50104 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 5 L
					Control  cmdID= 50104 
					Use Routing  value= 0  
					Tone  value= 1  
					Silence  value= 2  "
		::= { iqudc31CmdEntry 50104 }


	iqudc31OutputPairs18OutputPair5RProcessPairsSourc52012 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 5 R
					Process Pairs Sourc  cmdID= 52012 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52012 }


	iqudc31OutputPairs18OutputPair5RInvertPhase50712 OBJECT-TYPE
		SYNTAX		INTEGER { disable(0), enable(1) }
		MAX-ACCESS		read-write
		STATUS			current
		DESCRIPTION
				"TYPE: - Checkbox
				 PAGE: - Audio Shuffle-Ch1- Output Pairs 1-8- Output Pair 5 R
					Invert Phase  cmdID= 50712 "
		::= { iqudc31CmdEntry 50712 }


	iqudc31OutputPairs18OutputPair5RControl50112 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 5 R
					Control  cmdID= 50112 
					Use Routing  value= 0  
					Tone  value= 1  
					Silence  value= 2  "
		::= { iqudc31CmdEntry 50112 }


	iqudc31OutputPairs18OutputPair6LProcessPairsSourc52005 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 6 L
					Process Pairs Sourc  cmdID= 52005 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52005 }


	iqudc31OutputPairs18OutputPair6LInvertPhase50705 OBJECT-TYPE
		SYNTAX		INTEGER { disable(0), enable(1) }
		MAX-ACCESS		read-write
		STATUS			current
		DESCRIPTION
				"TYPE: - Checkbox
				 PAGE: - Audio Shuffle-Ch1- Output Pairs 1-8- Output Pair 6 L
					Invert Phase  cmdID= 50705 "
		::= { iqudc31CmdEntry 50705 }


	iqudc31OutputPairs18OutputPair6LControl50105 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 6 L
					Control  cmdID= 50105 
					Use Routing  value= 0  
					Tone  value= 1  
					Silence  value= 2  "
		::= { iqudc31CmdEntry 50105 }


	iqudc31OutputPairs18OutputPair6RProcessPairsSourc52013 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 6 R
					Process Pairs Sourc  cmdID= 52013 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52013 }


	iqudc31OutputPairs18OutputPair6RInvertPhase50713 OBJECT-TYPE
		SYNTAX		INTEGER { disable(0), enable(1) }
		MAX-ACCESS		read-write
		STATUS			current
		DESCRIPTION
				"TYPE: - Checkbox
				 PAGE: - Audio Shuffle-Ch1- Output Pairs 1-8- Output Pair 6 R
					Invert Phase  cmdID= 50713 "
		::= { iqudc31CmdEntry 50713 }


	iqudc31OutputPairs18OutputPair6RControl50113 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 6 R
					Control  cmdID= 50113 
					Use Routing  value= 0  
					Tone  value= 1  
					Silence  value= 2  "
		::= { iqudc31CmdEntry 50113 }


	iqudc31OutputPairs18OutputPair7LProcessPairsSourc52006 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 7 L
					Process Pairs Sourc  cmdID= 52006 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52006 }


	iqudc31OutputPairs18OutputPair7LInvertPhase50706 OBJECT-TYPE
		SYNTAX		INTEGER { disable(0), enable(1) }
		MAX-ACCESS		read-write
		STATUS			current
		DESCRIPTION
				"TYPE: - Checkbox
				 PAGE: - Audio Shuffle-Ch1- Output Pairs 1-8- Output Pair 7 L
					Invert Phase  cmdID= 50706 "
		::= { iqudc31CmdEntry 50706 }


	iqudc31OutputPairs18OutputPair7LControl50106 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 7 L
					Control  cmdID= 50106 
					Use Routing  value= 0  
					Tone  value= 1  
					Silence  value= 2  "
		::= { iqudc31CmdEntry 50106 }


	iqudc31OutputPairs18OutputPair7RProcessPairsSourc52014 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 7 R
					Process Pairs Sourc  cmdID= 52014 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52014 }


	iqudc31OutputPairs18OutputPair7RInvertPhase50714 OBJECT-TYPE
		SYNTAX		INTEGER { disable(0), enable(1) }
		MAX-ACCESS		read-write
		STATUS			current
		DESCRIPTION
				"TYPE: - Checkbox
				 PAGE: - Audio Shuffle-Ch1- Output Pairs 1-8- Output Pair 7 R
					Invert Phase  cmdID= 50714 "
		::= { iqudc31CmdEntry 50714 }


	iqudc31OutputPairs18OutputPair7RControl50114 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 7 R
					Control  cmdID= 50114 
					Use Routing  value= 0  
					Tone  value= 1  
					Silence  value= 2  "
		::= { iqudc31CmdEntry 50114 }


	iqudc31OutputPairs18OutputPair8LProcessPairsSourc52007 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 8 L
					Process Pairs Sourc  cmdID= 52007 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52007 }


	iqudc31OutputPairs18OutputPair8LInvertPhase50707 OBJECT-TYPE
		SYNTAX		INTEGER { disable(0), enable(1) }
		MAX-ACCESS		read-write
		STATUS			current
		DESCRIPTION
				"TYPE: - Checkbox
				 PAGE: - Audio Shuffle-Ch1- Output Pairs 1-8- Output Pair 8 L
					Invert Phase  cmdID= 50707 "
		::= { iqudc31CmdEntry 50707 }


	iqudc31OutputPairs18OutputPair8LControl50107 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 8 L
					Control  cmdID= 50107 
					Use Routing  value= 0  
					Tone  value= 1  
					Silence  value= 2  "
		::= { iqudc31CmdEntry 50107 }


	iqudc31OutputPairs18OutputPair8RProcessPairsSourc52015 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 8 R
					Process Pairs Sourc  cmdID= 52015 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 52015 }


	iqudc31OutputPairs18OutputPair8RInvertPhase50715 OBJECT-TYPE
		SYNTAX		INTEGER { disable(0), enable(1) }
		MAX-ACCESS		read-write
		STATUS			current
		DESCRIPTION
				"TYPE: - Checkbox
				 PAGE: - Audio Shuffle-Ch1- Output Pairs 1-8- Output Pair 8 R
					Invert Phase  cmdID= 50715 "
		::= { iqudc31CmdEntry 50715 }


	iqudc31OutputPairs18OutputPair8RControl50115 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 8 R
					Control  cmdID= 50115 
					Use Routing  value= 0  
					Tone  value= 1  
					Silence  value= 2  "
		::= { iqudc31CmdEntry 50115 }


	iqudc31AudioShuffleCh1OutputPairs18StPair1 OBJECT-TYPE
		SYNTAX		RollCallString
		MAX-ACCESS		read-only
		STATUS			current
		DESCRIPTION
				"TYPE: - Display
				 PAGE: - Audio Shuffle-Ch1- Output Pairs 1-8 St
					Pair 1  cmdID= 50335  format=   "
		::= { iqudc31CmdEntry 50335 }


	iqudc31AudioShuffleCh1OutputPairs18StPair2 OBJECT-TYPE
		SYNTAX		RollCallString
		MAX-ACCESS		read-only
		STATUS			current
		DESCRIPTION
				"TYPE: - Display
				 PAGE: - Audio Shuffle-Ch1- Output Pairs 1-8 St
					Pair 2  cmdID= 50336  format=   "
		::= { iqudc31CmdEntry 50336 }


	iqudc31AudioShuffleCh1OutputPairs18StPair3 OBJECT-TYPE
		SYNTAX		RollCallString
		MAX-ACCESS		read-only
		STATUS			current
		DESCRIPTION
				"TYPE: - Display
				 PAGE: - Audio Shuffle-Ch1- Output Pairs 1-8 St
					Pair 3  cmdID= 50337  format=   "
		::= { iqudc31CmdEntry 50337 }


	iqudc31AudioShuffleCh1OutputPairs18StPair4 OBJECT-TYPE
		SYNTAX		RollCallString
		MAX-ACCESS		read-only
		STATUS			current
		DESCRIPTION
				"TYPE: - Display
				 PAGE: - Audio Shuffle-Ch1- Output Pairs 1-8 St
					Pair 4  cmdID= 50338  format=   "
		::= { iqudc31CmdEntry 50338 }


	iqudc31AudioShuffleCh1OutputPairs18StPair5 OBJECT-TYPE
		SYNTAX		RollCallString
		MAX-ACCESS		read-only
		STATUS			current
		DESCRIPTION
				"TYPE: - Display
				 PAGE: - Audio Shuffle-Ch1- Output Pairs 1-8 St
					Pair 5  cmdID= 50339  format=   "
		::= { iqudc31CmdEntry 50339 }


	iqudc31AudioShuffleCh1OutputPairs18StPair6 OBJECT-TYPE
		SYNTAX		RollCallString
		MAX-ACCESS		read-only
		STATUS			current
		DESCRIPTION
				"TYPE: - Display
				 PAGE: - Audio Shuffle-Ch1- Output Pairs 1-8 St
					Pair 6  cmdID= 50340  format=   "
		::= { iqudc31CmdEntry 50340 }


	iqudc31AudioShuffleCh1OutputPairs18StPair7 OBJECT-TYPE
		SYNTAX		RollCallString
		MAX-ACCESS		read-only
		STATUS			current
		DESCRIPTION
				"TYPE: - Display
				 PAGE: - Audio Shuffle-Ch1- Output Pairs 1-8 St
					Pair 7  cmdID= 50341  format=   "
		::= { iqudc31CmdEntry 50341 }


	iqudc31AudioShuffleCh1OutputPairs18StPair8 OBJECT-TYPE
		SYNTAX		RollCallString
		MAX-ACCESS		read-only
		STATUS			current
		DESCRIPTION
				"TYPE: - Display
				 PAGE: - Audio Shuffle-Ch1- Output Pairs 1-8 St
					Pair 8  cmdID= 50342  format=   "
		::= { iqudc31CmdEntry 50342 }


	iqudc31MenuAudioShuffleCh1NewDisplay OBJECT-TYPE
		SYNTAX		RollCallString
		MAX-ACCESS		read-only
		STATUS			current
		DESCRIPTION
				"TYPE: - Display
				 PAGE: - Audio Shuffle-Ch1
					New Display  cmdID= 44461  format=   "
		::= { iqudc31CmdEntry 44461 }


	iqudc31OutputPairs18OutputPair1LProcessPairsSourc50800 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 1 L
					Process Pairs Sourc  cmdID= 50800 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50800 }


	iqudc31OutputPairs18OutputPair1LInvertPhase50816 OBJECT-TYPE
		SYNTAX		INTEGER { disable(0), enable(1) }
		MAX-ACCESS		read-write
		STATUS			current
		DESCRIPTION
				"TYPE: - Checkbox
				 PAGE: - Audio Shuffle-Ch2- Output Pairs 1-8- Output Pair 1 L
					Invert Phase  cmdID= 50816 "
		::= { iqudc31CmdEntry 50816 }


	iqudc31OutputPairs18OutputPair1LControl50832 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 1 L
					Control  cmdID= 50832 
					Use Routing  value= 0  
					Tone  value= 1  
					Silence  value= 2  "
		::= { iqudc31CmdEntry 50832 }


	iqudc31OutputPairs18OutputPair1RProcessPairsSourc50808 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 1 R
					Process Pairs Sourc  cmdID= 50808 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50808 }


	iqudc31OutputPairs18OutputPair1RInvertPhase50824 OBJECT-TYPE
		SYNTAX		INTEGER { disable(0), enable(1) }
		MAX-ACCESS		read-write
		STATUS			current
		DESCRIPTION
				"TYPE: - Checkbox
				 PAGE: - Audio Shuffle-Ch2- Output Pairs 1-8- Output Pair 1 R
					Invert Phase  cmdID= 50824 "
		::= { iqudc31CmdEntry 50824 }


	iqudc31OutputPairs18OutputPair1RControl50840 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 1 R
					Control  cmdID= 50840 
					Use Routing  value= 0  
					Tone  value= 1  
					Silence  value= 2  "
		::= { iqudc31CmdEntry 50840 }


	iqudc31OutputPairs18OutputPair2LProcessPairsSourc50801 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 2 L
					Process Pairs Sourc  cmdID= 50801 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50801 }


	iqudc31OutputPairs18OutputPair2LInvertPhase50817 OBJECT-TYPE
		SYNTAX		INTEGER { disable(0), enable(1) }
		MAX-ACCESS		read-write
		STATUS			current
		DESCRIPTION
				"TYPE: - Checkbox
				 PAGE: - Audio Shuffle-Ch2- Output Pairs 1-8- Output Pair 2 L
					Invert Phase  cmdID= 50817 "
		::= { iqudc31CmdEntry 50817 }


	iqudc31OutputPairs18OutputPair2LControl50833 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 2 L
					Control  cmdID= 50833 
					Use Routing  value= 0  
					Tone  value= 1  
					Silence  value= 2  "
		::= { iqudc31CmdEntry 50833 }


	iqudc31OutputPairs18OutputPair2RProcessPairsSourc50809 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 2 R
					Process Pairs Sourc  cmdID= 50809 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50809 }


	iqudc31OutputPairs18OutputPair2RInvertPhase50825 OBJECT-TYPE
		SYNTAX		INTEGER { disable(0), enable(1) }
		MAX-ACCESS		read-write
		STATUS			current
		DESCRIPTION
				"TYPE: - Checkbox
				 PAGE: - Audio Shuffle-Ch2- Output Pairs 1-8- Output Pair 2 R
					Invert Phase  cmdID= 50825 "
		::= { iqudc31CmdEntry 50825 }


	iqudc31OutputPairs18OutputPair2RControl50841 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 2 R
					Control  cmdID= 50841 
					Use Routing  value= 0  
					Tone  value= 1  
					Silence  value= 2  "
		::= { iqudc31CmdEntry 50841 }


	iqudc31OutputPairs18OutputPair3LProcessPairsSourc50802 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 3 L
					Process Pairs Sourc  cmdID= 50802 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50802 }


	iqudc31OutputPairs18OutputPair3LInvertPhase50818 OBJECT-TYPE
		SYNTAX		INTEGER { disable(0), enable(1) }
		MAX-ACCESS		read-write
		STATUS			current
		DESCRIPTION
				"TYPE: - Checkbox
				 PAGE: - Audio Shuffle-Ch2- Output Pairs 1-8- Output Pair 3 L
					Invert Phase  cmdID= 50818 "
		::= { iqudc31CmdEntry 50818 }


	iqudc31OutputPairs18OutputPair3LControl50834 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 3 L
					Control  cmdID= 50834 
					Use Routing  value= 0  
					Tone  value= 1  
					Silence  value= 2  "
		::= { iqudc31CmdEntry 50834 }


	iqudc31OutputPairs18OutputPair3RProcessPairsSourc50810 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 3 R
					Process Pairs Sourc  cmdID= 50810 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50810 }


	iqudc31OutputPairs18OutputPair3RInvertPhase50826 OBJECT-TYPE
		SYNTAX		INTEGER { disable(0), enable(1) }
		MAX-ACCESS		read-write
		STATUS			current
		DESCRIPTION
				"TYPE: - Checkbox
				 PAGE: - Audio Shuffle-Ch2- Output Pairs 1-8- Output Pair 3 R
					Invert Phase  cmdID= 50826 "
		::= { iqudc31CmdEntry 50826 }


	iqudc31OutputPairs18OutputPair3RControl50842 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 3 R
					Control  cmdID= 50842 
					Use Routing  value= 0  
					Tone  value= 1  
					Silence  value= 2  "
		::= { iqudc31CmdEntry 50842 }


	iqudc31OutputPairs18OutputPair4LProcessPairsSourc50803 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 4 L
					Process Pairs Sourc  cmdID= 50803 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50803 }


	iqudc31OutputPairs18OutputPair4LInvertPhase50819 OBJECT-TYPE
		SYNTAX		INTEGER { disable(0), enable(1) }
		MAX-ACCESS		read-write
		STATUS			current
		DESCRIPTION
				"TYPE: - Checkbox
				 PAGE: - Audio Shuffle-Ch2- Output Pairs 1-8- Output Pair 4 L
					Invert Phase  cmdID= 50819 "
		::= { iqudc31CmdEntry 50819 }


	iqudc31OutputPairs18OutputPair4LControl50835 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 4 L
					Control  cmdID= 50835 
					Use Routing  value= 0  
					Tone  value= 1  
					Silence  value= 2  "
		::= { iqudc31CmdEntry 50835 }


	iqudc31OutputPairs18OutputPair4RProcessPairsSourc50811 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 4 R
					Process Pairs Sourc  cmdID= 50811 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50811 }


	iqudc31OutputPairs18OutputPair4RInvertPhase50827 OBJECT-TYPE
		SYNTAX		INTEGER { disable(0), enable(1) }
		MAX-ACCESS		read-write
		STATUS			current
		DESCRIPTION
				"TYPE: - Checkbox
				 PAGE: - Audio Shuffle-Ch2- Output Pairs 1-8- Output Pair 4 R
					Invert Phase  cmdID= 50827 "
		::= { iqudc31CmdEntry 50827 }


	iqudc31OutputPairs18OutputPair4RControl50843 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 4 R
					Control  cmdID= 50843 
					Use Routing  value= 0  
					Tone  value= 1  
					Silence  value= 2  "
		::= { iqudc31CmdEntry 50843 }


	iqudc31OutputPairs18OutputPair5LProcessPairsSourc50804 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 5 L
					Process Pairs Sourc  cmdID= 50804 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50804 }


	iqudc31OutputPairs18OutputPair5LInvertPhase50820 OBJECT-TYPE
		SYNTAX		INTEGER { disable(0), enable(1) }
		MAX-ACCESS		read-write
		STATUS			current
		DESCRIPTION
				"TYPE: - Checkbox
				 PAGE: - Audio Shuffle-Ch2- Output Pairs 1-8- Output Pair 5 L
					Invert Phase  cmdID= 50820 "
		::= { iqudc31CmdEntry 50820 }


	iqudc31OutputPairs18OutputPair5LControl50836 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 5 L
					Control  cmdID= 50836 
					Use Routing  value= 0  
					Tone  value= 1  
					Silence  value= 2  "
		::= { iqudc31CmdEntry 50836 }


	iqudc31OutputPairs18OutputPair5RProcessPairsSourc50812 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 5 R
					Process Pairs Sourc  cmdID= 50812 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50812 }


	iqudc31OutputPairs18OutputPair5RInvertPhase50828 OBJECT-TYPE
		SYNTAX		INTEGER { disable(0), enable(1) }
		MAX-ACCESS		read-write
		STATUS			current
		DESCRIPTION
				"TYPE: - Checkbox
				 PAGE: - Audio Shuffle-Ch2- Output Pairs 1-8- Output Pair 5 R
					Invert Phase  cmdID= 50828 "
		::= { iqudc31CmdEntry 50828 }


	iqudc31OutputPairs18OutputPair5RControl50844 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 5 R
					Control  cmdID= 50844 
					Use Routing  value= 0  
					Tone  value= 1  
					Silence  value= 2  "
		::= { iqudc31CmdEntry 50844 }


	iqudc31OutputPairs18OutputPair6LProcessPairsSourc50805 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 6 L
					Process Pairs Sourc  cmdID= 50805 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50805 }


	iqudc31OutputPairs18OutputPair6LInvertPhase50821 OBJECT-TYPE
		SYNTAX		INTEGER { disable(0), enable(1) }
		MAX-ACCESS		read-write
		STATUS			current
		DESCRIPTION
				"TYPE: - Checkbox
				 PAGE: - Audio Shuffle-Ch2- Output Pairs 1-8- Output Pair 6 L
					Invert Phase  cmdID= 50821 "
		::= { iqudc31CmdEntry 50821 }


	iqudc31OutputPairs18OutputPair6LControl50837 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 6 L
					Control  cmdID= 50837 
					Use Routing  value= 0  
					Tone  value= 1  
					Silence  value= 2  "
		::= { iqudc31CmdEntry 50837 }


	iqudc31OutputPairs18OutputPair6RProcessPairsSourc50813 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 6 R
					Process Pairs Sourc  cmdID= 50813 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50813 }


	iqudc31OutputPairs18OutputPair6RInvertPhase50829 OBJECT-TYPE
		SYNTAX		INTEGER { disable(0), enable(1) }
		MAX-ACCESS		read-write
		STATUS			current
		DESCRIPTION
				"TYPE: - Checkbox
				 PAGE: - Audio Shuffle-Ch2- Output Pairs 1-8- Output Pair 6 R
					Invert Phase  cmdID= 50829 "
		::= { iqudc31CmdEntry 50829 }


	iqudc31OutputPairs18OutputPair6RControl50845 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 6 R
					Control  cmdID= 50845 
					Use Routing  value= 0  
					Tone  value= 1  
					Silence  value= 2  "
		::= { iqudc31CmdEntry 50845 }


	iqudc31OutputPairs18OutputPair7LProcessPairsSourc50806 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 7 L
					Process Pairs Sourc  cmdID= 50806 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50806 }


	iqudc31OutputPairs18OutputPair7LInvertPhase50822 OBJECT-TYPE
		SYNTAX		INTEGER { disable(0), enable(1) }
		MAX-ACCESS		read-write
		STATUS			current
		DESCRIPTION
				"TYPE: - Checkbox
				 PAGE: - Audio Shuffle-Ch2- Output Pairs 1-8- Output Pair 7 L
					Invert Phase  cmdID= 50822 "
		::= { iqudc31CmdEntry 50822 }


	iqudc31OutputPairs18OutputPair7LControl50838 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 7 L
					Control  cmdID= 50838 
					Use Routing  value= 0  
					Tone  value= 1  
					Silence  value= 2  "
		::= { iqudc31CmdEntry 50838 }


	iqudc31OutputPairs18OutputPair7RProcessPairsSourc50814 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 7 R
					Process Pairs Sourc  cmdID= 50814 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50814 }


	iqudc31OutputPairs18OutputPair7RInvertPhase50830 OBJECT-TYPE
		SYNTAX		INTEGER { disable(0), enable(1) }
		MAX-ACCESS		read-write
		STATUS			current
		DESCRIPTION
				"TYPE: - Checkbox
				 PAGE: - Audio Shuffle-Ch2- Output Pairs 1-8- Output Pair 7 R
					Invert Phase  cmdID= 50830 "
		::= { iqudc31CmdEntry 50830 }


	iqudc31OutputPairs18OutputPair7RControl50846 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 7 R
					Control  cmdID= 50846 
					Use Routing  value= 0  
					Tone  value= 1  
					Silence  value= 2  "
		::= { iqudc31CmdEntry 50846 }


	iqudc31OutputPairs18OutputPair8LProcessPairsSourc50807 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 8 L
					Process Pairs Sourc  cmdID= 50807 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50807 }


	iqudc31OutputPairs18OutputPair8LInvertPhase50823 OBJECT-TYPE
		SYNTAX		INTEGER { disable(0), enable(1) }
		MAX-ACCESS		read-write
		STATUS			current
		DESCRIPTION
				"TYPE: - Checkbox
				 PAGE: - Audio Shuffle-Ch2- Output Pairs 1-8- Output Pair 8 L
					Invert Phase  cmdID= 50823 "
		::= { iqudc31CmdEntry 50823 }


	iqudc31OutputPairs18OutputPair8LControl50839 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 8 L
					Control  cmdID= 50839 
					Use Routing  value= 0  
					Tone  value= 1  
					Silence  value= 2  "
		::= { iqudc31CmdEntry 50839 }


	iqudc31OutputPairs18OutputPair8RProcessPairsSourc50815 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 8 R
					Process Pairs Sourc  cmdID= 50815 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc31CmdEntry 50815 }


	iqudc31OutputPairs18OutputPair8RInvertPhase50831 OBJECT-TYPE
		SYNTAX		INTEGER { disable(0), enable(1) }
		MAX-ACCESS		read-write
		STATUS			current
		DESCRIPTION
				"TYPE: - Checkbox
				 PAGE: - Audio Shuffle-Ch2- Output Pairs 1-8- Output Pair 8 R
					Invert Phase  cmdID= 50831 "
		::= { iqudc31CmdEntry 50831 }


	iqudc31OutputPairs18OutputPair8RControl50847 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 8 R
					Control  cmdID= 50847 
					Use Routing  value= 0  
					Tone  value= 1  
					Silence  value= 2  "
		::= { iqudc31CmdEntry 50847 }


	iqudc31AudioShuffleCh2OutputPairs18StPair1 OBJECT-TYPE
		SYNTAX		RollCallString
		MAX-ACCESS		read-only
		STATUS			current
		DESCRIPTION
				"TYPE: - Display
				 PAGE: - Audio Shuffle-Ch2- Output Pairs 1-8 St
					Pair 1  cmdID= 50348  format=   "
		::= { iqudc31CmdEntry 50348 }


	iqudc31AudioShuffleCh2OutputPairs18StPair2 OBJECT-TYPE
		SYNTAX		RollCallString
		MAX-ACCESS		read-only
		STATUS			current
		DESCRIPTION
				"TYPE: - Display
				 PAGE: - Audio Shuffle-Ch2- Output Pairs 1-8 St
					Pair 2  cmdID= 50349  format=   "
		::= { iqudc31CmdEntry 50349 }


	iqudc31AudioShuffleCh2OutputPairs18StPair3 OBJECT-TYPE
		SYNTAX		RollCallString
		MAX-ACCESS		read-only
		STATUS			current
		DESCRIPTION
				"TYPE: - Display
				 PAGE: - Audio Shuffle-Ch2- Output Pairs 1-8 St
					Pair 3  cmdID= 50350  format=   "
		::= { iqudc31CmdEntry 50350 }


	iqudc31AudioShuffleCh2OutputPairs18StPair4 OBJECT-TYPE
		SYNTAX		RollCallString
		MAX-ACCESS		read-only
		STATUS			current
		DESCRIPTION
				"TYPE: - Display
				 PAGE: - Audio Shuffle-Ch2- Output Pairs 1-8 St
					Pair 4  cmdID= 50351  format=   "
		::= { iqudc31CmdEntry 50351 }


	iqudc31AudioShuffleCh2OutputPairs18StPair5 OBJECT-TYPE
		SYNTAX		RollCallString
		MAX-ACCESS		read-only
		STATUS			current
		DESCRIPTION
				"TYPE: - Display
				 PAGE: - Audio Shuffle-Ch2- Output Pairs 1-8 St
					Pair 5  cmdID= 50352  format=   "
		::= { iqudc31CmdEntry 50352 }


	iqudc31AudioShuffleCh2OutputPairs18StPair6 OBJECT-TYPE
		SYNTAX		RollCallString
		MAX-ACCESS		read-only
		STATUS			current
		DESCRIPTION
				"TYPE: - Display
				 PAGE: - Audio Shuffle-Ch2- Output Pairs 1-8 St
					Pair 6  cmdID= 50353  format=   "
		::= { iqudc31CmdEntry 50353 }


	iqudc31AudioShuffleCh2OutputPairs18StPair7 OBJECT-TYPE
		SYNTAX		RollCallString
		MAX-ACCESS		read-only
		STATUS			current
		DESCRIPTION
				"TYPE: - Display
				 PAGE: - Audio Shuffle-Ch2- Output Pairs 1-8 St
					Pair 7  cmdID= 50354  format=   "
		::= { iqudc31CmdEntry 50354 }


	iqudc31AudioShuffleCh2OutputPairs18StPair8 OBJECT-TYPE
		SYNTAX		RollCallString
		MAX-ACCESS		read-only
		STATUS			current
		DESCRIPTION
				"TYPE: - Display
				 PAGE: - Audio Shuffle-Ch2- Output Pairs 1-8 St
					Pair 8  cmdID= 50355  format=   "
		::= { iqudc31CmdEntry 50355 }


	iqudc31MenuAudioShuffleCh2NewDisplay OBJECT-TYPE
		SYNTAX		RollCallString
		MAX-ACCESS		read-only
		STATUS			current
		DESCRIPTION
				"TYPE: - Display
				 PAGE: - Audio Shuffle-Ch2
					New Display  cmdID= 44457  format=   "
		::= { iqudc31CmdEntry 44457 }


	iqudc31AudioControlCh1GainPair1L OBJECT-TYPE
		SYNTAX		INTEGER
		MAX-ACCESS		read-write
		STATUS			current
		DESCRIPTION
				"TYPE: - Number
				 PAGE: - Audio Control-Ch1
					Pair 1 L  cmdID= 50228  min= -180  max= 180  step= 1  format= %0.1fdB  div_scale= 10 
					Min = -18.0dB  Max = 18.0dB  Step = 0.1dB "
		::= { iqudc31CmdEntry 50228 }


	iqudc31AudioControlCh1GainPair1R OBJECT-TYPE
		SYNTAX		INTEGER
		MAX-ACCESS		read-write
		STATUS			current
		DESCRIPTION
				"TYPE: - Number
				 PAGE: - Audio Control-Ch1
					Pair 1 R  cmdID= 50229  min= -180  max= 180  step= 1  format= %0.1fdB  div_scale= 10 
					Min = -18.0dB  Max = 18.0dB  Step = 0.1dB "
		::= { iqudc31CmdEntry 50229 }


	iqudc31AudioControlCh1GainPair2L OBJECT-TYPE
		SYNTAX		INTEGER
		MAX-ACCESS		read-write
		STATUS			current
		DESCRIPTION
				"TYPE: - Number
				 PAGE: - Audio Control-Ch1
					Pair 2 L  cmdID= 50202  min= -180  max= 180  step= 1  format= %0.1fdB  div_scale= 10 
					Min = -18.0dB  Max = 18.0dB  Step = 0.1dB "
		::= { iqudc31CmdEntry 50202 }


	iqudc31AudioControlCh1GainPair2R OBJECT-TYPE
		SYNTAX		INTEGER
		MAX-ACCESS		read-write
		STATUS			current
		DESCRIPTION
				"TYPE: - Number
				 PAGE: - Audio Control-Ch1
					Pair 2 R  cmdID= 50231  min= -180  max= 180  step= 1  format= %0.1fdB  div_scale= 10 
					Min = -18.0dB  Max = 18.0dB  Step = 0.1dB "
		::= { iqudc31CmdEntry 50231 }


	iqudc31AudioControlCh1GainPair3L OBJECT-TYPE
		SYNTAX		INTEGER
		MAX-ACCESS		read-write
		STATUS			current
		DESCRIPTION
				"TYPE: - Number
				 PAGE: - Audio Control-Ch1
					Pair 3 L  cmdID= 50204  min= -180  max= 180  step= 1  format= %0.1fdB  div_scale= 10 
					Min = -18.0dB  Max = 18.0dB  Step = 0.1dB "
		::= { iqudc31CmdEntry 50204 }


	iqudc31AudioControlCh1GainPair3R OBJECT-TYPE
		SYNTAX		INTEGER
		MAX-ACCESS		read-write
		STATUS			current
		DESCRIPTION
				"TYPE: - Number
				 PAGE: - Audio Control-Ch1
					Pair 3 R  cmdID= 50205  min= -180  max= 180  step= 1  format= %0.1fdB  div_scale= 10 
					Min = -18.0dB  Max = 18.0dB  Step = 0.1dB "
		::= { iqudc31CmdEntry 50205 }


	iqudc31AudioControlCh1GainPair4L OBJECT-TYPE
		SYNTAX		INTEGER
		MAX-ACCESS		read-write
		STATUS			current
		DESCRIPTION
				"TYPE: - Number
				 PAGE: - Audio Control-Ch1
					Pair 4 L  cmdID= 50206  min= -180  max= 180  step= 1  format= %0.1fdB  div_scale= 10 
					Min = -18.0dB  Max = 18.0dB  Step = 0.1dB "
		::= { iqudc31CmdEntry 50206 }


	iqudc31AudioControlCh1GainPair4R OBJECT-TYPE
		SYNTAX		INTEGER
		MAX-ACCESS		read-write
		STATUS			current
		DESCRIPTION
				"TYPE: - Number
				 PAGE: - Audio Control-Ch1
					Pair 4 R  cmdID= 50235  min= -180  max= 180  step= 1  format= %0.1fdB  div_scale= 10 
					Min = -18.0dB  Max = 18.0dB  Step = 0.1dB "
		::= { iqudc31CmdEntry 50235 }


	iqudc31AudioControlCh1GainPair5L OBJECT-TYPE
		SYNTAX		INTEGER
		MAX-ACCESS		read-write
		STATUS			current
		DESCRIPTION
				"TYPE: - Number
				 PAGE: - Audio Control-Ch1
					Pair 5 L  cmdID= 50208  min= -180  max= 180  step= 1  format= %0.1fdB  div_scale= 10 
					Min = -18.0dB  Max = 18.0dB  Step = 0.1dB "
		::= { iqudc31CmdEntry 50208 }


	iqudc31AudioControlCh1GainPair5R OBJECT-TYPE
		SYNTAX		INTEGER
		MAX-ACCESS		read-write
		STATUS			current
		DESCRIPTION
				"TYPE: - Number
				 PAGE: - Audio Control-Ch1
					Pair 5 R  cmdID= 50209  min= -180  max= 180  step= 1  format= %0.1fdB  div_scale= 10 
					Min = -18.0dB  Max = 18.0dB  Step = 0.1dB "
		::= { iqudc31CmdEntry 50209 }


	iqudc31AudioControlCh1GainPair6L OBJECT-TYPE
		SYNTAX		INTEGER
		MAX-ACCESS		read-write
		STATUS			current
		DESCRIPTION
				"TYPE: - Number
				 PAGE: - Audio Control-Ch1
					Pair 6 L  cmdID= 50210  min= -180  max= 180  step= 1  format= %0.1fdB  div_scale= 10 
					Min = -18.0dB  Max = 18.0dB  Step = 0.1dB "
		::= { iqudc31CmdEntry 50210 }


	iqudc31AudioControlCh1GainPair6R OBJECT-TYPE
		SYNTAX		INTEGER
		MAX-ACCESS		read-write
		STATUS			current
		DESCRIPTION
				"TYPE: - Number
				 PAGE: - Audio Control-Ch1
					Pair 6 R  cmdID= 50211  min= -180  max= 180  step= 1  format= %0.1fdB  div_scale= 10 
					Min = -18.0dB  Max = 18.0dB  Step = 0.1dB "
		::= { iqudc31CmdEntry 50211 }


	iqudc31AudioControlCh1GainPair7L OBJECT-TYPE
		SYNTAX		INTEGER
		MAX-ACCESS		read-write
		STATUS			current
		DESCRIPTION
				"TYPE: - Number
				 PAGE: - Audio Control-Ch1
					Pair 7 L  cmdID= 50238  min= -180  max= 180  step= 1  format= %0.1fdB  div_scale= 10 
					Min = -18.0dB  Max = 18.0dB  Step = 0.1dB "
		::= { iqudc31CmdEntry 50238 }


	iqudc31AudioControlCh1GainPair7R OBJECT-TYPE
		SYNTAX		INTEGER
		MAX-ACCESS		read-write
		STATUS			current
		DESCRIPTION
				"TYPE: - Number
				 PAGE: - Audio Control-Ch1
					Pair 7 R  cmdID= 50239  min= -180  max= 180  step= 1  format= %0.1fdB  div_scale= 10 
					Min = -18.0dB  Max = 18.0dB  Step = 0.1dB "
		::= { iqudc31CmdEntry 50239 }


	iqudc31AudioControlCh1GainPair8L OBJECT-TYPE
		SYNTAX		INTEGER
		MAX-ACCESS		read-write
		STATUS			current
		DESCRIPTION
				"TYPE: - Number
				 PAGE: - Audio Control-Ch1
					Pair 8 L  cmdID= 50240  min= -180  max= 180  step= 1  format= %0.1fdB  div_scale= 10 
					Min = -18.0dB  Max = 18.0dB  Step = 0.1dB "
		::= { iqudc31CmdEntry 50240 }


	iqudc31AudioControlCh1GainPair8R OBJECT-TYPE
		SYNTAX		INTEGER
		MAX-ACCESS		read-write
		STATUS			current
		DESCRIPTION
				"TYPE: - Number
				 PAGE: - Audio Control-Ch1
					Pair 8 R  cmdID= 50241  min= -180  max= 180  step= 1  format= %0.1fdB  div_scale= 10 
					Min = -18.0dB  Max = 18.0dB  Step = 0.1dB "
		::= { iqudc31CmdEntry 50241 }


	iqudc31MenuAudioControlCh1ToneFrequency OBJECT-TYPE
		SYNTAX		INTEGER
		MAX-ACCESS		read-write
		STATUS			current
		DESCRIPTION
				"TYPE: - Number
				 PAGE: - Audio Control-Ch1
					Tone Frequency  cmdID= 50500  min= 100  max= 10000  step= 100  format= %0.1f KHz  div_scale= 1000 
					Min = 0.1 KHz  Max = 10.0 KHz  Step = 0.1 KHz "
		::= { iqudc31CmdEntry 50500 }


	iqudc31MenuAudioControlCh1DolbyEAlignmentO OBJECT-TYPE
		SYNTAX		INTEGER
		MAX-ACCESS		read-write
		STATUS			current
		DESCRIPTION
				"TYPE: - Number
				 PAGE: - Audio Control-Ch1
					Dolby E Alignment O  cmdID= 50502  min= -10  max= 10  step= 1  format= %0.0f Lines  div_scale= 1 
					Min = -10 Lines  Max = 10 Lines  Step = 1 Lines "
		::= { iqudc31CmdEntry 50502 }


	iqudc31DelayGlobalDelayPairOPair150319 OBJECT-TYPE
		SYNTAX		INTEGER
		MAX-ACCESS		read-write
		STATUS			current
		DESCRIPTION
				"TYPE: - Number
				 PAGE: - Audio Control-Ch1
					Pair 1  cmdID= 50319  min= -40  max= 200  step= 1  format= %0.0f ms  div_scale= 1 
					Min = -40 ms  Max = 200 ms  Step = 1 ms "
		::= { iqudc31CmdEntry 50319 }


	iqudc31DelayGlobalDelayPairOPair1Total50327 OBJECT-TYPE
		SYNTAX		RollCallString
		MAX-ACCESS		read-only
		STATUS			current
		DESCRIPTION
				"TYPE: - Display
				 PAGE: - Audio Control-Ch1
					Pair 1 Total  cmdID= 50327  format=   "
		::= { iqudc31CmdEntry 50327 }


	iqudc31DelayGlobalDelayPairOPair250320 OBJECT-TYPE
		SYNTAX		INTEGER
		MAX-ACCESS		read-write
		STATUS			current
		DESCRIPTION
				"TYPE: - Number
				 PAGE: - Audio Control-Ch1
					Pair 2  cmdID= 50320  min= -40  max= 200  step= 1  format= %0.0f ms  div_scale= 1 
					Min = -40 ms  Max = 200 ms  Step = 1 ms "
		::= { iqudc31CmdEntry 50320 }


	iqudc31DelayGlobalDelayPairOPair2Total50328 OBJECT-TYPE
		SYNTAX		RollCallString
		MAX-ACCESS		read-only
		STATUS			current
		DESCRIPTION
				"TYPE: - Display
				 PAGE: - Audio Control-Ch1
					Pair 2 Total  cmdID= 50328  format=   "
		::= { iqudc31CmdEntry 50328 }


	iqudc31DelayGlobalDelayPairOPair350321 OBJECT-TYPE
		SYNTAX		INTEGER
		MAX-ACCESS		read-write
		STATUS			current
		DESCRIPTION
				"TYPE: - Number
				 PAGE: - Audio Control-Ch1
					Pair 3  cmdID= 50321  min= -40  max= 200  step= 1  format= %0.0f ms  div_scale= 1 
					Min = -40 ms  Max = 200 ms  Step = 1 ms "
		::= { iqudc31CmdEntry 50321 }


	iqudc31DelayGlobalDelayPairOPair3Total50329 OBJECT-TYPE
		SYNTAX		RollCallString
		MAX-ACCESS		read-only
		STATUS			current
		DESCRIPTION
				"TYPE: - Display
				 PAGE: - Audio Control-Ch1
					Pair 3 Total  cmdID= 50329  format=   "
		::= { iqudc31CmdEntry 50329 }


	iqudc31DelayGlobalDelayPairOPair450322 OBJECT-TYPE
		SYNTAX		INTEGER
		MAX-ACCESS		read-write
		STATUS			current
		DESCRIPTION
				"TYPE: - Number
				 PAGE: - Audio Control-Ch1
					Pair 4  cmdID= 50322  min= -40  max= 200  step= 1  format= %0.0f ms  div_scale= 1 
					Min = -40 ms  Max = 200 ms  Step = 1 ms "
		::= { iqudc31CmdEntry 50322 }


	iqudc31DelayGlobalDelayPairOPair4Total50330 OBJECT-TYPE
		SYNTAX		RollCallString
		MAX-ACCESS		read-only
		STATUS			current
		DESCRIPTION
				"TYPE: - Display
				 PAGE: - Audio Control-Ch1
					Pair 4 Total  cmdID= 50330  format=   "
		::= { iqudc31CmdEntry 50330 }


	iqudc31DelayGlobalDelayPairOPair550323 OBJECT-TYPE
		SYNTAX		INTEGER
		MAX-ACCESS		read-write
		STATUS			current
		DESCRIPTION
				"TYPE: - Number
				 PAGE: - Audio Control-Ch1
					Pair 5  cmdID= 50323  min= -40  max= 200  step= 1  format= %0.0f ms  div_scale= 1 
					Min = -40 ms  Max = 200 ms  Step = 1 ms "
		::= { iqudc31CmdEntry 50323 }


	iqudc31DelayGlobalDelayPairOPair5Total50331 OBJECT-TYPE
		SYNTAX		RollCallString
		MAX-ACCESS		read-only
		STATUS			current
		DESCRIPTION
				"TYPE: - Display
				 PAGE: - Audio Control-Ch1
					Pair 5 Total  cmdID= 50331  format=   "
		::= { iqudc31CmdEntry 50331 }


	iqudc31DelayGlobalDelayPairOPair650324 OBJECT-TYPE
		SYNTAX		INTEGER
		MAX-ACCESS		read-write
		STATUS			current
		DESCRIPTION
				"TYPE: - Number
				 PAGE: - Audio Control-Ch1
					Pair 6  cmdID= 50324  min= -40  max= 200  step= 1  format= %0.0f ms  div_scale= 1 
					Min = -40 ms  Max = 200 ms  Step = 1 ms "
		::= { iqudc31CmdEntry 50324 }


	iqudc31DelayGlobalDelayPairOPair6Total50332 OBJECT-TYPE
		SYNTAX		RollCallString
		MAX-ACCESS		read-only
		STATUS			current
		DESCRIPTION
				"TYPE: - Display
				 PAGE: - Audio Control-Ch1
					Pair 6 Total  cmdID= 50332  format=   "
		::= { iqudc31CmdEntry 50332 }


	iqudc31DelayGlobalDelayPairOPair750325 OBJECT-TYPE
		SYNTAX		INTEGER
		MAX-ACCESS		read-write
		STATUS			current
		DESCRIPTION
				"TYPE: - Number
				 PAGE: - Audio Control-Ch1
					Pair 7  cmdID= 50325  min= -40  max= 200  step= 1  format= %0.0f ms  div_scale= 1 
					Min = -40 ms  Max = 200 ms  Step = 1 ms "
		::= { iqudc31CmdEntry 50325 }


	iqudc31DelayGlobalDelayPairOPair7Total50333 OBJECT-TYPE
		SYNTAX		RollCallString
		MAX-ACCESS		read-only
		STATUS			current
		DESCRIPTION
				"TYPE: - Display
				 PAGE: - Audio Control-Ch1
					Pair 7 Total  cmdID= 50333  format=   "
		::= { iqudc31CmdEntry 50333 }


	iqudc31DelayGlobalDelayPairOPair850326 OBJECT-TYPE
		SYNTAX		INTEGER
		MAX-ACCESS		read-write
		STATUS			current
		DESCRIPTION
				"TYPE: - Number
				 PAGE: - Audio Control-Ch1
					Pair 8  cmdID= 50326  min= -40  max= 200  step= 1  format= %0.0f ms  div_scale= 1 
					Min = -40 ms  Max = 200 ms  Step = 1 ms "
		::= { iqudc31CmdEntry 50326 }


	iqudc31DelayGlobalDelayPairOPair8Total50334 OBJECT-TYPE
		SYNTAX		RollCallString
		MAX-ACCESS		read-only
		STATUS			current
		DESCRIPTION
				"TYPE: - Display
				 PAGE: - Audio Control-Ch1
					Pair 8 Total  cmdID= 50334  format=   "
		::= { iqudc31CmdEntry 50334 }


	iqudc31AudioControlCh1GlobalDelayAudio OBJECT-TYPE
		SYNTAX		INTEGER
		MAX-ACCESS		read-write
		STATUS			current
		DESCRIPTION
				"TYPE: - Number
				 PAGE: - Audio Control-Ch1
					Audio  cmdID= 50316  min= -40  max= 200  step= 1  format= %0.0f ms  div_scale= 1 
					Min = -40 ms  Max = 200 ms  Step = 1 ms "
		::= { iqudc31CmdEntry 50316 }


	iqudc31AudioControlCh1GlobalDelayAudioTotal OBJECT-TYPE
		SYNTAX		RollCallString
		MAX-ACCESS		read-only
		STATUS			current
		DESCRIPTION
				"TYPE: - Display
				 PAGE: - Audio Control-Ch1
					Audio Total  cmdID= 50301  format=   "
		::= { iqudc31CmdEntry 50301 }


	iqudc31AudioControlCh1GlobalDelayVideoTotal OBJECT-TYPE
		SYNTAX		RollCallString
		MAX-ACCESS		read-only
		STATUS			current
		DESCRIPTION
				"TYPE: - Display
				 PAGE: - Audio Control-Ch1
					Video Total  cmdID= 50302  format=   "
		::= { iqudc31CmdEntry 50302 }


	iqudc31MenuAudioControlCh1NewDisplay OBJECT-TYPE
		SYNTAX		RollCallString
		MAX-ACCESS		read-only
		STATUS			current
		DESCRIPTION
				"TYPE: - Display
				 PAGE: - Audio Control-Ch1
					New Display  cmdID= 44462  format=   "
		::= { iqudc31CmdEntry 44462 }


	iqudc31AudioControlCh2GainPair1L OBJECT-TYPE
		SYNTAX		INTEGER
		MAX-ACCESS		read-write
		STATUS			current
		DESCRIPTION
				"TYPE: - Number
				 PAGE: - Audio Control-Ch2
					Pair 1 L  cmdID= 50300  min= -180  max= 180  step= 1  format= %0.1fdB  div_scale= 10 
					Min = -18.0dB  Max = 18.0dB  Step = 0.1dB "
		::= { iqudc31CmdEntry 50300 }


	iqudc31AudioControlCh2GainPair1R OBJECT-TYPE
		SYNTAX		INTEGER
		MAX-ACCESS		read-write
		STATUS			current
		DESCRIPTION
				"TYPE: - Number
				 PAGE: - Audio Control-Ch2
					Pair 1 R  cmdID= 50317  min= -180  max= 180  step= 1  format= %0.1fdB  div_scale= 10 
					Min = -18.0dB  Max = 18.0dB  Step = 0.1dB "
		::= { iqudc31CmdEntry 50317 }


	iqudc31AudioControlCh2GainPair2L OBJECT-TYPE
		SYNTAX		INTEGER
		MAX-ACCESS		read-write
		STATUS			current
		DESCRIPTION
				"TYPE: - Number
				 PAGE: - Audio Control-Ch2
					Pair 2 L  cmdID= 50318  min= -180  max= 180  step= 1  format= %0.1fdB  div_scale= 10 
					Min = -18.0dB  Max = 18.0dB  Step = 0.1dB "
		::= { iqudc31CmdEntry 50318 }


	iqudc31AudioControlCh2GainPair2R OBJECT-TYPE
		SYNTAX		INTEGER
		MAX-ACCESS		read-write
		STATUS			current
		DESCRIPTION
				"TYPE: - Number
				 PAGE: - Audio Control-Ch2
					Pair 2 R  cmdID= 50303  min= -180  max= 180  step= 1  format= %0.1fdB  div_scale= 10 
					Min = -18.0dB  Max = 18.0dB  Step = 0.1dB "
		::= { iqudc31CmdEntry 50303 }


	iqudc31AudioControlCh2GainPair3L OBJECT-TYPE
		SYNTAX		INTEGER
		MAX-ACCESS		read-write
		STATUS			current
		DESCRIPTION
				"TYPE: - Number
				 PAGE: - Audio Control-Ch2
					Pair 3 L  cmdID= 50304  min= -180  max= 180  step= 1  format= %0.1fdB  div_scale= 10 
					Min = -18.0dB  Max = 18.0dB  Step = 0.1dB "
		::= { iqudc31CmdEntry 50304 }


	iqudc31AudioControlCh2GainPair3R OBJECT-TYPE
		SYNTAX		INTEGER
		MAX-ACCESS		read-write
		STATUS			current
		DESCRIPTION
				"TYPE: - Number
				 PAGE: - Audio Control-Ch2
					Pair 3 R  cmdID= 50305  min= -180  max= 180  step= 1  format= %0.1fdB  div_scale= 10 
					Min = -18.0dB  Max = 18.0dB  Step = 0.1dB "
		::= { iqudc31CmdEntry 50305 }


	iqudc31AudioControlCh2GainPair4L OBJECT-TYPE
		SYNTAX		INTEGER
		MAX-ACCESS		read-write
		STATUS			current
		DESCRIPTION
				"TYPE: - Number
				 PAGE: - Audio Control-Ch2
					Pair 4 L  cmdID= 50306  min= -180  max= 180  step= 1  format= %0.1fdB  div_scale= 10 
					Min = -18.0dB  Max = 18.0dB  Step = 0.1dB "
		::= { iqudc31CmdEntry 50306 }


	iqudc31AudioControlCh2GainPair4R OBJECT-TYPE
		SYNTAX		INTEGER
		MAX-ACCESS		read-write
		STATUS			current
		DESCRIPTION
				"TYPE: - Number
				 PAGE: - Audio Control-Ch2
					Pair 4 R  cmdID= 50307  min= -180  max= 180  step= 1  format= %0.1fdB  div_scale= 10 
					Min = -18.0dB  Max = 18.0dB  Step = 0.1dB "
		::= { iqudc31CmdEntry 50307 }


	iqudc31AudioControlCh2GainPair5L OBJECT-TYPE
		SYNTAX		INTEGER
		MAX-ACCESS		read-write
		STATUS			current
		DESCRIPTION
				"TYPE: - Number
				 PAGE: - Audio Control-Ch2
					Pair 5 L  cmdID= 50308  min= -180  max= 180  step= 1  format= %0.1fdB  div_scale= 10 
					Min = -18.0dB  Max = 18.0dB  Step = 0.1dB "
		::= { iqudc31CmdEntry 50308 }


	iqudc31AudioControlCh2GainPair5R OBJECT-TYPE
		SYNTAX		INTEGER
		MAX-ACCESS		read-write
		STATUS			current
		DESCRIPTION
				"TYPE: - Number
				 PAGE: - Audio Control-Ch2
					Pair 5 R  cmdID= 50309  min= -180  max= 180  step= 1  format= %0.1fdB  div_scale= 10 
					Min = -18.0dB  Max = 18.0dB  Step = 0.1dB "
		::= { iqudc31CmdEntry 50309 }


	iqudc31AudioControlCh2GainPair6L OBJECT-TYPE
		SYNTAX		INTEGER
		MAX-ACCESS		read-write
		STATUS			current
		DESCRIPTION
				"TYPE: - Number
				 PAGE: - Audio Control-Ch2
					Pair 6 L  cmdID= 50310  min= -180  max= 180  step= 1  format= %0.1fdB  div_scale= 10 
					Min = -18.0dB  Max = 18.0dB  Step = 0.1dB "
		::= { iqudc31CmdEntry 50310 }


	iqudc31AudioControlCh2GainPair6R OBJECT-TYPE
		SYNTAX		INTEGER
		MAX-ACCESS		read-write
		STATUS			current
		DESCRIPTION
				"TYPE: - Number
				 PAGE: - Audio Control-Ch2
					Pair 6 R  cmdID= 50311  min= -180  max= 180  step= 1  format= %0.1fdB  div_scale= 10 
					Min = -18.0dB  Max = 18.0dB  Step = 0.1dB "
		::= { iqudc31CmdEntry 50311 }


	iqudc31AudioControlCh2GainPair7L OBJECT-TYPE
		SYNTAX		INTEGER
		MAX-ACCESS		read-write
		STATUS			current
		DESCRIPTION
				"TYPE: - Number
				 PAGE: - Audio Control-Ch2
					Pair 7 L  cmdID= 50312  min= -180  max= 180  step= 1  format= %0.1fdB  div_scale= 10 
					Min = -18.0dB  Max = 18.0dB  Step = 0.1dB "
		::= { iqudc31CmdEntry 50312 }


	iqudc31AudioControlCh2GainPair7R OBJECT-TYPE
		SYNTAX		INTEGER
		MAX-ACCESS		read-write
		STATUS			current
		DESCRIPTION
				"TYPE: - Number
				 PAGE: - Audio Control-Ch2
					Pair 7 R  cmdID= 50313  min= -180  max= 180  step= 1  format= %0.1fdB  div_scale= 10 
					Min = -18.0dB  Max = 18.0dB  Step = 0.1dB "
		::= { iqudc31CmdEntry 50313 }


	iqudc31AudioControlCh2GainPair8L OBJECT-TYPE
		SYNTAX		INTEGER
		MAX-ACCESS		read-write
		STATUS			current
		DESCRIPTION
				"TYPE: - Number
				 PAGE: - Audio Control-Ch2
					Pair 8 L  cmdID= 50314  min= -180  max= 180  step= 1  format= %0.1fdB  div_scale= 10 
					Min = -18.0dB  Max = 18.0dB  Step = 0.1dB "
		::= { iqudc31CmdEntry 50314 }


	iqudc31AudioControlCh2GainPair8R OBJECT-TYPE
		SYNTAX		INTEGER
		MAX-ACCESS		read-write
		STATUS			current
		DESCRIPTION
				"TYPE: - Number
				 PAGE: - Audio Control-Ch2
					Pair 8 R  cmdID= 50315  min= -180  max= 180  step= 1  format= %0.1fdB  div_scale= 10 
					Min = -18.0dB  Max = 18.0dB  Step = 0.1dB "
		::= { iqudc31CmdEntry 50315 }


	iqudc31MenuAudioControlCh2ToneFrequency OBJECT-TYPE
		SYNTAX		INTEGER
		MAX-ACCESS		read-write
		STATUS			current
		DESCRIPTION
				"TYPE: - Number
				 PAGE: - Audio Control-Ch2
					Tone Frequency  cmdID= 50600  min= 100  max= 10000  step= 100  format= %0.1f KHz  div_scale= 1000 
					Min = 0.1 KHz  Max = 10.0 KHz  Step = 0.1 KHz "
		::= { iqudc31CmdEntry 50600 }


	iqudc31MenuAudioControlCh2DolbyEAlignmentO OBJECT-TYPE
		SYNTAX		INTEGER
		MAX-ACCESS		read-write
		STATUS			current
		DESCRIPTION
				"TYPE: - Number
				 PAGE: - Audio Control-Ch2
					Dolby E Alignment O  cmdID= 50504  min= -10  max= 10  step= 1  format= %0.0f Lines  div_scale= 1 
					Min = -10 Lines  Max = 10 Lines  Step = 1 Lines "
		::= { iqudc31CmdEntry 50504 }


	iqudc31DelayGlobalDelayPairOPair150505 OBJECT-TYPE
		SYNTAX		INTEGER
		MAX-ACCESS		read-write
		STATUS			current
		DESCRIPTION
				"TYPE: - Number
				 PAGE: - Audio Control-Ch2
					Pair 1  cmdID= 50505  min= -40  max= 200  step= 1  format= %0.0f ms  div_scale= 1 
					Min = -40 ms  Max = 200 ms  Step = 1 ms "
		::= { iqudc31CmdEntry 50505 }


	iqudc31DelayGlobalDelayPairOPair1Total50513 OBJECT-TYPE
		SYNTAX		RollCallString
		MAX-ACCESS		read-only
		STATUS			current
		DESCRIPTION
				"TYPE: - Display
				 PAGE: - Audio Control-Ch2
					Pair 1 Total  cmdID= 50513  format=   "
		::= { iqudc31CmdEntry 50513 }


	iqudc31DelayGlobalDelayPairOPair250506 OBJECT-TYPE
		SYNTAX		INTEGER
		MAX-ACCESS		read-write
		STATUS			current
		DESCRIPTION
				"TYPE: - Number
				 PAGE: - Audio Control-Ch2
					Pair 2  cmdID= 50506  min= -40  max= 200  step= 1  format= %0.0f ms  div_scale= 1 
					Min = -40 ms  Max = 200 ms  Step = 1 ms "
		::= { iqudc31CmdEntry 50506 }


	iqudc31DelayGlobalDelayPairOPair2Total50514 OBJECT-TYPE
		SYNTAX		RollCallString
		MAX-ACCESS		read-only
		STATUS			current
		DESCRIPTION
				"TYPE: - Display
				 PAGE: - Audio Control-Ch2
					Pair 2 Total  cmdID= 50514  format=   "
		::= { iqudc31CmdEntry 50514 }


	iqudc31DelayGlobalDelayPairOPair350507 OBJECT-TYPE
		SYNTAX		INTEGER
		MAX-ACCESS		read-write
		STATUS			current
		DESCRIPTION
				"TYPE: - Number
				 PAGE: - Audio Control-Ch2
					Pair 3  cmdID= 50507  min= -40  max= 200  step= 1  format= %0.0f ms  div_scale= 1 
					Min = -40 ms  Max = 200 ms  Step = 1 ms "
		::= { iqudc31CmdEntry 50507 }


	iqudc31DelayGlobalDelayPairOPair3Total50515 OBJECT-TYPE
		SYNTAX		RollCallString
		MAX-ACCESS		read-only
		STATUS			current
		DESCRIPTION
				"TYPE: - Display
				 PAGE: - Audio Control-Ch2
					Pair 3 Total  cmdID= 50515  format=   "
		::= { iqudc31CmdEntry 50515 }


	iqudc31DelayGlobalDelayPairOPair450508 OBJECT-TYPE
		SYNTAX		INTEGER
		MAX-ACCESS		read-write
		STATUS			current
		DESCRIPTION
				"TYPE: - Number
				 PAGE: - Audio Control-Ch2
					Pair 4  cmdID= 50508  min= -40  max= 200  step= 1  format= %0.0f ms  div_scale= 1 
					Min = -40 ms  Max = 200 ms  Step = 1 ms "
		::= { iqudc31CmdEntry 50508 }


	iqudc31DelayGlobalDelayPairOPair4Total50516 OBJECT-TYPE
		SYNTAX		RollCallString
		MAX-ACCESS		read-only
		STATUS			current
		DESCRIPTION
				"TYPE: - Display
				 PAGE: - Audio Control-Ch2
					Pair 4 Total  cmdID= 50516  format=   "
		::= { iqudc31CmdEntry 50516 }


	iqudc31DelayGlobalDelayPairOPair550509 OBJECT-TYPE
		SYNTAX		INTEGER
		MAX-ACCESS		read-write
		STATUS			current
		DESCRIPTION
				"TYPE: - Number
				 PAGE: - Audio Control-Ch2
					Pair 5  cmdID= 50509  min= -40  max= 200  step= 1  format= %0.0f ms  div_scale= 1 
					Min = -40 ms  Max = 200 ms  Step = 1 ms "
		::= { iqudc31CmdEntry 50509 }


	iqudc31DelayGlobalDelayPairOPair5Total50517 OBJECT-TYPE
		SYNTAX		RollCallString
		MAX-ACCESS		read-only
		STATUS			current
		DESCRIPTION
				"TYPE: - Display
				 PAGE: - Audio Control-Ch2
					Pair 5 Total  cmdID= 50517  format=   "
		::= { iqudc31CmdEntry 50517 }


	iqudc31DelayGlobalDelayPairOPair650510 OBJECT-TYPE
		SYNTAX		INTEGER
		MAX-ACCESS		read-write
		STATUS			current
		DESCRIPTION
				"TYPE: - Number
				 PAGE: - Audio Control-Ch2
					Pair 6  cmdID= 50510  min= -40  max= 200  step= 1  format= %0.0f ms  div_scale= 1 
					Min = -40 ms  Max = 200 ms  Step = 1 ms "
		::= { iqudc31CmdEntry 50510 }


	iqudc31DelayGlobalDelayPairOPair6Total50518 OBJECT-TYPE
		SYNTAX		RollCallString
		MAX-ACCESS		read-only
		STATUS			current
		DESCRIPTION
				"TYPE: - Display
				 PAGE: - Audio Control-Ch2
					Pair 6 Total  cmdID= 50518  format=   "
		::= { iqudc31CmdEntry 50518 }


	iqudc31DelayGlobalDelayPairOPair750511 OBJECT-TYPE
		SYNTAX		INTEGER
		MAX-ACCESS		read-write
		STATUS			current
		DESCRIPTION
				"TYPE: - Number
				 PAGE: - Audio Control-Ch2
					Pair 7  cmdID= 50511  min= -40  max= 200  step= 1  format= %0.0f ms  div_scale= 1 
					Min = -40 ms  Max = 200 ms  Step = 1 ms "
		::= { iqudc31CmdEntry 50511 }


	iqudc31DelayGlobalDelayPairOPair7Total50519 OBJECT-TYPE
		SYNTAX		RollCallString
		MAX-ACCESS		read-only
		STATUS			current
		DESCRIPTION
				"TYPE: - Display
				 PAGE: - Audio Control-Ch2
					Pair 7 Total  cmdID= 50519  format=   "
		::= { iqudc31CmdEntry 50519 }


	iqudc31DelayGlobalDelayPairOPair850512 OBJECT-TYPE
		SYNTAX		INTEGER
		MAX-ACCESS		read-write
		STATUS			current
		DESCRIPTION
				"TYPE: - Number
				 PAGE: - Audio Control-Ch2
					Pair 8  cmdID= 50512  min= -40  max= 200  step= 1  format= %0.0f ms  div_scale= 1 
					Min = -40 ms  Max = 200 ms  Step = 1 ms "
		::= { iqudc31CmdEntry 50512 }


	iqudc31DelayGlobalDelayPairOPair8Total50520 OBJECT-TYPE
		SYNTAX		RollCallString
		MAX-ACCESS		read-only
		STATUS			current
		DESCRIPTION
				"TYPE: - Display
				 PAGE: - Audio Control-Ch2
					Pair 8 Total  cmdID= 50520  format=   "
		::= { iqudc31CmdEntry 50520 }


	iqudc31AudioControlCh2GlobalDelay OBJECT-TYPE
		SYNTAX		INTEGER
		MAX-ACCESS		read-write
		STATUS			current
		DESCRIPTION
				"TYPE: - Number
				 PAGE: - Audio Control-Ch2
					Global  cmdID= 50400  min= -40  max= 200  step= 1  format= %0.0f ms  div_scale= 1 
					Min = -40 ms  Max = 200 ms  Step = 1 ms "
		::= { iqudc31CmdEntry 50400 }


	iqudc31AudioControlCh2GlobalDelayGlobalTotal OBJECT-TYPE
		SYNTAX		RollCallString
		MAX-ACCESS		read-only
		STATUS			current
		DESCRIPTION
				"TYPE: - Display
				 PAGE: - Audio Control-Ch2
					Global Total  cmdID= 50401  format=   "
		::= { iqudc31CmdEntry 50401 }


	iqudc31AudioControlCh2GlobalDelayVideoTotal OBJECT-TYPE
		SYNTAX		RollCallString
		MAX-ACCESS		read-only
		STATUS			current
		DESCRIPTION
				"TYPE: - Display
				 PAGE: - Audio Control-Ch2
					Video Total  cmdID= 50402  format=   "
		::= { iqudc31CmdEntry 50402 }


	iqudc31MenuAudioControlCh2NewDisplay OBJECT-TYPE
		SYNTAX		RollCallString
		MAX-ACCESS		read-only
		STATUS			current
		DESCRIPTION
				"TYPE: - Display
				 PAGE: - Audio Control-Ch2
					New Display  cmdID= 44458  format=   "
		::= { iqudc31CmdEntry 44458 }


	iqudc31AudioIOAESAESOutput14AES1 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 1  cmdID= 40400 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40400 }


	iqudc31MenuAudioIOAESAES2 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 2  cmdID= 40401 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40401 }


	iqudc31MenuAudioIOAESAES3 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 3  cmdID= 40402 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40402 }


	iqudc31MenuAudioIOAESAES4 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 4  cmdID= 40403 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40403 }


	iqudc31AudioIOAESAESOutput58AES5 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 5  cmdID= 40404 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40404 }


	iqudc31MenuAudioIOAESAES6 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 6  cmdID= 40405 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40405 }


	iqudc31MenuAudioIOAESAES7 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 7  cmdID= 40406 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40406 }


	iqudc31MenuAudioIOAESAES8 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 8  cmdID= 40407 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc31CmdEntry 40407 }


	iqudc31MenuAudioIOAESNewDisplay OBJECT-TYPE
		SYNTAX		RollCallString
		MAX-ACCESS		read-only
		STATUS			current
		DESCRIPTION
				"TYPE: - Display
				 PAGE: - Audio I/O AES
					New Display  cmdID= 40005  format=   "
		::= { iqudc31CmdEntry 40005 }


	iqudc31AudioIOAnalogAnalogOutput12Analog1 OBJECT-TYPE
		SYNTAX		INTEGER {
							val-Ch-1-Pair-1(0),
							val-Ch-1-Pair-2(1),
							val-Ch-1-Pair-3(2),
							val-Ch-1-Pair-4(3),
							val-Ch-1-Pair-5(4),
							val-Ch-1-Pair-6(5),
							val-Ch-1-Pair-7(6),
							val-Ch-1-Pair-8(7),
							val-Ch-2-Pair-1(8),
							val-Ch-2-Pair-2(9),
							val-Ch-2-Pair-3(10),
							val-Ch-2-Pair-4(11),
							val-Ch-2-Pair-5(12),
							val-Ch-2-Pair-6(13),
							val-Ch-2-Pair-7(14),
							val-Ch-2-Pair-8(15)
							}
		MAX-ACCESS		read-write
		STATUS			current
		DESCRIPTION
				"TYPE: - RadiobuttonList
				 PAGE: - Audio I/O Analog
					Analog 1  cmdID= 40410 
					Ch 1 Pair 1  value= 0  
					Ch 1 Pair 2  value= 1  
					Ch 1 Pair 3  value= 2  
					Ch 1 Pair 4  value= 3  
					Ch 1 Pair 5  value= 4  
					Ch 1 Pair 6  value= 5  
					Ch 1 Pair 7  value= 6  
					Ch 1 Pair 8  value= 7  
					Ch 2 Pair 1  value= 8  
					Ch 2 Pair 2  value= 9  
					Ch 2 Pair 3  value= 10  
					Ch 2 Pair 4  value= 11  
					Ch 2 Pair 5  value= 12  
					Ch 2 Pair 6  value= 13  
					Ch 2 Pair 7  value= 14  
					Ch 2 Pair 8  value= 15  "
		::= { iqudc31CmdEntry 40410 }


	iqudc31MenuAudioIOAnalogAnalog2 OBJECT-TYPE
		SYNTAX		INTEGER {
							val-Ch-1-Pair-1(0),
							val-Ch-1-Pair-2(1),
							val-Ch-1-Pair-3(2),
							val-Ch-1-Pair-4(3),
							val-Ch-1-Pair-5(4),
							val-Ch-1-Pair-6(5),
							val-Ch-1-Pair-7(6),
							val-Ch-1-Pair-8(7),
							val-Ch-2-Pair-1(8),
							val-Ch-2-Pair-2(9),
							val-Ch-2-Pair-3(10),
							val-Ch-2-Pair-4(11),
							val-Ch-2-Pair-5(12),
							val-Ch-2-Pair-6(13),
							val-Ch-2-Pair-7(14),
							val-Ch-2-Pair-8(15)
							}
		MAX-ACCESS		read-write
		STATUS			current
		DESCRIPTION
				"TYPE: - RadiobuttonList
				 PAGE: - Audio I/O Analog
					Analog 2  cmdID= 40411 
					Ch 1 Pair 1  value= 0  
					Ch 1 Pair 2  value= 1  
					Ch 1 Pair 3  value= 2  
					Ch 1 Pair 4  value= 3  
					Ch 1 Pair 5  value= 4  
					Ch 1 Pair 6  value= 5  
					Ch 1 Pair 7  value= 6  
					Ch 1 Pair 8  value= 7  
					Ch 2 Pair 1  value= 8  
					Ch 2 Pair 2  value= 9  
					Ch 2 Pair 3  value= 10  
					Ch 2 Pair 4  value= 11  
					Ch 2 Pair 5  value= 12  
					Ch 2 Pair 6  value= 13  
					Ch 2 Pair 7  value= 14  
					Ch 2 Pair 8  value= 15  "
		::= { iqudc31CmdEntry 40411 }


	iqudc31InputAnalogInADCHeadrPair1 OBJECT-TYPE
		SYNTAX		INTEGER
		MAX-ACCESS		read-write
		STATUS			current
		DESCRIPTION
				"TYPE: - Number
				 PAGE: - Audio I/O Analog
					Pair 1  cmdID= 40000  min= 24  max= 48  step= 1  format= %d  div_scale= 2 
					Min = 12  Max = 24  Step = 0 "
		::= { iqudc31CmdEntry 40000 }


	iqudc31InputAnalogInADCHeadrPair2 OBJECT-TYPE
		SYNTAX		INTEGER
		MAX-ACCESS		read-write
		STATUS			current
		DESCRIPTION
				"TYPE: - Number
				 PAGE: - Audio I/O Analog
					Pair 2  cmdID= 40001  min= 24  max= 48  step= 1  format= %d  div_scale= 2 
					Min = 12  Max = 24  Step = 0 "
		::= { iqudc31CmdEntry 40001 }


	iqudc31OutputAnalogOutDACLevePair1 OBJECT-TYPE
		SYNTAX		INTEGER
		MAX-ACCESS		read-write
		STATUS			current
		DESCRIPTION
				"TYPE: - Number
				 PAGE: - Audio I/O Analog
					Pair 1  cmdID= 40200  min= 24  max= 48  step= 1  format= %d  div_scale= 2 
					Min = 12  Max = 24  Step = 0 "
		::= { iqudc31CmdEntry 40200 }


	iqudc31OutputAnalogOutDACLevePair2 OBJECT-TYPE
		SYNTAX		INTEGER
		MAX-ACCESS		read-write
		STATUS			current
		DESCRIPTION
				"TYPE: - Number
				 PAGE: - Audio I/O Analog
					Pair 2  cmdID= 40201  min= 24  max= 48  step= 1  format= %d  div_scale= 2 
					Min = 12  Max = 24  Step = 0 "
		::= { iqudc31CmdEntry 40201 }


	iqudc31MenuAudioIOAnalogNewDisplay OBJECT-TYPE
		SYNTAX		RollCallString
		MAX-ACCESS		read-only
		STATUS			current
		DESCRIPTION
				"TYPE: - Display
				 PAGE: - Audio I/O Analog
					New Display  cmdID= 40004  format=   "
		::= { iqudc31CmdEntry 40004 }


	iqudc31DolbySetupDolbyCh1Mode OBJECT-TYPE
		SYNTAX		INTEGER {
							val-Decode(0),
							val-Encode(1),
							val-Transcode(2)
							}
		MAX-ACCESS		read-write
		STATUS			current
		DESCRIPTION
				"TYPE: - RadiobuttonList
				 PAGE: - Dolby Setup
					Mode  cmdID= 40529 
					Decode  value= 0  
					Encode  value= 1  
					Transcode  value= 2  "
		::= { iqudc31CmdEntry 40529 }


	iqudc31DolbySetupDolbyCh1DolbyEDelayCompen OBJECT-TYPE
		SYNTAX		INTEGER {
							val-Early-Early(0),
							val-Early-Normal(1),
							val-Early-Late(2),
							val-Normal-Normal(3),
							val-Normal-Late(4),
							val-Late-Late(5)
							}
		MAX-ACCESS		read-write
		STATUS			current
		DESCRIPTION
				"TYPE: - RadiobuttonList
				 PAGE: - Dolby Setup
					DolbyE Delay Compen  cmdID= 40507 
					Early > Early  value= 0  
					Early > Normal  value= 1  
					Early > Late  value= 2  
					Normal > Normal  value= 3  
					Normal > Late  value= 4  
					Late > Late  value= 5  "
		::= { iqudc31CmdEntry 40507 }


	iqudc31DolbySetupDolbyCh1MetadataSource OBJECT-TYPE
		SYNTAX		INTEGER {
							val-Dolby-Decoder(0),
							val-SMPTE-2020(1)
							}
		MAX-ACCESS		read-write
		STATUS			current
		DESCRIPTION
				"TYPE: - RadiobuttonList
				 PAGE: - Dolby Setup
					Metadata Source  cmdID= 40506 
					Dolby Decoder  value= 0  
					SMPTE 2020  value= 1  "
		::= { iqudc31CmdEntry 40506 }


	iqudc31DolbyCh1SMPTE2020OutputOutputLine OBJECT-TYPE
		SYNTAX		INTEGER
		MAX-ACCESS		read-write
		STATUS			current
		DESCRIPTION
				"TYPE: - Number
				 PAGE: - Dolby Setup
					Output Line  cmdID= 40510  min= 8  max= 20  step= 1  format= %0.0f  div_scale= 1 
					Min = 8  Max = 20  Step = 1 "
		::= { iqudc31CmdEntry 40510 }


	iqudc31DolbyCh1SMPTE2020OutputOutputEnable OBJECT-TYPE
		SYNTAX		INTEGER { disable(0), enable(1) }
		MAX-ACCESS		read-write
		STATUS			current
		DESCRIPTION
				"TYPE: - Checkbox
				 PAGE: - Dolby Setup
					Output Enable  cmdID= 40509 "
		::= { iqudc31CmdEntry 40509 }


	iqudc31DolbySetupDolbyCh1DecoderSource OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Decoder Source  cmdID= 40500 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc31CmdEntry 40500 }


	iqudc31MenuDolbySetupEncoderSource1 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 1  cmdID= 40520 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc31CmdEntry 40520 }


	iqudc31MenuDolbySetupEncoderSource2 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 2  cmdID= 40521 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc31CmdEntry 40521 }


	iqudc31MenuDolbySetupEncoderSource3 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 3  cmdID= 40522 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc31CmdEntry 40522 }


	iqudc31MenuDolbySetupEncoderSource4 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 4  cmdID= 40523 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc31CmdEntry 40523 }


	iqudc31MenuDolbySetupEncoderFormat OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Format  cmdID= 40524 
					1  value= 0  
					2  value= 1  
					3  value= 2  
					4  value= 3  
					5  value= 4  
					6  value= 5  
					7  value= 6  
					8  value= 7  "
		::= { iqudc31CmdEntry 40524 }


	iqudc31MenuDolbySetupEncoderFormatED OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Format E D  cmdID= 40525 
					1  value= 0  
					2  value= 1  
					3  value= 2  
					4  value= 3  
					5  value= 4  
					6  value= 5  
					7  value= 6  
					8  value= 7  "
		::= { iqudc31CmdEntry 40525 }


	iqudc31MenuDolbySetupEncoderRate OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Rate  cmdID= 40526 
					1  value= 0  
					2  value= 1  
					3  value= 2  
					4  value= 3  
					5  value= 4  
					6  value= 5  
					7  value= 6  
					8  value= 7  "
		::= { iqudc31CmdEntry 40526 }


	iqudc31MenuDolbySetupEncoderBitDepth OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Bit Depth  cmdID= 40527 
					1  value= 0  
					2  value= 1  
					3  value= 2  
					4  value= 3  
					5  value= 4  
					6  value= 5  
					7  value= 6  
					8  value= 7  "
		::= { iqudc31CmdEntry 40527 }


	iqudc31MenuDolbySetupEncoderConfig OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Config  cmdID= 40528 
					1  value= 0  
					2  value= 1  
					3  value= 2  
					4  value= 3  
					5  value= 4  
					6  value= 5  
					7  value= 6  
					8  value= 7  "
		::= { iqudc31CmdEntry 40528 }


	iqudc31MenuDolbySetupInputStatus OBJECT-TYPE
		SYNTAX		RollCallString
		MAX-ACCESS		read-only
		STATUS			current
		DESCRIPTION
				"TYPE: - Display
				 PAGE: - Dolby Setup
					Input Status  cmdID= 40501  format=   "
		::= { iqudc31CmdEntry 40501 }


	iqudc31MenuDolbySetupDecoderRate OBJECT-TYPE
		SYNTAX		RollCallString
		MAX-ACCESS		read-only
		STATUS			current
		DESCRIPTION
				"TYPE: - Display
				 PAGE: - Dolby Setup
					Decoder Rate  cmdID= 40503  format=   "
		::= { iqudc31CmdEntry 40503 }


	iqudc31MenuDolbySetupDecoderFormat OBJECT-TYPE
		SYNTAX		RollCallString
		MAX-ACCESS		read-only
		STATUS			current
		DESCRIPTION
				"TYPE: - Display
				 PAGE: - Dolby Setup
					Decoder Format  cmdID= 40502  format=   "
		::= { iqudc31CmdEntry 40502 }


	iqudc31MenuDolbySetupDecoderVersion OBJECT-TYPE
		SYNTAX		RollCallString
		MAX-ACCESS		read-only
		STATUS			current
		DESCRIPTION
				"TYPE: - Display
				 PAGE: - Dolby Setup
					Decoder Version  cmdID= 40504  format=   "
		::= { iqudc31CmdEntry 40504 }


	iqudc31MenuDolbySetupEncoderVersion OBJECT-TYPE
		SYNTAX		RollCallString
		MAX-ACCESS		read-only
		STATUS			current
		DESCRIPTION
				"TYPE: - Display
				 PAGE: - Dolby Setup
					Encoder Version  cmdID= 40508  format=   "
		::= { iqudc31CmdEntry 40508 }


	iqudc31MenuDolbySetupNewDisplay OBJECT-TYPE
		SYNTAX		RollCallString
		MAX-ACCESS		read-only
		STATUS			current
		DESCRIPTION
				"TYPE: - Display
				 PAGE: - Dolby Setup
					New Display  cmdID= 44467  format=   "
		::= { iqudc31CmdEntry 44467 }


	iqudc31MenuGenlockSourceCh12 OBJECT-TYPE
		SYNTAX		INTEGER {
							val-Module-Reference(0),
							val-Chassis-Reference-A(1),
							val-Chassis-Reference-B(2),
							val-Ch-1-Input(3),
							val-Ch-2-Input(4),
							val-Free-Run(5)
							}
		MAX-ACCESS		read-write
		STATUS			current
		DESCRIPTION
				"TYPE: - RadiobuttonList
				 PAGE: - Genlock
					Source Ch 1 & 2  cmdID= 30000 
					Module Reference  value= 0  
					Chassis Reference A  value= 1  
					Chassis Reference B  value= 2  
					Ch 1 Input  value= 3  
					Ch 2 Input  value= 4  
					Free Run  value= 5  "
		::= { iqudc31CmdEntry 30000 }


	iqudc31GenlockTimingCh1VerticalTiming OBJECT-TYPE
		SYNTAX		INTEGER
		MAX-ACCESS		read-write
		STATUS			current
		DESCRIPTION
				"TYPE: - Number
				 PAGE: - Genlock
					Vertical Timing  cmdID= 30010  min= -1125  max= 1125  step= 1  format= %0.0f lines  div_scale= 1 
					Min = -1125 lines  Max = 1125 lines  Step = 1 lines "
		::= { iqudc31CmdEntry 30010 }


	iqudc31GenlockTimingCh1HorizontalTiming OBJECT-TYPE
		SYNTAX		INTEGER
		MAX-ACCESS		read-write
		STATUS			current
		DESCRIPTION
				"TYPE: - Number
				 PAGE: - Genlock
					Horizontal Timing  cmdID= 30011  min= -2640  max= 2640  step= 1  format= %0.0f pixels  div_scale= 1 
					Min = -2640 pixels  Max = 2640 pixels  Step = 1 pixels "
		::= { iqudc31CmdEntry 30011 }


	iqudc31GenlockTimingCh1Status OBJECT-TYPE
		SYNTAX		RollCallString
		MAX-ACCESS		read-only
		STATUS			current
		DESCRIPTION
				"TYPE: - Display
				 PAGE: - Genlock
					Status  cmdID= 61006  format=   "
		::= { iqudc31CmdEntry 61006 }


	iqudc31GenlockTimingCh2VerticalTiming OBJECT-TYPE
		SYNTAX		INTEGER
		MAX-ACCESS		read-write
		STATUS			current
		DESCRIPTION
				"TYPE: - Number
				 PAGE: - Genlock
					Vertical Timing  cmdID= 30012  min= -1125  max= 1125  step= 1  format= %0.0f lines  div_scale= 1 
					Min = -1125 lines  Max = 1125 lines  Step = 1 lines "
		::= { iqudc31CmdEntry 30012 }


	iqudc31GenlockTimingCh2HorizontalTiming OBJECT-TYPE
		SYNTAX		INTEGER
		MAX-ACCESS		read-write
		STATUS			current
		DESCRIPTION
				"TYPE: - Number
				 PAGE: - Genlock
					Horizontal Timing  cmdID= 30013  min= -2640  max= 2640  step= 1  format= %0.0f pixels  div_scale= 1 
					Min = -2640 pixels  Max = 2640 pixels  Step = 1 pixels "
		::= { iqudc31CmdEntry 30013 }


	iqudc31GenlockTimingCh2Status OBJECT-TYPE
		SYNTAX		RollCallString
		MAX-ACCESS		read-only
		STATUS			current
		DESCRIPTION
				"TYPE: - Display
				 PAGE: - Genlock
					Status  cmdID= 61007  format=   "
		::= { iqudc31CmdEntry 61007 }


	iqudc31MenuTimecodeCh1SourceHD OBJECT-TYPE
		SYNTAX		INTEGER {
							val-LTC(0),
							val-VITC(1)
							}
		MAX-ACCESS		read-write
		STATUS			current
		DESCRIPTION
				"TYPE: - RadiobuttonList
				 PAGE: - Timecode-Ch1
					Source (HD)  cmdID= 60100 
					LTC  value= 0  
					VITC  value= 1  "
		::= { iqudc31CmdEntry 60100 }


	iqudc31MenuTimecodeCh1SourceSD OBJECT-TYPE
		SYNTAX		INTEGER {
							val-VITC(0),
							val-ATC-LTC(1),
							val-ATC-VITC(2)
							}
		MAX-ACCESS		read-write
		STATUS			current
		DESCRIPTION
				"TYPE: - RadiobuttonList
				 PAGE: - Timecode-Ch1
					Source (SD)  cmdID= 60101 
					VITC  value= 0  
					ATC LTC  value= 1  
					ATC VITC  value= 2  "
		::= { iqudc31CmdEntry 60101 }


	iqudc31MenuTimecodeCh1Status OBJECT-TYPE
		SYNTAX		RollCallString
		MAX-ACCESS		read-only
		STATUS			current
		DESCRIPTION
				"TYPE: - Display
				 PAGE: - Timecode-Ch1
					Status  cmdID= 60112  format=   "
		::= { iqudc31CmdEntry 60112 }


	iqudc31MenuTimecodeCh1Mode OBJECT-TYPE
		SYNTAX		INTEGER {
							val-Follow-Input(0),
							val-Generate(1)
							}
		MAX-ACCESS		read-write
		STATUS			current
		DESCRIPTION
				"TYPE: - RadiobuttonList
				 PAGE: - Timecode-Ch1
					Mode  cmdID= 60102 
					Follow Input  value= 0  
					Generate  value= 1  "
		::= { iqudc31CmdEntry 60102 }


	iqudc31MenuTimecodeCh1OnTimecodeLoss OBJECT-TYPE
		SYNTAX		INTEGER {
							val-Freeze(0),
							val-Free-Run(1)
							}
		MAX-ACCESS		read-write
		STATUS			current
		DESCRIPTION
				"TYPE: - RadiobuttonList
				 PAGE: - Timecode-Ch1
					On Timecode Loss  cmdID= 60107 
					Freeze  value= 0  
					Free Run  value= 1  "
		::= { iqudc31CmdEntry 60107 }


	iqudc31MenuTimecodeCh1TimecodeEntry OBJECT-TYPE
		SYNTAX		RollCallString
		MAX-ACCESS		read-write
		STATUS			current
		DESCRIPTION
				"TYPE: - Editstring
				 PAGE: - Timecode-Ch1
					Timecode Entry  cmdID= 60110  "
		::= { iqudc31CmdEntry 60110 }


	iqudc31MenuTimecodeCh1TimecodeLoad OBJECT-TYPE
		SYNTAX		INTEGER { noAction(0),val-Timecode-Load(1) }
		MAX-ACCESS		read-write
		STATUS			current
		DESCRIPTION
				"TYPE: - Button
				 PAGE: - Timecode-Ch1
					Timecode Load  cmdID= 60113  value= 1  "
		::= { iqudc31CmdEntry 60113 }


	iqudc31MenuTimecodeCh1NondropFrame OBJECT-TYPE
		SYNTAX		INTEGER { disable(0), enable(1) }
		MAX-ACCESS		read-write
		STATUS			current
		DESCRIPTION
				"TYPE: - Checkbox
				 PAGE: - Timecode-Ch1
					Non-drop Frame  cmdID= 60109 "
		::= { iqudc31CmdEntry 60109 }


	iqudc31MenuTimecodeCh1VITCEnable OBJECT-TYPE
		SYNTAX		INTEGER { disable(0), enable(1) }
		MAX-ACCESS		read-write
		STATUS			current
		DESCRIPTION
				"TYPE: - Checkbox
				 PAGE: - Timecode-Ch1
					VITC Enable  cmdID= 60111 "
		::= { iqudc31CmdEntry 60111 }


	iqudc31MenuTimecodeCh1OutputLine525 OBJECT-TYPE
		SYNTAX		INTEGER
		MAX-ACCESS		read-write
		STATUS			current
		DESCRIPTION
				"TYPE: - Number
				 PAGE: - Timecode-Ch1
					Output Line (525)  cmdID= 60103  min= 11  max= 17  step= 1  format= %0.0f  div_scale= 1 
					Min = 11  Max = 17  Step = 1 "
		::= { iqudc31CmdEntry 60103 }


	iqudc31MenuTimecodeCh1OutputLine625 OBJECT-TYPE
		SYNTAX		INTEGER
		MAX-ACCESS		read-write
		STATUS			current
		DESCRIPTION
				"TYPE: - Number
				 PAGE: - Timecode-Ch1
					Output Line (625)  cmdID= 60104  min= 7  max= 20  step= 1  format= %0.0f  div_scale= 1 
					Min = 7  Max = 20  Step = 1 "
		::= { iqudc31CmdEntry 60104 }


	iqudc31MenuTimecodeCh1OutputLineStatus OBJECT-TYPE
		SYNTAX		RollCallString
		MAX-ACCESS		read-only
		STATUS			current
		DESCRIPTION
				"TYPE: - Display
				 PAGE: - Timecode-Ch1
					Output Line Status  cmdID= 20165  format=   "
		::= { iqudc31CmdEntry 20165 }


	iqudc31MenuTimecodeCh1NewDisplay OBJECT-TYPE
		SYNTAX		RollCallString
		MAX-ACCESS		read-only
		STATUS			current
		DESCRIPTION
				"TYPE: - Display
				 PAGE: - Timecode-Ch1
					New Display  cmdID= 44465  format=   "
		::= { iqudc31CmdEntry 44465 }


	iqudc31MenuTimecodeCh2SourceHD OBJECT-TYPE
		SYNTAX		INTEGER {
							val-LTC(0),
							val-VITC(1)
							}
		MAX-ACCESS		read-write
		STATUS			current
		DESCRIPTION
				"TYPE: - RadiobuttonList
				 PAGE: - Timecode-Ch2
					Source (HD)  cmdID= 60214 
					LTC  value= 0  
					VITC  value= 1  "
		::= { iqudc31CmdEntry 60214 }


	iqudc31MenuTimecodeCh2SourceSD OBJECT-TYPE
		SYNTAX		INTEGER {
							val-VITC(0),
							val-ATC-LTC(1),
							val-ATC-VITC(2)
							}
		MAX-ACCESS		read-write
		STATUS			current
		DESCRIPTION
				"TYPE: - RadiobuttonList
				 PAGE: - Timecode-Ch2
					Source (SD)  cmdID= 60215 
					VITC  value= 0  
					ATC LTC  value= 1  
					ATC VITC  value= 2  "
		::= { iqudc31CmdEntry 60215 }


	iqudc31MenuTimecodeCh2Status OBJECT-TYPE
		SYNTAX		RollCallString
		MAX-ACCESS		read-only
		STATUS			current
		DESCRIPTION
				"TYPE: - Display
				 PAGE: - Timecode-Ch2
					Status  cmdID= 60212  format=   "
		::= { iqudc31CmdEntry 60212 }


	iqudc31MenuTimecodeCh2Mode OBJECT-TYPE
		SYNTAX		INTEGER {
							val-Follow-Input(0),
							val-Generate(1)
							}
		MAX-ACCESS		read-write
		STATUS			current
		DESCRIPTION
				"TYPE: - RadiobuttonList
				 PAGE: - Timecode-Ch2
					Mode  cmdID= 60202 
					Follow Input  value= 0  
					Generate  value= 1  "
		::= { iqudc31CmdEntry 60202 }


	iqudc31MenuTimecodeCh2OnTimecodeLoss OBJECT-TYPE
		SYNTAX		INTEGER {
							val-Freeze(0),
							val-Free-Run(1)
							}
		MAX-ACCESS		read-write
		STATUS			current
		DESCRIPTION
				"TYPE: - RadiobuttonList
				 PAGE: - Timecode-Ch2
					On Timecode Loss  cmdID= 60207 
					Freeze  value= 0  
					Free Run  value= 1  "
		::= { iqudc31CmdEntry 60207 }


	iqudc31MenuTimecodeCh2TimecodeEntry OBJECT-TYPE
		SYNTAX		RollCallString
		MAX-ACCESS		read-write
		STATUS			current
		DESCRIPTION
				"TYPE: - Editstring
				 PAGE: - Timecode-Ch2
					Timecode Entry  cmdID= 60210  "
		::= { iqudc31CmdEntry 60210 }


	iqudc31MenuTimecodeCh2TimecodeLoad OBJECT-TYPE
		SYNTAX		INTEGER { noAction(0),val-Timecode-Load(1) }
		MAX-ACCESS		read-write
		STATUS			current
		DESCRIPTION
				"TYPE: - Button
				 PAGE: - Timecode-Ch2
					Timecode Load  cmdID= 60213  value= 1  "
		::= { iqudc31CmdEntry 60213 }


	iqudc31MenuTimecodeCh2NondropFrame OBJECT-TYPE
		SYNTAX		INTEGER { disable(0), enable(1) }
		MAX-ACCESS		read-write
		STATUS			current
		DESCRIPTION
				"TYPE: - Checkbox
				 PAGE: - Timecode-Ch2
					Non-drop Frame  cmdID= 60220 "
		::= { iqudc31CmdEntry 60220 }


	iqudc31MenuTimecodeCh2VITCEnable OBJECT-TYPE
		SYNTAX		INTEGER { disable(0), enable(1) }
		MAX-ACCESS		read-write
		STATUS			current
		DESCRIPTION
				"TYPE: - Checkbox
				 PAGE: - Timecode-Ch2
					VITC Enable  cmdID= 60211 "
		::= { iqudc31CmdEntry 60211 }


	iqudc31MenuTimecodeCh2OutputLine525 OBJECT-TYPE
		SYNTAX		INTEGER
		MAX-ACCESS		read-write
		STATUS			current
		DESCRIPTION
				"TYPE: - Number
				 PAGE: - Timecode-Ch2
					Output Line (525)  cmdID= 60203  min= 11  max= 17  step= 1  format= %0.0f  div_scale= 1 
					Min = 11  Max = 17  Step = 1 "
		::= { iqudc31CmdEntry 60203 }


	iqudc31MenuTimecodeCh2OutputLine625 OBJECT-TYPE
		SYNTAX		INTEGER
		MAX-ACCESS		read-write
		STATUS			current
		DESCRIPTION
				"TYPE: - Number
				 PAGE: - Timecode-Ch2
					Output Line (625)  cmdID= 60204  min= 7  max= 20  step= 1  format= %0.0f  div_scale= 1 
					Min = 7  Max = 20  Step = 1 "
		::= { iqudc31CmdEntry 60204 }


	iqudc31MenuTimecodeCh2OutputLineStatus OBJECT-TYPE
		SYNTAX		RollCallString
		MAX-ACCESS		read-only
		STATUS			current
		DESCRIPTION
				"TYPE: - Display
				 PAGE: - Timecode-Ch2
					Output Line Status  cmdID= 20175  format=   "
		::= { iqudc31CmdEntry 20175 }


	iqudc31MenuTimecodeCh2NewDisplay OBJECT-TYPE
		SYNTAX		RollCallString
		MAX-ACCESS		read-only
		STATUS			current
		DESCRIPTION
				"TYPE: - Display
				 PAGE: - Timecode-Ch2
					New Display  cmdID= 44451  format=   "
		::= { iqudc31CmdEntry 44451 }


	iqudc31MetadataCh1ClosedCaptionsInputStatus OBJECT-TYPE
		SYNTAX		RollCallString
		MAX-ACCESS		read-only
		STATUS			current
		DESCRIPTION
				"TYPE: - Display
				 PAGE: - Metadata-Ch1
					Input Status  cmdID= 60208  format=   "
		::= { iqudc31CmdEntry 60208 }


	iqudc31MetadataCh1ClosedCaptionsCEA608OutputEnab OBJECT-TYPE
		SYNTAX		INTEGER {
							val-Off(0),
							val-On(1)
							}
		MAX-ACCESS		read-write
		STATUS			current
		DESCRIPTION
				"TYPE: - RadiobuttonList
				 PAGE: - Metadata-Ch1
					CEA-608 Output Enab  cmdID= 60200 
					Off  value= 0  
					On  value= 1  "
		::= { iqudc31CmdEntry 60200 }


	iqudc31MetadataCh1ClosedCaptionsCEA708OutputEnab OBJECT-TYPE
		SYNTAX		INTEGER {
							val-Off(0),
							val-On(1)
							}
		MAX-ACCESS		read-write
		STATUS			current
		DESCRIPTION
				"TYPE: - RadiobuttonList
				 PAGE: - Metadata-Ch1
					CEA-708 Output Enab  cmdID= 60201 
					Off  value= 0  
					On  value= 1  "
		::= { iqudc31CmdEntry 60201 }


	iqudc31MenuMetadataCh1CEA708OutputLine60216 OBJECT-TYPE
		SYNTAX		INTEGER
		MAX-ACCESS		read-write
		STATUS			current
		DESCRIPTION
				"TYPE: - Number
				 PAGE: - Metadata-Ch1
					CEA-708 Output Line  cmdID= 60216  min= 8  max= 20  step= 1  format= %0.0f  div_scale= 1 
					Min = 8  Max = 20  Step = 1 "
		::= { iqudc31CmdEntry 60216 }


	iqudc31MenuMetadataCh1CEA708OutputLine60221 OBJECT-TYPE
		SYNTAX		RollCallString
		MAX-ACCESS		read-only
		STATUS			current
		DESCRIPTION
				"TYPE: - Display
				 PAGE: - Metadata-Ch1
					CEA-708 Output Line  cmdID= 60221  format=   "
		::= { iqudc31CmdEntry 60221 }


	iqudc31MetadataCh1TeletextTeletextPresentSt OBJECT-TYPE
		SYNTAX		RollCallString
		MAX-ACCESS		read-only
		STATUS			current
		DESCRIPTION
				"TYPE: - Display
				 PAGE: - Metadata-Ch1
					Teletext Present St  cmdID= 60209  format=   "
		::= { iqudc31CmdEntry 60209 }


	iqudc31MetadataCh1TeletextWSTInputLine OBJECT-TYPE
		SYNTAX		INTEGER
		MAX-ACCESS		read-write
		STATUS			current
		DESCRIPTION
				"TYPE: - Number
				 PAGE: - Metadata-Ch1
					WST Input Line  cmdID= 60217  min= 7  max= 22  step= 1  format= %0.0f  div_scale= 1 
					Min = 7  Max = 22  Step = 1 "
		::= { iqudc31CmdEntry 60217 }


	iqudc31MetadataCh1TeletextWSTOutputEnable OBJECT-TYPE
		SYNTAX		INTEGER {
							val-Off(0),
							val-On(1)
							}
		MAX-ACCESS		read-write
		STATUS			current
		DESCRIPTION
				"TYPE: - RadiobuttonList
				 PAGE: - Metadata-Ch1
					WST Output Enable  cmdID= 60218 
					Off  value= 0  
					On  value= 1  "
		::= { iqudc31CmdEntry 60218 }


	iqudc31MetadataCh1TeletextWSTOutputLine OBJECT-TYPE
		SYNTAX		INTEGER
		MAX-ACCESS		read-write
		STATUS			current
		DESCRIPTION
				"TYPE: - Number
				 PAGE: - Metadata-Ch1
					WST Output Line  cmdID= 60230  min= 7  max= 22  step= 1  format= %0.0f  div_scale= 1 
					Min = 7  Max = 22  Step = 1 "
		::= { iqudc31CmdEntry 60230 }


	iqudc31MetadataCh1TeletextWSTOutputLineSta OBJECT-TYPE
		SYNTAX		RollCallString
		MAX-ACCESS		read-only
		STATUS			current
		DESCRIPTION
				"TYPE: - Display
				 PAGE: - Metadata-Ch1
					WST Output Line Sta  cmdID= 20168  format=   "
		::= { iqudc31CmdEntry 20168 }


	iqudc31MetadataCh1TeletextRDD08InputLine OBJECT-TYPE
		SYNTAX		INTEGER
		MAX-ACCESS		read-write
		STATUS			current
		DESCRIPTION
				"TYPE: - Number
				 PAGE: - Metadata-Ch1
					RDD-08 Input Line  cmdID= 60206  min= 8  max= 20  step= 1  format= %0.0f  div_scale= 1 
					Min = 8  Max = 20  Step = 1 "
		::= { iqudc31CmdEntry 60206 }


	iqudc31MetadataCh1TeletextRDD08OutputEnabl OBJECT-TYPE
		SYNTAX		INTEGER {
							val-Off(0),
							val-On(1)
							}
		MAX-ACCESS		read-write
		STATUS			current
		DESCRIPTION
				"TYPE: - RadiobuttonList
				 PAGE: - Metadata-Ch1
					RDD-08 Output Enabl  cmdID= 60205 
					Off  value= 0  
					On  value= 1  "
		::= { iqudc31CmdEntry 60205 }


	iqudc31MenuMetadataCh1RDD08OutputLine60219 OBJECT-TYPE
		SYNTAX		INTEGER
		MAX-ACCESS		read-write
		STATUS			current
		DESCRIPTION
				"TYPE: - Number
				 PAGE: - Metadata-Ch1
					RDD-08 Output Line  cmdID= 60219  min= 8  max= 20  step= 1  format= %0.0f  div_scale= 1 
					Min = 8  Max = 20  Step = 1 "
		::= { iqudc31CmdEntry 60219 }


	iqudc31MenuMetadataCh1RDD08OutputLine20167 OBJECT-TYPE
		SYNTAX		RollCallString
		MAX-ACCESS		read-only
		STATUS			current
		DESCRIPTION
				"TYPE: - Display
				 PAGE: - Metadata-Ch1
					RDD-08 Output Line   cmdID= 20167  format=   "
		::= { iqudc31CmdEntry 20167 }


	iqudc31MenuMetadataCh1NewDisplay OBJECT-TYPE
		SYNTAX		RollCallString
		MAX-ACCESS		read-only
		STATUS			current
		DESCRIPTION
				"TYPE: - Display
				 PAGE: - Metadata-Ch1
					New Display  cmdID= 44466  format=   "
		::= { iqudc31CmdEntry 44466 }


	iqudc31MetadataCh2ClosedCaptionsInputStatus OBJECT-TYPE
		SYNTAX		RollCallString
		MAX-ACCESS		read-only
		STATUS			current
		DESCRIPTION
				"TYPE: - Display
				 PAGE: - Metadata-Ch2
					Input Status  cmdID= 60308  format=   "
		::= { iqudc31CmdEntry 60308 }


	iqudc31MetadataCh2ClosedCaptionsCEA608OutputEnab OBJECT-TYPE
		SYNTAX		INTEGER {
							val-Off(0),
							val-On(1)
							}
		MAX-ACCESS		read-write
		STATUS			current
		DESCRIPTION
				"TYPE: - RadiobuttonList
				 PAGE: - Metadata-Ch2
					CEA-608 Output Enab  cmdID= 60300 
					Off  value= 0  
					On  value= 1  "
		::= { iqudc31CmdEntry 60300 }


	iqudc31MetadataCh2ClosedCaptionsCEA708OutputEnab OBJECT-TYPE
		SYNTAX		INTEGER {
							val-Off(0),
							val-On(1)
							}
		MAX-ACCESS		read-write
		STATUS			current
		DESCRIPTION
				"TYPE: - RadiobuttonList
				 PAGE: - Metadata-Ch2
					CEA-708 Output Enab  cmdID= 60301 
					Off  value= 0  
					On  value= 1  "
		::= { iqudc31CmdEntry 60301 }


	iqudc31MenuMetadataCh2CEA708OutputLine60302 OBJECT-TYPE
		SYNTAX		INTEGER
		MAX-ACCESS		read-write
		STATUS			current
		DESCRIPTION
				"TYPE: - Number
				 PAGE: - Metadata-Ch2
					CEA-708 Output Line  cmdID= 60302  min= 8  max= 20  step= 1  format= %0.0f  div_scale= 1 
					Min = 8  Max = 20  Step = 1 "
		::= { iqudc31CmdEntry 60302 }


	iqudc31MenuMetadataCh2CEA708OutputLine60222 OBJECT-TYPE
		SYNTAX		RollCallString
		MAX-ACCESS		read-only
		STATUS			current
		DESCRIPTION
				"TYPE: - Display
				 PAGE: - Metadata-Ch2
					CEA-708 Output Line  cmdID= 60222  format=   "
		::= { iqudc31CmdEntry 60222 }


	iqudc31MetadataCh2TeletextTeletextPresentSt OBJECT-TYPE
		SYNTAX		RollCallString
		MAX-ACCESS		read-only
		STATUS			current
		DESCRIPTION
				"TYPE: - Display
				 PAGE: - Metadata-Ch2
					Teletext Present St  cmdID= 60309  format=   "
		::= { iqudc31CmdEntry 60309 }


	iqudc31MetadataCh2TeletextWSTInputLine OBJECT-TYPE
		SYNTAX		INTEGER
		MAX-ACCESS		read-write
		STATUS			current
		DESCRIPTION
				"TYPE: - Number
				 PAGE: - Metadata-Ch2
					WST Input Line  cmdID= 60303  min= 7  max= 22  step= 1  format= %0.0f  div_scale= 1 
					Min = 7  Max = 22  Step = 1 "
		::= { iqudc31CmdEntry 60303 }


	iqudc31MetadataCh2TeletextWSTOutputEnable OBJECT-TYPE
		SYNTAX		INTEGER {
							val-Off(0),
							val-On(1)
							}
		MAX-ACCESS		read-write
		STATUS			current
		DESCRIPTION
				"TYPE: - RadiobuttonList
				 PAGE: - Metadata-Ch2
					WST Output Enable  cmdID= 60304 
					Off  value= 0  
					On  value= 1  "
		::= { iqudc31CmdEntry 60304 }


	iqudc31MetadataCh2TeletextWSTOutputLine OBJECT-TYPE
		SYNTAX		INTEGER
		MAX-ACCESS		read-write
		STATUS			current
		DESCRIPTION
				"TYPE: - Number
				 PAGE: - Metadata-Ch2
					WST Output Line  cmdID= 60231  min= 7  max= 22  step= 1  format= %0.0f  div_scale= 1 
					Min = 7  Max = 22  Step = 1 "
		::= { iqudc31CmdEntry 60231 }


	iqudc31MetadataCh2TeletextWSTOutputLineSta OBJECT-TYPE
		SYNTAX		RollCallString
		MAX-ACCESS		read-only
		STATUS			current
		DESCRIPTION
				"TYPE: - Display
				 PAGE: - Metadata-Ch2
					WST Output Line Sta  cmdID= 20178  format=   "
		::= { iqudc31CmdEntry 20178 }


	iqudc31MetadataCh2TeletextRDD08InputLine OBJECT-TYPE
		SYNTAX		INTEGER
		MAX-ACCESS		read-write
		STATUS			current
		DESCRIPTION
				"TYPE: - Number
				 PAGE: - Metadata-Ch2
					RDD-08 Input Line  cmdID= 60306  min= 8  max= 20  step= 1  format= %0.0f  div_scale= 1 
					Min = 8  Max = 20  Step = 1 "
		::= { iqudc31CmdEntry 60306 }


	iqudc31MetadataCh2TeletextRDD08OutputEnabl OBJECT-TYPE
		SYNTAX		INTEGER {
							val-Off(0),
							val-On(1)
							}
		MAX-ACCESS		read-write
		STATUS			current
		DESCRIPTION
				"TYPE: - RadiobuttonList
				 PAGE: - Metadata-Ch2
					RDD-08 Output Enabl  cmdID= 60305 
					Off  value= 0  
					On  value= 1  "
		::= { iqudc31CmdEntry 60305 }


	iqudc31MenuMetadataCh2RDD08OutputLine60307 OBJECT-TYPE
		SYNTAX		INTEGER
		MAX-ACCESS		read-write
		STATUS			current
		DESCRIPTION
				"TYPE: - Number
				 PAGE: - Metadata-Ch2
					RDD-08 Output Line  cmdID= 60307  min= 8  max= 20  step= 1  format= %0.0f  div_scale= 1 
					Min = 8  Max = 20  Step = 1 "
		::= { iqudc31CmdEntry 60307 }


	iqudc31MenuMetadataCh2RDD08OutputLine20177 OBJECT-TYPE
		SYNTAX		RollCallString
		MAX-ACCESS		read-only
		STATUS			current
		DESCRIPTION
				"TYPE: - Display
				 PAGE: - Metadata-Ch2
					RDD-08 Output Line   cmdID= 20177  format=   "
		::= { iqudc31CmdEntry 20177 }


	iqudc31MenuMetadataCh2NewDisplay OBJECT-TYPE
		SYNTAX		RollCallString
		MAX-ACCESS		read-only
		STATUS			current
		DESCRIPTION
				"TYPE: - Display
				 PAGE: - Metadata-Ch2
					New Display  cmdID= 44452  format=   "
		::= { iqudc31CmdEntry 44452 }


	iqudc31GPIOGPI1GPIO1Mode OBJECT-TYPE
		SYNTAX		INTEGER {
							val-Unused(0),
							val-Input-GPI1(1),
							val-Output-GPO1(2)
							}
		MAX-ACCESS		read-write
		STATUS			current
		DESCRIPTION
				"TYPE: - RadiobuttonList
				 PAGE: - GPIO
					GPI/O 1 Mode  cmdID= 40600 
					Unused  value= 0  
					Input (GPI1)  value= 1  
					Output (GPO1)  value= 2  "
		::= { iqudc31CmdEntry 40600 }


	iqudc31MenuGPIOGPI1ipSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5),
							val-User-Memory-1(6),
							val-User-Memory-2(7),
							val-User-Memory-3(8),
							val-User-Memory-4(9),
							val-User-Memory-5(10),
							val-User-Memory-6(11),
							val-User-Memory-7(12),
							val-User-Memory-8(13),
							val-User-Memory-9(14),
							val-User-Memory-10(15),
							val-User-Memory-11(16),
							val-User-Memory-12(17),
							val-User-Memory-13(18),
							val-User-Memory-14(19),
							val-User-Memory-15(20),
							val-User-Memory-16(21)
							}
		MAX-ACCESS		read-write
		STATUS			current
		DESCRIPTION
				"TYPE: - RadiobuttonList
				 PAGE: - GPIO
					GPI 1-i/p Select  cmdID= 40602 
					Unused  value= 255  
					Freeze Ch1  value= 0  
					Black Ch1  value= 1  
					Pattern Ch1  value= 2  
					Freeze Ch2  value= 3  
					Black Ch2  value= 4  
					Pattern Ch2  value= 5  
					User Memory 1  value= 6  
					User Memory 2  value= 7  
					User Memory 3  value= 8  
					User Memory 4  value= 9  
					User Memory 5  value= 10  
					User Memory 6  value= 11  
					User Memory 7  value= 12  
					User Memory 8  value= 13  
					User Memory 9  value= 14  
					User Memory 10  value= 15  
					User Memory 11  value= 16  
					User Memory 12  value= 17  
					User Memory 13  value= 18  
					User Memory 14  value= 19  
					User Memory 15  value= 20  
					User Memory 16  value= 21  "
		::= { iqudc31CmdEntry 40602 }


	iqudc31MenuGPIOGPO1opSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5)
							}
		MAX-ACCESS		read-write
		STATUS			current
		DESCRIPTION
				"TYPE: - RadiobuttonList
				 PAGE: - GPIO
					GPO 1-o/p Select  cmdID= 40603 
					Unused  value= 255  
					Freeze Ch1  value= 0  
					Black Ch1  value= 1  
					Pattern Ch1  value= 2  
					Freeze Ch2  value= 3  
					Black Ch2  value= 4  
					Pattern Ch2  value= 5  "
		::= { iqudc31CmdEntry 40603 }


	iqudc31GPIOGPI2GPIO2Mode OBJECT-TYPE
		SYNTAX		INTEGER {
							val-Unused(0),
							val-Input-GPI2(1),
							val-Output-GPO2(2)
							}
		MAX-ACCESS		read-write
		STATUS			current
		DESCRIPTION
				"TYPE: - RadiobuttonList
				 PAGE: - GPIO
					GPI/O 2 Mode  cmdID= 40601 
					Unused  value= 0  
					Input (GPI2)  value= 1  
					Output (GPO2)  value= 2  "
		::= { iqudc31CmdEntry 40601 }


	iqudc31MenuGPIOGPI2ipSelect OBJECT-TYPE
		SYNTAX		INTEGER {
							val-Unused(255),
							val-Freeze-Ch1(0),
							val-Black-Ch-1(1),
							val-Pattern-Ch1(2),
							val-Freeze-Ch2(3),
							val-Black-Ch-2(4),
							val-Pattern-Ch2(5),
							val-User-Memory-1(6),
							val-User-Memory-2(7),
							val-User-Memory-3(8),
							val-User-Memory-4(9),
							val-User-Memory-5(10),
							val-User-Memory-6(11),
							val-User-Memory-7(12),
							val-User-Memory-8(13),
							val-User-Memory-9(14),
							val-User-Memory-10(15),
							val-User-Memory-11(16),
							val-User-Memory-12(17),
							val-User-Memory-13(18),
							val-User-Memory-14(19),
							val-User-Memory-15(20),
							val-User-Memory-16(21)
							}
		MAX-ACCESS		read-write
		STATUS			current
		DESCRIPTION
				"TYPE: - RadiobuttonList
				 PAGE: - GPIO
					GPI 2-i/p Select  cmdID= 40604 
					Unused  value= 255  
					Freeze Ch1  value= 0  
					Black Ch 1  value= 1  
					Pattern Ch1  value= 2  
					Freeze Ch2  value= 3  
					Black Ch 2  value= 4  
					Pattern Ch2  value= 5  
					User Memory 1  value= 6  
					User Memory 2  value= 7  
					User Memory 3  value= 8  
					User Memory 4  value= 9  
					User Memory 5  value= 10  
					User Memory 6  value= 11  
					User Memory 7  value= 12  
					User Memory 8  value= 13  
					User Memory 9  value= 14  
					User Memory 10  value= 15  
					User Memory 11  value= 16  
					User Memory 12  value= 17  
					User Memory 13  value= 18  
					User Memory 14  value= 19  
					User Memory 15  value= 20  
					User Memory 16  value= 21  "
		::= { iqudc31CmdEntry 40604 }


	iqudc31MenuGPIOGPO2opSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5)
							}
		MAX-ACCESS		read-write
		STATUS			current
		DESCRIPTION
				"TYPE: - RadiobuttonList
				 PAGE: - GPIO
					GPO 2-o/p Select  cmdID= 40605 
					Unused  value= 255  
					Freeze Ch1  value= 0  
					Black Ch1  value= 1  
					Pattern Ch1  value= 2  
					Freeze Ch2  value= 3  
					Black Ch2  value= 4  
					Pattern Ch2  value= 5  "
		::= { iqudc31CmdEntry 40605 }


	iqudc31MenuGPIONewDisplay OBJECT-TYPE
		SYNTAX		RollCallString
		MAX-ACCESS		read-only
		STATUS			current
		DESCRIPTION
				"TYPE: - Display
				 PAGE: - GPIO
					New Display  cmdID= 44453  format=   "
		::= { iqudc31CmdEntry 44453 }


	iqudc31MenuRollCallUnitName OBJECT-TYPE
		SYNTAX		RollCallString
		MAX-ACCESS		read-write
		STATUS			current
		DESCRIPTION
				"TYPE: - Editstring
				 PAGE: - RollCall
					Unit Name  cmdID= 51101  "
		::= { iqudc31CmdEntry 51101 }


	iqudc31MenuRollCallIPSharePort OBJECT-TYPE
		SYNTAX		INTEGER
		MAX-ACCESS		read-write
		STATUS			current
		DESCRIPTION
				"TYPE: - Number
				 PAGE: - RollCall
					IP Share Port  cmdID= 51105  min= 1024  max= 65535  step= 1  format= %d  div_scale= 1 
					Min = 1024  Max = -1  Step = 1 "
		::= { iqudc31CmdEntry 51105 }


	iqudc31MenuRollCallIPBridgingPort OBJECT-TYPE
		SYNTAX		INTEGER
		MAX-ACCESS		read-write
		STATUS			current
		DESCRIPTION
				"TYPE: - Number
				 PAGE: - RollCall
					IP Bridging Port  cmdID= 51106  min= 1024  max= 65535  step= 1  format= %d  div_scale= 1 
					Min = 1024  Max = -1  Step = 1 "
		::= { iqudc31CmdEntry 51106 }


	iqudc31MenuMemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Recall Memory  cmdID= 55002 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc31CmdEntry 55002 }


	iqudc31MenuMemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Sel Memory  cmdID= 55000 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc31CmdEntry 55000 }


	iqudc31MenuMemoriesSaveMemory OBJECT-TYPE
		SYNTAX		INTEGER { noAction(0),val-Save-Memory(1) }
		MAX-ACCESS		read-write
		STATUS			current
		DESCRIPTION
				"TYPE: - Button
				 PAGE: - Memories
					Save Memory  cmdID= 55001  value= 1  "
		::= { iqudc31CmdEntry 55001 }


	iqudc31MenuMemoriesClearMemory OBJECT-TYPE
		SYNTAX		INTEGER { noAction(0),val-Clear-Memory(1) }
		MAX-ACCESS		read-write
		STATUS			current
		DESCRIPTION
				"TYPE: - Button
				 PAGE: - Memories
					Clear Memory  cmdID= 55005  value= 1  "
		::= { iqudc31CmdEntry 55005 }


	iqudc31MemoriesMemoryNameChangeName OBJECT-TYPE
		SYNTAX		RollCallString
		MAX-ACCESS		read-write
		STATUS			current
		DESCRIPTION
				"TYPE: - Editstring
				 PAGE: - Memories
					Change Name  cmdID= 55003  "
		::= { iqudc31CmdEntry 55003 }


	iqudc31MenuMemoriesLastDisplayMemory OBJECT-TYPE
		SYNTAX		RollCallString
		MAX-ACCESS		read-only
		STATUS			current
		DESCRIPTION
				"TYPE: - Display
				 PAGE: - Memories
					Last Display Memory  cmdID= 55004  format=   "
		::= { iqudc31CmdEntry 55004 }


	iqudc31MenuRollTrackDisableAll OBJECT-TYPE
		SYNTAX		INTEGER { disable(0), enable(1) }
		MAX-ACCESS		read-write
		STATUS			current
		DESCRIPTION
				"TYPE: - Checkbox
				 PAGE: - RollTrack
					Disable All  cmdID= 60312 "
		::= { iqudc31CmdEntry 60312 }


	iqudc31MenuRollTrackIndex OBJECT-TYPE
		SYNTAX		INTEGER
		MAX-ACCESS		read-write
		STATUS			current
		DESCRIPTION
				"TYPE: - BarGraph
				 PAGE: - RollTrack
					Index  cmdID= 60313  min= 1  max= 50   step= 1  format= %0.0f  div_scale= 1 
					Min = 1  Max = 50  Step = 1 "
		::= { iqudc31CmdEntry 60313 }


	iqudc31MenuRollTrackSource OBJECT-TYPE
		SYNTAX		INTEGER {
							val-Unused(-1),
							val-Input-Present-Ch1(0),
							val-Input-Loss-Ch1(1),
							val-Reference-OK(2),
							val-Reference-Lost(3),
							val-Input-Present-Ch2(4),
							val-Input-Loss-Ch2(5)
							}
		MAX-ACCESS		read-write
		STATUS			current
		DESCRIPTION
				"TYPE: - RadiobuttonList
				 PAGE: - RollTrack
					Source  cmdID= 60315 
					Unused  value= -1  
					Input Present Ch1  value= 0  
					Input Loss Ch1  value= 1  
					Reference OK  value= 2  
					Reference Lost  value= 3  
					Input Present Ch2  value= 4  
					Input Loss Ch2  value= 5  "
		::= { iqudc31CmdEntry 60315 }


	iqudc31MenuRollTrackAddress OBJECT-TYPE
		SYNTAX		RollCallString
		MAX-ACCESS		read-write
		STATUS			current
		DESCRIPTION
				"TYPE: - Editstring
				 PAGE: - RollTrack
					Address  cmdID= 60317  "
		::= { iqudc31CmdEntry 60317 }


	iqudc31MenuRollTrackCommand OBJECT-TYPE
		SYNTAX		RollCallString
		MAX-ACCESS		read-write
		STATUS			current
		DESCRIPTION
				"TYPE: - Editstring
				 PAGE: - RollTrack
					Command  cmdID= 60318  "
		::= { iqudc31CmdEntry 60318 }


	iqudc31MenuRollTrackStatus OBJECT-TYPE
		SYNTAX		RollCallString
		MAX-ACCESS		read-only
		STATUS			current
		DESCRIPTION
				"TYPE: - Display
				 PAGE: - RollTrack
					Status  cmdID= 60316  format=   "
		::= { iqudc31CmdEntry 60316 }


	iqudc31MenuRollTrackSending OBJECT-TYPE
		SYNTAX		RollCallString
		MAX-ACCESS		read-only
		STATUS			current
		DESCRIPTION
				"TYPE: - Display
				 PAGE: - RollTrack
					Sending  cmdID= 60314  format=   "
		::= { iqudc31CmdEntry 60314 }


	iqudc31MenuMiscLoggingSerialNumberEnabl OBJECT-TYPE
		SYNTAX		INTEGER { disable(0), enable(1) }
		MAX-ACCESS		read-write
		STATUS			current
		DESCRIPTION
				"TYPE: - Checkbox
				 PAGE: - Misc. Logging
					Serial Number Enabl  cmdID= 62000 "
		::= { iqudc31CmdEntry 62000 }


	iqudc31MenuMiscLoggingSerialNumberStatu OBJECT-TYPE
		SYNTAX		RollCallString
		MAX-ACCESS		read-only
		STATUS			current
		DESCRIPTION
				"TYPE: - Display
				 PAGE: - Misc. Logging
					Serial Number Statu  cmdID= 62001  format=   "
		::= { iqudc31CmdEntry 62001 }


	iqudc31MenuMiscLoggingUpTimeEnable OBJECT-TYPE
		SYNTAX		INTEGER { disable(0), enable(1) }
		MAX-ACCESS		read-write
		STATUS			current
		DESCRIPTION
				"TYPE: - Checkbox
				 PAGE: - Misc. Logging
					Up Time Enable  cmdID= 62004 "
		::= { iqudc31CmdEntry 62004 }


	iqudc31MenuMiscLoggingUpTimeStatus OBJECT-TYPE
		SYNTAX		RollCallString
		MAX-ACCESS		read-only
		STATUS			current
		DESCRIPTION
				"TYPE: - Display
				 PAGE: - Misc. Logging
					Up Time Status  cmdID= 62005  format=   "
		::= { iqudc31CmdEntry 62005 }


	iqudc31MenuMiscLoggingPowerUsageStateE OBJECT-TYPE
		SYNTAX		INTEGER { disable(0), enable(1) }
		MAX-ACCESS		read-write
		STATUS			current
		DESCRIPTION
				"TYPE: - Checkbox
				 PAGE: - Misc. Logging
					Power Usage State E  cmdID= 62006 "
		::= { iqudc31CmdEntry 62006 }


	iqudc31MenuMiscLoggingPowerUsageStateS OBJECT-TYPE
		SYNTAX		RollCallString
		MAX-ACCESS		read-only
		STATUS			current
		DESCRIPTION
				"TYPE: - Display
				 PAGE: - Misc. Logging
					Power Usage State S  cmdID= 62007  format=   "
		::= { iqudc31CmdEntry 62007 }


	iqudc31MenuMiscLoggingBuild62011 OBJECT-TYPE
		SYNTAX		INTEGER { disable(0), enable(1) }
		MAX-ACCESS		read-write
		STATUS			current
		DESCRIPTION
				"TYPE: - Checkbox
				 PAGE: - Misc. Logging
					Build  cmdID= 62011 "
		::= { iqudc31CmdEntry 62011 }


	iqudc31MenuMiscLoggingBuild62010 OBJECT-TYPE
		SYNTAX		RollCallString
		MAX-ACCESS		read-only
		STATUS			current
		DESCRIPTION
				"TYPE: - Display
				 PAGE: - Misc. Logging
					Build  cmdID= 62010  format=   "
		::= { iqudc31CmdEntry 62010 }


	iqudc31MenuMiscLoggingAESOutput14Place OBJECT-TYPE
		SYNTAX		RollCallString
		MAX-ACCESS		read-only
		STATUS			current
		DESCRIPTION
				"TYPE: - Display
				 PAGE: - Misc. Logging
					AES Output1-4 Place  cmdID= 61009  format=   "
		::= { iqudc31CmdEntry 61009 }


	iqudc31MenuMiscLoggingAESOutput58Place OBJECT-TYPE
		SYNTAX		RollCallString
		MAX-ACCESS		read-only
		STATUS			current
		DESCRIPTION
				"TYPE: - Display
				 PAGE: - Misc. Logging
					AES Output5-8 Place  cmdID= 61010  format=   "
		::= { iqudc31CmdEntry 61010 }


	iqudc31MenuMiscLoggingInputADCPlacehold OBJECT-TYPE
		SYNTAX		RollCallString
		MAX-ACCESS		read-only
		STATUS			current
		DESCRIPTION
				"TYPE: - Display
				 PAGE: - Misc. Logging
					Input ADC Placehold  cmdID= 61011  format=   "
		::= { iqudc31CmdEntry 61011 }


	iqudc31MenuMiscLoggingSourceCh1Ch2Pl OBJECT-TYPE
		SYNTAX		RollCallString
		MAX-ACCESS		read-only
		STATUS			current
		DESCRIPTION
				"TYPE: - Display
				 PAGE: - Misc. Logging
					Source Ch1 & Ch2 Pl  cmdID= 61012  format=   "
		::= { iqudc31CmdEntry 61012 }


	iqudc31MenuMiscLoggingCVBSDecoderPlaceh OBJECT-TYPE
		SYNTAX		RollCallString
		MAX-ACCESS		read-only
		STATUS			current
		DESCRIPTION
				"TYPE: - Display
				 PAGE: - Misc. Logging
					CVBS Decoder Placeh  cmdID= 20500  format=   "
		::= { iqudc31CmdEntry 20500 }


	iqudc31MenuMiscLoggingFanSpeedPlacehold OBJECT-TYPE
		SYNTAX		RollCallString
		MAX-ACCESS		read-only
		STATUS			current
		DESCRIPTION
				"TYPE: - Display
				 PAGE: - Misc. Logging
					Fan Speed Placehold  cmdID= 61002  format=   "
		::= { iqudc31CmdEntry 61002 }


	iqudc31MenuVideoInputLoggingInput1Type62100 OBJECT-TYPE
		SYNTAX		INTEGER { disable(0), enable(1) }
		MAX-ACCESS		read-write
		STATUS			current
		DESCRIPTION
				"TYPE: - Checkbox
				 PAGE: - Video Input Logging
					Input 1 Type  cmdID= 62100 "
		::= { iqudc31CmdEntry 62100 }


	iqudc31MenuVideoInputLoggingInput1Type62101 OBJECT-TYPE
		SYNTAX		RollCallString
		MAX-ACCESS		read-only
		STATUS			current
		DESCRIPTION
				"TYPE: - Display
				 PAGE: - Video Input Logging
					Input 1 Type=  cmdID= 62101  format=   "
		::= { iqudc31CmdEntry 62101 }


	iqudc31MenuVideoInputLoggingInput1State62102 OBJECT-TYPE
		SYNTAX		INTEGER { disable(0), enable(1) }
		MAX-ACCESS		read-write
		STATUS			current
		DESCRIPTION
				"TYPE: - Checkbox
				 PAGE: - Video Input Logging
					Input 1 State  cmdID= 62102 "
		::= { iqudc31CmdEntry 62102 }


	iqudc31MenuVideoInputLoggingInput1State62103 OBJECT-TYPE
		SYNTAX		RollCallString
		MAX-ACCESS		read-only
		STATUS			current
		DESCRIPTION
				"TYPE: - Display
				 PAGE: - Video Input Logging
					Input 1 State=  cmdID= 62103  format=   "
		::= { iqudc31CmdEntry 62103 }


	iqudc31MenuVideoInputLoggingInput1Std62104 OBJECT-TYPE
		SYNTAX		INTEGER { disable(0), enable(1) }
		MAX-ACCESS		read-write
		STATUS			current
		DESCRIPTION
				"TYPE: - Checkbox
				 PAGE: - Video Input Logging
					Input 1 Std.  cmdID= 62104 "
		::= { iqudc31CmdEntry 62104 }


	iqudc31MenuVideoInputLoggingInput1Std62105 OBJECT-TYPE
		SYNTAX		RollCallString
		MAX-ACCESS		read-only
		STATUS			current
		DESCRIPTION
				"TYPE: - Display
				 PAGE: - Video Input Logging
					Input 1 Std.=  cmdID= 62105  format=   "
		::= { iqudc31CmdEntry 62105 }


	iqudc31MenuVideoInputLoggingInput2Type62200 OBJECT-TYPE
		SYNTAX		INTEGER { disable(0), enable(1) }
		MAX-ACCESS		read-write
		STATUS			current
		DESCRIPTION
				"TYPE: - Checkbox
				 PAGE: - Video Input Logging
					Input 2 Type  cmdID= 62200 "
		::= { iqudc31CmdEntry 62200 }


	iqudc31MenuVideoInputLoggingInput2Type62201 OBJECT-TYPE
		SYNTAX		RollCallString
		MAX-ACCESS		read-only
		STATUS			current
		DESCRIPTION
				"TYPE: - Display
				 PAGE: - Video Input Logging
					Input 2 Type=  cmdID= 62201  format=   "
		::= { iqudc31CmdEntry 62201 }


	iqudc31MenuVideoInputLoggingInput2State62202 OBJECT-TYPE
		SYNTAX		INTEGER { disable(0), enable(1) }
		MAX-ACCESS		read-write
		STATUS			current
		DESCRIPTION
				"TYPE: - Checkbox
				 PAGE: - Video Input Logging
					Input 2 State  cmdID= 62202 "
		::= { iqudc31CmdEntry 62202 }


	iqudc31MenuVideoInputLoggingInput2State62203 OBJECT-TYPE
		SYNTAX		RollCallString
		MAX-ACCESS		read-only
		STATUS			current
		DESCRIPTION
				"TYPE: - Display
				 PAGE: - Video Input Logging
					Input 2 State=  cmdID= 62203  format=   "
		::= { iqudc31CmdEntry 62203 }


	iqudc31MenuVideoInputLoggingInput2Std62204 OBJECT-TYPE
		SYNTAX		INTEGER { disable(0), enable(1) }
		MAX-ACCESS		read-write
		STATUS			current
		DESCRIPTION
				"TYPE: - Checkbox
				 PAGE: - Video Input Logging
					Input 2 Std.  cmdID= 62204 "
		::= { iqudc31CmdEntry 62204 }


	iqudc31MenuVideoInputLoggingInput2Std62205 OBJECT-TYPE
		SYNTAX		RollCallString
		MAX-ACCESS		read-only
		STATUS			current
		DESCRIPTION
				"TYPE: - Display
				 PAGE: - Video Input Logging
					Input 2 Std.=  cmdID= 62205  format=   "
		::= { iqudc31CmdEntry 62205 }


	iqudc31MenuVideoInputLoggingInput3Type62300 OBJECT-TYPE
		SYNTAX		INTEGER { disable(0), enable(1) }
		MAX-ACCESS		read-write
		STATUS			current
		DESCRIPTION
				"TYPE: - Checkbox
				 PAGE: - Video Input Logging
					Input 3 Type  cmdID= 62300 "
		::= { iqudc31CmdEntry 62300 }


	iqudc31MenuVideoInputLoggingInput3Type62301 OBJECT-TYPE
		SYNTAX		RollCallString
		MAX-ACCESS		read-only
		STATUS			current
		DESCRIPTION
				"TYPE: - Display
				 PAGE: - Video Input Logging
					Input 3 Type=  cmdID= 62301  format=   "
		::= { iqudc31CmdEntry 62301 }


	iqudc31MenuVideoInputLoggingInput3State62302 OBJECT-TYPE
		SYNTAX		INTEGER { disable(0), enable(1) }
		MAX-ACCESS		read-write
		STATUS			current
		DESCRIPTION
				"TYPE: - Checkbox
				 PAGE: - Video Input Logging
					Input 3 State  cmdID= 62302 "
		::= { iqudc31CmdEntry 62302 }


	iqudc31MenuVideoInputLoggingInput3State62303 OBJECT-TYPE
		SYNTAX		RollCallString
		MAX-ACCESS		read-only
		STATUS			current
		DESCRIPTION
				"TYPE: - Display
				 PAGE: - Video Input Logging
					Input 3 State=  cmdID= 62303  format=   "
		::= { iqudc31CmdEntry 62303 }


	iqudc31MenuVideoInputLoggingInput3Std62304 OBJECT-TYPE
		SYNTAX		INTEGER { disable(0), enable(1) }
		MAX-ACCESS		read-write
		STATUS			current
		DESCRIPTION
				"TYPE: - Checkbox
				 PAGE: - Video Input Logging
					Input 3 Std.  cmdID= 62304 "
		::= { iqudc31CmdEntry 62304 }


	iqudc31MenuVideoInputLoggingInput3Std62305 OBJECT-TYPE
		SYNTAX		RollCallString
		MAX-ACCESS		read-only
		STATUS			current
		DESCRIPTION
				"TYPE: - Display
				 PAGE: - Video Input Logging
					Input 3 Std.=  cmdID= 62305  format=   "
		::= { iqudc31CmdEntry 62305 }


	iqudc31MenuVideoInputLoggingInput4Type62400 OBJECT-TYPE
		SYNTAX		INTEGER { disable(0), enable(1) }
		MAX-ACCESS		read-write
		STATUS			current
		DESCRIPTION
				"TYPE: - Checkbox
				 PAGE: - Video Input Logging
					Input 4 Type  cmdID= 62400 "
		::= { iqudc31CmdEntry 62400 }


	iqudc31MenuVideoInputLoggingInput4Type62401 OBJECT-TYPE
		SYNTAX		RollCallString
		MAX-ACCESS		read-only
		STATUS			current
		DESCRIPTION
				"TYPE: - Display
				 PAGE: - Video Input Logging
					Input 4 Type=  cmdID= 62401  format=   "
		::= { iqudc31CmdEntry 62401 }


	iqudc31MenuVideoInputLoggingInput4State62402 OBJECT-TYPE
		SYNTAX		INTEGER { disable(0), enable(1) }
		MAX-ACCESS		read-write
		STATUS			current
		DESCRIPTION
				"TYPE: - Checkbox
				 PAGE: - Video Input Logging
					Input 4 State  cmdID= 62402 "
		::= { iqudc31CmdEntry 62402 }


	iqudc31MenuVideoInputLoggingInput4State62403 OBJECT-TYPE
		SYNTAX		RollCallString
		MAX-ACCESS		read-only
		STATUS			current
		DESCRIPTION
				"TYPE: - Display
				 PAGE: - Video Input Logging
					Input 4 State=  cmdID= 62403  format=   "
		::= { iqudc31CmdEntry 62403 }


	iqudc31MenuVideoInputLoggingInput4Std62404 OBJECT-TYPE
		SYNTAX		INTEGER { disable(0), enable(1) }
		MAX-ACCESS		read-write
		STATUS			current
		DESCRIPTION
				"TYPE: - Checkbox
				 PAGE: - Video Input Logging
					Input 4 Std.  cmdID= 62404 "
		::= { iqudc31CmdEntry 62404 }


	iqudc31MenuVideoInputLoggingInput4Std62405 OBJECT-TYPE
		SYNTAX		RollCallString
		MAX-ACCESS		read-only
		STATUS			current
		DESCRIPTION
				"TYPE: - Display
				 PAGE: - Video Input Logging
					Input 4 Std.=  cmdID= 62405  format=   "
		::= { iqudc31CmdEntry 62405 }


	iqudc31MenuVideoInputLoggingInput5Type62500 OBJECT-TYPE
		SYNTAX		INTEGER { disable(0), enable(1) }
		MAX-ACCESS		read-write
		STATUS			current
		DESCRIPTION
				"TYPE: - Checkbox
				 PAGE: - Video Input Logging
					Input 5 Type  cmdID= 62500 "
		::= { iqudc31CmdEntry 62500 }


	iqudc31MenuVideoInputLoggingInput5Type62501 OBJECT-TYPE
		SYNTAX		RollCallString
		MAX-ACCESS		read-only
		STATUS			current
		DESCRIPTION
				"TYPE: - Display
				 PAGE: - Video Input Logging
					Input 5 Type=  cmdID= 62501  format=   "
		::= { iqudc31CmdEntry 62501 }


	iqudc31MenuVideoInputLoggingInput5State62502 OBJECT-TYPE
		SYNTAX		INTEGER { disable(0), enable(1) }
		MAX-ACCESS		read-write
		STATUS			current
		DESCRIPTION
				"TYPE: - Checkbox
				 PAGE: - Video Input Logging
					Input 5 State  cmdID= 62502 "
		::= { iqudc31CmdEntry 62502 }


	iqudc31MenuVideoInputLoggingInput5State62503 OBJECT-TYPE
		SYNTAX		RollCallString
		MAX-ACCESS		read-only
		STATUS			current
		DESCRIPTION
				"TYPE: - Display
				 PAGE: - Video Input Logging
					Input 5 State=  cmdID= 62503  format=   "
		::= { iqudc31CmdEntry 62503 }


	iqudc31MenuVideoInputLoggingInput5Std62504 OBJECT-TYPE
		SYNTAX		INTEGER { disable(0), enable(1) }
		MAX-ACCESS		read-write
		STATUS			current
		DESCRIPTION
				"TYPE: - Checkbox
				 PAGE: - Video Input Logging
					Input 5 Std.  cmdID= 62504 "
		::= { iqudc31CmdEntry 62504 }


	iqudc31MenuVideoInputLoggingInput5Std62505 OBJECT-TYPE
		SYNTAX		RollCallString
		MAX-ACCESS		read-only
		STATUS			current
		DESCRIPTION
				"TYPE: - Display
				 PAGE: - Video Input Logging
					Input 5 Std.=  cmdID= 62505  format=   "
		::= { iqudc31CmdEntry 62505 }


	iqudc31MenuOutputLoggingOutput1Type62600 OBJECT-TYPE
		SYNTAX		INTEGER { disable(0), enable(1) }
		MAX-ACCESS		read-write
		STATUS			current
		DESCRIPTION
				"TYPE: - Checkbox
				 PAGE: - Output Logging
					Output 1 Type  cmdID= 62600 "
		::= { iqudc31CmdEntry 62600 }


	iqudc31MenuOutputLoggingOutput1Type62601 OBJECT-TYPE
		SYNTAX		RollCallString
		MAX-ACCESS		read-only
		STATUS			current
		DESCRIPTION
				"TYPE: - Display
				 PAGE: - Output Logging
					Output 1 Type=  cmdID= 62601  format=   "
		::= { iqudc31CmdEntry 62601 }


	iqudc31MenuOutputLoggingOutput1State62602 OBJECT-TYPE
		SYNTAX		INTEGER { disable(0), enable(1) }
		MAX-ACCESS		read-write
		STATUS			current
		DESCRIPTION
				"TYPE: - Checkbox
				 PAGE: - Output Logging
					Output 1 State  cmdID= 62602 "
		::= { iqudc31CmdEntry 62602 }


	iqudc31MenuOutputLoggingOutput1State62603 OBJECT-TYPE
		SYNTAX		RollCallString
		MAX-ACCESS		read-only
		STATUS			current
		DESCRIPTION
				"TYPE: - Display
				 PAGE: - Output Logging
					Output 1 State=  cmdID= 62603  format=   "
		::= { iqudc31CmdEntry 62603 }


	iqudc31MenuOutputLoggingOutput1Std62604 OBJECT-TYPE
		SYNTAX		INTEGER { disable(0), enable(1) }
		MAX-ACCESS		read-write
		STATUS			current
		DESCRIPTION
				"TYPE: - Checkbox
				 PAGE: - Output Logging
					Output 1 Std.  cmdID= 62604 "
		::= { iqudc31CmdEntry 62604 }


	iqudc31MenuOutputLoggingOutput1Std62605 OBJECT-TYPE
		SYNTAX		RollCallString
		MAX-ACCESS		read-only
		STATUS			current
		DESCRIPTION
				"TYPE: - Display
				 PAGE: - Output Logging
					Output 1 Std.=  cmdID= 62605  format=   "
		::= { iqudc31CmdEntry 62605 }


	iqudc31MenuOutputLoggingOutput2Type62612 OBJECT-TYPE
		SYNTAX		INTEGER { disable(0), enable(1) }
		MAX-ACCESS		read-write
		STATUS			current
		DESCRIPTION
				"TYPE: - Checkbox
				 PAGE: - Output Logging
					Output 2 Type  cmdID= 62612 "
		::= { iqudc31CmdEntry 62612 }


	iqudc31MenuOutputLoggingOutput2Type62613 OBJECT-TYPE
		SYNTAX		RollCallString
		MAX-ACCESS		read-only
		STATUS			current
		DESCRIPTION
				"TYPE: - Display
				 PAGE: - Output Logging
					Output 2 Type=  cmdID= 62613  format=   "
		::= { iqudc31CmdEntry 62613 }


	iqudc31MenuOutputLoggingOutput2State62614 OBJECT-TYPE
		SYNTAX		INTEGER { disable(0), enable(1) }
		MAX-ACCESS		read-write
		STATUS			current
		DESCRIPTION
				"TYPE: - Checkbox
				 PAGE: - Output Logging
					Output 2 State  cmdID= 62614 "
		::= { iqudc31CmdEntry 62614 }


	iqudc31MenuOutputLoggingOutput2State62615 OBJECT-TYPE
		SYNTAX		RollCallString
		MAX-ACCESS		read-only
		STATUS			current
		DESCRIPTION
				"TYPE: - Display
				 PAGE: - Output Logging
					Output 2 State=  cmdID= 62615  format=   "
		::= { iqudc31CmdEntry 62615 }


	iqudc31MenuOutputLoggingOutput2Std62616 OBJECT-TYPE
		SYNTAX		INTEGER { disable(0), enable(1) }
		MAX-ACCESS		read-write
		STATUS			current
		DESCRIPTION
				"TYPE: - Checkbox
				 PAGE: - Output Logging
					Output 2 Std.  cmdID= 62616 "
		::= { iqudc31CmdEntry 62616 }


	iqudc31MenuOutputLoggingOutput2Std62617 OBJECT-TYPE
		SYNTAX		RollCallString
		MAX-ACCESS		read-only
		STATUS			current
		DESCRIPTION
				"TYPE: - Display
				 PAGE: - Output Logging
					Output 2 Std.=  cmdID= 62617  format=   "
		::= { iqudc31CmdEntry 62617 }


	iqudc31MenuOPAudioStateCh1OutputEmbPair1s62620 OBJECT-TYPE
		SYNTAX		INTEGER { disable(0), enable(1) }
		MAX-ACCESS		read-write
		STATUS			current
		DESCRIPTION
				"TYPE: - Checkbox
				 PAGE: - O/P Audio State Ch1
					Output Emb.Pair 1 s  cmdID= 62620 "
		::= { iqudc31CmdEntry 62620 }


	iqudc31MenuOPAudioStateCh1OutputEmbPair1s62621 OBJECT-TYPE
		SYNTAX		RollCallString
		MAX-ACCESS		read-only
		STATUS			current
		DESCRIPTION
				"TYPE: - Display
				 PAGE: - O/P Audio State Ch1
					Output Emb.Pair 1 s  cmdID= 62621  format=   "
		::= { iqudc31CmdEntry 62621 }


	iqudc31MenuOPAudioStateCh1OutputEmbPair2s62622 OBJECT-TYPE
		SYNTAX		INTEGER { disable(0), enable(1) }
		MAX-ACCESS		read-write
		STATUS			current
		DESCRIPTION
				"TYPE: - Checkbox
				 PAGE: - O/P Audio State Ch1
					Output Emb.Pair 2 s  cmdID= 62622 "
		::= { iqudc31CmdEntry 62622 }


	iqudc31MenuOPAudioStateCh1OutputEmbPair2s62623 OBJECT-TYPE
		SYNTAX		RollCallString
		MAX-ACCESS		read-only
		STATUS			current
		DESCRIPTION
				"TYPE: - Display
				 PAGE: - O/P Audio State Ch1
					Output Emb.Pair 2 s  cmdID= 62623  format=   "
		::= { iqudc31CmdEntry 62623 }


	iqudc31MenuOPAudioStateCh1OutputEmbPair3s62624 OBJECT-TYPE
		SYNTAX		INTEGER { disable(0), enable(1) }
		MAX-ACCESS		read-write
		STATUS			current
		DESCRIPTION
				"TYPE: - Checkbox
				 PAGE: - O/P Audio State Ch1
					Output Emb.Pair 3 s  cmdID= 62624 "
		::= { iqudc31CmdEntry 62624 }


	iqudc31MenuOPAudioStateCh1OutputEmbPair3s62625 OBJECT-TYPE
		SYNTAX		RollCallString
		MAX-ACCESS		read-only
		STATUS			current
		DESCRIPTION
				"TYPE: - Display
				 PAGE: - O/P Audio State Ch1
					Output Emb.Pair 3 s  cmdID= 62625  format=   "
		::= { iqudc31CmdEntry 62625 }


	iqudc31MenuOPAudioStateCh1OutputEmbPair4s62626 OBJECT-TYPE
		SYNTAX		INTEGER { disable(0), enable(1) }
		MAX-ACCESS		read-write
		STATUS			current
		DESCRIPTION
				"TYPE: - Checkbox
				 PAGE: - O/P Audio State Ch1
					Output Emb.Pair 4 s  cmdID= 62626 "
		::= { iqudc31CmdEntry 62626 }


	iqudc31MenuOPAudioStateCh1OutputEmbPair4s62627 OBJECT-TYPE
		SYNTAX		RollCallString
		MAX-ACCESS		read-only
		STATUS			current
		DESCRIPTION
				"TYPE: - Display
				 PAGE: - O/P Audio State Ch1
					Output Emb.Pair 4 s  cmdID= 62627  format=   "
		::= { iqudc31CmdEntry 62627 }


	iqudc31MenuOPAudioStateCh1OutputEmbPair5s62628 OBJECT-TYPE
		SYNTAX		INTEGER { disable(0), enable(1) }
		MAX-ACCESS		read-write
		STATUS			current
		DESCRIPTION
				"TYPE: - Checkbox
				 PAGE: - O/P Audio State Ch1
					Output Emb.Pair 5 s  cmdID= 62628 "
		::= { iqudc31CmdEntry 62628 }


	iqudc31MenuOPAudioStateCh1OutputEmbPair5s62629 OBJECT-TYPE
		SYNTAX		RollCallString
		MAX-ACCESS		read-only
		STATUS			current
		DESCRIPTION
				"TYPE: - Display
				 PAGE: - O/P Audio State Ch1
					Output Emb.Pair 5 s  cmdID= 62629  format=   "
		::= { iqudc31CmdEntry 62629 }


	iqudc31MenuOPAudioStateCh1OutputEmbPair6s62630 OBJECT-TYPE
		SYNTAX		INTEGER { disable(0), enable(1) }
		MAX-ACCESS		read-write
		STATUS			current
		DESCRIPTION
				"TYPE: - Checkbox
				 PAGE: - O/P Audio State Ch1
					Output Emb.Pair 6 s  cmdID= 62630 "
		::= { iqudc31CmdEntry 62630 }


	iqudc31MenuOPAudioStateCh1OutputEmbPair6s62631 OBJECT-TYPE
		SYNTAX		RollCallString
		MAX-ACCESS		read-only
		STATUS			current
		DESCRIPTION
				"TYPE: - Display
				 PAGE: - O/P Audio State Ch1
					Output Emb.Pair 6 s  cmdID= 62631  format=   "
		::= { iqudc31CmdEntry 62631 }


	iqudc31MenuOPAudioStateCh1OutputEmbPair7s62632 OBJECT-TYPE
		SYNTAX		INTEGER { disable(0), enable(1) }
		MAX-ACCESS		read-write
		STATUS			current
		DESCRIPTION
				"TYPE: - Checkbox
				 PAGE: - O/P Audio State Ch1
					Output Emb.Pair 7 s  cmdID= 62632 "
		::= { iqudc31CmdEntry 62632 }


	iqudc31MenuOPAudioStateCh1OutputEmbPair7s62633 OBJECT-TYPE
		SYNTAX		RollCallString
		MAX-ACCESS		read-only
		STATUS			current
		DESCRIPTION
				"TYPE: - Display
				 PAGE: - O/P Audio State Ch1
					Output Emb.Pair 7 s  cmdID= 62633  format=   "
		::= { iqudc31CmdEntry 62633 }


	iqudc31MenuOPAudioStateCh1OutputEmbPair8s62634 OBJECT-TYPE
		SYNTAX		INTEGER { disable(0), enable(1) }
		MAX-ACCESS		read-write
		STATUS			current
		DESCRIPTION
				"TYPE: - Checkbox
				 PAGE: - O/P Audio State Ch1
					Output Emb.Pair 8 s  cmdID= 62634 "
		::= { iqudc31CmdEntry 62634 }


	iqudc31MenuOPAudioStateCh1OutputEmbPair8s62635 OBJECT-TYPE
		SYNTAX		RollCallString
		MAX-ACCESS		read-only
		STATUS			current
		DESCRIPTION
				"TYPE: - Display
				 PAGE: - O/P Audio State Ch1
					Output Emb.Pair 8 s  cmdID= 62635  format=   "
		::= { iqudc31CmdEntry 62635 }


	iqudc31MenuOPAudioStateCh2OutputEmbPair1s62636 OBJECT-TYPE
		SYNTAX		INTEGER { disable(0), enable(1) }
		MAX-ACCESS		read-write
		STATUS			current
		DESCRIPTION
				"TYPE: - Checkbox
				 PAGE: - O/P Audio State Ch2
					Output Emb.Pair 1 s  cmdID= 62636 "
		::= { iqudc31CmdEntry 62636 }


	iqudc31MenuOPAudioStateCh2OutputEmbPair1s62637 OBJECT-TYPE
		SYNTAX		RollCallString
		MAX-ACCESS		read-only
		STATUS			current
		DESCRIPTION
				"TYPE: - Display
				 PAGE: - O/P Audio State Ch2
					Output Emb.Pair 1 s  cmdID= 62637  format=   "
		::= { iqudc31CmdEntry 62637 }


	iqudc31MenuOPAudioStateCh2OutputEmbPair2s62638 OBJECT-TYPE
		SYNTAX		INTEGER { disable(0), enable(1) }
		MAX-ACCESS		read-write
		STATUS			current
		DESCRIPTION
				"TYPE: - Checkbox
				 PAGE: - O/P Audio State Ch2
					Output Emb.Pair 2 s  cmdID= 62638 "
		::= { iqudc31CmdEntry 62638 }


	iqudc31MenuOPAudioStateCh2OutputEmbPair2s62639 OBJECT-TYPE
		SYNTAX		RollCallString
		MAX-ACCESS		read-only
		STATUS			current
		DESCRIPTION
				"TYPE: - Display
				 PAGE: - O/P Audio State Ch2
					Output Emb.Pair 2 s  cmdID= 62639  format=   "
		::= { iqudc31CmdEntry 62639 }


	iqudc31MenuOPAudioStateCh2OutputEmbPair3s62640 OBJECT-TYPE
		SYNTAX		INTEGER { disable(0), enable(1) }
		MAX-ACCESS		read-write
		STATUS			current
		DESCRIPTION
				"TYPE: - Checkbox
				 PAGE: - O/P Audio State Ch2
					Output Emb.Pair 3 s  cmdID= 62640 "
		::= { iqudc31CmdEntry 62640 }


	iqudc31MenuOPAudioStateCh2OutputEmbPair3s62641 OBJECT-TYPE
		SYNTAX		RollCallString
		MAX-ACCESS		read-only
		STATUS			current
		DESCRIPTION
				"TYPE: - Display
				 PAGE: - O/P Audio State Ch2
					Output Emb.Pair 3 s  cmdID= 62641  format=   "
		::= { iqudc31CmdEntry 62641 }


	iqudc31MenuOPAudioStateCh2OutputEmbPair4s62642 OBJECT-TYPE
		SYNTAX		INTEGER { disable(0), enable(1) }
		MAX-ACCESS		read-write
		STATUS			current
		DESCRIPTION
				"TYPE: - Checkbox
				 PAGE: - O/P Audio State Ch2
					Output Emb.Pair 4 s  cmdID= 62642 "
		::= { iqudc31CmdEntry 62642 }


	iqudc31MenuOPAudioStateCh2OutputEmbPair4s62643 OBJECT-TYPE
		SYNTAX		RollCallString
		MAX-ACCESS		read-only
		STATUS			current
		DESCRIPTION
				"TYPE: - Display
				 PAGE: - O/P Audio State Ch2
					Output Emb.Pair 4 s  cmdID= 62643  format=   "
		::= { iqudc31CmdEntry 62643 }


	iqudc31MenuOPAudioStateCh2OutputEmbPair5s62644 OBJECT-TYPE
		SYNTAX		INTEGER { disable(0), enable(1) }
		MAX-ACCESS		read-write
		STATUS			current
		DESCRIPTION
				"TYPE: - Checkbox
				 PAGE: - O/P Audio State Ch2
					Output Emb.Pair 5 s  cmdID= 62644 "
		::= { iqudc31CmdEntry 62644 }


	iqudc31MenuOPAudioStateCh2OutputEmbPair5s62645 OBJECT-TYPE
		SYNTAX		RollCallString
		MAX-ACCESS		read-only
		STATUS			current
		DESCRIPTION
				"TYPE: - Display
				 PAGE: - O/P Audio State Ch2
					Output Emb.Pair 5 s  cmdID= 62645  format=   "
		::= { iqudc31CmdEntry 62645 }


	iqudc31MenuOPAudioStateCh2OutputEmbPair6s62646 OBJECT-TYPE
		SYNTAX		INTEGER { disable(0), enable(1) }
		MAX-ACCESS		read-write
		STATUS			current
		DESCRIPTION
				"TYPE: - Checkbox
				 PAGE: - O/P Audio State Ch2
					Output Emb.Pair 6 s  cmdID= 62646 "
		::= { iqudc31CmdEntry 62646 }


	iqudc31MenuOPAudioStateCh2OutputEmbPair6s62647 OBJECT-TYPE
		SYNTAX		RollCallString
		MAX-ACCESS		read-only
		STATUS			current
		DESCRIPTION
				"TYPE: - Display
				 PAGE: - O/P Audio State Ch2
					Output Emb.Pair 6 s  cmdID= 62647  format=   "
		::= { iqudc31CmdEntry 62647 }


	iqudc31MenuOPAudioStateCh2OutputEmbPair7s62648 OBJECT-TYPE
		SYNTAX		INTEGER { disable(0), enable(1) }
		MAX-ACCESS		read-write
		STATUS			current
		DESCRIPTION
				"TYPE: - Checkbox
				 PAGE: - O/P Audio State Ch2
					Output Emb.Pair 7 s  cmdID= 62648 "
		::= { iqudc31CmdEntry 62648 }


	iqudc31MenuOPAudioStateCh2OutputEmbPair7s62649 OBJECT-TYPE
		SYNTAX		RollCallString
		MAX-ACCESS		read-only
		STATUS			current
		DESCRIPTION
				"TYPE: - Display
				 PAGE: - O/P Audio State Ch2
					Output Emb.Pair 7 s  cmdID= 62649  format=   "
		::= { iqudc31CmdEntry 62649 }


	iqudc31MenuOPAudioStateCh2OutputEmbPair8s62650 OBJECT-TYPE
		SYNTAX		INTEGER { disable(0), enable(1) }
		MAX-ACCESS		read-write
		STATUS			current
		DESCRIPTION
				"TYPE: - Checkbox
				 PAGE: - O/P Audio State Ch2
					Output Emb.Pair 8 s  cmdID= 62650 "
		::= { iqudc31CmdEntry 62650 }


	iqudc31MenuOPAudioStateCh2OutputEmbPair8s62651 OBJECT-TYPE
		SYNTAX		RollCallString
		MAX-ACCESS		read-only
		STATUS			current
		DESCRIPTION
				"TYPE: - Display
				 PAGE: - O/P Audio State Ch2
					Output Emb.Pair 8 s  cmdID= 62651  format=   "
		::= { iqudc31CmdEntry 62651 }


	iqudc31MenuOPAudioStateCh2NewDisplay OBJECT-TYPE
		SYNTAX		RollCallString
		MAX-ACCESS		read-only
		STATUS			current
		DESCRIPTION
				"TYPE: - Display
				 PAGE: - O/P Audio State Ch2
					New Display  cmdID= 62652  format=   "
		::= { iqudc31CmdEntry 62652 }


	iqudc31MenuOPAudioTypeCh1OutputEmbPair1t62653 OBJECT-TYPE
		SYNTAX		INTEGER { disable(0), enable(1) }
		MAX-ACCESS		read-write
		STATUS			current
		DESCRIPTION
				"TYPE: - Checkbox
				 PAGE: - O/P Audio Type Ch1 
					Output Emb.Pair 1 t  cmdID= 62653 "
		::= { iqudc31CmdEntry 62653 }


	iqudc31MenuOPAudioTypeCh1OutputEmbPair1t62654 OBJECT-TYPE
		SYNTAX		RollCallString
		MAX-ACCESS		read-only
		STATUS			current
		DESCRIPTION
				"TYPE: - Display
				 PAGE: - O/P Audio Type Ch1 
					Output Emb.Pair 1 t  cmdID= 62654  format=   "
		::= { iqudc31CmdEntry 62654 }


	iqudc31MenuOPAudioTypeCh1OutputEmbPair2t OBJECT-TYPE
		SYNTAX		INTEGER { disable(0), enable(1) }
		MAX-ACCESS		read-write
		STATUS			current
		DESCRIPTION
				"TYPE: - Checkbox
				 PAGE: - O/P Audio Type Ch1 
					Output Emb.Pair 2 t  cmdID= 62655 "
		::= { iqudc31CmdEntry 62655 }


	iqudc31MenuOPAudioTypeCh1OutputEmbPair2s OBJECT-TYPE
		SYNTAX		RollCallString
		MAX-ACCESS		read-only
		STATUS			current
		DESCRIPTION
				"TYPE: - Display
				 PAGE: - O/P Audio Type Ch1 
					Output Emb.Pair 2 s  cmdID= 62656  format=   "
		::= { iqudc31CmdEntry 62656 }


	iqudc31MenuOPAudioTypeCh1OutputEmbPair3t62657 OBJECT-TYPE
		SYNTAX		INTEGER { disable(0), enable(1) }
		MAX-ACCESS		read-write
		STATUS			current
		DESCRIPTION
				"TYPE: - Checkbox
				 PAGE: - O/P Audio Type Ch1 
					Output Emb.Pair 3 t  cmdID= 62657 "
		::= { iqudc31CmdEntry 62657 }


	iqudc31MenuOPAudioTypeCh1OutputEmbPair3t62658 OBJECT-TYPE
		SYNTAX		RollCallString
		MAX-ACCESS		read-only
		STATUS			current
		DESCRIPTION
				"TYPE: - Display
				 PAGE: - O/P Audio Type Ch1 
					Output Emb.Pair 3 t  cmdID= 62658  format=   "
		::= { iqudc31CmdEntry 62658 }


	iqudc31MenuOPAudioTypeCh1OutputEmbPair4t62659 OBJECT-TYPE
		SYNTAX		INTEGER { disable(0), enable(1) }
		MAX-ACCESS		read-write
		STATUS			current
		DESCRIPTION
				"TYPE: - Checkbox
				 PAGE: - O/P Audio Type Ch1 
					Output Emb.Pair 4 t  cmdID= 62659 "
		::= { iqudc31CmdEntry 62659 }


	iqudc31MenuOPAudioTypeCh1OutputEmbPair4t62660 OBJECT-TYPE
		SYNTAX		RollCallString
		MAX-ACCESS		read-only
		STATUS			current
		DESCRIPTION
				"TYPE: - Display
				 PAGE: - O/P Audio Type Ch1 
					Output Emb.Pair 4 t  cmdID= 62660  format=   "
		::= { iqudc31CmdEntry 62660 }


	iqudc31MenuOPAudioTypeCh1OutputEmbPair5t62661 OBJECT-TYPE
		SYNTAX		INTEGER { disable(0), enable(1) }
		MAX-ACCESS		read-write
		STATUS			current
		DESCRIPTION
				"TYPE: - Checkbox
				 PAGE: - O/P Audio Type Ch1 
					Output Emb.Pair 5 t  cmdID= 62661 "
		::= { iqudc31CmdEntry 62661 }


	iqudc31MenuOPAudioTypeCh1OutputEmbPair5t62662 OBJECT-TYPE
		SYNTAX		RollCallString
		MAX-ACCESS		read-only
		STATUS			current
		DESCRIPTION
				"TYPE: - Display
				 PAGE: - O/P Audio Type Ch1 
					Output Emb.Pair 5 t  cmdID= 62662  format=   "
		::= { iqudc31CmdEntry 62662 }


	iqudc31MenuOPAudioTypeCh1OutputEmbPair6t62663 OBJECT-TYPE
		SYNTAX		INTEGER { disable(0), enable(1) }
		MAX-ACCESS		read-write
		STATUS			current
		DESCRIPTION
				"TYPE: - Checkbox
				 PAGE: - O/P Audio Type Ch1 
					Output Emb.Pair 6 t  cmdID= 62663 "
		::= { iqudc31CmdEntry 62663 }


	iqudc31MenuOPAudioTypeCh1OutputEmbPair6t62664 OBJECT-TYPE
		SYNTAX		RollCallString
		MAX-ACCESS		read-only
		STATUS			current
		DESCRIPTION
				"TYPE: - Display
				 PAGE: - O/P Audio Type Ch1 
					Output Emb.Pair 6 t  cmdID= 62664  format=   "
		::= { iqudc31CmdEntry 62664 }


	iqudc31MenuOPAudioTypeCh1OutputEmbPair7t62665 OBJECT-TYPE
		SYNTAX		INTEGER { disable(0), enable(1) }
		MAX-ACCESS		read-write
		STATUS			current
		DESCRIPTION
				"TYPE: - Checkbox
				 PAGE: - O/P Audio Type Ch1 
					Output Emb.Pair 7 t  cmdID= 62665 "
		::= { iqudc31CmdEntry 62665 }


	iqudc31MenuOPAudioTypeCh1OutputEmbPair7t62666 OBJECT-TYPE
		SYNTAX		RollCallString
		MAX-ACCESS		read-only
		STATUS			current
		DESCRIPTION
				"TYPE: - Display
				 PAGE: - O/P Audio Type Ch1 
					Output Emb.Pair 7 t  cmdID= 62666  format=   "
		::= { iqudc31CmdEntry 62666 }


	iqudc31MenuOPAudioTypeCh1OutputEmbPair8t62667 OBJECT-TYPE
		SYNTAX		INTEGER { disable(0), enable(1) }
		MAX-ACCESS		read-write
		STATUS			current
		DESCRIPTION
				"TYPE: - Checkbox
				 PAGE: - O/P Audio Type Ch1 
					Output Emb.Pair 8 t  cmdID= 62667 "
		::= { iqudc31CmdEntry 62667 }


	iqudc31MenuOPAudioTypeCh1OutputEmbPair8t62668 OBJECT-TYPE
		SYNTAX		RollCallString
		MAX-ACCESS		read-only
		STATUS			current
		DESCRIPTION
				"TYPE: - Display
				 PAGE: - O/P Audio Type Ch1 
					Output Emb.Pair 8 t  cmdID= 62668  format=   "
		::= { iqudc31CmdEntry 62668 }


	iqudc31MenuOPAudioTypeCh2OutputEmbPair1t62669 OBJECT-TYPE
		SYNTAX		INTEGER { disable(0), enable(1) }
		MAX-ACCESS		read-write
		STATUS			current
		DESCRIPTION
				"TYPE: - Checkbox
				 PAGE: - O/P Audio Type Ch2 
					Output Emb.Pair 1 t  cmdID= 62669 "
		::= { iqudc31CmdEntry 62669 }


	iqudc31MenuOPAudioTypeCh2OutputEmbPair1t62670 OBJECT-TYPE
		SYNTAX		RollCallString
		MAX-ACCESS		read-only
		STATUS			current
		DESCRIPTION
				"TYPE: - Display
				 PAGE: - O/P Audio Type Ch2 
					Output Emb.Pair 1 t  cmdID= 62670  format=   "
		::= { iqudc31CmdEntry 62670 }


	iqudc31MenuOPAudioTypeCh2OutputEmbPair2t62671 OBJECT-TYPE
		SYNTAX		INTEGER { disable(0), enable(1) }
		MAX-ACCESS		read-write
		STATUS			current
		DESCRIPTION
				"TYPE: - Checkbox
				 PAGE: - O/P Audio Type Ch2 
					Output Emb.Pair 2 t  cmdID= 62671 "
		::= { iqudc31CmdEntry 62671 }


	iqudc31MenuOPAudioTypeCh2OutputEmbPair2t62672 OBJECT-TYPE
		SYNTAX		RollCallString
		MAX-ACCESS		read-only
		STATUS			current
		DESCRIPTION
				"TYPE: - Display
				 PAGE: - O/P Audio Type Ch2 
					Output Emb.Pair 2 t  cmdID= 62672  format=   "
		::= { iqudc31CmdEntry 62672 }


	iqudc31MenuOPAudioTypeCh2OutputEmbPair3t62673 OBJECT-TYPE
		SYNTAX		INTEGER { disable(0), enable(1) }
		MAX-ACCESS		read-write
		STATUS			current
		DESCRIPTION
				"TYPE: - Checkbox
				 PAGE: - O/P Audio Type Ch2 
					Output Emb.Pair 3 t  cmdID= 62673 "
		::= { iqudc31CmdEntry 62673 }


	iqudc31MenuOPAudioTypeCh2OutputEmbPair3t62674 OBJECT-TYPE
		SYNTAX		RollCallString
		MAX-ACCESS		read-only
		STATUS			current
		DESCRIPTION
				"TYPE: - Display
				 PAGE: - O/P Audio Type Ch2 
					Output Emb.Pair 3 t  cmdID= 62674  format=   "
		::= { iqudc31CmdEntry 62674 }


	iqudc31MenuOPAudioTypeCh2OutputEmbPair4t62675 OBJECT-TYPE
		SYNTAX		INTEGER { disable(0), enable(1) }
		MAX-ACCESS		read-write
		STATUS			current
		DESCRIPTION
				"TYPE: - Checkbox
				 PAGE: - O/P Audio Type Ch2 
					Output Emb.Pair 4 t  cmdID= 62675 "
		::= { iqudc31CmdEntry 62675 }


	iqudc31MenuOPAudioTypeCh2OutputEmbPair4t62676 OBJECT-TYPE
		SYNTAX		RollCallString
		MAX-ACCESS		read-only
		STATUS			current
		DESCRIPTION
				"TYPE: - Display
				 PAGE: - O/P Audio Type Ch2 
					Output Emb.Pair 4 t  cmdID= 62676  format=   "
		::= { iqudc31CmdEntry 62676 }


	iqudc31MenuOPAudioTypeCh2OutputEmbPair5t62677 OBJECT-TYPE
		SYNTAX		INTEGER { disable(0), enable(1) }
		MAX-ACCESS		read-write
		STATUS			current
		DESCRIPTION
				"TYPE: - Checkbox
				 PAGE: - O/P Audio Type Ch2 
					Output Emb.Pair 5 t  cmdID= 62677 "
		::= { iqudc31CmdEntry 62677 }


	iqudc31MenuOPAudioTypeCh2OutputEmbPair5t62678 OBJECT-TYPE
		SYNTAX		RollCallString
		MAX-ACCESS		read-only
		STATUS			current
		DESCRIPTION
				"TYPE: - Display
				 PAGE: - O/P Audio Type Ch2 
					Output Emb.Pair 5 t  cmdID= 62678  format=   "
		::= { iqudc31CmdEntry 62678 }


	iqudc31MenuOPAudioTypeCh2OutputEmbPair6t62679 OBJECT-TYPE
		SYNTAX		INTEGER { disable(0), enable(1) }
		MAX-ACCESS		read-write
		STATUS			current
		DESCRIPTION
				"TYPE: - Checkbox
				 PAGE: - O/P Audio Type Ch2 
					Output Emb.Pair 6 t  cmdID= 62679 "
		::= { iqudc31CmdEntry 62679 }


	iqudc31MenuOPAudioTypeCh2OutputEmbPair6t62680 OBJECT-TYPE
		SYNTAX		RollCallString
		MAX-ACCESS		read-only
		STATUS			current
		DESCRIPTION
				"TYPE: - Display
				 PAGE: - O/P Audio Type Ch2 
					Output Emb.Pair 6 t  cmdID= 62680  format=   "
		::= { iqudc31CmdEntry 62680 }


	iqudc31MenuOPAudioTypeCh2OutputEmbPair7t62681 OBJECT-TYPE
		SYNTAX		INTEGER { disable(0), enable(1) }
		MAX-ACCESS		read-write
		STATUS			current
		DESCRIPTION
				"TYPE: - Checkbox
				 PAGE: - O/P Audio Type Ch2 
					Output Emb.Pair 7 t  cmdID= 62681 "
		::= { iqudc31CmdEntry 62681 }


	iqudc31MenuOPAudioTypeCh2OutputEmbPair7t62682 OBJECT-TYPE
		SYNTAX		RollCallString
		MAX-ACCESS		read-only
		STATUS			current
		DESCRIPTION
				"TYPE: - Display
				 PAGE: - O/P Audio Type Ch2 
					Output Emb.Pair 7 t  cmdID= 62682  format=   "
		::= { iqudc31CmdEntry 62682 }


	iqudc31MenuOPAudioTypeCh2OutputEmbPair8t62683 OBJECT-TYPE
		SYNTAX		INTEGER { disable(0), enable(1) }
		MAX-ACCESS		read-write
		STATUS			current
		DESCRIPTION
				"TYPE: - Checkbox
				 PAGE: - O/P Audio Type Ch2 
					Output Emb.Pair 8 t  cmdID= 62683 "
		::= { iqudc31CmdEntry 62683 }


	iqudc31MenuOPAudioTypeCh2OutputEmbPair8t62684 OBJECT-TYPE
		SYNTAX		RollCallString
		MAX-ACCESS		read-only
		STATUS			current
		DESCRIPTION
				"TYPE: - Display
				 PAGE: - O/P Audio Type Ch2 
					Output Emb.Pair 8 t  cmdID= 62684  format=   "
		::= { iqudc31CmdEntry 62684 }


	iqudc31MenuOPAudioTypeCh2NewDisplay OBJECT-TYPE
		SYNTAX		RollCallString
		MAX-ACCESS		read-only
		STATUS			current
		DESCRIPTION
				"TYPE: - Display
				 PAGE: - O/P Audio Type Ch2 
					New Display  cmdID= 62685  format=   "
		::= { iqudc31CmdEntry 62685 }


	iqudc31MenuSetupSoftwareVersion OBJECT-TYPE
		SYNTAX		RollCallString
		MAX-ACCESS		read-only
		STATUS			current
		DESCRIPTION
				"TYPE: - Display
				 PAGE: - Setup
					Software Version  cmdID= 2  format=   "
		::= { iqudc31CmdEntry 2 }


	iqudc31MenuSetupSerialNumber OBJECT-TYPE
		SYNTAX		RollCallString
		MAX-ACCESS		read-only
		STATUS			current
		DESCRIPTION
				"TYPE: - Display
				 PAGE: - Setup
					Serial Number  cmdID= 1  format=   "
		::= { iqudc31CmdEntry 1 }


	iqudc31MenuSetupNumberOfChannels OBJECT-TYPE
		SYNTAX		RollCallString
		MAX-ACCESS		read-only
		STATUS			current
		DESCRIPTION
				"TYPE: - Display
				 PAGE: - Setup
					Number Of Channels  cmdID= 44456  format=   "
		::= { iqudc31CmdEntry 44456 }


	iqudc31MenuSetupFrameSlotNumber OBJECT-TYPE
		SYNTAX		RollCallString
		MAX-ACCESS		read-only
		STATUS			current
		DESCRIPTION
				"TYPE: - Display
				 PAGE: - Setup
					Frame Slot Number  cmdID= 44455  format=   "
		::= { iqudc31CmdEntry 44455 }


	iqudc31MenuSetupRearId OBJECT-TYPE
		SYNTAX		RollCallString
		MAX-ACCESS		read-only
		STATUS			current
		DESCRIPTION
				"TYPE: - Display
				 PAGE: - Setup
					Rear Id  cmdID= 44444  format=   "
		::= { iqudc31CmdEntry 44444 }


	iqudc31MenuSetupFanSpeed OBJECT-TYPE
		SYNTAX		RollCallString
		MAX-ACCESS		read-only
		STATUS			current
		DESCRIPTION
				"TYPE: - Display
				 PAGE: - Setup
					Fan Speed  cmdID= 61003  format=   "
		::= { iqudc31CmdEntry 61003 }


	iqudc31MenuSetupIQOPTMNR OBJECT-TYPE
		SYNTAX		RollCallString
		MAX-ACCESS		read-only
		STATUS			current
		DESCRIPTION
				"TYPE: - Display
				 PAGE: - Setup
					IQOPTM-NR  cmdID= 62687  format=   "
		::= { iqudc31CmdEntry 62687 }


	iqudc31MenuSetupIQOPTMSBK OBJECT-TYPE
		SYNTAX		RollCallString
		MAX-ACCESS		read-only
		STATUS			current
		DESCRIPTION
				"TYPE: - Display
				 PAGE: - Setup
					IQOPTM-SBK  cmdID= 62688  format=   "
		::= { iqudc31CmdEntry 62688 }


	iqudc31MenuSetupIQOPTMLFR OBJECT-TYPE
		SYNTAX		RollCallString
		MAX-ACCESS		read-only
		STATUS			current
		DESCRIPTION
				"TYPE: - Display
				 PAGE: - Setup
					IQOPTM-LFR  cmdID= 62691  format=   "
		::= { iqudc31CmdEntry 62691 }


	iqudc31MenuSetupIQOPTMLOG OBJECT-TYPE
		SYNTAX		RollCallString
		MAX-ACCESS		read-only
		STATUS			current
		DESCRIPTION
				"TYPE: - Display
				 PAGE: - Setup
					IQOPTM-LOG  cmdID= 62692  format=   "
		::= { iqudc31CmdEntry 62692 }


	iqudc31MenuSetupIQOPTMLC OBJECT-TYPE
		SYNTAX		RollCallString
		MAX-ACCESS		read-only
		STATUS			current
		DESCRIPTION
				"TYPE: - Display
				 PAGE: - Setup
					IQOPTM-LC  cmdID= 62693  format=   "
		::= { iqudc31CmdEntry 62693 }


	iqudc31MenuSetupIQOPTMDBD OBJECT-TYPE
		SYNTAX		RollCallString
		MAX-ACCESS		read-only
		STATUS			current
		DESCRIPTION
				"TYPE: - Display
				 PAGE: - Setup
					IQOPTM-DBD  cmdID= 62694  format=   "
		::= { iqudc31CmdEntry 62694 }


	iqudc31MenuSetupIQOPTMDBEE OBJECT-TYPE
		SYNTAX		RollCallString
		MAX-ACCESS		read-only
		STATUS			current
		DESCRIPTION
				"TYPE: - Display
				 PAGE: - Setup
					IQOPTM-DBE-E  cmdID= 62695  format=   "
		::= { iqudc31CmdEntry 62695 }


	iqudc31MenuSetupIQOPTMDBED OBJECT-TYPE
		SYNTAX		RollCallString
		MAX-ACCESS		read-only
		STATUS			current
		DESCRIPTION
				"TYPE: - Display
				 PAGE: - Setup
					IQOPTM-DBE-D  cmdID= 62696  format=   "
		::= { iqudc31CmdEntry 62696 }


	iqudc31MenuSetupIQOPTMLOUDJ OBJECT-TYPE
		SYNTAX		RollCallString
		MAX-ACCESS		read-only
		STATUS			current
		DESCRIPTION
				"TYPE: - Display
				 PAGE: - Setup
					IQOPTM-LOUD-J  cmdID= 62697  format=   "
		::= { iqudc31CmdEntry 62697 }


	iqudc31MenuSetupIQOPTMLOUDMC OBJECT-TYPE
		SYNTAX		RollCallString
		MAX-ACCESS		read-only
		STATUS			current
		DESCRIPTION
				"TYPE: - Display
				 PAGE: - Setup
					IQOPTM-LOUD-MC  cmdID= 62698  format=   "
		::= { iqudc31CmdEntry 62698 }


	iqudc31MenuSetupBuild OBJECT-TYPE
		SYNTAX		RollCallString
		MAX-ACCESS		read-only
		STATUS			current
		DESCRIPTION
				"TYPE: - Display
				 PAGE: - Setup
					Build  cmdID= 62689  format=   "
		::= { iqudc31CmdEntry 62689 }


	iqudc31MenuSetupLicencedOptionsH OBJECT-TYPE
		SYNTAX		RollCallString
		MAX-ACCESS		read-only
		STATUS			current
		DESCRIPTION
				"TYPE: - Display
				 PAGE: - Setup
					Licenced Options (H  cmdID= 62690  format=   "
		::= { iqudc31CmdEntry 62690 }


	iqudc31MenuSetupFactoryDefaults OBJECT-TYPE
		SYNTAX		INTEGER { noAction(0),val-Factory-Defaults(1) }
		MAX-ACCESS		read-write
		STATUS			current
		DESCRIPTION
				"TYPE: - Button
				 PAGE: - Setup
					Factory Defaults  cmdID= 55555  value= 1  "
		::= { iqudc31CmdEntry 55555 }


	iqudc31MenuSetupDefaultSettings OBJECT-TYPE
		SYNTAX		INTEGER { noAction(0),val-Default-Settings(1) }
		MAX-ACCESS		read-write
		STATUS			current
		DESCRIPTION
				"TYPE: - Button
				 PAGE: - Setup
					Default Settings  cmdID= 55054  value= 1  "
		::= { iqudc31CmdEntry 55054 }


	iqudc31MenuSetupRestart OBJECT-TYPE
		SYNTAX		INTEGER { noAction(0),val-Restart(1) }
		MAX-ACCESS		read-write
		STATUS			current
		DESCRIPTION
				"TYPE: - Button
				 PAGE: - Setup
					Restart  cmdID= 4  value= 1  "
		::= { iqudc31CmdEntry 4 }


	iqudc31MenuSetupUpgradeStartHide OBJECT-TYPE
		SYNTAX		INTEGER { noAction(0),val-Upgrade-Start-Hide(1) }
		MAX-ACCESS		read-write
		STATUS			current
		DESCRIPTION
				"TYPE: - Button
				 PAGE: - Setup
					Upgrade Start (Hide  cmdID= 5  value= 1  "
		::= { iqudc31CmdEntry 5 }


	iqudc31MenuSetupUpgradeFinishHid OBJECT-TYPE
		SYNTAX		INTEGER { noAction(0),val-Upgrade-Finish-Hid(1) }
		MAX-ACCESS		read-write
		STATUS			current
		DESCRIPTION
				"TYPE: - Button
				 PAGE: - Setup
					Upgrade Finish (Hid  cmdID= 6  value= 1  "
		::= { iqudc31CmdEntry 6 }


	iqudc31MenuDisplaymenu OBJECT-TYPE
		SYNTAX		INTEGER {
							val-Video-Input(0),
							val-Video-Output(1),
							val-Audio(2),
							val-Metadata(3),
							val-Reference(4)
							}
		MAX-ACCESS		read-write
		STATUS			current
		DESCRIPTION
				"TYPE: - RadiobuttonList
				 PAGE: - Displaymenu
					Display  cmdID= 62686 
					Video Input  value= 0  
					Video Output  value= 1  
					Audio  value= 2  
					Metadata  value= 3  
					Reference  value= 4  "
		::= { iqudc31CmdEntry 62686 }


	iqudc31MenuPlaceholderCh1ScrollingCaptionG OBJECT-TYPE
		SYNTAX		RollCallString
		MAX-ACCESS		read-only
		STATUS			current
		DESCRIPTION
				"TYPE: - Display
				 PAGE: - Placeholder-Ch1
					Scrolling Caption G  cmdID= 44459  format=   "
		::= { iqudc31CmdEntry 44459 }


	iqudc31MenuPlaceholderCh1SFPOutputRouting OBJECT-TYPE
		SYNTAX		RollCallString
		MAX-ACCESS		read-only
		STATUS			current
		DESCRIPTION
				"TYPE: - Display
				 PAGE: - Placeholder-Ch1
					SFP Output Routing   cmdID= 20515  format=   "
		::= { iqudc31CmdEntry 20515 }


	iqudc31MenuPlaceholderCh1CVBSEncoderPlaceh OBJECT-TYPE
		SYNTAX		RollCallString
		MAX-ACCESS		read-only
		STATUS			current
		DESCRIPTION
				"TYPE: - Display
				 PAGE: - Placeholder-Ch1
					CVBS Encoder Placeh  cmdID= 20507  format=   "
		::= { iqudc31CmdEntry 20507 }


	iqudc31MenuPlaceholderCh1NonlinearEnhancer OBJECT-TYPE
		SYNTAX		RollCallString
		MAX-ACCESS		read-only
		STATUS			current
		DESCRIPTION
				"TYPE: - Display
				 PAGE: - Placeholder-Ch1
					Nonlinear Enhancer   cmdID= 64120  format=   "
		::= { iqudc31CmdEntry 64120 }


	iqudc31MenuPlaceholderCh1ConversionAperture OBJECT-TYPE
		SYNTAX		RollCallString
		MAX-ACCESS		read-only
		STATUS			current
		DESCRIPTION
				"TYPE: - Display
				 PAGE: - Placeholder-Ch1
					Conversion Aperture  cmdID= 64121  format=   "
		::= { iqudc31CmdEntry 64121 }


	iqudc31MenuPlaceholderCh1NoiseReducerPlace OBJECT-TYPE
		SYNTAX		RollCallString
		MAX-ACCESS		read-only
		STATUS			current
		DESCRIPTION
				"TYPE: - Display
				 PAGE: - Placeholder-Ch1
					Noise Reducer Place  cmdID= 64102  format=   "
		::= { iqudc31CmdEntry 64102 }


	iqudc31MenuPlaceholderCh1UpConversionPlace OBJECT-TYPE
		SYNTAX		RollCallString
		MAX-ACCESS		read-only
		STATUS			current
		DESCRIPTION
				"TYPE: - Display
				 PAGE: - Placeholder-Ch1
					Up Conversion Place  cmdID= 64103  format=   "
		::= { iqudc31CmdEntry 64103 }


	iqudc31MenuPlaceholderCh1GenlockTimingPlac OBJECT-TYPE
		SYNTAX		RollCallString
		MAX-ACCESS		read-only
		STATUS			current
		DESCRIPTION
				"TYPE: - Display
				 PAGE: - Placeholder-Ch1
					Genlock Timing Plac  cmdID= 64201  format=   "
		::= { iqudc31CmdEntry 64201 }


	iqudc31MenuPlaceholderCh1ClosedCaptions708 OBJECT-TYPE
		SYNTAX		RollCallString
		MAX-ACCESS		read-only
		STATUS			current
		DESCRIPTION
				"TYPE: - Display
				 PAGE: - Placeholder-Ch1
					Closed Captions 708  cmdID= 62699  format=   "
		::= { iqudc31CmdEntry 62699 }


	iqudc31MenuPlaceholderCh2InputSourcePlaceh OBJECT-TYPE
		SYNTAX		RollCallString
		MAX-ACCESS		read-only
		STATUS			current
		DESCRIPTION
				"TYPE: - Display
				 PAGE: - Placeholder-Ch2
					Input Source Placeh  cmdID= 44445  format=   "
		::= { iqudc31CmdEntry 44445 }


	iqudc31MenuPlaceholderCh2ScrollingCaptionG OBJECT-TYPE
		SYNTAX		RollCallString
		MAX-ACCESS		read-only
		STATUS			current
		DESCRIPTION
				"TYPE: - Display
				 PAGE: - Placeholder-Ch2
					Scrolling Caption G  cmdID= 44460  format=   "
		::= { iqudc31CmdEntry 44460 }


	iqudc31MenuPlaceholderCh2SFPOutputRouting OBJECT-TYPE
		SYNTAX		RollCallString
		MAX-ACCESS		read-only
		STATUS			current
		DESCRIPTION
				"TYPE: - Display
				 PAGE: - Placeholder-Ch2
					SFP Output Routing   cmdID= 20518  format=   "
		::= { iqudc31CmdEntry 20518 }


	iqudc31MenuPlaceholderCh2CVBSEncoderPlaceh OBJECT-TYPE
		SYNTAX		RollCallString
		MAX-ACCESS		read-only
		STATUS			current
		DESCRIPTION
				"TYPE: - Display
				 PAGE: - Placeholder-Ch2
					CVBS Encoder Placeh  cmdID= 20511  format=   "
		::= { iqudc31CmdEntry 20511 }


	iqudc31MenuPlaceholderCh2NonlinearEnhancer OBJECT-TYPE
		SYNTAX		RollCallString
		MAX-ACCESS		read-only
		STATUS			current
		DESCRIPTION
				"TYPE: - Display
				 PAGE: - Placeholder-Ch2
					Nonlinear Enhancer   cmdID= 64122  format=   "
		::= { iqudc31CmdEntry 64122 }


	iqudc31MenuPlaceholderCh2ConversionAperture OBJECT-TYPE
		SYNTAX		RollCallString
		MAX-ACCESS		read-only
		STATUS			current
		DESCRIPTION
				"TYPE: - Display
				 PAGE: - Placeholder-Ch2
					Conversion Aperture  cmdID= 64123  format=   "
		::= { iqudc31CmdEntry 64123 }


	iqudc31MenuPlaceholderCh2NoiseReducerPlace OBJECT-TYPE
		SYNTAX		RollCallString
		MAX-ACCESS		read-only
		STATUS			current
		DESCRIPTION
				"TYPE: - Display
				 PAGE: - Placeholder-Ch2
					Noise Reducer Place  cmdID= 64202  format=   "
		::= { iqudc31CmdEntry 64202 }


	iqudc31MenuPlaceholderCh2UpConversionPlace OBJECT-TYPE
		SYNTAX		RollCallString
		MAX-ACCESS		read-only
		STATUS			current
		DESCRIPTION
				"TYPE: - Display
				 PAGE: - Placeholder-Ch2
					Up Conversion Place  cmdID= 64203  format=   "
		::= { iqudc31CmdEntry 64203 }


	iqudc31MenuPlaceholderCh2GenlockTimingPlac OBJECT-TYPE
		SYNTAX		RollCallString
		MAX-ACCESS		read-only
		STATUS			current
		DESCRIPTION
				"TYPE: - Display
				 PAGE: - Placeholder-Ch2
					Genlock Timing Plac  cmdID= 64210  format=   "
		::= { iqudc31CmdEntry 64210 }


	iqudc31MenuPlaceholderCh2ClosedCaptions708 OBJECT-TYPE
		SYNTAX		RollCallString
		MAX-ACCESS		read-only
		STATUS			current
		DESCRIPTION
				"TYPE: - Display
				 PAGE: - Placeholder-Ch2
					Closed Captions 708  cmdID= 62700  format=   "
		::= { iqudc31CmdEntry 62700 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 13450104
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: POWER_USAGE
--
-- MIB ref		: swCardEventLogSlotXX       .11.80.79.87.69.82.95.85.83.65.71.69
-- absolute OID	: 1.3.6.1.4.1.7995.2.6.1.1.XX.11.80.79.87.69.82.95.85.83.65.71.69
-- Vary			: YES
--
-- Value(s)		: 
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: 
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: 
--				: 
-- Comments		: 
--
---------------------------------------------------------------------------------------------------
-- Header		: INPUT_3_TYPE
--
-- MIB ref		: swCardEventLogSlotXX       .12.73.78.80.85.84.95.51.95.84.89.80.69
-- absolute OID	: 1.3.6.1.4.1.7995.2.6.1.1.XX.12.73.78.80.85.84.95.51.95.84.89.80.69
-- Vary			: YES
--
-- Value(s)		: 
--				: 
-- Comments		: 
--
---------------------------------------------------------------------------------------------------
-- Header		: INPUT_4_TYPE
--
-- MIB ref		: swCardEventLogSlotXX       .12.73.78.80.85.84.95.52.95.84.89.80.69
-- absolute OID	: 1.3.6.1.4.1.7995.2.6.1.1.XX.12.73.78.80.85.84.95.52.95.84.89.80.69
-- Vary			: YES
--
-- Value(s)		: 
--				: 
-- Comments		: 
--
---------------------------------------------------------------------------------------------------
-- Header		: INPUT_5_TYPE
--
-- MIB ref		: swCardEventLogSlotXX       .12.73.78.80.85.84.95.53.95.84.89.80.69
-- absolute OID	: 1.3.6.1.4.1.7995.2.6.1.1.XX.12.73.78.80.85.84.95.53.95.84.89.80.69
-- Vary			: YES
--
-- Value(s)		: 
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2014-01-15T09:50:10Z
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: 
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: 
--				: 
-- Comments		: 
--
---------------------------------------------------------------------------------------------------
-- Header		: INPUT_3_STATE
--
-- MIB ref		: swCardEventLogSlotXX       .13.73.78.80.85.84.95.51.95.83.84.65.84.69
-- absolute OID	: 1.3.6.1.4.1.7995.2.6.1.1.XX.13.73.78.80.85.84.95.51.95.83.84.65.84.69
-- Vary			: YES
--
-- Value(s)		: 
--				: 
-- Comments		: 
--
---------------------------------------------------------------------------------------------------
-- Header		: INPUT_4_STATE
--
-- MIB ref		: swCardEventLogSlotXX       .13.73.78.80.85.84.95.52.95.83.84.65.84.69
-- absolute OID	: 1.3.6.1.4.1.7995.2.6.1.1.XX.13.73.78.80.85.84.95.52.95.83.84.65.84.69
-- Vary			: YES
--
-- Value(s)		: 
--				: 
-- Comments		: 
--
---------------------------------------------------------------------------------------------------
-- Header		: INPUT_5_STATE
--
-- MIB ref		: swCardEventLogSlotXX       .13.73.78.80.85.84.95.53.95.83.84.65.84.69
-- absolute OID	: 1.3.6.1.4.1.7995.2.6.1.1.XX.13.73.78.80.85.84.95.53.95.83.84.65.84.69
-- Vary			: YES
--
-- Value(s)		: 
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 
--				: 
-- Comments		: 
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
-- Vary			: YES
--
-- Value(s)		: 
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: 
--				: 
-- Comments		: 
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
-- Vary			: YES
--
-- Value(s)		: 
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: 
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: 
--				: 
-- Comments		: 
--
---------------------------------------------------------------------------------------------------
-- Header		: INPUT_3_STANDARD
--
-- MIB ref		: swCardEventLogSlotXX       .16.73.78.80.85.84.95.51.95.83.84.65.78.68.65.82.68
-- absolute OID	: 1.3.6.1.4.1.7995.2.6.1.1.XX.16.73.78.80.85.84.95.51.95.83.84.65.78.68.65.82.68
-- Vary			: YES
--
-- Value(s)		: 
--				: 
-- Comments		: 
--
---------------------------------------------------------------------------------------------------
-- Header		: INPUT_4_STANDARD
--
-- MIB ref		: swCardEventLogSlotXX       .16.73.78.80.85.84.95.52.95.83.84.65.78.68.65.82.68
-- absolute OID	: 1.3.6.1.4.1.7995.2.6.1.1.XX.16.73.78.80.85.84.95.52.95.83.84.65.78.68.65.82.68
-- Vary			: YES
--
-- Value(s)		: 
--				: 
-- Comments		: 
--
---------------------------------------------------------------------------------------------------
-- Header		: INPUT_5_STANDARD
--
-- MIB ref		: swCardEventLogSlotXX       .16.73.78.80.85.84.95.53.95.83.84.65.78.68.65.82.68
-- absolute OID	: 1.3.6.1.4.1.7995.2.6.1.1.XX.16.73.78.80.85.84.95.53.95.83.84.65.78.68.65.82.68
-- Vary			: YES
--
-- Value(s)		: 
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 
--				: 
-- Comments		: 
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
-- Vary			: YES
--
-- Value(s)		: 
--				: 
-- Comments		: 
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: 
--				: 
-- Comments		: 
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: 
--				: 
-- Comments		: 
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: 
--				: 
-- Comments		: 
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: 
--				: 
-- Comments		: 
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: 
--				: 
-- Comments		: 
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: 
--				: 
-- Comments		: 
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: 
--				: 
-- Comments		: 
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: 
--				: 
-- Comments		: 
--
---------------------------------------------------------------------------------------------------
-- Header		: OUTPUT_2_EMBEDDED_AUDIO_1_TYPE
--
-- MIB ref		: swCardEventLogSlotXX       .30.79.85.84.80.85.84.95.50.95.69.77.66.69.68.68.69.68.95.65.85.68.73.79.95.49.95.84.89.80.69
-- absolute OID	: 1.3.6.1.4.1.7995.2.6.1.1.XX.30.79.85.84.80.85.84.95.50.95.69.77.66.69.68.68.69.68.95.65.85.68.73.79.95.49.95.84.89.80.69
-- Vary			: YES
--
-- Value(s)		: 
--				: 
-- Comments		: 
--
---------------------------------------------------------------------------------------------------
-- Header		: OUTPUT_2_EMBEDDED_AUDIO_2_TYPE
--
-- MIB ref		: swCardEventLogSlotXX       .30.79.85.84.80.85.84.95.50.95.69.77.66.69.68.68.69.68.95.65.85.68.73.79.95.50.95.84.89.80.69
-- absolute OID	: 1.3.6.1.4.1.7995.2.6.1.1.XX.30.79.85.84.80.85.84.95.50.95.69.77.66.69.68.68.69.68.95.65.85.68.73.79.95.50.95.84.89.80.69
-- Vary			: YES
--
-- Value(s)		: 
--				: 
-- Comments		: 
--
---------------------------------------------------------------------------------------------------
-- Header		: OUTPUT_2_EMBEDDED_AUDIO_3_TYPE
--
-- MIB ref		: swCardEventLogSlotXX       .30.79.85.84.80.85.84.95.50.95.69.77.66.69.68.68.69.68.95.65.85.68.73.79.95.51.95.84.89.80.69
-- absolute OID	: 1.3.6.1.4.1.7995.2.6.1.1.XX.30.79.85.84.80.85.84.95.50.95.69.77.66.69.68.68.69.68.95.65.85.68.73.79.95.51.95.84.89.80.69
-- Vary			: YES
--
-- Value(s)		: 
--				: 
-- Comments		: 
--
---------------------------------------------------------------------------------------------------
-- Header		: OUTPUT_2_EMBEDDED_AUDIO_4_TYPE
--
-- MIB ref		: swCardEventLogSlotXX       .30.79.85.84.80.85.84.95.50.95.69.77.66.69.68.68.69.68.95.65.85.68.73.79.95.52.95.84.89.80.69
-- absolute OID	: 1.3.6.1.4.1.7995.2.6.1.1.XX.30.79.85.84.80.85.84.95.50.95.69.77.66.69.68.68.69.68.95.65.85.68.73.79.95.52.95.84.89.80.69
-- Vary			: YES
--
-- Value(s)		: 
--				: 
-- Comments		: 
--
---------------------------------------------------------------------------------------------------
-- Header		: OUTPUT_2_EMBEDDED_AUDIO_5_TYPE
--
-- MIB ref		: swCardEventLogSlotXX       .30.79.85.84.80.85.84.95.50.95.69.77.66.69.68.68.69.68.95.65.85.68.73.79.95.53.95.84.89.80.69
-- absolute OID	: 1.3.6.1.4.1.7995.2.6.1.1.XX.30.79.85.84.80.85.84.95.50.95.69.77.66.69.68.68.69.68.95.65.85.68.73.79.95.53.95.84.89.80.69
-- Vary			: YES
--
-- Value(s)		: 
--				: 
-- Comments		: 
--
---------------------------------------------------------------------------------------------------
-- Header		: OUTPUT_2_EMBEDDED_AUDIO_6_TYPE
--
-- MIB ref		: swCardEventLogSlotXX       .30.79.85.84.80.85.84.95.50.95.69.77.66.69.68.68.69.68.95.65.85.68.73.79.95.54.95.84.89.80.69
-- absolute OID	: 1.3.6.1.4.1.7995.2.6.1.1.XX.30.79.85.84.80.85.84.95.50.95.69.77.66.69.68.68.69.68.95.65.85.68.73.79.95.54.95.84.89.80.69
-- Vary			: YES
--
-- Value(s)		: 
--				: 
-- Comments		: 
--
---------------------------------------------------------------------------------------------------
-- Header		: OUTPUT_2_EMBEDDED_AUDIO_7_TYPE
--
-- MIB ref		: swCardEventLogSlotXX       .30.79.85.84.80.85.84.95.50.95.69.77.66.69.68.68.69.68.95.65.85.68.73.79.95.55.95.84.89.80.69
-- absolute OID	: 1.3.6.1.4.1.7995.2.6.1.1.XX.30.79.85.84.80.85.84.95.50.95.69.77.66.69.68.68.69.68.95.65.85.68.73.79.95.55.95.84.89.80.69
-- Vary			: YES
--
-- Value(s)		: 
--				: 
-- Comments		: 
--
---------------------------------------------------------------------------------------------------
-- Header		: OUTPUT_2_EMBEDDED_AUDIO_8_TYPE
--
-- MIB ref		: swCardEventLogSlotXX       .30.79.85.84.80.85.84.95.50.95.69.77.66.69.68.68.69.68.95.65.85.68.73.79.95.56.95.84.89.80.69
-- absolute OID	: 1.3.6.1.4.1.7995.2.6.1.1.XX.30.79.85.84.80.85.84.95.50.95.69.77.66.69.68.68.69.68.95.65.85.68.73.79.95.56.95.84.89.80.69
-- Vary			: YES
--
-- Value(s)		: 
--				: 
-- Comments		: 
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: 
--				: 
-- Comments		: 
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: 
--				: 
-- Comments		: 
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: 
--				: 
-- Comments		: 
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: 
--				: 
-- Comments		: 
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: 
--				: 
-- Comments		: 
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: 
--				: 
-- Comments		: 
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: 
--				: 
-- Comments		: 
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: 
--				: 
-- Comments		: 
--
---------------------------------------------------------------------------------------------------
-- Header		: OUTPUT_2_EMBEDDED_AUDIO_1_STATE
--
-- MIB ref		: swCardEventLogSlotXX       .31.79.85.84.80.85.84.95.50.95.69.77.66.69.68.68.69.68.95.65.85.68.73.79.95.49.95.83.84.65.84.69
-- absolute OID	: 1.3.6.1.4.1.7995.2.6.1.1.XX.31.79.85.84.80.85.84.95.50.95.69.77.66.69.68.68.69.68.95.65.85.68.73.79.95.49.95.83.84.65.84.69
-- Vary			: YES
--
-- Value(s)		: 
--				: 
-- Comments		: 
--
---------------------------------------------------------------------------------------------------
-- Header		: OUTPUT_2_EMBEDDED_AUDIO_2_STATE
--
-- MIB ref		: swCardEventLogSlotXX       .31.79.85.84.80.85.84.95.50.95.69.77.66.69.68.68.69.68.95.65.85.68.73.79.95.50.95.83.84.65.84.69
-- absolute OID	: 1.3.6.1.4.1.7995.2.6.1.1.XX.31.79.85.84.80.85.84.95.50.95.69.77.66.69.68.68.69.68.95.65.85.68.73.79.95.50.95.83.84.65.84.69
-- Vary			: YES
--
-- Value(s)		: 
--				: 
-- Comments		: 
--
---------------------------------------------------------------------------------------------------
-- Header		: OUTPUT_2_EMBEDDED_AUDIO_3_STATE
--
-- MIB ref		: swCardEventLogSlotXX       .31.79.85.84.80.85.84.95.50.95.69.77.66.69.68.68.69.68.95.65.85.68.73.79.95.51.95.83.84.65.84.69
-- absolute OID	: 1.3.6.1.4.1.7995.2.6.1.1.XX.31.79.85.84.80.85.84.95.50.95.69.77.66.69.68.68.69.68.95.65.85.68.73.79.95.51.95.83.84.65.84.69
-- Vary			: YES
--
-- Value(s)		: 
--				: 
-- Comments		: 
--
---------------------------------------------------------------------------------------------------
-- Header		: OUTPUT_2_EMBEDDED_AUDIO_4_STATE
--
-- MIB ref		: swCardEventLogSlotXX       .31.79.85.84.80.85.84.95.50.95.69.77.66.69.68.68.69.68.95.65.85.68.73.79.95.52.95.83.84.65.84.69
-- absolute OID	: 1.3.6.1.4.1.7995.2.6.1.1.XX.31.79.85.84.80.85.84.95.50.95.69.77.66.69.68.68.69.68.95.65.85.68.73.79.95.52.95.83.84.65.84.69
-- Vary			: YES
--
-- Value(s)		: 
--				: 
-- Comments		: 
--
---------------------------------------------------------------------------------------------------
-- Header		: OUTPUT_2_EMBEDDED_AUDIO_5_STATE
--
-- MIB ref		: swCardEventLogSlotXX       .31.79.85.84.80.85.84.95.50.95.69.77.66.69.68.68.69.68.95.65.85.68.73.79.95.53.95.83.84.65.84.69
-- absolute OID	: 1.3.6.1.4.1.7995.2.6.1.1.XX.31.79.85.84.80.85.84.95.50.95.69.77.66.69.68.68.69.68.95.65.85.68.73.79.95.53.95.83.84.65.84.69
-- Vary			: YES
--
-- Value(s)		: 
--				: 
-- Comments		: 
--
---------------------------------------------------------------------------------------------------
-- Header		: OUTPUT_2_EMBEDDED_AUDIO_6_STATE
--
-- MIB ref		: swCardEventLogSlotXX       .31.79.85.84.80.85.84.95.50.95.69.77.66.69.68.68.69.68.95.65.85.68.73.79.95.54.95.83.84.65.84.69
-- absolute OID	: 1.3.6.1.4.1.7995.2.6.1.1.XX.31.79.85.84.80.85.84.95.50.95.69.77.66.69.68.68.69.68.95.65.85.68.73.79.95.54.95.83.84.65.84.69
-- Vary			: YES
--
-- Value(s)		: 
--				: 
-- Comments		: 
--
---------------------------------------------------------------------------------------------------
-- Header		: OUTPUT_2_EMBEDDED_AUDIO_7_STATE
--
-- MIB ref		: swCardEventLogSlotXX       .31.79.85.84.80.85.84.95.50.95.69.77.66.69.68.68.69.68.95.65.85.68.73.79.95.55.95.83.84.65.84.69
-- absolute OID	: 1.3.6.1.4.1.7995.2.6.1.1.XX.31.79.85.84.80.85.84.95.50.95.69.77.66.69.68.68.69.68.95.65.85.68.73.79.95.55.95.83.84.65.84.69
-- Vary			: YES
--
-- Value(s)		: 
--				: 
-- Comments		: 
--
---------------------------------------------------------------------------------------------------
-- Header		: OUTPUT_2_EMBEDDED_AUDIO_8_STATE
--
-- MIB ref		: swCardEventLogSlotXX       .31.79.85.84.80.85.84.95.50.95.69.77.66.69.68.68.69.68.95.65.85.68.73.79.95.56.95.83.84.65.84.69
-- absolute OID	: 1.3.6.1.4.1.7995.2.6.1.1.XX.31.79.85.84.80.85.84.95.50.95.69.77.66.69.68.68.69.68.95.65.85.68.73.79.95.56.95.83.84.65.84.69
-- Vary			: YES
--
-- Value(s)		: 
--				: 
-- Comments		: 
--
---------------------------------------------------------------------------------------------------
