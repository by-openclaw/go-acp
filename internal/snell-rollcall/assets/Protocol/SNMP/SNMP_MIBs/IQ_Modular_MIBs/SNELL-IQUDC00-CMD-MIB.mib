-- ************************************************************************************
-- Snell&Wilcox Card:IQUDC00
--        Module Id#:430
--       Command Set:14
--          Filename:SNELL-IQUDC00-CMD-MIB.mib
--            Author:Jonathan Riches
--              Date:10/01/2008
--              Time:10:13
--
-- Copyright (c) 2005 Snell & Wilcox Ltd
-- All rights reserved.
--
-- ************************************************************************************

SNELL-IQUDC00-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUDC00,
    moduleIQUDC00MIB
        FROM SNELL-WILCOX-PRODUCT-REG;

 moduleIQUDC00CmdMi MODULE-IDENTITY
    LAST-UPDATED "0801101013Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQUDC00MIB 1 }




--********************************************************************************
--*
--*  Snell Wilcox Card:
--*  command set:
--*  list commands/menus:
--*
--******************************************************************************
	iqudc00CmdTable OBJECT-TYPE
		SYNTAX			SEQUENCE OF Iqudc00CmdEntry
		MAX-ACCESS		not-accessible
		STATUS			current
		DESCRIPTION
				"Note the instance of this table is relected in the command set Version"
		::= { moduleIQUDC00 1 }

	iqudc00CmdEntry OBJECT-TYPE
		SYNTAX		Iqudc00CmdEntry
		MAX-ACCESS		not-accessible
		STATUS			current
		DESCRIPTION
				"Entry in command table."
		INDEX	{ iqudc00SlotIndex }
		::= { iqudc00CmdTable 1 }

	Iqudc00CmdEntry ::=
		SEQUENCE {
			iqudc00SlotIndex
				Unsigned32,
			iqudc00InputIPSelect
				INTEGER,
			iqudc00InputYCDelay
				INTEGER,
			iqudc00InputValidStandardsAllValid
				INTEGER,
			iqudc00InputValidStandardsAllInvalid
				INTEGER,
			iqudc00InputValidStandards108025i
				INTEGER,
			iqudc00InputValidStandards108029i
				INTEGER,
			iqudc00InputValidStandards72050p
				INTEGER,
			iqudc00InputValidStandards72059p
				INTEGER,
			iqudc00InputValidStandards62525i
				INTEGER,
			iqudc00InputValidStandards52529i
				INTEGER,
			iqudc00InputInpBackupEnable
				INTEGER,
			iqudc00InpBackupDefineInput1OkValidipStd
				INTEGER,
			iqudc00InpBackupDefineInput1OkEDHCRCisOK
				INTEGER,
			iqudc00InpBackupDefineInput1OkAudioPair1present
				INTEGER,
			iqudc00InpBackupDefineInput1OkAudioPair2present
				INTEGER,
			iqudc00InpBackupDefineInput1OkAudioPair3present
				INTEGER,
			iqudc00InpBackupDefineInput1OkAudioPair4present
				INTEGER,
			iqudc00InpBackupDefineInput1OkAudioPair5present
				INTEGER,
			iqudc00InpBackupDefineInput1OkAudioPair6present
				INTEGER,
			iqudc00InpBackupDefineInput1OkAudioPair7present
				INTEGER,
			iqudc00InpBackupDefineInput1OkAudioPair8present
				INTEGER,
			iqudc00InpBackupDefineInput2OkValidipStd
				INTEGER,
			iqudc00InpBackupDefineInput2OkEDHCRCisOK
				INTEGER,
			iqudc00InpBackupDefineInput2OkAudioPair1present
				INTEGER,
			iqudc00InpBackupDefineInput2OkAudioPair2present
				INTEGER,
			iqudc00InpBackupDefineInput2OkAudioPair3present
				INTEGER,
			iqudc00InpBackupDefineInput2OkAudioPair4present
				INTEGER,
			iqudc00InpBackupDefineInput2OkAudioPair5present
				INTEGER,
			iqudc00InpBackupDefineInput2OkAudioPair6present
				INTEGER,
			iqudc00InpBackupDefineInput2OkAudioPair7present
				INTEGER,
			iqudc00InpBackupDefineInput2OkAudioPair8present
				INTEGER,
			iqudc00InpBackupRules1SetRule1
				INTEGER,
			iqudc00InpBackupRules1SelectInput
				INTEGER,
			iqudc00InpBackupRules1TimeDelay
				INTEGER,
			iqudc00InpBackupRules2SetRule2
				INTEGER,
			iqudc00InpBackupRules2SelectInput
				INTEGER,
			iqudc00InpBackupRules2TimeDelay
				INTEGER,
			iqudc00InpBackupRules3SetRule3
				INTEGER,
			iqudc00InpBackupRules3SelectInput
				INTEGER,
			iqudc00InpBackupRules3TimeDelay
				INTEGER,
			iqudc00InpBackupRules4SetRule4
				INTEGER,
			iqudc00InpBackupRules4SelectInput
				INTEGER,
			iqudc00InpBackupRules4TimeDelay
				INTEGER,
			iqudc00InpBackupRules5SetRule5
				INTEGER,
			iqudc00InpBackupRules5SelectInput
				INTEGER,
			iqudc00InpBackupRules5TimeDelay
				INTEGER,
			iqudc00InputErrorsCRCErrs
				RollCallString,
			iqudc00InputErrorsCRCErrSec
				RollCallString,
			iqudc00InputErrorsANCErrs
				RollCallString,
			iqudc00InputErrorsANCErrSec
				RollCallString,
			iqudc00InputErrorsResetSec
				RollCallString,
			iqudc00InputErrorsErrorReset
				INTEGER,
			iqudc00OutputOPStd
				INTEGER,
			iqudc00OutputVideoProcMasterGain
				INTEGER,
			iqudc00OutputVideoProcYGain
				INTEGER,
			iqudc00OutputVideoProcCGain
				INTEGER,
			iqudc00OutputVideoProcBlackLevel
				INTEGER,
			iqudc00OutputDefaultOutput
				INTEGER,
			iqudc00OutputFreezeForceFreeze
				INTEGER,
			iqudc00PictureOutputBorderLeft
				INTEGER,
			iqudc00PictureOutputBorderRight
				INTEGER,
			iqudc00PictureOutputBorderTop
				INTEGER,
			iqudc00PictureOutputBorderBottom
				INTEGER,
			iqudc00PictureOutputBorderRed
				INTEGER,
			iqudc00PictureOutputBorderGreen
				INTEGER,
			iqudc00PictureOutputBorderBlue
				INTEGER,
			iqudc00PictureOutputEnhanceVEnhance
				INTEGER,
			iqudc00PictureOutputEnhanceHEnhance
				INTEGER,
			iqudc00PictureOutputColorimetry
				INTEGER,
			iqudc00PictureOutputFilmVideo
				INTEGER,
			iqudc00PictureOutputDetail
				INTEGER,
			iqudc00ARCSetupRecallDisplayMemo
				INTEGER,
			iqudc00ARCSetupSelDisplayMemory
				INTEGER,
			iqudc00ARCSetupSaveDispMemory
				INTEGER,
			iqudc00ARCSetupDispMemoryNameChangeName
				RollCallString,
			iqudc00ARCSetupARCSize
				INTEGER,
			iqudc00ARCSetupARCApect
				INTEGER,
			iqudc00ARCSetupARCTilt
				INTEGER,
			iqudc00ARCSetupARCPan
				INTEGER,
			iqudc00ARCSetupARCOrigin
				INTEGER,
			iqudc00ARCSetupInputCropLeft
				INTEGER,
			iqudc00ARCSetupInputCropRight
				INTEGER,
			iqudc00ARCSetupInputCropTop
				INTEGER,
			iqudc00ARCSetupInputCropBottom
				INTEGER,
			iqudc00ARCSetupSelStdPreset
				INTEGER,
			iqudc00ARCSetupRecallStdPreset
				INTEGER,
			iqudc00ARCSetupDefaultALLMemory
				INTEGER,
			iqudc00ARCSetupLastDisplayMemory
				RollCallString,
			iqudc00WSSCtrlOutputAspect
				INTEGER,
			iqudc00WSSCtrlIPWSSSignal
				INTEGER,
			iqudc00WSSCtrlForceInputMode
				INTEGER,
			iqudc00WSSCtrlOPWSS43
				INTEGER,
			iqudc00WSSCtrlDispMem43
				INTEGER,
			iqudc00WSSCtrlOPWSS169
				INTEGER,
			iqudc00WSSCtrlDispMem169
				INTEGER,
			iqudc00WSSCtrlWSSVIIPWSSETSI
				INTEGER,
			iqudc00WSSCtrlWSSVIIPWSSAFD
				INTEGER,
			iqudc00WSSCtrlWSSVIIPVISMPTE
				INTEGER,
			iqudc00WSSCtrlWSSVIIPVIAFD
				INTEGER,
			iqudc00WSSCtrlWSSVIIPWSSLine
				INTEGER,
			iqudc00WSSCtrlWSSVIIPWSSVIPriority
				INTEGER,
			iqudc00WSSCtrlWSSVIOPWSSETSI
				INTEGER,
			iqudc00WSSCtrlWSSVIOPWSSAFD
				INTEGER,
			iqudc00WSSCtrlWSSVIOPVISMPTE
				INTEGER,
			iqudc00WSSCtrlWSSVIOPVIAFD
				INTEGER,
			iqudc00WSSCtrlWSSVIOPWSSLine
				INTEGER,
			iqudc00WSSCtrlWSSVIOPIPLine
				INTEGER,
			iqudc00WSSCtrlAutoModify
				INTEGER,
			iqudc00GenlockDelayMode
				INTEGER,
			iqudc00GenlockSetDelayVerticalTiming
				INTEGER,
			iqudc00GenlockSetDelayHorizontalTiming
				INTEGER,
			iqudc00GenlockSetDelayDelayms
				INTEGER,
			iqudc00GenlockInternalDelay
				RollCallString,
			iqudc00GenlockSyncAmplitude
				RollCallString,
			iqudc00GenlockScalerMinDelay
				INTEGER,
			iqudc00AudioDelayADelaySourcesManual
				INTEGER,
			iqudc00AudioDelayADelaySourcesGPIPWM
				INTEGER,
			iqudc00AudioDelayADelaySourcesRollTrack14
				INTEGER,
			iqudc00AudioDelayADelaySourcesRollTrack15
				INTEGER,
			iqudc00AudioDelayADelaySourcesRollTrack16
				INTEGER,
			iqudc00AudioDelayADelaySourcesRollTrack17
				INTEGER,
			iqudc00AudDelaysAudioDelayAAdjustManualDelay
				INTEGER,
			iqudc00AudDelaysAudioDelayACurrentAudioDelay
				RollCallString,
			iqudc00AudioDelayBDelaySourcesManual
				INTEGER,
			iqudc00AudioDelayBDelaySourcesGPIPWM
				INTEGER,
			iqudc00AudioDelayBDelaySourcesRollTrack14
				INTEGER,
			iqudc00AudioDelayBDelaySourcesRollTrack15
				INTEGER,
			iqudc00AudioDelayBDelaySourcesRollTrack16
				INTEGER,
			iqudc00AudioDelayBDelaySourcesRollTrack17
				INTEGER,
			iqudc00AudDelaysAudioDelayBAdjustManualDelay
				INTEGER,
			iqudc00AudDelaysAudioDelayBCurrentAudioDelay
				RollCallString,
			iqudc00AudDelaysDelaySelectDelay1
				INTEGER,
			iqudc00AudDelaysDelaySelectInternal1
				INTEGER,
			iqudc00AudDelaysDelaySelectDelay1Limit
				RollCallString,
			iqudc00AudDelaysDelaySelectDelay2
				INTEGER,
			iqudc00AudDelaysDelaySelectInternal2
				INTEGER,
			iqudc00AudDelaysDelaySelectDelay2Limit
				RollCallString,
			iqudc00AudDelaysDelaySelectDelay3
				INTEGER,
			iqudc00AudDelaysDelaySelectInternal3
				INTEGER,
			iqudc00AudDelaysDelaySelectDelay3Limit
				RollCallString,
			iqudc00AudDelaysDelaySelectDelay4
				INTEGER,
			iqudc00AudDelaysDelaySelectInternal4
				INTEGER,
			iqudc00AudDelaysDelaySelectDelay4Limit
				RollCallString,
			iqudc00AudDelaysDelaySelectDelay5
				INTEGER,
			iqudc00AudDelaysDelaySelectInternal5
				INTEGER,
			iqudc00AudDelaysDelaySelectDelay5Limit
				RollCallString,
			iqudc00AudDelaysDelaySelectDelay6
				INTEGER,
			iqudc00AudDelaysDelaySelectInternal6
				INTEGER,
			iqudc00AudDelaysDelaySelectDelay6Limit
				RollCallString,
			iqudc00AudDelaysDelaySelectDelay7
				INTEGER,
			iqudc00AudDelaysDelaySelectInternal7
				INTEGER,
			iqudc00AudDelaysDelaySelectDelay7Limit
				RollCallString,
			iqudc00AudDelaysDelaySelectDelay8
				INTEGER,
			iqudc00AudDelaysDelaySelectInternal8
				INTEGER,
			iqudc00AudDelaysDelaySelectDelay8Limit
				RollCallString,
			iqudc00AudioAudDelaysRollTrack14
				RollCallString,
			iqudc00AudioAudDelaysRollTrack15
				RollCallString,
			iqudc00AudioAudDelaysRollTrack16
				RollCallString,
			iqudc00AudioAudDelaysRollTrack17
				RollCallString,
			iqudc00AudioEmbCtrlAudio
				INTEGER,
			iqudc00EmbCtrlGroupGroup1Active
				INTEGER,
			iqudc00EmbCtrlGroupGroup2Active
				INTEGER,
			iqudc00EmbCtrlGroupGroup3Active
				INTEGER,
			iqudc00EmbCtrlGroupGroup4Active
				INTEGER,
			iqudc00EmbCtrlChannelPair1LActive
				INTEGER,
			iqudc00EmbCtrlChannelPair1RActive
				INTEGER,
			iqudc00EmbCtrlChannelPair2LActive
				INTEGER,
			iqudc00EmbCtrlChannelPair2RActive
				INTEGER,
			iqudc00EmbCtrlChannelPair3LActive
				INTEGER,
			iqudc00EmbCtrlChannelPair3RActive
				INTEGER,
			iqudc00EmbCtrlChannelPair4LActive
				INTEGER,
			iqudc00EmbCtrlChannelPair4RActive
				INTEGER,
			iqudc00EmbCtrlChannelPair5LActive
				INTEGER,
			iqudc00EmbCtrlChannelPair5RActive
				INTEGER,
			iqudc00EmbCtrlChannelPair6LActive
				INTEGER,
			iqudc00EmbCtrlChannelPair6RActive
				INTEGER,
			iqudc00EmbCtrlChannelPair7LActive
				INTEGER,
			iqudc00EmbCtrlChannelPair7RActive
				INTEGER,
			iqudc00EmbCtrlChannelPair8LActive
				INTEGER,
			iqudc00EmbCtrlChannelPair8RActive
				INTEGER,
			iqudc00EmbGainEmbedPair1Embed1MuteL
				INTEGER,
			iqudc00EmbGainEmbedPair1Embed1MuteR
				INTEGER,
			iqudc00EmbGainEmbedPair1Embed1LGain
				INTEGER,
			iqudc00EmbGainEmbedPair1Embed1RGain
				INTEGER,
			iqudc00EmbGainEmbedPair1Stereo
				INTEGER,
			iqudc00EmbGainEmbedPair1Embed1InvertL
				INTEGER,
			iqudc00EmbGainEmbedPair1Embed1InvertR
				INTEGER,
			iqudc00EmbGainEmbedPair1Embed1LClip
				RollCallString,
			iqudc00EmbGainEmbedPair1Embed1RClip
				RollCallString,
			iqudc00EmbGainEmbedPair2Embed2MuteL
				INTEGER,
			iqudc00EmbGainEmbedPair2Embed2MuteR
				INTEGER,
			iqudc00EmbGainEmbedPair2Embed2LGain
				INTEGER,
			iqudc00EmbGainEmbedPair2Embed2RGain
				INTEGER,
			iqudc00EmbGainEmbedPair2Stereo
				INTEGER,
			iqudc00EmbGainEmbedPair2Embed2InvertL
				INTEGER,
			iqudc00EmbGainEmbedPair2Embed2InvertR
				INTEGER,
			iqudc00EmbGainEmbedPair2Embed2LClip
				RollCallString,
			iqudc00EmbGainEmbedPair2Embed2RClip
				RollCallString,
			iqudc00EmbGainEmbedPair3Embed3MuteL
				INTEGER,
			iqudc00EmbGainEmbedPair3Embed3MuteR
				INTEGER,
			iqudc00EmbGainEmbedPair3Embed3LGain
				INTEGER,
			iqudc00EmbGainEmbedPair3Embed3RGain
				INTEGER,
			iqudc00EmbGainEmbedPair3Stereo
				INTEGER,
			iqudc00EmbGainEmbedPair3Embed3InvertL
				INTEGER,
			iqudc00EmbGainEmbedPair3Embed3InvertR
				INTEGER,
			iqudc00EmbGainEmbedPair3Embed3LClip
				RollCallString,
			iqudc00EmbGainEmbedPair3Embed3RClip
				RollCallString,
			iqudc00EmbGainEmbedPair4Embed4MuteL
				INTEGER,
			iqudc00EmbGainEmbedPair4Embed4MuteR
				INTEGER,
			iqudc00EmbGainEmbedPair4Embed4LGain
				INTEGER,
			iqudc00EmbGainEmbedPair4Embed4RGain
				INTEGER,
			iqudc00EmbGainEmbedPair4Stereo
				INTEGER,
			iqudc00EmbGainEmbedPair4Embed4InvertL
				INTEGER,
			iqudc00EmbGainEmbedPair4Embed4InvertR
				INTEGER,
			iqudc00EmbGainEmbedPair4Embed4LClip
				RollCallString,
			iqudc00EmbGainEmbedPair4Embed4RClip
				RollCallString,
			iqudc00EmbGainEmbedPair5Embed5MuteL
				INTEGER,
			iqudc00EmbGainEmbedPair5Embed5MuteR
				INTEGER,
			iqudc00EmbGainEmbedPair5Embed5LGain
				INTEGER,
			iqudc00EmbGainEmbedPair5Embed5RGain
				INTEGER,
			iqudc00EmbGainEmbedPair5Stereo
				INTEGER,
			iqudc00EmbGainEmbedPair5Embed5InvertL
				INTEGER,
			iqudc00EmbGainEmbedPair5Embed5InvertR
				INTEGER,
			iqudc00EmbGainEmbedPair5Embed5LClip
				RollCallString,
			iqudc00EmbGainEmbedPair5Embed5RClip
				RollCallString,
			iqudc00EmbGainEmbedPair6Embed6MuteL
				INTEGER,
			iqudc00EmbGainEmbedPair6Embed6MuteR
				INTEGER,
			iqudc00EmbGainEmbedPair6Embed6LGain
				INTEGER,
			iqudc00EmbGainEmbedPair6Embed6RGain
				INTEGER,
			iqudc00EmbGainEmbedPair6Stereo
				INTEGER,
			iqudc00EmbGainEmbedPair6Embed6InvertL
				INTEGER,
			iqudc00EmbGainEmbedPair6Embed6InvertR
				INTEGER,
			iqudc00EmbGainEmbedPair6Embed6LClip
				RollCallString,
			iqudc00EmbGainEmbedPair6Embed6RClip
				RollCallString,
			iqudc00EmbGainEmbedPair7Embed7MuteL
				INTEGER,
			iqudc00EmbGainEmbedPair7Embed7MuteR
				INTEGER,
			iqudc00EmbGainEmbedPair7Embed7LGain
				INTEGER,
			iqudc00EmbGainEmbedPair7Embed7RGain
				INTEGER,
			iqudc00EmbGainEmbedPair7Stereo
				INTEGER,
			iqudc00EmbGainEmbedPair7Embed7InvertL
				INTEGER,
			iqudc00EmbGainEmbedPair7Embed7InvertR
				INTEGER,
			iqudc00EmbGainEmbedPair7Embed7LClip
				RollCallString,
			iqudc00EmbGainEmbedPair7Embed7RClip
				RollCallString,
			iqudc00EmbGainEmbedPair8Embed8MuteL
				INTEGER,
			iqudc00EmbGainEmbedPair8Embed8MuteR
				INTEGER,
			iqudc00EmbGainEmbedPair8Embed8LGain
				INTEGER,
			iqudc00EmbGainEmbedPair8Embed8RGain
				INTEGER,
			iqudc00EmbGainEmbedPair8Stereo
				INTEGER,
			iqudc00EmbGainEmbedPair8Embed8InvertL
				INTEGER,
			iqudc00EmbGainEmbedPair8Embed8InvertR
				INTEGER,
			iqudc00EmbGainEmbedPair8Embed8LClip
				RollCallString,
			iqudc00EmbGainEmbedPair8Embed8RClip
				RollCallString,
			iqudc00EmbOutEmbedPair1Embed1L
				INTEGER,
			iqudc00EmbOutEmbedPair1Embed1R
				INTEGER,
			iqudc00EmbOutEmbedPair1LinkLRSelection
				INTEGER,
			iqudc00EmbOutEmbedPair2Embed2L
				INTEGER,
			iqudc00EmbOutEmbedPair2Embed2R
				INTEGER,
			iqudc00EmbOutEmbedPair2LinkLRSelection
				INTEGER,
			iqudc00EmbOutEmbedPair3Embed3L
				INTEGER,
			iqudc00EmbOutEmbedPair3Embed3R
				INTEGER,
			iqudc00EmbOutEmbedPair3LinkLRSelection
				INTEGER,
			iqudc00EmbOutEmbedPair4Embed4L
				INTEGER,
			iqudc00EmbOutEmbedPair4Embed4R
				INTEGER,
			iqudc00EmbOutEmbedPair4LinkLRSelection
				INTEGER,
			iqudc00EmbOutEmbedPair5Embed5L
				INTEGER,
			iqudc00EmbOutEmbedPair5Embed5R
				INTEGER,
			iqudc00EmbOutEmbedPair5LinkLRSelection
				INTEGER,
			iqudc00EmbOutEmbedPair6Embed6L
				INTEGER,
			iqudc00EmbOutEmbedPair6Embed6R
				INTEGER,
			iqudc00EmbOutEmbedPair6LinkLRSelection
				INTEGER,
			iqudc00EmbOutEmbedPair7Embed7L
				INTEGER,
			iqudc00EmbOutEmbedPair7Embed7R
				INTEGER,
			iqudc00EmbOutEmbedPair7LinkLRSelection
				INTEGER,
			iqudc00EmbOutEmbedPair8Embed8L
				INTEGER,
			iqudc00EmbOutEmbedPair8Embed8R
				INTEGER,
			iqudc00EmbOutEmbedPair8LinkLRSelection
				INTEGER,
			iqudc00AudioEmbDataInput1
				INTEGER,
			iqudc00AudioEmbDataInput2
				INTEGER,
			iqudc00AudioEmbDataInput3
				INTEGER,
			iqudc00AudioEmbDataInput4
				INTEGER,
			iqudc00AudioEmbDataInput5
				INTEGER,
			iqudc00AudioEmbDataInput6
				INTEGER,
			iqudc00AudioEmbDataInput7
				INTEGER,
			iqudc00AudioEmbDataInput8
				INTEGER,
			iqudc00DisembedderNamesDisemb1L
				RollCallString,
			iqudc00DisembedderNamesDisemb1R
				RollCallString,
			iqudc00DisembedderNamesDisemb2L
				RollCallString,
			iqudc00DisembedderNamesDisemb2R
				RollCallString,
			iqudc00DisembedderNamesDisemb3L
				RollCallString,
			iqudc00DisembedderNamesDisemb3R
				RollCallString,
			iqudc00DisembedderNamesDisemb4L
				RollCallString,
			iqudc00DisembedderNamesDisemb4R
				RollCallString,
			iqudc00DisembedderNamesDisemb5L
				RollCallString,
			iqudc00DisembedderNamesDisemb5R
				RollCallString,
			iqudc00DisembedderNamesDisemb6L
				RollCallString,
			iqudc00DisembedderNamesDisemb6R
				RollCallString,
			iqudc00DisembedderNamesDisemb7L
				RollCallString,
			iqudc00DisembedderNamesDisemb7R
				RollCallString,
			iqudc00DisembedderNamesDisemb8L
				RollCallString,
			iqudc00DisembedderNamesDisemb8R
				RollCallString,
			iqudc00DisembedderNamesEmbeddedOP1L
				RollCallString,
			iqudc00DisembedderNamesEmbeddedOP1R
				RollCallString,
			iqudc00DisembedderNamesEmbeddedOP2L
				RollCallString,
			iqudc00DisembedderNamesEmbeddedOP2R
				RollCallString,
			iqudc00DisembedderNamesEmbeddedOP3L
				RollCallString,
			iqudc00DisembedderNamesEmbeddedOP3R
				RollCallString,
			iqudc00DisembedderNamesEmbeddedOP4L
				RollCallString,
			iqudc00DisembedderNamesEmbeddedOP4R
				RollCallString,
			iqudc00DisembedderNamesEmbeddedOP5L
				RollCallString,
			iqudc00DisembedderNamesEmbeddedOP5R
				RollCallString,
			iqudc00DisembedderNamesEmbeddedOP6L
				RollCallString,
			iqudc00DisembedderNamesEmbeddedOP6R
				RollCallString,
			iqudc00DisembedderNamesEmbeddedOP7L
				RollCallString,
			iqudc00DisembedderNamesEmbeddedOP7R
				RollCallString,
			iqudc00DisembedderNamesEmbeddedOP8L
				RollCallString,
			iqudc00DisembedderNamesEmbeddedOP8R
				RollCallString,
			iqudc00DisembedderNamesIPStereoDisemb1
				INTEGER,
			iqudc00DisembedderNamesIPStereoDisemb2
				INTEGER,
			iqudc00DisembedderNamesIPStereoDisemb3
				INTEGER,
			iqudc00DisembedderNamesIPStereoDisemb4
				INTEGER,
			iqudc00DisembedderNamesIPStereoDisemb5
				INTEGER,
			iqudc00DisembedderNamesIPStereoDisemb6
				INTEGER,
			iqudc00DisembedderNamesIPStereoDisemb7
				INTEGER,
			iqudc00DisembedderNamesIPStereoDisemb8
				INTEGER,
			iqudc00DisembedderNamesOPStereoEmbed1
				INTEGER,
			iqudc00DisembedderNamesOPStereoEmbed2
				INTEGER,
			iqudc00DisembedderNamesOPStereoEmbed3
				INTEGER,
			iqudc00DisembedderNamesOPStereoEmbed4
				INTEGER,
			iqudc00DisembedderNamesOPStereoEmbed5
				INTEGER,
			iqudc00DisembedderNamesOPStereoEmbed6
				INTEGER,
			iqudc00DisembedderNamesOPStereoEmbed7
				INTEGER,
			iqudc00DisembedderNamesOPStereoEmbed8
				INTEGER,
			iqudc00NamesMix1
				RollCallString,
			iqudc00NamesMix2
				RollCallString,
			iqudc00NamesMix3
				RollCallString,
			iqudc00NamesMix4
				RollCallString,
			iqudc00Mix1RoutingSource1
				INTEGER,
			iqudc00Mix1RoutingInvert1
				INTEGER,
			iqudc00Mix1RoutingSource2
				INTEGER,
			iqudc00Mix1RoutingInvert2
				INTEGER,
			iqudc00Mix1RoutingSource3
				INTEGER,
			iqudc00Mix1RoutingInvert3
				INTEGER,
			iqudc00Mix1RoutingSource4
				INTEGER,
			iqudc00Mix1RoutingInvert4
				INTEGER,
			iqudc00Mix1GainGain1
				INTEGER,
			iqudc00Mix1GainMute1
				INTEGER,
			iqudc00Mix1GainGain2
				INTEGER,
			iqudc00Mix1GainMute2
				INTEGER,
			iqudc00Mix1GainGain3
				INTEGER,
			iqudc00Mix1GainMute3
				INTEGER,
			iqudc00Mix1GainGain4
				INTEGER,
			iqudc00Mix1GainMute4
				INTEGER,
			iqudc00Mix1GainInp1Clip
				RollCallString,
			iqudc00Mix1GainInp2Clip
				RollCallString,
			iqudc00Mix1GainInp3Clip
				RollCallString,
			iqudc00Mix1GainInp4Clip
				RollCallString,
			iqudc00Mix1GainOPClip
				RollCallString,
			iqudc00Mix2RoutingSource1
				INTEGER,
			iqudc00Mix2RoutingInvert1
				INTEGER,
			iqudc00Mix2RoutingSource2
				INTEGER,
			iqudc00Mix2RoutingInvert2
				INTEGER,
			iqudc00Mix2RoutingSource3
				INTEGER,
			iqudc00Mix2RoutingInvert3
				INTEGER,
			iqudc00Mix2RoutingSource4
				INTEGER,
			iqudc00Mix2RoutingInvert4
				INTEGER,
			iqudc00Mix2GainGain1
				INTEGER,
			iqudc00Mix2GainMute1
				INTEGER,
			iqudc00Mix2GainGain2
				INTEGER,
			iqudc00Mix2GainMute2
				INTEGER,
			iqudc00Mix2GainGain3
				INTEGER,
			iqudc00Mix2GainMute3
				INTEGER,
			iqudc00Mix2GainGain4
				INTEGER,
			iqudc00Mix2GainMute4
				INTEGER,
			iqudc00Mix2GainInp1Clip
				RollCallString,
			iqudc00Mix2GainInp2Clip
				RollCallString,
			iqudc00Mix2GainInp3Clip
				RollCallString,
			iqudc00Mix2GainInp4Clip
				RollCallString,
			iqudc00Mix2GainOPClip
				RollCallString,
			iqudc00Mix3RoutingSource1
				INTEGER,
			iqudc00Mix3RoutingInvert1
				INTEGER,
			iqudc00Mix3RoutingSource2
				INTEGER,
			iqudc00Mix3RoutingInvert2
				INTEGER,
			iqudc00Mix3RoutingSource3
				INTEGER,
			iqudc00Mix3RoutingInvert3
				INTEGER,
			iqudc00Mix3RoutingSource4
				INTEGER,
			iqudc00Mix3RoutingInvert4
				INTEGER,
			iqudc00Mix3GainGain1
				INTEGER,
			iqudc00Mix3GainMute1
				INTEGER,
			iqudc00Mix3GainGain2
				INTEGER,
			iqudc00Mix3GainMute2
				INTEGER,
			iqudc00Mix3GainGain3
				INTEGER,
			iqudc00Mix3GainMute3
				INTEGER,
			iqudc00Mix3GainGain4
				INTEGER,
			iqudc00Mix3GainMute4
				INTEGER,
			iqudc00Mix3GainInp1Clip
				RollCallString,
			iqudc00Mix3GainInp2Clip
				RollCallString,
			iqudc00Mix3GainInp3Clip
				RollCallString,
			iqudc00Mix3GainInp4Clip
				RollCallString,
			iqudc00Mix3GainOPClip
				RollCallString,
			iqudc00Mix4RoutingSource1
				INTEGER,
			iqudc00Mix4RoutingInvert1
				INTEGER,
			iqudc00Mix4RoutingSource2
				INTEGER,
			iqudc00Mix4RoutingInvert2
				INTEGER,
			iqudc00Mix4RoutingSource3
				INTEGER,
			iqudc00Mix4RoutingInvert3
				INTEGER,
			iqudc00Mix4RoutingSource4
				INTEGER,
			iqudc00Mix4RoutingInvert4
				INTEGER,
			iqudc00Mix4GainGain1
				INTEGER,
			iqudc00Mix4GainMute1
				INTEGER,
			iqudc00Mix4GainGain2
				INTEGER,
			iqudc00Mix4GainMute2
				INTEGER,
			iqudc00Mix4GainGain3
				INTEGER,
			iqudc00Mix4GainMute3
				INTEGER,
			iqudc00Mix4GainGain4
				INTEGER,
			iqudc00Mix4GainMute4
				INTEGER,
			iqudc00Mix4GainInp1Clip
				RollCallString,
			iqudc00Mix4GainInp2Clip
				RollCallString,
			iqudc00Mix4GainInp3Clip
				RollCallString,
			iqudc00Mix4GainInp4Clip
				RollCallString,
			iqudc00Mix4GainOPClip
				RollCallString,
			iqudc00AudioDolbyETimingSelAudioPair
				INTEGER,
			iqudc00AudioDolbyETimingRelativeTiming
				RollCallString,
			iqudc00AudioDolbyETimingLineNumber
				RollCallString,
			iqudc00AudioDolbyETimingStatus
				RollCallString,
			iqudc00AudioDolbyETimingError
				RollCallString,
			iqudc00UtilsPatternsPatternEnable
				INTEGER,
			iqudc00UtilsPatternsScrollPattern
				INTEGER,
			iqudc00UtilsPatternsPatternType
				INTEGER,
			iqudc00UtilsClosedCaptionEnable
				INTEGER,
			iqudc00UtilsClosedCaptionHDCaptionLine
				INTEGER,
			iqudc00UtilsClosedCaptionHDFollowIPLine
				INTEGER,
			iqudc00UtilsClosedCaptionSDCaptionIPLine
				INTEGER,
			iqudc00UtilsClosedCaptionSDCaptionOutLine
				INTEGER,
			iqudc00UtilsClosedCaptionSDFollowIPLine
				INTEGER,
			iqudc00UtilsMonochrome
				INTEGER,
			iqudc00UtilsMonochromeMonochromeType
				INTEGER,
			iqudc00GPIGPI1GPIO1Mode
				INTEGER,
			iqudc00GPIGPI1GPI1ipSelect
				INTEGER,
			iqudc00GPIGPI1GPO1opSelect
				INTEGER,
			iqudc00GPIGPI1InvertGPIO1
				INTEGER,
			iqudc00GPIGPI2GPIO2Mode
				INTEGER,
			iqudc00GPIGPI2GPI2ipSelect
				INTEGER,
			iqudc00GPIGPI2GPO2opSelect
				INTEGER,
			iqudc00GPIGPI2InvertGPIO2
				INTEGER,
			iqudc00GPIGPIPWMDelayTimerTimerSource
				INTEGER,
			iqudc00GPIGPIPWMDelayTimerActiveHigh
				INTEGER,
			iqudc00MemoriesRecallMemory
				INTEGER,
			iqudc00MemoriesSelMemory
				INTEGER,
			iqudc00MemoriesSaveMemory
				INTEGER,
			iqudc00MemoriesMemoryNameChangeName
				RollCallString,
			iqudc00MemoriesLastDisplayMemory
				RollCallString,
			iqudc00RollCallRollTrackDisableAll
				INTEGER,
			iqudc00RollCallRollTrackIndex
				INTEGER,
			iqudc00RollCallRollTrackSource
				INTEGER,
			iqudc00RollCallRollTrackAddress
				RollCallString,
			iqudc00RollCallRollTrackCommand
				RollCallString,
			iqudc00RollCallRollTrackStatus
				RollCallString,
			iqudc00RollCallRollTrackSending
				RollCallString,
			iqudc00LoggingVideoInputLogInput1Type
				INTEGER,
			iqudc00LoggingVideoInputInput1Type
				RollCallString,
			iqudc00LoggingVideoInputLogInput1Status
				INTEGER,
			iqudc00LoggingVideoInputInput1Status
				RollCallString,
			iqudc00LoggingVideoInputLogInput1Std
				INTEGER,
			iqudc00LoggingVideoInputInput1Std
				RollCallString,
			iqudc00LoggingVideoInputLogInput1Errors
				INTEGER,
			iqudc00LoggingVideoInputInput1Errors
				RollCallString,
			iqudc00LoggingVideoInputLogInput1ErrSecs
				INTEGER,
			iqudc00LoggingVideoInputInput1ErrSecs
				RollCallString,
			iqudc00LoggingVideoInputLogInput1ANCErr
				INTEGER,
			iqudc00LoggingVideoInputInput1ANCErrors
				RollCallString,
			iqudc00LoggingVideoInputLogInput1ANCErrSecs
				INTEGER,
			iqudc00LoggingVideoInputInput1ANCErrSecs
				RollCallString,
			iqudc00LoggingVideoInputLogInput2Type
				INTEGER,
			iqudc00LoggingVideoInputInput2Type
				RollCallString,
			iqudc00LoggingVideoInputLogInput2Status
				INTEGER,
			iqudc00LoggingVideoInputInput2Status
				RollCallString,
			iqudc00LoggingVideoInputLogInput2Std
				INTEGER,
			iqudc00LoggingVideoInputInput2Std
				RollCallString,
			iqudc00LoggingVideoInputLogInput2Errors
				INTEGER,
			iqudc00LoggingVideoInputInput2Errors
				RollCallString,
			iqudc00LoggingVideoInputLogInput2ErrSecs
				INTEGER,
			iqudc00LoggingVideoInputInput2ErrSecs
				RollCallString,
			iqudc00LoggingVideoInputLogInput2ANCErr
				INTEGER,
			iqudc00LoggingVideoInputInput2ANCErrors
				RollCallString,
			iqudc00LoggingVideoInputLogInput2ANCErrSecs
				INTEGER,
			iqudc00LoggingVideoInputInput2ANCErrSecs
				RollCallString,
			iqudc00LoggingIn1AudStateLogInp1Emb1stat
				INTEGER,
			iqudc00LoggingIn1AudStateInp1Emb1state
				RollCallString,
			iqudc00LoggingIn1AudStateLogInp1Emb2stat
				INTEGER,
			iqudc00LoggingIn1AudStateInp1Emb2state
				RollCallString,
			iqudc00LoggingIn1AudStateLogInp1Emb3stat
				INTEGER,
			iqudc00LoggingIn1AudStateInp1Emb3state
				RollCallString,
			iqudc00LoggingIn1AudStateLogInp1Emb4stat
				INTEGER,
			iqudc00LoggingIn1AudStateInp1Emb4state
				RollCallString,
			iqudc00LoggingIn1AudStateLogInp1Emb5stat
				INTEGER,
			iqudc00LoggingIn1AudStateInp1Emb5state
				RollCallString,
			iqudc00LoggingIn1AudStateLogInp1Emb6stat
				INTEGER,
			iqudc00LoggingIn1AudStateInp1Emb6state
				RollCallString,
			iqudc00LoggingIn1AudStateLogInp1Emb7stat
				INTEGER,
			iqudc00LoggingIn1AudStateInp1Emb7state
				RollCallString,
			iqudc00LoggingIn1AudStateLogInp1Emb8stat
				INTEGER,
			iqudc00LoggingIn1AudStateInp1Emb8state
				RollCallString,
			iqudc00LoggingIn2AudStateLogInp2Emb1stat
				INTEGER,
			iqudc00LoggingIn2AudStateInp2Emb1state
				RollCallString,
			iqudc00LoggingIn2AudStateLogInp2Emb2stat
				INTEGER,
			iqudc00LoggingIn2AudStateInp2Emb2state
				RollCallString,
			iqudc00LoggingIn2AudStateLogInp2Emb3stat
				INTEGER,
			iqudc00LoggingIn2AudStateInp2Emb3state
				RollCallString,
			iqudc00LoggingIn2AudStateLogInp2Emb4stat
				INTEGER,
			iqudc00LoggingIn2AudStateInp2Emb4state
				RollCallString,
			iqudc00LoggingIn2AudStateLogInp2Emb5stat
				INTEGER,
			iqudc00LoggingIn2AudStateInp2Emb5state
				RollCallString,
			iqudc00LoggingIn2AudStateLogInp2Emb6stat
				INTEGER,
			iqudc00LoggingIn2AudStateInp2Emb6state
				RollCallString,
			iqudc00LoggingIn2AudStateLogInp2Emb7stat
				INTEGER,
			iqudc00LoggingIn2AudStateInp2Emb7state
				RollCallString,
			iqudc00LoggingIn2AudStateLogInp2Emb8stat
				INTEGER,
			iqudc00LoggingIn2AudStateInp2Emb8state
				RollCallString,
			iqudc00LoggingIn1AudTypeLogInp1Emb1type
				INTEGER,
			iqudc00LoggingIn1AudTypeInp1Emb1type
				RollCallString,
			iqudc00LoggingIn1AudTypeLogInp1Emb2type
				INTEGER,
			iqudc00LoggingIn1AudTypeInp1Emb2type
				RollCallString,
			iqudc00LoggingIn1AudTypeLogInp1Emb3type
				INTEGER,
			iqudc00LoggingIn1AudTypeInp1Emb3type
				RollCallString,
			iqudc00LoggingIn1AudTypeLogInp1Emb4type
				INTEGER,
			iqudc00LoggingIn1AudTypeInp1Emb4type
				RollCallString,
			iqudc00LoggingIn1AudTypeLogInp1Emb5type
				INTEGER,
			iqudc00LoggingIn1AudTypeInp1Emb5type
				RollCallString,
			iqudc00LoggingIn1AudTypeLogInp1Emb6type
				INTEGER,
			iqudc00LoggingIn1AudTypeInp1Emb6type
				RollCallString,
			iqudc00LoggingIn1AudTypeLogInp1Emb7type
				INTEGER,
			iqudc00LoggingIn1AudTypeInp1Emb7type
				RollCallString,
			iqudc00LoggingIn1AudTypeLogInp1Emb8type
				INTEGER,
			iqudc00LoggingIn1AudTypeInp1Emb8type
				RollCallString,
			iqudc00LoggingIn2AudTypeLogInp2Emb1type
				INTEGER,
			iqudc00LoggingIn2AudTypeInp2Emb1type
				RollCallString,
			iqudc00LoggingIn2AudTypeLogInp2Emb2type
				INTEGER,
			iqudc00LoggingIn2AudTypeInp2Emb2type
				RollCallString,
			iqudc00LoggingIn2AudTypeLogInp2Emb3type
				INTEGER,
			iqudc00LoggingIn2AudTypeInp2Emb3type
				RollCallString,
			iqudc00LoggingIn2AudTypeLogInp2Emb4type
				INTEGER,
			iqudc00LoggingIn2AudTypeInp2Emb4type
				RollCallString,
			iqudc00LoggingIn2AudTypeLogInp2Emb5type
				INTEGER,
			iqudc00LoggingIn2AudTypeInp2Emb5type
				RollCallString,
			iqudc00LoggingIn2AudTypeLogInp2Emb6type
				INTEGER,
			iqudc00LoggingIn2AudTypeInp2Emb6type
				RollCallString,
			iqudc00LoggingIn2AudTypeLogInp2Emb7type
				INTEGER,
			iqudc00LoggingIn2AudTypeInp2Emb7type
				RollCallString,
			iqudc00LoggingIn2AudTypeLogInp2Emb8type
				INTEGER,
			iqudc00LoggingIn2AudTypeInp2Emb8type
				RollCallString,
			iqudc00LoggingOPAudStateLogOutEmb1state
				INTEGER,
			iqudc00LoggingOPAudStateOutEmb1state
				RollCallString,
			iqudc00LoggingOPAudStateLogOutEmb2state
				INTEGER,
			iqudc00LoggingOPAudStateOutEmb2state
				RollCallString,
			iqudc00LoggingOPAudStateLogOutEmb3state
				INTEGER,
			iqudc00LoggingOPAudStateOutEmb3state
				RollCallString,
			iqudc00LoggingOPAudStateLogOutEmb4state
				INTEGER,
			iqudc00LoggingOPAudStateOutEmb4state
				RollCallString,
			iqudc00LoggingOPAudStateLogOutEmb5state
				INTEGER,
			iqudc00LoggingOPAudStateOutEmb5state
				RollCallString,
			iqudc00LoggingOPAudStateLogOutEmb6state
				INTEGER,
			iqudc00LoggingOPAudStateOutEmb6state
				RollCallString,
			iqudc00LoggingOPAudStateLogOutEmb7state
				INTEGER,
			iqudc00LoggingOPAudStateOutEmb7state
				RollCallString,
			iqudc00LoggingOPAudStateLogOutEmb8state
				INTEGER,
			iqudc00LoggingOPAudStateOutEmb8state
				RollCallString,
			iqudc00LoggingOPAudTypeLogOutEmb1type
				INTEGER,
			iqudc00LoggingOPAudTypeOutEmb1type
				RollCallString,
			iqudc00LoggingOPAudTypeLogOutEmb2type
				INTEGER,
			iqudc00LoggingOPAudTypeOutEmb2type
				RollCallString,
			iqudc00LoggingOPAudTypeLogOutEmb3type
				INTEGER,
			iqudc00LoggingOPAudTypeOutEmb3type
				RollCallString,
			iqudc00LoggingOPAudTypeLogOutEmb4type
				INTEGER,
			iqudc00LoggingOPAudTypeOutEmb4type
				RollCallString,
			iqudc00LoggingOPAudTypeLogOutEmb5type
				INTEGER,
			iqudc00LoggingOPAudTypeOutEmb5type
				RollCallString,
			iqudc00LoggingOPAudTypeLogOutEmb6type
				INTEGER,
			iqudc00LoggingOPAudTypeOutEmb6type
				RollCallString,
			iqudc00LoggingOPAudTypeLogOutEmb7type
				INTEGER,
			iqudc00LoggingOPAudTypeOutEmb7type
				RollCallString,
			iqudc00LoggingOPAudTypeLogOutEmb8type
				INTEGER,
			iqudc00LoggingOPAudTypeOutEmb8type
				RollCallString,
			iqudc00LoggingOPAudLevelLogOutEmb1LLev
				INTEGER,
			iqudc00LoggingOPAudLevelOutEmb1LLevel
				RollCallString,
			iqudc00LoggingOPAudLevelLogOutEmb1RLev
				INTEGER,
			iqudc00LoggingOPAudLevelOutEmb1RLevel
				RollCallString,
			iqudc00LoggingOPAudLevelLogOutEmb2LLev
				INTEGER,
			iqudc00LoggingOPAudLevelOutEmb2LLevel
				RollCallString,
			iqudc00LoggingOPAudLevelLogOutEmb2RLev
				INTEGER,
			iqudc00LoggingOPAudLevelOutEmb2RLevel
				RollCallString,
			iqudc00LoggingOPAudLevelLogOutEmb3LLev
				INTEGER,
			iqudc00LoggingOPAudLevelOutEmb3LLevel
				RollCallString,
			iqudc00LoggingOPAudLevelLogOutEmb3RLev
				INTEGER,
			iqudc00LoggingOPAudLevelOutEmb3RLevel
				RollCallString,
			iqudc00LoggingOPAudLevelLogOutEmb4LLev
				INTEGER,
			iqudc00LoggingOPAudLevelOutEmb4LLevel
				RollCallString,
			iqudc00LoggingOPAudLevelLogOutEmb4RLev
				INTEGER,
			iqudc00LoggingOPAudLevelOutEmb4RLevel
				RollCallString,
			iqudc00LoggingOPAudLevelLogOutEmb5LLev
				INTEGER,
			iqudc00LoggingOPAudLevelOutEmb5LLevel
				RollCallString,
			iqudc00LoggingOPAudLevelLogOutEmb5RLev
				INTEGER,
			iqudc00LoggingOPAudLevelOutEmb5RLevel
				RollCallString,
			iqudc00LoggingOPAudLevelLogOutEmb6LLev
				INTEGER,
			iqudc00LoggingOPAudLevelOutEmb6LLevel
				RollCallString,
			iqudc00LoggingOPAudLevelLogOutEmb6RLev
				INTEGER,
			iqudc00LoggingOPAudLevelOutEmb6RLevel
				RollCallString,
			iqudc00LoggingOPAudLevelLogOutEmb7LLev
				INTEGER,
			iqudc00LoggingOPAudLevelOutEmb7LLevel
				RollCallString,
			iqudc00LoggingOPAudLevelLogOutEmb7RLev
				INTEGER,
			iqudc00LoggingOPAudLevelOutEmb7RLevel
				RollCallString,
			iqudc00LoggingOPAudLevelLogOutEmb8LLev
				INTEGER,
			iqudc00LoggingOPAudLevelOutEmb8LLevel
				RollCallString,
			iqudc00LoggingOPAudLevelLogOutEmb8RLev
				INTEGER,
			iqudc00LoggingOPAudLevelOutEmb8RLevel
				RollCallString,
			iqudc00LoggingRefOutputLogOutputState
				INTEGER,
			iqudc00LoggingRefOutputOutputState
				RollCallString,
			iqudc00LoggingRefOutputLogOutputType
				INTEGER,
			iqudc00LoggingRefOutputOutputType
				RollCallString,
			iqudc00LoggingRefOutputLogOutputStandard
				INTEGER,
			iqudc00LoggingRefOutputOutputStandard
				RollCallString,
			iqudc00LoggingRefOutputLogOutputSource
				INTEGER,
			iqudc00LoggingRefOutputOutputSource
				RollCallString,
			iqudc00LoggingRefOutputLogReferenceType
				INTEGER,
			iqudc00LoggingRefOutputReferenceType
				RollCallString,
			iqudc00LoggingRefOutputLogReferenceState
				INTEGER,
			iqudc00LoggingRefOutputReferenceState
				RollCallString,
			iqudc00LoggingRefOutputLogReferenceStand
				INTEGER,
			iqudc00LoggingRefOutputReferenceStandard
				RollCallString,
			iqudc00LoggingMiscLogSerialNo
				INTEGER,
			iqudc00LoggingMiscSerialNo
				RollCallString,
			iqudc00LoggingMiscLogOSVersion
				INTEGER,
			iqudc00LoggingMiscOSVersion
				RollCallString,
			iqudc00LoggingMiscLogBuildNo
				INTEGER,
			iqudc00LoggingMiscBuildNo
				RollCallString,
			iqudc00LoggingMiscLogHardwareVer
				INTEGER,
			iqudc00LoggingMiscHardwareVer
				RollCallString,
			iqudc00LoggingMiscLogFirmwareVer
				INTEGER,
			iqudc00LoggingMiscFirmwareVer
				RollCallString,
			iqudc00LoggingMiscLogUpTime
				INTEGER,
			iqudc00LoggingMiscUpTime
				RollCallString,
			iqudc00LoggingWideScreenLogInput1Aspect
				INTEGER,
			iqudc00LoggingWideScreenInput1Aspect
				RollCallString,
			iqudc00LoggingWideScreenLogInput1AFD
				INTEGER,
			iqudc00LoggingWideScreenInput1AFD
				RollCallString,
			iqudc00LoggingWideScreenLogInput1WSS
				INTEGER,
			iqudc00LoggingWideScreenInput1WSS
				RollCallString,
			iqudc00LoggingWideScreenLogInput1VI
				INTEGER,
			iqudc00LoggingWideScreenInput1VI
				RollCallString,
			iqudc00LoggingWideScreenLogInput2Aspect
				INTEGER,
			iqudc00LoggingWideScreenInput2Aspect
				RollCallString,
			iqudc00LoggingWideScreenLogInput2AFD
				INTEGER,
			iqudc00LoggingWideScreenInput2AFD
				RollCallString,
			iqudc00LoggingWideScreenLogInput2WSS
				INTEGER,
			iqudc00LoggingWideScreenInput2WSS
				RollCallString,
			iqudc00LoggingWideScreenLogInput2VI
				INTEGER,
			iqudc00LoggingWideScreenInput2VI
				RollCallString,
			iqudc00LoggingWideScreenLogOutputAspect
				INTEGER,
			iqudc00LoggingWideScreenOutputAspect
				RollCallString,
			iqudc00LoggingWideScreenLogOutputAFD
				INTEGER,
			iqudc00LoggingWideScreenOutputAFD
				RollCallString,
			iqudc00LoggingOPDolbyELogEmbDolbyE1
				INTEGER,
			iqudc00LoggingOPDolbyEEmbDolbyE1
				RollCallString,
			iqudc00LoggingOPDolbyELogEmbDolbyE2
				INTEGER,
			iqudc00LoggingOPDolbyEEmbDolbyE2
				RollCallString,
			iqudc00LoggingOPDolbyELogEmbDolbyE3
				INTEGER,
			iqudc00LoggingOPDolbyEEmbDolbyE3
				RollCallString,
			iqudc00LoggingOPDolbyELogEmbDolbyE4
				INTEGER,
			iqudc00LoggingOPDolbyEEmbDolbyE4
				RollCallString,
			iqudc00LoggingOPDolbyELogEmbDolbyE5
				INTEGER,
			iqudc00LoggingOPDolbyEEmbDolbyE5
				RollCallString,
			iqudc00LoggingOPDolbyELogEmbDolbyE6
				INTEGER,
			iqudc00LoggingOPDolbyEEmbDolbyE6
				RollCallString,
			iqudc00LoggingOPDolbyELogEmbDolbyE7
				INTEGER,
			iqudc00LoggingOPDolbyEEmbDolbyE7
				RollCallString,
			iqudc00LoggingOPDolbyELogEmbDolbyE8
				INTEGER,
			iqudc00LoggingOPDolbyEEmbDolbyE8
				RollCallString,
			iqudc00SetupProduct
				RollCallString,
			iqudc00SetupProductSerial
				RollCallString,
			iqudc00SetupProductPCB
				RollCallString,
			iqudc00SetupRestart
				INTEGER,
			iqudc00SetupSoftwareRelease
				RollCallString,
			iqudc00SetupSoftwareBuild
				RollCallString,
			iqudc00SetupSoftwareKOS
				RollCallString,
			iqudc00SetupFactory
				INTEGER,
			iqudc00SetupFirmwareMIO
				RollCallString,
			iqudc00SetupFirmwareMV
				RollCallString,
			iqudc00SetupFirmwareMH
				RollCallString,
			iqudc00SetupDisplay
				INTEGER,
			iqudc00DiagnosticsSelectTestVideoMemtest
				INTEGER,
			iqudc00DiagnosticsSelectTestVideoMemloop
				INTEGER,
			iqudc00DiagnosticsDiagnosticErrorsLoopCount
				RollCallString,
			iqudc00DiagnosticsDiagnosticErrorsProgress
				RollCallString,
			iqudc00DiagnosticsDiagnosticErrorsGpIoErrs
				RollCallString,
			iqudc00DiagnosticsDiagnosticErrorsVideoMemErrs
				RollCallString,
			iqudc00DiagnosticsDiagnosticErrorsSDI1Errs
				RollCallString,
			iqudc00DiagnosticsDiagnosticErrorsSDI2Errs
				RollCallString,
			iqudc00DiagnosticsDiagnosticErrorsSDI3Errs
				RollCallString,
			iqudc00DiagnosticsDiagnosticErrorsSDI4Errs
				RollCallString,
			iqudc00DiagnosticsDiagnosticErrorsSRCErrs
				RollCallString,
			iqudc00DiagnosticsDiagnosticErrorsLVDSErrs
				RollCallString,
			iqudc00DiagnosticsSTOPTests
				INTEGER,
			iqudc00DiagnosticsTestId
				RollCallString,
			iqudc00DiagnosticsLastError
				RollCallString
		}

	iqudc00SlotIndex OBJECT-TYPE
		SYNTAX		Unsigned32
		MAX-ACCESS		not-accessible
		STATUS			current
		DESCRIPTION
				"The unique Index value for each slot.  Its value
					ranges between 1 and the value of slotNumber."
		::= { iqudc00CmdEntry 0 }


	iqudc00InputIPSelect OBJECT-TYPE
		SYNTAX		INTEGER {
							val_Input_1(1),
							val_Input_2(2)
							}
		MAX-ACCESS		read-write
		STATUS			current
		DESCRIPTION
				"TYPE: - RadiobuttonList
				 PAGE: - Input
					I/P Select  cmdID= 32930
					Input 1  value= 1
					Input 2  value= 2  "
		::= { iqudc00CmdEntry 32930 }


	iqudc00InputYCDelay OBJECT-TYPE
		SYNTAX		INTEGER
		MAX-ACCESS		read-write
		STATUS			current
		DESCRIPTION
				"TYPE: - Number
				 PAGE: - Input
					YC Delay  cmdID= 33005  min= -10  max= 10  step= 1  format= %0.0f pix  div_scale= 1
					Min = -10 pix  Max = 10 pix  Step = 1 pix "
		::= { iqudc00CmdEntry 33005 }


	iqudc00InputValidStandardsAllValid OBJECT-TYPE
		SYNTAX		INTEGER { noAction(0),val_All_Valid(1) }
		MAX-ACCESS		read-write
		STATUS			current
		DESCRIPTION
				"TYPE: - Button
				 PAGE: - Input
					All Valid  cmdID= 32900  value= 1  "
		::= { iqudc00CmdEntry 32900 }


	iqudc00InputValidStandardsAllInvalid OBJECT-TYPE
		SYNTAX		INTEGER { noAction(0),val_AllInvalid(1) }
		MAX-ACCESS		read-write
		STATUS			current
		DESCRIPTION
				"TYPE: - Button
				 PAGE: - Input
					AllInvalid  cmdID= 32901  value= 1  "
		::= { iqudc00CmdEntry 32901 }


	iqudc00InputValidStandards108025i OBJECT-TYPE
		SYNTAX		INTEGER { disable(0), enable(1) }
		MAX-ACCESS		read-write
		STATUS			current
		DESCRIPTION
				"TYPE: - Checkbox
				 PAGE: - Input
					1080/25i  cmdID= 32910 "
		::= { iqudc00CmdEntry 32910 }


	iqudc00InputValidStandards108029i OBJECT-TYPE
		SYNTAX		INTEGER { disable(0), enable(1) }
		MAX-ACCESS		read-write
		STATUS			current
		DESCRIPTION
				"TYPE: - Checkbox
				 PAGE: - Input
					1080/29i  cmdID= 32919 "
		::= { iqudc00CmdEntry 32919 }


	iqudc00InputValidStandards72050p OBJECT-TYPE
		SYNTAX		INTEGER { disable(0), enable(1) }
		MAX-ACCESS		read-write
		STATUS			current
		DESCRIPTION
				"TYPE: - Checkbox
				 PAGE: - Input
					720/50p  cmdID= 32922 "
		::= { iqudc00CmdEntry 32922 }


	iqudc00InputValidStandards72059p OBJECT-TYPE
		SYNTAX		INTEGER { disable(0), enable(1) }
		MAX-ACCESS		read-write
		STATUS			current
		DESCRIPTION
				"TYPE: - Checkbox
				 PAGE: - Input
					720/59p  cmdID= 32924 "
		::= { iqudc00CmdEntry 32924 }


	iqudc00InputValidStandards62525i OBJECT-TYPE
		SYNTAX		INTEGER { disable(0), enable(1) }
		MAX-ACCESS		read-write
		STATUS			current
		DESCRIPTION
				"TYPE: - Checkbox
				 PAGE: - Input
					625/25i  cmdID= 32925 "
		::= { iqudc00CmdEntry 32925 }


	iqudc00InputValidStandards52529i OBJECT-TYPE
		SYNTAX		INTEGER { disable(0), enable(1) }
		MAX-ACCESS		read-write
		STATUS			current
		DESCRIPTION
				"TYPE: - Checkbox
				 PAGE: - Input
					525/29i  cmdID= 32926 "
		::= { iqudc00CmdEntry 32926 }


	iqudc00InputInpBackupEnable OBJECT-TYPE
		SYNTAX		INTEGER { disable(0), enable(1) }
		MAX-ACCESS		read-write
		STATUS			current
		DESCRIPTION
				"TYPE: - Checkbox
				 PAGE: - Input
					Backup Enable  cmdID= 32931 "
		::= { iqudc00CmdEntry 32931 }


	iqudc00InpBackupDefineInput1OkValidipStd OBJECT-TYPE
		SYNTAX		INTEGER { disable(0), enable(1) }
		MAX-ACCESS		read-write
		STATUS			current
		DESCRIPTION
				"TYPE: - Checkbox
				 PAGE: - Input
					Valid i/p Std  cmdID= 37901 "
		::= { iqudc00CmdEntry 37901 }


	iqudc00InpBackupDefineInput1OkEDHCRCisOK OBJECT-TYPE
		SYNTAX		INTEGER { disable(0), enable(1) }
		MAX-ACCESS		read-write
		STATUS			current
		DESCRIPTION
				"TYPE: - Checkbox
				 PAGE: - Input
					EDH/CRC is OK  cmdID= 37900 "
		::= { iqudc00CmdEntry 37900 }


	iqudc00InpBackupDefineInput1OkAudioPair1present OBJECT-TYPE
		SYNTAX		INTEGER { disable(0), enable(1) }
		MAX-ACCESS		read-write
		STATUS			current
		DESCRIPTION
				"TYPE: - Checkbox
				 PAGE: - Input
					Audio Pair 1 present  cmdID= 37902 "
		::= { iqudc00CmdEntry 37902 }


	iqudc00InpBackupDefineInput1OkAudioPair2present OBJECT-TYPE
		SYNTAX		INTEGER { disable(0), enable(1) }
		MAX-ACCESS		read-write
		STATUS			current
		DESCRIPTION
				"TYPE: - Checkbox
				 PAGE: - Input
					Audio Pair 2 present  cmdID= 37903 "
		::= { iqudc00CmdEntry 37903 }


	iqudc00InpBackupDefineInput1OkAudioPair3present OBJECT-TYPE
		SYNTAX		INTEGER { disable(0), enable(1) }
		MAX-ACCESS		read-write
		STATUS			current
		DESCRIPTION
				"TYPE: - Checkbox
				 PAGE: - Input
					Audio Pair 3 present  cmdID= 37904 "
		::= { iqudc00CmdEntry 37904 }


	iqudc00InpBackupDefineInput1OkAudioPair4present OBJECT-TYPE
		SYNTAX		INTEGER { disable(0), enable(1) }
		MAX-ACCESS		read-write
		STATUS			current
		DESCRIPTION
				"TYPE: - Checkbox
				 PAGE: - Input
					Audio Pair 4 present  cmdID= 37905 "
		::= { iqudc00CmdEntry 37905 }


	iqudc00InpBackupDefineInput1OkAudioPair5present OBJECT-TYPE
		SYNTAX		INTEGER { disable(0), enable(1) }
		MAX-ACCESS		read-write
		STATUS			current
		DESCRIPTION
				"TYPE: - Checkbox
				 PAGE: - Input
					Audio Pair 5 present  cmdID= 37906 "
		::= { iqudc00CmdEntry 37906 }


	iqudc00InpBackupDefineInput1OkAudioPair6present OBJECT-TYPE
		SYNTAX		INTEGER { disable(0), enable(1) }
		MAX-ACCESS		read-write
		STATUS			current
		DESCRIPTION
				"TYPE: - Checkbox
				 PAGE: - Input
					Audio Pair 6 present  cmdID= 37907 "
		::= { iqudc00CmdEntry 37907 }


	iqudc00InpBackupDefineInput1OkAudioPair7present OBJECT-TYPE
		SYNTAX		INTEGER { disable(0), enable(1) }
		MAX-ACCESS		read-write
		STATUS			current
		DESCRIPTION
				"TYPE: - Checkbox
				 PAGE: - Input
					Audio Pair 7 present  cmdID= 37908 "
		::= { iqudc00CmdEntry 37908 }


	iqudc00InpBackupDefineInput1OkAudioPair8present OBJECT-TYPE
		SYNTAX		INTEGER { disable(0), enable(1) }
		MAX-ACCESS		read-write
		STATUS			current
		DESCRIPTION
				"TYPE: - Checkbox
				 PAGE: - Input
					Audio Pair 8 present  cmdID= 37909 "
		::= { iqudc00CmdEntry 37909 }


	iqudc00InpBackupDefineInput2OkValidipStd OBJECT-TYPE
		SYNTAX		INTEGER { disable(0), enable(1) }
		MAX-ACCESS		read-write
		STATUS			current
		DESCRIPTION
				"TYPE: - Checkbox
				 PAGE: - Input
					Valid i/p Std  cmdID= 37911 "
		::= { iqudc00CmdEntry 37911 }


	iqudc00InpBackupDefineInput2OkEDHCRCisOK OBJECT-TYPE
		SYNTAX		INTEGER { disable(0), enable(1) }
		MAX-ACCESS		read-write
		STATUS			current
		DESCRIPTION
				"TYPE: - Checkbox
				 PAGE: - Input
					EDH/CRC is OK  cmdID= 37910 "
		::= { iqudc00CmdEntry 37910 }


	iqudc00InpBackupDefineInput2OkAudioPair1present OBJECT-TYPE
		SYNTAX		INTEGER { disable(0), enable(1) }
		MAX-ACCESS		read-write
		STATUS			current
		DESCRIPTION
				"TYPE: - Checkbox
				 PAGE: - Input
					Audio Pair 1 present  cmdID= 37912 "
		::= { iqudc00CmdEntry 37912 }


	iqudc00InpBackupDefineInput2OkAudioPair2present OBJECT-TYPE
		SYNTAX		INTEGER { disable(0), enable(1) }
		MAX-ACCESS		read-write
		STATUS			current
		DESCRIPTION
				"TYPE: - Checkbox
				 PAGE: - Input
					Audio Pair 2 present  cmdID= 37913 "
		::= { iqudc00CmdEntry 37913 }


	iqudc00InpBackupDefineInput2OkAudioPair3present OBJECT-TYPE
		SYNTAX		INTEGER { disable(0), enable(1) }
		MAX-ACCESS		read-write
		STATUS			current
		DESCRIPTION
				"TYPE: - Checkbox
				 PAGE: - Input
					Audio Pair 3 present  cmdID= 37914 "
		::= { iqudc00CmdEntry 37914 }


	iqudc00InpBackupDefineInput2OkAudioPair4present OBJECT-TYPE
		SYNTAX		INTEGER { disable(0), enable(1) }
		MAX-ACCESS		read-write
		STATUS			current
		DESCRIPTION
				"TYPE: - Checkbox
				 PAGE: - Input
					Audio Pair 4 present  cmdID= 37915 "
		::= { iqudc00CmdEntry 37915 }


	iqudc00InpBackupDefineInput2OkAudioPair5present OBJECT-TYPE
		SYNTAX		INTEGER { disable(0), enable(1) }
		MAX-ACCESS		read-write
		STATUS			current
		DESCRIPTION
				"TYPE: - Checkbox
				 PAGE: - Input
					Audio Pair 5 present  cmdID= 37916 "
		::= { iqudc00CmdEntry 37916 }


	iqudc00InpBackupDefineInput2OkAudioPair6present OBJECT-TYPE
		SYNTAX		INTEGER { disable(0), enable(1) }
		MAX-ACCESS		read-write
		STATUS			current
		DESCRIPTION
				"TYPE: - Checkbox
				 PAGE: - Input
					Audio Pair 6 present  cmdID= 37917 "
		::= { iqudc00CmdEntry 37917 }


	iqudc00InpBackupDefineInput2OkAudioPair7present OBJECT-TYPE
		SYNTAX		INTEGER { disable(0), enable(1) }
		MAX-ACCESS		read-write
		STATUS			current
		DESCRIPTION
				"TYPE: - Checkbox
				 PAGE: - Input
					Audio Pair 7 present  cmdID= 37918 "
		::= { iqudc00CmdEntry 37918 }


	iqudc00InpBackupDefineInput2OkAudioPair8present OBJECT-TYPE
		SYNTAX		INTEGER { disable(0), enable(1) }
		MAX-ACCESS		read-write
		STATUS			current
		DESCRIPTION
				"TYPE: - Checkbox
				 PAGE: - Input
					Audio Pair 8 present  cmdID= 37919 "
		::= { iqudc00CmdEntry 37919 }


	iqudc00InpBackupRules1SetRule1 OBJECT-TYPE
		SYNTAX		INTEGER {
							val_Off(0),
							val_Input_1_is_OK(1),
							val_Input_2_is_OK(2),
							val_Input_1_in_Error(3),
							val_Input_2_in_Error(4),
							val_GPI_1_Open(5),
							val_GPI_1_Closed(6),
							val_GPI_2_Open(7),
							val_GPI_2_Closed(8)
							}
		MAX-ACCESS		read-write
		STATUS			current
		DESCRIPTION
				"TYPE: - RadiobuttonList
				 PAGE: - Input
					Set Rule 1  cmdID= 38010
					Off  value= 0
					Input 1 is OK  value= 1
					Input 2 is OK  value= 2
					Input 1 in Error  value= 3
					Input 2 in Error  value= 4
					GPI 1 Open  value= 5
					GPI 1 Closed  value= 6
					GPI 2 Open  value= 7
					GPI 2 Closed  value= 8  "
		::= { iqudc00CmdEntry 38010 }


	iqudc00InpBackupRules1SelectInput OBJECT-TYPE
		SYNTAX		INTEGER {
							val_Input_1(1),
							val_Input_2(2)
							}
		MAX-ACCESS		read-write
		STATUS			current
		DESCRIPTION
				"TYPE: - RadiobuttonList
				 PAGE: - Input
					Select Input  cmdID= 38020
					Input 1  value= 1
					Input 2  value= 2  "
		::= { iqudc00CmdEntry 38020 }


	iqudc00InpBackupRules1TimeDelay OBJECT-TYPE
		SYNTAX		INTEGER
		MAX-ACCESS		read-write
		STATUS			current
		DESCRIPTION
				"TYPE: - Number
				 PAGE: - Input
					Time Delay  cmdID= 38000  min= 0  max= 100  step= 1  format= %0.1f s  div_scale= 10
					Min = 0.0 s  Max = 10.0 s  Step = 0.1 s "
		::= { iqudc00CmdEntry 38000 }


	iqudc00InpBackupRules2SetRule2 OBJECT-TYPE
		SYNTAX		INTEGER {
							val_Off(0),
							val_Input_1_is_OK(1),
							val_Input_2_is_OK(2),
							val_Input_1_in_Error(3),
							val_Input_2_in_Error(4),
							val_GPI_1_Open(5),
							val_GPI_1_Closed(6),
							val_GPI_2_Open(7),
							val_GPI_2_Closed(8)
							}
		MAX-ACCESS		read-write
		STATUS			current
		DESCRIPTION
				"TYPE: - RadiobuttonList
				 PAGE: - Input
					Set Rule 2  cmdID= 38011
					Off  value= 0
					Input 1 is OK  value= 1
					Input 2 is OK  value= 2
					Input 1 in Error  value= 3
					Input 2 in Error  value= 4
					GPI 1 Open  value= 5
					GPI 1 Closed  value= 6
					GPI 2 Open  value= 7
					GPI 2 Closed  value= 8  "
		::= { iqudc00CmdEntry 38011 }


	iqudc00InpBackupRules2SelectInput OBJECT-TYPE
		SYNTAX		INTEGER {
							val_Input_1(1),
							val_Input_2(2)
							}
		MAX-ACCESS		read-write
		STATUS			current
		DESCRIPTION
				"TYPE: - RadiobuttonList
				 PAGE: - Input
					Select Input  cmdID= 38021
					Input 1  value= 1
					Input 2  value= 2  "
		::= { iqudc00CmdEntry 38021 }


	iqudc00InpBackupRules2TimeDelay OBJECT-TYPE
		SYNTAX		INTEGER
		MAX-ACCESS		read-write
		STATUS			current
		DESCRIPTION
				"TYPE: - Number
				 PAGE: - Input
					Time Delay  cmdID= 38001  min= 0  max= 100  step= 1  format= %0.1f s  div_scale= 10
					Min = 0.0 s  Max = 10.0 s  Step = 0.1 s "
		::= { iqudc00CmdEntry 38001 }


	iqudc00InpBackupRules3SetRule3 OBJECT-TYPE
		SYNTAX		INTEGER {
							val_Off(0),
							val_Input_1_is_OK(1),
							val_Input_2_is_OK(2),
							val_Input_1_in_Error(3),
							val_Input_2_in_Error(4),
							val_GPI_1_Open(5),
							val_GPI_1_Closed(6),
							val_GPI_2_Open(7),
							val_GPI_2_Closed(8)
							}
		MAX-ACCESS		read-write
		STATUS			current
		DESCRIPTION
				"TYPE: - RadiobuttonList
				 PAGE: - Input
					Set Rule 3  cmdID= 38012
					Off  value= 0
					Input 1 is OK  value= 1
					Input 2 is OK  value= 2
					Input 1 in Error  value= 3
					Input 2 in Error  value= 4
					GPI 1 Open  value= 5
					GPI 1 Closed  value= 6
					GPI 2 Open  value= 7
					GPI 2 Closed  value= 8  "
		::= { iqudc00CmdEntry 38012 }


	iqudc00InpBackupRules3SelectInput OBJECT-TYPE
		SYNTAX		INTEGER {
							val_Input_1(1),
							val_Input_2(2)
							}
		MAX-ACCESS		read-write
		STATUS			current
		DESCRIPTION
				"TYPE: - RadiobuttonList
				 PAGE: - Input
					Select Input  cmdID= 38022
					Input 1  value= 1
					Input 2  value= 2  "
		::= { iqudc00CmdEntry 38022 }


	iqudc00InpBackupRules3TimeDelay OBJECT-TYPE
		SYNTAX		INTEGER
		MAX-ACCESS		read-write
		STATUS			current
		DESCRIPTION
				"TYPE: - Number
				 PAGE: - Input
					Time Delay  cmdID= 38002  min= 0  max= 100  step= 1  format= %0.1f s  div_scale= 10
					Min = 0.0 s  Max = 10.0 s  Step = 0.1 s "
		::= { iqudc00CmdEntry 38002 }


	iqudc00InpBackupRules4SetRule4 OBJECT-TYPE
		SYNTAX		INTEGER {
							val_Off(0),
							val_Input_1_is_OK(1),
							val_Input_2_is_OK(2),
							val_Input_1_in_Error(3),
							val_Input_2_in_Error(4),
							val_GPI_1_Open(5),
							val_GPI_1_Closed(6),
							val_GPI_2_Open(7),
							val_GPI_2_Closed(8)
							}
		MAX-ACCESS		read-write
		STATUS			current
		DESCRIPTION
				"TYPE: - RadiobuttonList
				 PAGE: - Input
					Set Rule 4  cmdID= 38013
					Off  value= 0
					Input 1 is OK  value= 1
					Input 2 is OK  value= 2
					Input 1 in Error  value= 3
					Input 2 in Error  value= 4
					GPI 1 Open  value= 5
					GPI 1 Closed  value= 6
					GPI 2 Open  value= 7
					GPI 2 Closed  value= 8  "
		::= { iqudc00CmdEntry 38013 }


	iqudc00InpBackupRules4SelectInput OBJECT-TYPE
		SYNTAX		INTEGER {
							val_Input_1(1),
							val_Input_2(2)
							}
		MAX-ACCESS		read-write
		STATUS			current
		DESCRIPTION
				"TYPE: - RadiobuttonList
				 PAGE: - Input
					Select Input  cmdID= 38023
					Input 1  value= 1
					Input 2  value= 2  "
		::= { iqudc00CmdEntry 38023 }


	iqudc00InpBackupRules4TimeDelay OBJECT-TYPE
		SYNTAX		INTEGER
		MAX-ACCESS		read-write
		STATUS			current
		DESCRIPTION
				"TYPE: - Number
				 PAGE: - Input
					Time Delay  cmdID= 38003  min= 0  max= 100  step= 1  format= %0.1f s  div_scale= 10
					Min = 0.0 s  Max = 10.0 s  Step = 0.1 s "
		::= { iqudc00CmdEntry 38003 }


	iqudc00InpBackupRules5SetRule5 OBJECT-TYPE
		SYNTAX		INTEGER {
							val_Off(0),
							val_Input_1_is_OK(1),
							val_Input_2_is_OK(2),
							val_Input_1_in_Error(3),
							val_Input_2_in_Error(4),
							val_GPI_1_Open(5),
							val_GPI_1_Closed(6),
							val_GPI_2_Open(7),
							val_GPI_2_Closed(8)
							}
		MAX-ACCESS		read-write
		STATUS			current
		DESCRIPTION
				"TYPE: - RadiobuttonList
				 PAGE: - Input
					Set Rule 5  cmdID= 38014
					Off  value= 0
					Input 1 is OK  value= 1
					Input 2 is OK  value= 2
					Input 1 in Error  value= 3
					Input 2 in Error  value= 4
					GPI 1 Open  value= 5
					GPI 1 Closed  value= 6
					GPI 2 Open  value= 7
					GPI 2 Closed  value= 8  "
		::= { iqudc00CmdEntry 38014 }


	iqudc00InpBackupRules5SelectInput OBJECT-TYPE
		SYNTAX		INTEGER {
							val_Input_1(1),
							val_Input_2(2)
							}
		MAX-ACCESS		read-write
		STATUS			current
		DESCRIPTION
				"TYPE: - RadiobuttonList
				 PAGE: - Input
					Select Input  cmdID= 38024
					Input 1  value= 1
					Input 2  value= 2  "
		::= { iqudc00CmdEntry 38024 }


	iqudc00InpBackupRules5TimeDelay OBJECT-TYPE
		SYNTAX		INTEGER
		MAX-ACCESS		read-write
		STATUS			current
		DESCRIPTION
				"TYPE: - Number
				 PAGE: - Input
					Time Delay  cmdID= 38004  min= 0  max= 100  step= 1  format= %0.1f s  div_scale= 10
					Min = 0.0 s  Max = 10.0 s  Step = 0.1 s "
		::= { iqudc00CmdEntry 38004 }


	iqudc00InputErrorsCRCErrs OBJECT-TYPE
		SYNTAX		RollCallString
		MAX-ACCESS		read-only
		STATUS			current
		DESCRIPTION
				"TYPE: - Display
				 PAGE: - Input
					CRC Errs  cmdID= 33050  format=   "
		::= { iqudc00CmdEntry 33050 }


	iqudc00InputErrorsCRCErrSec OBJECT-TYPE
		SYNTAX		RollCallString
		MAX-ACCESS		read-only
		STATUS			current
		DESCRIPTION
				"TYPE: - Display
				 PAGE: - Input
					CRC ErrSec  cmdID= 33051  format=   "
		::= { iqudc00CmdEntry 33051 }


	iqudc00InputErrorsANCErrs OBJECT-TYPE
		SYNTAX		RollCallString
		MAX-ACCESS		read-only
		STATUS			current
		DESCRIPTION
				"TYPE: - Display
				 PAGE: - Input
					ANC Errs  cmdID= 33053  format=   "
		::= { iqudc00CmdEntry 33053 }


	iqudc00InputErrorsANCErrSec OBJECT-TYPE
		SYNTAX		RollCallString
		MAX-ACCESS		read-only
		STATUS			current
		DESCRIPTION
				"TYPE: - Display
				 PAGE: - Input
					ANC ErrSec  cmdID= 33054  format=   "
		::= { iqudc00CmdEntry 33054 }


	iqudc00InputErrorsResetSec OBJECT-TYPE
		SYNTAX		RollCallString
		MAX-ACCESS		read-only
		STATUS			current
		DESCRIPTION
				"TYPE: - Display
				 PAGE: - Input
					ResetSec  cmdID= 33055  format=   "
		::= { iqudc00CmdEntry 33055 }


	iqudc00InputErrorsErrorReset OBJECT-TYPE
		SYNTAX		INTEGER { noAction(0),val_Error_Reset(1) }
		MAX-ACCESS		read-write
		STATUS			current
		DESCRIPTION
				"TYPE: - Button
				 PAGE: - Input
					Error Reset  cmdID= 33052  value= 1  "
		::= { iqudc00CmdEntry 33052 }


	iqudc00OutputOPStd OBJECT-TYPE
		SYNTAX		INTEGER {
							val_1080i(1),
							val_720p(2),
							val_SD(3)
							}
		MAX-ACCESS		read-write
		STATUS			current
		DESCRIPTION
				"TYPE: - RadiobuttonList
				 PAGE: - Output
					O/P Std.  cmdID= 33004
					1080i  value= 1
					720p  value= 2
					SD  value= 3  "
		::= { iqudc00CmdEntry 33004 }


	iqudc00OutputVideoProcMasterGain OBJECT-TYPE
		SYNTAX		INTEGER
		MAX-ACCESS		read-write
		STATUS			current
		DESCRIPTION
				"TYPE: - Number
				 PAGE: - Output
					Master Gain  cmdID= 33000  min= -600  max= 600  step= 10  format= %0.1f dB  div_scale= 100
					Min = -6.0 dB  Max = 6.0 dB  Step = 0.1 dB "
		::= { iqudc00CmdEntry 33000 }


	iqudc00OutputVideoProcYGain OBJECT-TYPE
		SYNTAX		INTEGER
		MAX-ACCESS		read-write
		STATUS			current
		DESCRIPTION
				"TYPE: - Number
				 PAGE: - Output
					Y Gain  cmdID= 33001  min= -600  max= 600  step= 10  format= %0.1f dB  div_scale= 100
					Min = -6.0 dB  Max = 6.0 dB  Step = 0.1 dB "
		::= { iqudc00CmdEntry 33001 }


	iqudc00OutputVideoProcCGain OBJECT-TYPE
		SYNTAX		INTEGER
		MAX-ACCESS		read-write
		STATUS			current
		DESCRIPTION
				"TYPE: - Number
				 PAGE: - Output
					C Gain  cmdID= 33003  min= -600  max= 600  step= 10  format= %0.1f dB  div_scale= 100
					Min = -6.0 dB  Max = 6.0 dB  Step = 0.1 dB "
		::= { iqudc00CmdEntry 33003 }


	iqudc00OutputVideoProcBlackLevel OBJECT-TYPE
		SYNTAX		INTEGER
		MAX-ACCESS		read-write
		STATUS			current
		DESCRIPTION
				"TYPE: - Number
				 PAGE: - Output
					Black Level  cmdID= 33002  min= -200  max= 200  step= 1  format= %0.0f mV  div_scale= 1
					Min = -200 mV  Max = 200 mV  Step = 1 mV "
		::= { iqudc00CmdEntry 33002 }


	iqudc00OutputDefaultOutput OBJECT-TYPE
		SYNTAX		INTEGER {
							val_Freeze_Field(5),
							val_Black(2),
							val_Input(3),
							val_Out_Pattern(4)
							}
		MAX-ACCESS		read-write
		STATUS			current
		DESCRIPTION
				"TYPE: - RadiobuttonList
				 PAGE: - Output
					Default Output  cmdID= 33031
					Freeze Field  value= 5
					Black  value= 2
					Input  value= 3
					Out Pattern  value= 4  "
		::= { iqudc00CmdEntry 33031 }


	iqudc00OutputFreezeForceFreeze OBJECT-TYPE
		SYNTAX		INTEGER { disable(0), enable(1) }
		MAX-ACCESS		read-write
		STATUS			current
		DESCRIPTION
				"TYPE: - Checkbox
				 PAGE: - Output
					Force Freeze  cmdID= 33032 "
		::= { iqudc00CmdEntry 33032 }


	iqudc00PictureOutputBorderLeft OBJECT-TYPE
		SYNTAX		INTEGER
		MAX-ACCESS		read-write
		STATUS			current
		DESCRIPTION
				"TYPE: - Number
				 PAGE: - Output
					Left  cmdID= 6009  min= 0  max= 4095  step= 1  format= %0.0f  div_scale= 1
					Min = 0  Max = 4095  Step = 1 "
		::= { iqudc00CmdEntry 6009 }


	iqudc00PictureOutputBorderRight OBJECT-TYPE
		SYNTAX		INTEGER
		MAX-ACCESS		read-write
		STATUS			current
		DESCRIPTION
				"TYPE: - Number
				 PAGE: - Output
					Right  cmdID= 6010  min= 0  max= 4095  step= 1  format= %0.0f  div_scale= 1
					Min = 0  Max = 4095  Step = 1 "
		::= { iqudc00CmdEntry 6010 }


	iqudc00PictureOutputBorderTop OBJECT-TYPE
		SYNTAX		INTEGER
		MAX-ACCESS		read-write
		STATUS			current
		DESCRIPTION
				"TYPE: - Number
				 PAGE: - Output
					Top  cmdID= 6011  min= 0  max= 2047  step= 1  format= %0.0f  div_scale= 1
					Min = 0  Max = 2047  Step = 1 "
		::= { iqudc00CmdEntry 6011 }


	iqudc00PictureOutputBorderBottom OBJECT-TYPE
		SYNTAX		INTEGER
		MAX-ACCESS		read-write
		STATUS			current
		DESCRIPTION
				"TYPE: - Number
				 PAGE: - Output
					Bottom  cmdID= 6012  min= 0  max= 2047  step= 1  format= %0.0f  div_scale= 1
					Min = 0  Max = 2047  Step = 1 "
		::= { iqudc00CmdEntry 6012 }


	iqudc00PictureOutputBorderRed OBJECT-TYPE
		SYNTAX		INTEGER
		MAX-ACCESS		read-write
		STATUS			current
		DESCRIPTION
				"TYPE: - Number
				 PAGE: - Output
					Red  cmdID= 6013  min= 0  max= 255  step= 1  format= %0.0f  div_scale= 1
					Min = 0  Max = 255  Step = 1 "
		::= { iqudc00CmdEntry 6013 }


	iqudc00PictureOutputBorderGreen OBJECT-TYPE
		SYNTAX		INTEGER
		MAX-ACCESS		read-write
		STATUS			current
		DESCRIPTION
				"TYPE: - Number
				 PAGE: - Output
					Green  cmdID= 6014  min= 0  max= 255  step= 1  format= %0.0f  div_scale= 1
					Min = 0  Max = 255  Step = 1 "
		::= { iqudc00CmdEntry 6014 }


	iqudc00PictureOutputBorderBlue OBJECT-TYPE
		SYNTAX		INTEGER
		MAX-ACCESS		read-write
		STATUS			current
		DESCRIPTION
				"TYPE: - Number
				 PAGE: - Output
					Blue  cmdID= 6015  min= 0  max= 255  step= 1  format= %0.0f  div_scale= 1
					Min = 0  Max = 255  Step = 1 "
		::= { iqudc00CmdEntry 6015 }


	iqudc00PictureOutputEnhanceVEnhance OBJECT-TYPE
		SYNTAX		INTEGER
		MAX-ACCESS		read-write
		STATUS			current
		DESCRIPTION
				"TYPE: - Number
				 PAGE: - Output
					V Enhance  cmdID= 6041  min= -2  max= 3  step= 1  format= %0.0f  div_scale= 1
					Min = -2  Max = 3  Step = 1 "
		::= { iqudc00CmdEntry 6041 }


	iqudc00PictureOutputEnhanceHEnhance OBJECT-TYPE
		SYNTAX		INTEGER
		MAX-ACCESS		read-write
		STATUS			current
		DESCRIPTION
				"TYPE: - Number
				 PAGE: - Output
					H Enhance  cmdID= 6042  min= -2  max= 3  step= 1  format= %0.0f  div_scale= 1
					Min = -2  Max = 3  Step = 1 "
		::= { iqudc00CmdEntry 6042 }


	iqudc00PictureOutputColorimetry OBJECT-TYPE
		SYNTAX		INTEGER {
							val_Auto(0),
							val_None(1),
							val_SD_to_HD(2),
							val_HD_to_SD(3)
							}
		MAX-ACCESS		read-write
		STATUS			current
		DESCRIPTION
				"TYPE: - RadiobuttonList
				 PAGE: - Output
					Colorimetry  cmdID= 6043
					Auto  value= 0
					None  value= 1
					SD to HD  value= 2
					HD to SD  value= 3  "
		::= { iqudc00CmdEntry 6043 }


	iqudc00PictureOutputFilmVideo OBJECT-TYPE
		SYNTAX		INTEGER {
							val_Auto(0),
							val_Normal_Video(1),
							val_Sports(2),
							val_Minimum_Delay(3)
							}
		MAX-ACCESS		read-write
		STATUS			current
		DESCRIPTION
				"TYPE: - RadiobuttonList
				 PAGE: - Output
					Film/Video  cmdID= 6044
					Auto  value= 0
					Normal (Video)  value= 1
					Sports  value= 2
					Minimum Delay  value= 3  "
		::= { iqudc00CmdEntry 6044 }


	iqudc00PictureOutputDetail OBJECT-TYPE
		SYNTAX		INTEGER { disable(0), enable(1) }
		MAX-ACCESS		read-write
		STATUS			current
		DESCRIPTION
				"TYPE: - Checkbox
				 PAGE: - Output
					Detail  cmdID= 6046 "
		::= { iqudc00CmdEntry 6046 }


	iqudc00ARCSetupRecallDisplayMemo OBJECT-TYPE
		SYNTAX		INTEGER {
							val_Display_Memory_1(1),
							val_Display_Memory_2(2),
							val_Display_Memory_3(3),
							val_Display_Memory_4(4),
							val_Display_Memory_5(5),
							val_Display_Memory_6(6),
							val_Display_Memory_7(7),
							val_Display_Memory_8(8),
							val_Display_Memory_9(9),
							val_Display_Memory_10(10),
							val_Display_Memory_11(11),
							val_Display_Memory_12(12),
							val_Display_Memory_13(13),
							val_Display_Memory_14(14),
							val_Display_Memory_15(15),
							val_Display_Memory_16(16),
							val_Display_Memory_17(17),
							val_Display_Memory_18(18),
							val_Display_Memory_19(19),
							val_Display_Memory_20(20),
							val_Display_Memory_21(21),
							val_Display_Memory_22(22),
							val_Display_Memory_23(23),
							val_Display_Memory_24(24),
							val_Display_Memory_25(25),
							val_Display_Memory_26(26),
							val_Display_Memory_27(27),
							val_Display_Memory_28(28),
							val_Display_Memory_29(29),
							val_Display_Memory_30(30),
							val_Display_Memory_31(31),
							val_Display_Memory_32(32),
							val_Display_Memory_33(33),
							val_Display_Memory_34(34),
							val_Display_Memory_35(35),
							val_Display_Memory_36(36),
							val_Display_Memory_37(37),
							val_Display_Memory_38(38),
							val_Display_Memory_39(39),
							val_Display_Memory_40(40)
							}
		MAX-ACCESS		read-write
		STATUS			current
		DESCRIPTION
				"TYPE: - RadiobuttonList
				 PAGE: - ARC Ctrl
					Recall Display Memo  cmdID= 38701
					Display Memory 1  value= 1
					Display Memory 2  value= 2
					Display Memory 3  value= 3
					Display Memory 4  value= 4
					Display Memory 5  value= 5
					Display Memory 6  value= 6
					Display Memory 7  value= 7
					Display Memory 8  value= 8
					Display Memory 9  value= 9
					Display Memory 10  value= 10
					Display Memory 11  value= 11
					Display Memory 12  value= 12
					Display Memory 13  value= 13
					Display Memory 14  value= 14
					Display Memory 15  value= 15
					Display Memory 16  value= 16
					Display Memory 17  value= 17
					Display Memory 18  value= 18
					Display Memory 19  value= 19
					Display Memory 20  value= 20
					Display Memory 21  value= 21
					Display Memory 22  value= 22
					Display Memory 23  value= 23
					Display Memory 24  value= 24
					Display Memory 25  value= 25
					Display Memory 26  value= 26
					Display Memory 27  value= 27
					Display Memory 28  value= 28
					Display Memory 29  value= 29
					Display Memory 30  value= 30
					Display Memory 31  value= 31
					Display Memory 32  value= 32
					Display Memory 33  value= 33
					Display Memory 34  value= 34
					Display Memory 35  value= 35
					Display Memory 36  value= 36
					Display Memory 37  value= 37
					Display Memory 38  value= 38
					Display Memory 39  value= 39
					Display Memory 40  value= 40  "
		::= { iqudc00CmdEntry 38701 }


	iqudc00ARCSetupSelDisplayMemory OBJECT-TYPE
		SYNTAX		INTEGER {
							val_Display_Memory_1(1),
							val_Display_Memory_2(2),
							val_Display_Memory_3(3),
							val_Display_Memory_4(4),
							val_Display_Memory_5(5),
							val_Display_Memory_6(6),
							val_Display_Memory_7(7),
							val_Display_Memory_8(8),
							val_Display_Memory_9(9),
							val_Display_Memory_10(10),
							val_Display_Memory_11(11),
							val_Display_Memory_12(12),
							val_Display_Memory_13(13),
							val_Display_Memory_14(14),
							val_Display_Memory_15(15),
							val_Display_Memory_16(16),
							val_Display_Memory_17(17),
							val_Display_Memory_18(18),
							val_Display_Memory_19(19),
							val_Display_Memory_20(20),
							val_Display_Memory_21(21),
							val_Display_Memory_22(22),
							val_Display_Memory_23(23),
							val_Display_Memory_24(24),
							val_Display_Memory_25(25),
							val_Display_Memory_26(26),
							val_Display_Memory_27(27),
							val_Display_Memory_28(28),
							val_Display_Memory_29(29),
							val_Display_Memory_30(30),
							val_Display_Memory_31(31),
							val_Display_Memory_32(32),
							val_Display_Memory_33(33),
							val_Display_Memory_34(34),
							val_Display_Memory_35(35),
							val_Display_Memory_36(36),
							val_Display_Memory_37(37),
							val_Display_Memory_38(38),
							val_Display_Memory_39(39),
							val_Display_Memory_40(40)
							}
		MAX-ACCESS		read-write
		STATUS			current
		DESCRIPTION
				"TYPE: - RadiobuttonList
				 PAGE: - ARC Ctrl
					Sel Display Memory  cmdID= 6040
					Display Memory 1  value= 1
					Display Memory 2  value= 2
					Display Memory 3  value= 3
					Display Memory 4  value= 4
					Display Memory 5  value= 5
					Display Memory 6  value= 6
					Display Memory 7  value= 7
					Display Memory 8  value= 8
					Display Memory 9  value= 9
					Display Memory 10  value= 10
					Display Memory 11  value= 11
					Display Memory 12  value= 12
					Display Memory 13  value= 13
					Display Memory 14  value= 14
					Display Memory 15  value= 15
					Display Memory 16  value= 16
					Display Memory 17  value= 17
					Display Memory 18  value= 18
					Display Memory 19  value= 19
					Display Memory 20  value= 20
					Display Memory 21  value= 21
					Display Memory 22  value= 22
					Display Memory 23  value= 23
					Display Memory 24  value= 24
					Display Memory 25  value= 25
					Display Memory 26  value= 26
					Display Memory 27  value= 27
					Display Memory 28  value= 28
					Display Memory 29  value= 29
					Display Memory 30  value= 30
					Display Memory 31  value= 31
					Display Memory 32  value= 32
					Display Memory 33  value= 33
					Display Memory 34  value= 34
					Display Memory 35  value= 35
					Display Memory 36  value= 36
					Display Memory 37  value= 37
					Display Memory 38  value= 38
					Display Memory 39  value= 39
					Display Memory 40  value= 40  "
		::= { iqudc00CmdEntry 6040 }


	iqudc00ARCSetupSaveDispMemory OBJECT-TYPE
		SYNTAX		INTEGER { noAction(0),val_Save_Disp_Memory(1) }
		MAX-ACCESS		read-write
		STATUS			current
		DESCRIPTION
				"TYPE: - Button
				 PAGE: - ARC Ctrl
					Save Disp Memory  cmdID= 38705  value= 1  "
		::= { iqudc00CmdEntry 38705 }


	iqudc00ARCSetupDispMemoryNameChangeName OBJECT-TYPE
		SYNTAX		RollCallString
		MAX-ACCESS		read-write
		STATUS			current
		DESCRIPTION
				"TYPE: - Editstring
				 PAGE: - ARC Ctrl
					Change Name  cmdID= 38703  "
		::= { iqudc00CmdEntry 38703 }


	iqudc00ARCSetupARCSize OBJECT-TYPE
		SYNTAX		INTEGER
		MAX-ACCESS		read-write
		STATUS			current
		DESCRIPTION
				"TYPE: - Number
				 PAGE: - ARC Ctrl
					Size  cmdID= 6000  min= 600  max= 2000  step= 1  format= %0.1f%  div_scale= 10
					Min = 60.0 Max = 200.0 Step = 0.1"
		::= { iqudc00CmdEntry 6000 }


	iqudc00ARCSetupARCApect OBJECT-TYPE
		SYNTAX		INTEGER
		MAX-ACCESS		read-write
		STATUS			current
		DESCRIPTION
				"TYPE: - Number
				 PAGE: - ARC Ctrl
					Apect  cmdID= 6001  min= 600  max= 2000  step= 1  format= %0.1f%  div_scale= 10
					Min = 60.0 Max = 200.0 Step = 0.1"
		::= { iqudc00CmdEntry 6001 }


	iqudc00ARCSetupARCTilt OBJECT-TYPE
		SYNTAX		INTEGER
		MAX-ACCESS		read-write
		STATUS			current
		DESCRIPTION
				"TYPE: - Number
				 PAGE: - ARC Ctrl
					Tilt  cmdID= 6002  min= -750  max= 750  step= 1  format= %0.1f%  div_scale= 10
					Min = -75.0 Max = 75.0 Step = 0.1"
		::= { iqudc00CmdEntry 6002 }


	iqudc00ARCSetupARCPan OBJECT-TYPE
		SYNTAX		INTEGER
		MAX-ACCESS		read-write
		STATUS			current
		DESCRIPTION
				"TYPE: - Number
				 PAGE: - ARC Ctrl
					Pan  cmdID= 6003  min= -750  max= 750  step= 1  format= %0.1f%  div_scale= 10
					Min = -75.0 Max = 75.0 Step = 0.1"
		::= { iqudc00CmdEntry 6003 }


	iqudc00ARCSetupARCOrigin OBJECT-TYPE
		SYNTAX		INTEGER {
							val_Top_Left(0),
							val_Center(1)
							}
		MAX-ACCESS		read-write
		STATUS			current
		DESCRIPTION
				"TYPE: - RadiobuttonList
				 PAGE: - ARC Ctrl
					Origin  cmdID= 6004
					Top Left  value= 0
					Center  value= 1  "
		::= { iqudc00CmdEntry 6004 }


	iqudc00ARCSetupInputCropLeft OBJECT-TYPE
		SYNTAX		INTEGER
		MAX-ACCESS		read-write
		STATUS			current
		DESCRIPTION
				"TYPE: - Number
				 PAGE: - ARC Ctrl
					Left  cmdID= 6005  min= 0  max= 4095  step= 1  format= %0.0f  div_scale= 1
					Min = 0  Max = 4095  Step = 1 "
		::= { iqudc00CmdEntry 6005 }


	iqudc00ARCSetupInputCropRight OBJECT-TYPE
		SYNTAX		INTEGER
		MAX-ACCESS		read-write
		STATUS			current
		DESCRIPTION
				"TYPE: - Number
				 PAGE: - ARC Ctrl
					Right  cmdID= 6006  min= 0  max= 4095  step= 1  format= %0.0f  div_scale= 1
					Min = 0  Max = 4095  Step = 1 "
		::= { iqudc00CmdEntry 6006 }


	iqudc00ARCSetupInputCropTop OBJECT-TYPE
		SYNTAX		INTEGER
		MAX-ACCESS		read-write
		STATUS			current
		DESCRIPTION
				"TYPE: - Number
				 PAGE: - ARC Ctrl
					Top  cmdID= 6007  min= 0  max= 2047  step= 1  format= %0.0f  div_scale= 1
					Min = 0  Max = 2047  Step = 1 "
		::= { iqudc00CmdEntry 6007 }


	iqudc00ARCSetupInputCropBottom OBJECT-TYPE
		SYNTAX		INTEGER
		MAX-ACCESS		read-write
		STATUS			current
		DESCRIPTION
				"TYPE: - Number
				 PAGE: - ARC Ctrl
					Bottom  cmdID= 6008  min= 0  max= 2047  step= 1  format= %0.0f  div_scale= 1
					Min = 0  Max = 2047  Step = 1 "
		::= { iqudc00CmdEntry 6008 }


	iqudc00ARCSetupSelStdPreset OBJECT-TYPE
		SYNTAX		INTEGER {
							val_Full_Frame(0),
							val_Box_16_9_Top_16_9(1),
							val_4_3_Box14_9Top_16_9(2),
							val_Box_16_9_16_9(3),
							val_Box_4_3_4_3(4),
							val_4_3_box_16_9(5),
							val_16_9_box_4_3(6),
							val_4_3_box_14_9_16_9(7),
							val_16_9_box_14_9_4_3(8)
							}
		MAX-ACCESS		read-write
		STATUS			current
		DESCRIPTION
				"TYPE: - RadiobuttonList
				 PAGE: - ARC Ctrl
					Sel Std. Preset  cmdID= 38704
					Full Frame  value= 0
					Box 16:9 Top > 16:9  value= 1
					4:3 Box14:9Top>16:9  value= 2
					Box 16:9 > 16:9  value= 3
					Box 4:3 > 4:3  value= 4
					4:3 > box 16:9  value= 5
					16:9 > box 4:3  value= 6
					4:3 box 14:9 > 16:9  value= 7
					16:9 box 14:9 > 4:3  value= 8  "
		::= { iqudc00CmdEntry 38704 }


	iqudc00ARCSetupRecallStdPreset OBJECT-TYPE
		SYNTAX		INTEGER { noAction(0),val_Recall_Std_Preset(1) }
		MAX-ACCESS		read-write
		STATUS			current
		DESCRIPTION
				"TYPE: - Button
				 PAGE: - ARC Ctrl
					Recall Std Preset  cmdID= 38700  value= 1  "
		::= { iqudc00CmdEntry 38700 }


	iqudc00ARCSetupDefaultALLMemory OBJECT-TYPE
		SYNTAX		INTEGER { noAction(0),val_Default_ALL_Memory(1) }
		MAX-ACCESS		read-write
		STATUS			current
		DESCRIPTION
				"TYPE: - Button
				 PAGE: - ARC Ctrl
					Default ALL Memory  cmdID= 38702  value= 1  "
		::= { iqudc00CmdEntry 38702 }


	iqudc00ARCSetupLastDisplayMemory OBJECT-TYPE
		SYNTAX		RollCallString
		MAX-ACCESS		read-only
		STATUS			current
		DESCRIPTION
				"TYPE: - Display
				 PAGE: - ARC Ctrl
					Last Display Memory  cmdID= 38706  format=   "
		::= { iqudc00CmdEntry 38706 }


	iqudc00WSSCtrlOutputAspect OBJECT-TYPE
		SYNTAX		INTEGER {
							val_Output_4_3(0),
							val_Output_16_9(1)
							}
		MAX-ACCESS		read-write
		STATUS			current
		DESCRIPTION
				"TYPE: - RadiobuttonList
				 PAGE: - WSS Ctrl
					Output Aspect  cmdID= 38751
					Output 4:3  value= 0
					Output 16:9  value= 1  "
		::= { iqudc00CmdEntry 38751 }


	iqudc00WSSCtrlIPWSSSignal OBJECT-TYPE
		SYNTAX		INTEGER {
							val_4_3_Coded_Frame(8),
							val_4_3_4_3(9),
							val_4_3_16_9(10),
							val_4_3_14_9(11),
							val_4_3_reserved(12),
							val_4_3_4_3_SP_14_9(13),
							val_4_3_16_9_SP_14_9(14),
							val_4_3_16_9_SP_4_3(15),
							val_4_3_box_16_9_top(2),
							val_4_3_box_14_9_top(3),
							val_4_3_box_16_9_ctr(4),
							val_4_3_Unknown(16),
							val_16_9_Coded_Frame(136),
							val_16_9_4_3(137),
							val_16_9_16_9(138),
							val_16_9_14_9(139),
							val_16_9_reserved(140),
							val_16_9_4_3_SP_14_9(141),
							val_16_9_16_9_SP_14_9(142),
							val_16_9_16_9_SP_4_3(143),
							val_16_9_box_16_9_top(130),
							val_16_9_box_14_9_top(131),
							val_16_9_box_16_9_ctr(132),
							val_16_9_Unknown(144)
							}
		MAX-ACCESS		read-write
		STATUS			current
		DESCRIPTION
				"TYPE: - RadiobuttonList
				 PAGE: - WSS Ctrl
					I/P WSS Signal  cmdID= 38740
					4:3 - Coded Frame  value= 8
					4:3 - 4:3  value= 9
					4:3 - 16:9  value= 10
					4:3 - 14:9  value= 11
					4:3 reserved  value= 12
					4:3 - 4:3 SP 14:9  value= 13
					4:3 - 16:9 SP 14:9  value= 14
					4:3 - 16:9 SP 4:3  value= 15
					4:3 - box 16:9 top  value= 2
					4:3 - box 14:9 top  value= 3
					4:3 - box>16:9 ctr  value= 4
					4:3 - Unknown  value= 16
					16:9 - Coded Frame  value= 136
					16:9 - 4:3  value= 137
					16:9 - 16:9  value= 138
					16:9 - 14:9  value= 139
					16:9 reserved  value= 140
					16:9 - 4:3 SP 14:9  value= 141
					16:9 - 16:9 SP 14:9  value= 142
					16:9 - 16:9 SP 4:3  value= 143
					16:9 - box 16:9 top  value= 130
					16:9 - box 14:9 top  value= 131
					16:9 - box>16:9 ctr  value= 132
					16:9 - Unknown  value= 144  "
		::= { iqudc00CmdEntry 38740 }


	iqudc00WSSCtrlForceInputMode OBJECT-TYPE
		SYNTAX		INTEGER { disable(0), enable(1) }
		MAX-ACCESS		read-write
		STATUS			current
		DESCRIPTION
				"TYPE: - Checkbox
				 PAGE: - WSS Ctrl
					Force Input Mode  cmdID= 38735 "
		::= { iqudc00CmdEntry 38735 }


	iqudc00WSSCtrlOPWSS43 OBJECT-TYPE
		SYNTAX		INTEGER {
							val_4_3_Coded_Frame(8),
							val_4_3_4_3(9),
							val_4_3_16_9(10),
							val_4_3_14_9(11),
							val_4_3_reserved_12(12),
							val_4_3_4_3_SP_14_9(13),
							val_4_3_16_9_SP_14_9(14),
							val_4_3_16_9_SP_4_3(15),
							val_4_3_box_16_9_top(2),
							val_4_3_box_14_9_top(3),
							val_4_3_box_16_9_ctr(4)
							}
		MAX-ACCESS		read-write
		STATUS			current
		DESCRIPTION
				"TYPE: - RadiobuttonList
				 PAGE: - WSS Ctrl
					O/P WSS 4:3  cmdID= 38745
					4:3 - Coded Frame  value= 8
					4:3 - 4:3  value= 9
					4:3 - 16:9  value= 10
					4:3 - 14:9  value= 11
					4:3 - reserved(12)  value= 12
					4:3 - 4:3 SP 14:9  value= 13
					4:3 - 16:9 SP 14:9  value= 14
					4:3 - 16:9 SP 4:3  value= 15
					4:3 - box 16:9 top  value= 2
					4:3 - box 14:9 top  value= 3
					4:3 - box>16:9 ctr  value= 4  "
		::= { iqudc00CmdEntry 38745 }


	iqudc00WSSCtrlDispMem43 OBJECT-TYPE
		SYNTAX		INTEGER {
							val_None(0),
							val_Display_Memory_1(1),
							val_Display_Memory_2(2),
							val_Display_Memory_3(3),
							val_Display_Memory_4(4),
							val_Display_Memory_5(5),
							val_Display_Memory_6(6),
							val_Display_Memory_7(7),
							val_Display_Memory_8(8),
							val_Display_Memory_9(9),
							val_Display_Memory_10(10),
							val_Display_Memory_11(11),
							val_Display_Memory_12(12),
							val_Display_Memory_13(13),
							val_Display_Memory_14(14),
							val_Display_Memory_15(15),
							val_Display_Memory_16(16),
							val_Display_Memory_17(17),
							val_Display_Memory_18(18),
							val_Display_Memory_19(19),
							val_Display_Memory_20(20),
							val_Display_Memory_21(21),
							val_Display_Memory_22(22),
							val_Display_Memory_23(23),
							val_Display_Memory_24(24),
							val_Display_Memory_25(25),
							val_Display_Memory_26(26),
							val_Display_Memory_27(27),
							val_Display_Memory_28(28),
							val_Display_Memory_29(29),
							val_Display_Memory_30(30),
							val_Display_Memory_31(31),
							val_Display_Memory_32(32),
							val_Display_Memory_33(33),
							val_Display_Memory_34(34),
							val_Display_Memory_35(35),
							val_Display_Memory_36(36),
							val_Display_Memory_37(37),
							val_Display_Memory_38(38),
							val_Display_Memory_39(39),
							val_Display_Memory_40(40)
							}
		MAX-ACCESS		read-write
		STATUS			current
		DESCRIPTION
				"TYPE: - RadiobuttonList
				 PAGE: - WSS Ctrl
					Disp Mem 4:3  cmdID= 38748
					None  value= 0
					Display Memory 1  value= 1
					Display Memory 2  value= 2
					Display Memory 3  value= 3
					Display Memory 4  value= 4
					Display Memory 5  value= 5
					Display Memory 6  value= 6
					Display Memory 7  value= 7
					Display Memory 8  value= 8
					Display Memory 9  value= 9
					Display Memory 10  value= 10
					Display Memory 11  value= 11
					Display Memory 12  value= 12
					Display Memory 13  value= 13
					Display Memory 14  value= 14
					Display Memory 15  value= 15
					Display Memory 16  value= 16
					Display Memory 17  value= 17
					Display Memory 18  value= 18
					Display Memory 19  value= 19
					Display Memory 20  value= 20
					Display Memory 21  value= 21
					Display Memory 22  value= 22
					Display Memory 23  value= 23
					Display Memory 24  value= 24
					Display Memory 25  value= 25
					Display Memory 26  value= 26
					Display Memory 27  value= 27
					Display Memory 28  value= 28
					Display Memory 29  value= 29
					Display Memory 30  value= 30
					Display Memory 31  value= 31
					Display Memory 32  value= 32
					Display Memory 33  value= 33
					Display Memory 34  value= 34
					Display Memory 35  value= 35
					Display Memory 36  value= 36
					Display Memory 37  value= 37
					Display Memory 38  value= 38
					Display Memory 39  value= 39
					Display Memory 40  value= 40  "
		::= { iqudc00CmdEntry 38748 }


	iqudc00WSSCtrlOPWSS169 OBJECT-TYPE
		SYNTAX		INTEGER {
							val_16_9_Coded_Frame(8),
							val_16_9_4_3(9),
							val_16_9_16_9(10),
							val_16_9_14_9(11),
							val_16_9_reserved_12(12),
							val_16_9_4_3_SP_14_9(13),
							val_16_9_16_9_SP_14_9(14),
							val_16_9_16_9_SP_4_3(15),
							val_16_9_box_16_9_top(2),
							val_16_9_box_14_9_top(3),
							val_16_9_box_16_9_ctr(4)
							}
		MAX-ACCESS		read-write
		STATUS			current
		DESCRIPTION
				"TYPE: - RadiobuttonList
				 PAGE: - WSS Ctrl
					O/P WSS 16:9  cmdID= 38746
					16:9 - Coded Frame  value= 8
					16:9 - 4:3  value= 9
					16:9 - 16:9  value= 10
					16:9 - 14:9  value= 11
					16:9 - reserved(12)  value= 12
					16:9 - 4:3 SP 14:9  value= 13
					16:9 - 16:9 SP 14:9  value= 14
					16:9 - 16:9 SP 4:3  value= 15
					16:9 - box 16:9 top  value= 2
					16:9 - box 14:9 top  value= 3
					16:9 - box>16:9 ctr  value= 4  "
		::= { iqudc00CmdEntry 38746 }


	iqudc00WSSCtrlDispMem169 OBJECT-TYPE
		SYNTAX		INTEGER {
							val_None(0),
							val_Display_Memory_1(1),
							val_Display_Memory_2(2),
							val_Display_Memory_3(3),
							val_Display_Memory_4(4),
							val_Display_Memory_5(5),
							val_Display_Memory_6(6),
							val_Display_Memory_7(7),
							val_Display_Memory_8(8),
							val_Display_Memory_9(9),
							val_Display_Memory_10(10),
							val_Display_Memory_11(11),
							val_Display_Memory_12(12),
							val_Display_Memory_13(13),
							val_Display_Memory_14(14),
							val_Display_Memory_15(15),
							val_Display_Memory_16(16),
							val_Display_Memory_17(17),
							val_Display_Memory_18(18),
							val_Display_Memory_19(19),
							val_Display_Memory_20(20),
							val_Display_Memory_21(21),
							val_Display_Memory_22(22),
							val_Display_Memory_23(23),
							val_Display_Memory_24(24),
							val_Display_Memory_25(25),
							val_Display_Memory_26(26),
							val_Display_Memory_27(27),
							val_Display_Memory_28(28),
							val_Display_Memory_29(29),
							val_Display_Memory_30(30),
							val_Display_Memory_31(31),
							val_Display_Memory_32(32),
							val_Display_Memory_33(33),
							val_Display_Memory_34(34),
							val_Display_Memory_35(35),
							val_Display_Memory_36(36),
							val_Display_Memory_37(37),
							val_Display_Memory_38(38),
							val_Display_Memory_39(39),
							val_Display_Memory_40(40)
							}
		MAX-ACCESS		read-write
		STATUS			current
		DESCRIPTION
				"TYPE: - RadiobuttonList
				 PAGE: - WSS Ctrl
					Disp Mem /16:9  cmdID= 38749
					None  value= 0
					Display Memory 1  value= 1
					Display Memory 2  value= 2
					Display Memory 3  value= 3
					Display Memory 4  value= 4
					Display Memory 5  value= 5
					Display Memory 6  value= 6
					Display Memory 7  value= 7
					Display Memory 8  value= 8
					Display Memory 9  value= 9
					Display Memory 10  value= 10
					Display Memory 11  value= 11
					Display Memory 12  value= 12
					Display Memory 13  value= 13
					Display Memory 14  value= 14
					Display Memory 15  value= 15
					Display Memory 16  value= 16
					Display Memory 17  value= 17
					Display Memory 18  value= 18
					Display Memory 19  value= 19
					Display Memory 20  value= 20
					Display Memory 21  value= 21
					Display Memory 22  value= 22
					Display Memory 23  value= 23
					Display Memory 24  value= 24
					Display Memory 25  value= 25
					Display Memory 26  value= 26
					Display Memory 27  value= 27
					Display Memory 28  value= 28
					Display Memory 29  value= 29
					Display Memory 30  value= 30
					Display Memory 31  value= 31
					Display Memory 32  value= 32
					Display Memory 33  value= 33
					Display Memory 34  value= 34
					Display Memory 35  value= 35
					Display Memory 36  value= 36
					Display Memory 37  value= 37
					Display Memory 38  value= 38
					Display Memory 39  value= 39
					Display Memory 40  value= 40  "
		::= { iqudc00CmdEntry 38749 }


	iqudc00WSSCtrlWSSVIIPWSSETSI OBJECT-TYPE
		SYNTAX		INTEGER { disable(0), enable(1) }
		MAX-ACCESS		read-write
		STATUS			current
		DESCRIPTION
				"TYPE: - Checkbox
				 PAGE: - WSS Ctrl
					WSS-ETSI  cmdID= 38720 "
		::= { iqudc00CmdEntry 38720 }


	iqudc00WSSCtrlWSSVIIPWSSAFD OBJECT-TYPE
		SYNTAX		INTEGER { disable(0), enable(1) }
		MAX-ACCESS		read-write
		STATUS			current
		DESCRIPTION
				"TYPE: - Checkbox
				 PAGE: - WSS Ctrl
					WSS-AFD  cmdID= 38721 "
		::= { iqudc00CmdEntry 38721 }


	iqudc00WSSCtrlWSSVIIPVISMPTE OBJECT-TYPE
		SYNTAX		INTEGER { disable(0), enable(1) }
		MAX-ACCESS		read-write
		STATUS			current
		DESCRIPTION
				"TYPE: - Checkbox
				 PAGE: - WSS Ctrl
					VI-SMPTE  cmdID= 38722 "
		::= { iqudc00CmdEntry 38722 }


	iqudc00WSSCtrlWSSVIIPVIAFD OBJECT-TYPE
		SYNTAX		INTEGER { disable(0), enable(1) }
		MAX-ACCESS		read-write
		STATUS			current
		DESCRIPTION
				"TYPE: - Checkbox
				 PAGE: - WSS Ctrl
					VI-AFD  cmdID= 38723 "
		::= { iqudc00CmdEntry 38723 }


	iqudc00WSSCtrlWSSVIIPWSSLine OBJECT-TYPE
		SYNTAX		INTEGER
		MAX-ACCESS		read-write
		STATUS			current
		DESCRIPTION
				"TYPE: - Number
				 PAGE: - WSS Ctrl
					WSS Line  cmdID= 38756  min= 7  max= 23  step= 1  format= %0.0f line  div_scale= 1
					Min = 7 line  Max = 23 line  Step = 1 line "
		::= { iqudc00CmdEntry 38756 }


	iqudc00WSSCtrlWSSVIIPWSSVIPriority OBJECT-TYPE
		SYNTAX		INTEGER {
							val_WSS(0),
							val_VI(1)
							}
		MAX-ACCESS		read-write
		STATUS			current
		DESCRIPTION
				"TYPE: - RadiobuttonList
				 PAGE: - WSS Ctrl
					WSS/VI Priority  cmdID= 38750
					WSS  value= 0
					VI  value= 1  "
		::= { iqudc00CmdEntry 38750 }


	iqudc00WSSCtrlWSSVIOPWSSETSI OBJECT-TYPE
		SYNTAX		INTEGER { disable(0), enable(1) }
		MAX-ACCESS		read-write
		STATUS			current
		DESCRIPTION
				"TYPE: - Checkbox
				 PAGE: - WSS Ctrl
					WSS-ETSI  cmdID= 38730 "
		::= { iqudc00CmdEntry 38730 }


	iqudc00WSSCtrlWSSVIOPWSSAFD OBJECT-TYPE
		SYNTAX		INTEGER { disable(0), enable(1) }
		MAX-ACCESS		read-write
		STATUS			current
		DESCRIPTION
				"TYPE: - Checkbox
				 PAGE: - WSS Ctrl
					WSS-AFD  cmdID= 38731 "
		::= { iqudc00CmdEntry 38731 }


	iqudc00WSSCtrlWSSVIOPVISMPTE OBJECT-TYPE
		SYNTAX		INTEGER { disable(0), enable(1) }
		MAX-ACCESS		read-write
		STATUS			current
		DESCRIPTION
				"TYPE: - Checkbox
				 PAGE: - WSS Ctrl
					VI-SMPTE  cmdID= 38732 "
		::= { iqudc00CmdEntry 38732 }


	iqudc00WSSCtrlWSSVIOPVIAFD OBJECT-TYPE
		SYNTAX		INTEGER { disable(0), enable(1) }
		MAX-ACCESS		read-write
		STATUS			current
		DESCRIPTION
				"TYPE: - Checkbox
				 PAGE: - WSS Ctrl
					VI-AFD  cmdID= 38733 "
		::= { iqudc00CmdEntry 38733 }


	iqudc00WSSCtrlWSSVIOPWSSLine OBJECT-TYPE
		SYNTAX		INTEGER
		MAX-ACCESS		read-write
		STATUS			current
		DESCRIPTION
				"TYPE: - Number
				 PAGE: - WSS Ctrl
					WSS Line  cmdID= 38757  min= 7  max= 23  step= 1  format= %0.0f line  div_scale= 1
					Min = 7 line  Max = 23 line  Step = 1 line "
		::= { iqudc00CmdEntry 38757 }


	iqudc00WSSCtrlWSSVIOPIPLine OBJECT-TYPE
		SYNTAX		INTEGER { disable(0), enable(1) }
		MAX-ACCESS		read-write
		STATUS			current
		DESCRIPTION
				"TYPE: - Checkbox
				 PAGE: - WSS Ctrl
					= I/P Line  cmdID= 38755 "
		::= { iqudc00CmdEntry 38755 }


	iqudc00WSSCtrlAutoModify OBJECT-TYPE
		SYNTAX		INTEGER { disable(0), enable(1) }
		MAX-ACCESS		read-write
		STATUS			current
		DESCRIPTION
				"TYPE: - Checkbox
				 PAGE: - WSS Ctrl
					Auto Modify  cmdID= 38747 "
		::= { iqudc00CmdEntry 38747 }


	iqudc00GenlockDelayMode OBJECT-TYPE
		SYNTAX		INTEGER {
							val_Lock_to_Reference(1),
							val_Lock_to_Ref_Mis_I(2),
							val_Manual_H_V(5),
							val_Manual_ms(6)
							}
		MAX-ACCESS		read-write
		STATUS			current
		DESCRIPTION
				"TYPE: - RadiobuttonList
				 PAGE: - Genlock
					Delay Mode  cmdID= 33026
					Lock to Reference  value= 1
					Lock to Ref.(Mis=I/  value= 2
					Manual H/V  value= 5
					Manual ms  value= 6  "
		::= { iqudc00CmdEntry 33026 }


	iqudc00GenlockSetDelayVerticalTiming OBJECT-TYPE
		SYNTAX		INTEGER
		MAX-ACCESS		read-write
		STATUS			current
		DESCRIPTION
				"TYPE: - Number
				 PAGE: - Genlock
					Vertical Timing  cmdID= 33022  min= 0  max= 1124  step= 1  format= %0.0f lines  div_scale= 1
					Min = 0 lines  Max = 1124 lines  Step = 1 lines "
		::= { iqudc00CmdEntry 33022 }


	iqudc00GenlockSetDelayHorizontalTiming OBJECT-TYPE
		SYNTAX		INTEGER
		MAX-ACCESS		read-write
		STATUS			current
		DESCRIPTION
				"TYPE: - Number
				 PAGE: - Genlock
					Horizontal Timing  cmdID= 33021  min= 0  max= 3000  step= 1  format= %0.0f pixels  div_scale= 1
					Min = 0 pixels  Max = 3000 pixels  Step = 1 pixels "
		::= { iqudc00CmdEntry 33021 }


	iqudc00GenlockSetDelayDelayms OBJECT-TYPE
		SYNTAX		INTEGER
		MAX-ACCESS		read-write
		STATUS			current
		DESCRIPTION
				"TYPE: - Number
				 PAGE: - Genlock
					Delay ms  cmdID= 33027  min= 0  max= 4000  step= 5  format= %0.2f ms  div_scale= 100
					Min = 0.00 ms  Max = 40.00 ms  Step = 0.05 ms "
		::= { iqudc00CmdEntry 33027 }


	iqudc00GenlockInternalDelay OBJECT-TYPE
		SYNTAX		RollCallString
		MAX-ACCESS		read-only
		STATUS			current
		DESCRIPTION
				"TYPE: - Display
				 PAGE: - Genlock
					Internal Delay  cmdID= 33025  format=   "
		::= { iqudc00CmdEntry 33025 }


	iqudc00GenlockSyncAmplitude OBJECT-TYPE
		SYNTAX		RollCallString
		MAX-ACCESS		read-only
		STATUS			current
		DESCRIPTION
				"TYPE: - Display
				 PAGE: - Genlock
					Sync Amplitude  cmdID= 33023  format=   "
		::= { iqudc00CmdEntry 33023 }


	iqudc00GenlockScalerMinDelay OBJECT-TYPE
		SYNTAX		INTEGER { disable(0), enable(1) }
		MAX-ACCESS		read-write
		STATUS			current
		DESCRIPTION
				"TYPE: - Checkbox
				 PAGE: - Genlock
					Scaler Min Delay  cmdID= 6050 "
		::= { iqudc00CmdEntry 6050 }


	iqudc00AudioDelayADelaySourcesManual OBJECT-TYPE
		SYNTAX		INTEGER { disable(0), enable(1) }
		MAX-ACCESS		read-write
		STATUS			current
		DESCRIPTION
				"TYPE: - Checkbox
				 PAGE: - Audio- Aud.Delays
					Manual  cmdID= 38041 "
		::= { iqudc00CmdEntry 38041 }


	iqudc00AudioDelayADelaySourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38042 "
		::= { iqudc00CmdEntry 38042 }


	iqudc00AudioDelayADelaySourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38044 "
		::= { iqudc00CmdEntry 38044 }


	iqudc00AudioDelayADelaySourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38045 "
		::= { iqudc00CmdEntry 38045 }


	iqudc00AudioDelayADelaySourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38046 "
		::= { iqudc00CmdEntry 38046 }


	iqudc00AudioDelayADelaySourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38047 "
		::= { iqudc00CmdEntry 38047 }


	iqudc00AudDelaysAudioDelayAAdjustManualDelay OBJECT-TYPE
		SYNTAX		INTEGER
		MAX-ACCESS		read-write
		STATUS			current
		DESCRIPTION
				"TYPE: - Number
				 PAGE: - Audio- Aud.Delays
					Adjust Manual Delay  cmdID= 38043  min= -4000  max= 200000  step= 25  format= %0.2f ms  div_scale= 100
					Min = -40.00 ms  Max = 2000.00 ms  Step = 0.25 ms "
		::= { iqudc00CmdEntry 38043 }


	iqudc00AudDelaysAudioDelayACurrentAudioDelay OBJECT-TYPE
		SYNTAX		RollCallString
		MAX-ACCESS		read-only
		STATUS			current
		DESCRIPTION
				"TYPE: - Display
				 PAGE: - Audio- Aud.Delays
					Current Audio Delay  cmdID= 38048  format=   "
		::= { iqudc00CmdEntry 38048 }


	iqudc00AudioDelayBDelaySourcesManual OBJECT-TYPE
		SYNTAX		INTEGER { disable(0), enable(1) }
		MAX-ACCESS		read-write
		STATUS			current
		DESCRIPTION
				"TYPE: - Checkbox
				 PAGE: - Audio- Aud.Delays
					Manual  cmdID= 38061 "
		::= { iqudc00CmdEntry 38061 }


	iqudc00AudioDelayBDelaySourcesGPIPWM OBJECT-TYPE
		SYNTAX		INTEGER { disable(0), enable(1) }
		MAX-ACCESS		read-write
		STATUS			current
		DESCRIPTION
				"TYPE: - Checkbox
				 PAGE: - Audio- Aud.Delays
					GPI PWM  cmdID= 38062 "
		::= { iqudc00CmdEntry 38062 }


	iqudc00AudioDelayBDelaySourcesRollTrack14 OBJECT-TYPE
		SYNTAX		INTEGER { disable(0), enable(1) }
		MAX-ACCESS		read-write
		STATUS			current
		DESCRIPTION
				"TYPE: - Checkbox
				 PAGE: - Audio- Aud.Delays
					RollTrack14  cmdID= 38064 "
		::= { iqudc00CmdEntry 38064 }


	iqudc00AudioDelayBDelaySourcesRollTrack15 OBJECT-TYPE
		SYNTAX		INTEGER { disable(0), enable(1) }
		MAX-ACCESS		read-write
		STATUS			current
		DESCRIPTION
				"TYPE: - Checkbox
				 PAGE: - Audio- Aud.Delays
					RollTrack15  cmdID= 38065 "
		::= { iqudc00CmdEntry 38065 }


	iqudc00AudioDelayBDelaySourcesRollTrack16 OBJECT-TYPE
		SYNTAX		INTEGER { disable(0), enable(1) }
		MAX-ACCESS		read-write
		STATUS			current
		DESCRIPTION
				"TYPE: - Checkbox
				 PAGE: - Audio- Aud.Delays
					RollTrack16  cmdID= 38066 "
		::= { iqudc00CmdEntry 38066 }


	iqudc00AudioDelayBDelaySourcesRollTrack17 OBJECT-TYPE
		SYNTAX		INTEGER { disable(0), enable(1) }
		MAX-ACCESS		read-write
		STATUS			current
		DESCRIPTION
				"TYPE: - Checkbox
				 PAGE: - Audio- Aud.Delays
					RollTrack17  cmdID= 38067 "
		::= { iqudc00CmdEntry 38067 }


	iqudc00AudDelaysAudioDelayBAdjustManualDelay OBJECT-TYPE
		SYNTAX		INTEGER
		MAX-ACCESS		read-write
		STATUS			current
		DESCRIPTION
				"TYPE: - Number
				 PAGE: - Audio- Aud.Delays
					Adjust Manual Delay  cmdID= 38063  min= -4000  max= 200000  step= 25  format= %0.2f ms  div_scale= 100
					Min = -40.00 ms  Max = 2000.00 ms  Step = 0.25 ms "
		::= { iqudc00CmdEntry 38063 }


	iqudc00AudDelaysAudioDelayBCurrentAudioDelay OBJECT-TYPE
		SYNTAX		RollCallString
		MAX-ACCESS		read-only
		STATUS			current
		DESCRIPTION
				"TYPE: - Display
				 PAGE: - Audio- Aud.Delays
					Current Audio Delay  cmdID= 38068  format=   "
		::= { iqudc00CmdEntry 38068 }


	iqudc00AudDelaysDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-1  cmdID= 38080
					Min  value= 0
					Delay A  value= 1
					Delay B  value= 2  "
		::= { iqudc00CmdEntry 38080 }


	iqudc00AudDelaysDelaySelectInternal1 OBJECT-TYPE
		SYNTAX		INTEGER { disable(0), enable(1) }
		MAX-ACCESS		read-write
		STATUS			current
		DESCRIPTION
				"TYPE: - Checkbox
				 PAGE: - Audio- Aud.Delays
					Internal-1  cmdID= 38100 "
		::= { iqudc00CmdEntry 38100 }


	iqudc00AudDelaysDelaySelectDelay1Limit OBJECT-TYPE
		SYNTAX		RollCallString
		MAX-ACCESS		read-only
		STATUS			current
		DESCRIPTION
				"TYPE: - Display
				 PAGE: - Audio- Aud.Delays
					Delay Limit  cmdID= 38308  format=   "
		::= { iqudc00CmdEntry 38308 }


	iqudc00AudDelaysDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-2  cmdID= 38081
					Min  value= 0
					Delay A  value= 1
					Delay B  value= 2  "
		::= { iqudc00CmdEntry 38081 }


	iqudc00AudDelaysDelaySelectInternal2 OBJECT-TYPE
		SYNTAX		INTEGER { disable(0), enable(1) }
		MAX-ACCESS		read-write
		STATUS			current
		DESCRIPTION
				"TYPE: - Checkbox
				 PAGE: - Audio- Aud.Delays
					Internal-2  cmdID= 38101 "
		::= { iqudc00CmdEntry 38101 }


	iqudc00AudDelaysDelaySelectDelay2Limit OBJECT-TYPE
		SYNTAX		RollCallString
		MAX-ACCESS		read-only
		STATUS			current
		DESCRIPTION
				"TYPE: - Display
				 PAGE: - Audio- Aud.Delays
					Delay Limit  cmdID= 38309  format=   "
		::= { iqudc00CmdEntry 38309 }


	iqudc00AudDelaysDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-3  cmdID= 38082
					Min  value= 0
					Delay A  value= 1
					Delay B  value= 2  "
		::= { iqudc00CmdEntry 38082 }


	iqudc00AudDelaysDelaySelectInternal3 OBJECT-TYPE
		SYNTAX		INTEGER { disable(0), enable(1) }
		MAX-ACCESS		read-write
		STATUS			current
		DESCRIPTION
				"TYPE: - Checkbox
				 PAGE: - Audio- Aud.Delays
					Internal-3  cmdID= 38102 "
		::= { iqudc00CmdEntry 38102 }


	iqudc00AudDelaysDelaySelectDelay3Limit OBJECT-TYPE
		SYNTAX		RollCallString
		MAX-ACCESS		read-only
		STATUS			current
		DESCRIPTION
				"TYPE: - Display
				 PAGE: - Audio- Aud.Delays
					Delay Limit  cmdID= 38310  format=   "
		::= { iqudc00CmdEntry 38310 }


	iqudc00AudDelaysDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-4  cmdID= 38083
					Min  value= 0
					Delay A  value= 1
					Delay B  value= 2  "
		::= { iqudc00CmdEntry 38083 }


	iqudc00AudDelaysDelaySelectInternal4 OBJECT-TYPE
		SYNTAX		INTEGER { disable(0), enable(1) }
		MAX-ACCESS		read-write
		STATUS			current
		DESCRIPTION
				"TYPE: - Checkbox
				 PAGE: - Audio- Aud.Delays
					Internal-4  cmdID= 38103 "
		::= { iqudc00CmdEntry 38103 }


	iqudc00AudDelaysDelaySelectDelay4Limit OBJECT-TYPE
		SYNTAX		RollCallString
		MAX-ACCESS		read-only
		STATUS			current
		DESCRIPTION
				"TYPE: - Display
				 PAGE: - Audio- Aud.Delays
					Delay Limit  cmdID= 38311  format=   "
		::= { iqudc00CmdEntry 38311 }


	iqudc00AudDelaysDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-5  cmdID= 38084
					Min  value= 0
					Delay A  value= 1
					Delay B  value= 2  "
		::= { iqudc00CmdEntry 38084 }


	iqudc00AudDelaysDelaySelectInternal5 OBJECT-TYPE
		SYNTAX		INTEGER { disable(0), enable(1) }
		MAX-ACCESS		read-write
		STATUS			current
		DESCRIPTION
				"TYPE: - Checkbox
				 PAGE: - Audio- Aud.Delays
					Internal-5  cmdID= 38104 "
		::= { iqudc00CmdEntry 38104 }


	iqudc00AudDelaysDelaySelectDelay5Limit OBJECT-TYPE
		SYNTAX		RollCallString
		MAX-ACCESS		read-only
		STATUS			current
		DESCRIPTION
				"TYPE: - Display
				 PAGE: - Audio- Aud.Delays
					Delay Limit  cmdID= 38312  format=   "
		::= { iqudc00CmdEntry 38312 }


	iqudc00AudDelaysDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-6  cmdID= 38085
					Min  value= 0
					Delay A  value= 1
					Delay B  value= 2  "
		::= { iqudc00CmdEntry 38085 }


	iqudc00AudDelaysDelaySelectInternal6 OBJECT-TYPE
		SYNTAX		INTEGER { disable(0), enable(1) }
		MAX-ACCESS		read-write
		STATUS			current
		DESCRIPTION
				"TYPE: - Checkbox
				 PAGE: - Audio- Aud.Delays
					Internal-6  cmdID= 38105 "
		::= { iqudc00CmdEntry 38105 }


	iqudc00AudDelaysDelaySelectDelay6Limit OBJECT-TYPE
		SYNTAX		RollCallString
		MAX-ACCESS		read-only
		STATUS			current
		DESCRIPTION
				"TYPE: - Display
				 PAGE: - Audio- Aud.Delays
					Delay Limit  cmdID= 38313  format=   "
		::= { iqudc00CmdEntry 38313 }


	iqudc00AudDelaysDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-7  cmdID= 38086
					Min  value= 0
					Delay A  value= 1
					Delay B  value= 2  "
		::= { iqudc00CmdEntry 38086 }


	iqudc00AudDelaysDelaySelectInternal7 OBJECT-TYPE
		SYNTAX		INTEGER { disable(0), enable(1) }
		MAX-ACCESS		read-write
		STATUS			current
		DESCRIPTION
				"TYPE: - Checkbox
				 PAGE: - Audio- Aud.Delays
					Internal-7  cmdID= 38106 "
		::= { iqudc00CmdEntry 38106 }


	iqudc00AudDelaysDelaySelectDelay7Limit OBJECT-TYPE
		SYNTAX		RollCallString
		MAX-ACCESS		read-only
		STATUS			current
		DESCRIPTION
				"TYPE: - Display
				 PAGE: - Audio- Aud.Delays
					Delay Limit  cmdID= 38314  format=   "
		::= { iqudc00CmdEntry 38314 }


	iqudc00AudDelaysDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Audio- Aud.Delays
					Delay-8  cmdID= 38087
					Min  value= 0
					Delay A  value= 1
					Delay B  value= 2  "
		::= { iqudc00CmdEntry 38087 }


	iqudc00AudDelaysDelaySelectInternal8 OBJECT-TYPE
		SYNTAX		INTEGER { disable(0), enable(1) }
		MAX-ACCESS		read-write
		STATUS			current
		DESCRIPTION
				"TYPE: - Checkbox
				 PAGE: - Audio- Aud.Delays
					Internal-8  cmdID= 38107 "
		::= { iqudc00CmdEntry 38107 }


	iqudc00AudDelaysDelaySelectDelay8Limit OBJECT-TYPE
		SYNTAX		RollCallString
		MAX-ACCESS		read-only
		STATUS			current
		DESCRIPTION
				"TYPE: - Display
				 PAGE: - Audio- Aud.Delays
					Delay Limit  cmdID= 38315  format=   "
		::= { iqudc00CmdEntry 38315 }


	iqudc00AudioAudDelaysRollTrack14 OBJECT-TYPE
		SYNTAX		RollCallString
		MAX-ACCESS		read-only
		STATUS			current
		DESCRIPTION
				"TYPE: - Display
				 PAGE: - Audio- Aud.Delays
					RollTrack14  cmdID= 14  format=   "
		::= { iqudc00CmdEntry 14 }


	iqudc00AudioAudDelaysRollTrack15 OBJECT-TYPE
		SYNTAX		RollCallString
		MAX-ACCESS		read-only
		STATUS			current
		DESCRIPTION
				"TYPE: - Display
				 PAGE: - Audio- Aud.Delays
					RollTrack15  cmdID= 15  format=   "
		::= { iqudc00CmdEntry 15 }


	iqudc00AudioAudDelaysRollTrack16 OBJECT-TYPE
		SYNTAX		RollCallString
		MAX-ACCESS		read-only
		STATUS			current
		DESCRIPTION
				"TYPE: - Display
				 PAGE: - Audio- Aud.Delays
					RollTrack16  cmdID= 16  format=   "
		::= { iqudc00CmdEntry 16 }


	iqudc00AudioAudDelaysRollTrack17 OBJECT-TYPE
		SYNTAX		RollCallString
		MAX-ACCESS		read-only
		STATUS			current
		DESCRIPTION
				"TYPE: - Display
				 PAGE: - Audio- Aud.Delays
					RollTrack17  cmdID= 17  format=   "
		::= { iqudc00CmdEntry 17 }


	iqudc00AudioEmbCtrlAudio OBJECT-TYPE
		SYNTAX		INTEGER {
							val_Off(0),
							val_Embed(1)
							}
		MAX-ACCESS		read-write
		STATUS			current
		DESCRIPTION
				"TYPE: - RadiobuttonList
				 PAGE: - Audio
					Audio  cmdID= 37430
					Off  value= 0
					Embed  value= 1  "
		::= { iqudc00CmdEntry 37430 }


	iqudc00EmbCtrlGroupGroup1Active OBJECT-TYPE
		SYNTAX		INTEGER { disable(0), enable(1) }
		MAX-ACCESS		read-write
		STATUS			current
		DESCRIPTION
				"TYPE: - Checkbox
				 PAGE: - Audio
					Group 1 Active  cmdID= 37450 "
		::= { iqudc00CmdEntry 37450 }


	iqudc00EmbCtrlGroupGroup2Active OBJECT-TYPE
		SYNTAX		INTEGER { disable(0), enable(1) }
		MAX-ACCESS		read-write
		STATUS			current
		DESCRIPTION
				"TYPE: - Checkbox
				 PAGE: - Audio
					Group 2 Active  cmdID= 37451 "
		::= { iqudc00CmdEntry 37451 }


	iqudc00EmbCtrlGroupGroup3Active OBJECT-TYPE
		SYNTAX		INTEGER { disable(0), enable(1) }
		MAX-ACCESS		read-write
		STATUS			current
		DESCRIPTION
				"TYPE: - Checkbox
				 PAGE: - Audio
					Group 3 Active  cmdID= 37452 "
		::= { iqudc00CmdEntry 37452 }


	iqudc00EmbCtrlGroupGroup4Active OBJECT-TYPE
		SYNTAX		INTEGER { disable(0), enable(1) }
		MAX-ACCESS		read-write
		STATUS			current
		DESCRIPTION
				"TYPE: - Checkbox
				 PAGE: - Audio
					Group 4 Active  cmdID= 37453 "
		::= { iqudc00CmdEntry 37453 }


	iqudc00EmbCtrlChannelPair1LActive OBJECT-TYPE
		SYNTAX		INTEGER { disable(0), enable(1) }
		MAX-ACCESS		read-write
		STATUS			current
		DESCRIPTION
				"TYPE: - Checkbox
				 PAGE: - Audio
					Pair 1-L Active  cmdID= 37431 "
		::= { iqudc00CmdEntry 37431 }


	iqudc00EmbCtrlChannelPair1RActive OBJECT-TYPE
		SYNTAX		INTEGER { disable(0), enable(1) }
		MAX-ACCESS		read-write
		STATUS			current
		DESCRIPTION
				"TYPE: - Checkbox
				 PAGE: - Audio
					Pair 1-R Active  cmdID= 37432 "
		::= { iqudc00CmdEntry 37432 }


	iqudc00EmbCtrlChannelPair2LActive OBJECT-TYPE
		SYNTAX		INTEGER { disable(0), enable(1) }
		MAX-ACCESS		read-write
		STATUS			current
		DESCRIPTION
				"TYPE: - Checkbox
				 PAGE: - Audio
					Pair 2-L Active  cmdID= 37433 "
		::= { iqudc00CmdEntry 37433 }


	iqudc00EmbCtrlChannelPair2RActive OBJECT-TYPE
		SYNTAX		INTEGER { disable(0), enable(1) }
		MAX-ACCESS		read-write
		STATUS			current
		DESCRIPTION
				"TYPE: - Checkbox
				 PAGE: - Audio
					Pair 2-R Active  cmdID= 37434 "
		::= { iqudc00CmdEntry 37434 }


	iqudc00EmbCtrlChannelPair3LActive OBJECT-TYPE
		SYNTAX		INTEGER { disable(0), enable(1) }
		MAX-ACCESS		read-write
		STATUS			current
		DESCRIPTION
				"TYPE: - Checkbox
				 PAGE: - Audio
					Pair 3-L Active  cmdID= 37435 "
		::= { iqudc00CmdEntry 37435 }


	iqudc00EmbCtrlChannelPair3RActive OBJECT-TYPE
		SYNTAX		INTEGER { disable(0), enable(1) }
		MAX-ACCESS		read-write
		STATUS			current
		DESCRIPTION
				"TYPE: - Checkbox
				 PAGE: - Audio
					Pair 3-R Active  cmdID= 37436 "
		::= { iqudc00CmdEntry 37436 }


	iqudc00EmbCtrlChannelPair4LActive OBJECT-TYPE
		SYNTAX		INTEGER { disable(0), enable(1) }
		MAX-ACCESS		read-write
		STATUS			current
		DESCRIPTION
				"TYPE: - Checkbox
				 PAGE: - Audio
					Pair 4-L Active  cmdID= 37437 "
		::= { iqudc00CmdEntry 37437 }


	iqudc00EmbCtrlChannelPair4RActive OBJECT-TYPE
		SYNTAX		INTEGER { disable(0), enable(1) }
		MAX-ACCESS		read-write
		STATUS			current
		DESCRIPTION
				"TYPE: - Checkbox
				 PAGE: - Audio
					Pair 4-R Active  cmdID= 37438 "
		::= { iqudc00CmdEntry 37438 }


	iqudc00EmbCtrlChannelPair5LActive OBJECT-TYPE
		SYNTAX		INTEGER { disable(0), enable(1) }
		MAX-ACCESS		read-write
		STATUS			current
		DESCRIPTION
				"TYPE: - Checkbox
				 PAGE: - Audio
					Pair 5-L Active  cmdID= 37439 "
		::= { iqudc00CmdEntry 37439 }


	iqudc00EmbCtrlChannelPair5RActive OBJECT-TYPE
		SYNTAX		INTEGER { disable(0), enable(1) }
		MAX-ACCESS		read-write
		STATUS			current
		DESCRIPTION
				"TYPE: - Checkbox
				 PAGE: - Audio
					Pair 5-R Active  cmdID= 37440 "
		::= { iqudc00CmdEntry 37440 }


	iqudc00EmbCtrlChannelPair6LActive OBJECT-TYPE
		SYNTAX		INTEGER { disable(0), enable(1) }
		MAX-ACCESS		read-write
		STATUS			current
		DESCRIPTION
				"TYPE: - Checkbox
				 PAGE: - Audio
					Pair 6-L Active  cmdID= 37441 "
		::= { iqudc00CmdEntry 37441 }


	iqudc00EmbCtrlChannelPair6RActive OBJECT-TYPE
		SYNTAX		INTEGER { disable(0), enable(1) }
		MAX-ACCESS		read-write
		STATUS			current
		DESCRIPTION
				"TYPE: - Checkbox
				 PAGE: - Audio
					Pair 6-R Active  cmdID= 37442 "
		::= { iqudc00CmdEntry 37442 }


	iqudc00EmbCtrlChannelPair7LActive OBJECT-TYPE
		SYNTAX		INTEGER { disable(0), enable(1) }
		MAX-ACCESS		read-write
		STATUS			current
		DESCRIPTION
				"TYPE: - Checkbox
				 PAGE: - Audio
					Pair 7-L Active  cmdID= 37443 "
		::= { iqudc00CmdEntry 37443 }


	iqudc00EmbCtrlChannelPair7RActive OBJECT-TYPE
		SYNTAX		INTEGER { disable(0), enable(1) }
		MAX-ACCESS		read-write
		STATUS			current
		DESCRIPTION
				"TYPE: - Checkbox
				 PAGE: - Audio
					Pair 7-R Active  cmdID= 37444 "
		::= { iqudc00CmdEntry 37444 }


	iqudc00EmbCtrlChannelPair8LActive OBJECT-TYPE
		SYNTAX		INTEGER { disable(0), enable(1) }
		MAX-ACCESS		read-write
		STATUS			current
		DESCRIPTION
				"TYPE: - Checkbox
				 PAGE: - Audio
					Pair 8-L Active  cmdID= 37445 "
		::= { iqudc00CmdEntry 37445 }


	iqudc00EmbCtrlChannelPair8RActive OBJECT-TYPE
		SYNTAX		INTEGER { disable(0), enable(1) }
		MAX-ACCESS		read-write
		STATUS			current
		DESCRIPTION
				"TYPE: - Checkbox
				 PAGE: - Audio
					Pair 8-R Active  cmdID= 37446 "
		::= { iqudc00CmdEntry 37446 }


	iqudc00EmbGainEmbedPair1Embed1MuteL OBJECT-TYPE
		SYNTAX		INTEGER { disable(0), enable(1) }
		MAX-ACCESS		read-write
		STATUS			current
		DESCRIPTION
				"TYPE: - Checkbox
				 PAGE: - Audio
					Embed 1 Mute L  cmdID= 37340 "
		::= { iqudc00CmdEntry 37340 }


	iqudc00EmbGainEmbedPair1Embed1MuteR OBJECT-TYPE
		SYNTAX		INTEGER { disable(0), enable(1) }
		MAX-ACCESS		read-write
		STATUS			current
		DESCRIPTION
				"TYPE: - Checkbox
				 PAGE: - Audio
					Embed 1 Mute R  cmdID= 37341 "
		::= { iqudc00CmdEntry 37341 }


	iqudc00EmbGainEmbedPair1Embed1LGain OBJECT-TYPE
		SYNTAX		INTEGER
		MAX-ACCESS		read-write
		STATUS			current
		DESCRIPTION
				"TYPE: - Number
				 PAGE: - Audio
					Embed 1 L Gain  cmdID= 37320  min= -360  max= 120  step= 1  format= %0.1f dB  div_scale= 10
					Min = -36.0 dB  Max = 12.0 dB  Step = 0.1 dB "
		::= { iqudc00CmdEntry 37320 }


	iqudc00EmbGainEmbedPair1Embed1RGain OBJECT-TYPE
		SYNTAX		INTEGER
		MAX-ACCESS		read-write
		STATUS			current
		DESCRIPTION
				"TYPE: - Number
				 PAGE: - Audio
					Embed 1 R Gain  cmdID= 37321  min= -360  max= 120  step= 1  format= %0.1f dB  div_scale= 10
					Min = -36.0 dB  Max = 12.0 dB  Step = 0.1 dB "
		::= { iqudc00CmdEntry 37321 }


	iqudc00EmbGainEmbedPair1Stereo OBJECT-TYPE
		SYNTAX		INTEGER { disable(0), enable(1) }
		MAX-ACCESS		read-write
		STATUS			current
		DESCRIPTION
				"TYPE: - Checkbox
				 PAGE: - Audio
					Stereo  cmdID= 37380 "
		::= { iqudc00CmdEntry 37380 }


	iqudc00EmbGainEmbedPair1Embed1InvertL OBJECT-TYPE
		SYNTAX		INTEGER { disable(0), enable(1) }
		MAX-ACCESS		read-write
		STATUS			current
		DESCRIPTION
				"TYPE: - Checkbox
				 PAGE: - Audio
					Embed 1 Invert L  cmdID= 37360 "
		::= { iqudc00CmdEntry 37360 }


	iqudc00EmbGainEmbedPair1Embed1InvertR OBJECT-TYPE
		SYNTAX		INTEGER { disable(0), enable(1) }
		MAX-ACCESS		read-write
		STATUS			current
		DESCRIPTION
				"TYPE: - Checkbox
				 PAGE: - Audio
					Embed 1 Invert R  cmdID= 37361 "
		::= { iqudc00CmdEntry 37361 }


	iqudc00EmbGainEmbedPair1Embed1LClip OBJECT-TYPE
		SYNTAX		RollCallString
		MAX-ACCESS		read-only
		STATUS			current
		DESCRIPTION
				"TYPE: - Display
				 PAGE: - Audio
					Embed 1-L Clip  cmdID= 37540  format=   "
		::= { iqudc00CmdEntry 37540 }


	iqudc00EmbGainEmbedPair1Embed1RClip OBJECT-TYPE
		SYNTAX		RollCallString
		MAX-ACCESS		read-only
		STATUS			current
		DESCRIPTION
				"TYPE: - Display
				 PAGE: - Audio
					Embed 1-R Clip  cmdID= 37541  format=   "
		::= { iqudc00CmdEntry 37541 }


	iqudc00EmbGainEmbedPair2Embed2MuteL OBJECT-TYPE
		SYNTAX		INTEGER { disable(0), enable(1) }
		MAX-ACCESS		read-write
		STATUS			current
		DESCRIPTION
				"TYPE: - Checkbox
				 PAGE: - Audio
					Embed 2 Mute L  cmdID= 37342 "
		::= { iqudc00CmdEntry 37342 }


	iqudc00EmbGainEmbedPair2Embed2MuteR OBJECT-TYPE
		SYNTAX		INTEGER { disable(0), enable(1) }
		MAX-ACCESS		read-write
		STATUS			current
		DESCRIPTION
				"TYPE: - Checkbox
				 PAGE: - Audio
					Embed 2 Mute R  cmdID= 37343 "
		::= { iqudc00CmdEntry 37343 }


	iqudc00EmbGainEmbedPair2Embed2LGain OBJECT-TYPE
		SYNTAX		INTEGER
		MAX-ACCESS		read-write
		STATUS			current
		DESCRIPTION
				"TYPE: - Number
				 PAGE: - Audio
					Embed 2 L Gain  cmdID= 37322  min= -360  max= 120  step= 1  format= %0.1f dB  div_scale= 10
					Min = -36.0 dB  Max = 12.0 dB  Step = 0.1 dB "
		::= { iqudc00CmdEntry 37322 }


	iqudc00EmbGainEmbedPair2Embed2RGain OBJECT-TYPE
		SYNTAX		INTEGER
		MAX-ACCESS		read-write
		STATUS			current
		DESCRIPTION
				"TYPE: - Number
				 PAGE: - Audio
					Embed 2 R Gain  cmdID= 37323  min= -360  max= 120  step= 1  format= %0.1f dB  div_scale= 10
					Min = -36.0 dB  Max = 12.0 dB  Step = 0.1 dB "
		::= { iqudc00CmdEntry 37323 }


	iqudc00EmbGainEmbedPair2Stereo OBJECT-TYPE
		SYNTAX		INTEGER { disable(0), enable(1) }
		MAX-ACCESS		read-write
		STATUS			current
		DESCRIPTION
				"TYPE: - Checkbox
				 PAGE: - Audio
					Stereo  cmdID= 37381 "
		::= { iqudc00CmdEntry 37381 }


	iqudc00EmbGainEmbedPair2Embed2InvertL OBJECT-TYPE
		SYNTAX		INTEGER { disable(0), enable(1) }
		MAX-ACCESS		read-write
		STATUS			current
		DESCRIPTION
				"TYPE: - Checkbox
				 PAGE: - Audio
					Embed 2 Invert L  cmdID= 37362 "
		::= { iqudc00CmdEntry 37362 }


	iqudc00EmbGainEmbedPair2Embed2InvertR OBJECT-TYPE
		SYNTAX		INTEGER { disable(0), enable(1) }
		MAX-ACCESS		read-write
		STATUS			current
		DESCRIPTION
				"TYPE: - Checkbox
				 PAGE: - Audio
					Embed 2 Invert R  cmdID= 37363 "
		::= { iqudc00CmdEntry 37363 }


	iqudc00EmbGainEmbedPair2Embed2LClip OBJECT-TYPE
		SYNTAX		RollCallString
		MAX-ACCESS		read-only
		STATUS			current
		DESCRIPTION
				"TYPE: - Display
				 PAGE: - Audio
					Embed 2-L Clip  cmdID= 37542  format=   "
		::= { iqudc00CmdEntry 37542 }


	iqudc00EmbGainEmbedPair2Embed2RClip OBJECT-TYPE
		SYNTAX		RollCallString
		MAX-ACCESS		read-only
		STATUS			current
		DESCRIPTION
				"TYPE: - Display
				 PAGE: - Audio
					Embed 2-R Clip  cmdID= 37543  format=   "
		::= { iqudc00CmdEntry 37543 }


	iqudc00EmbGainEmbedPair3Embed3MuteL OBJECT-TYPE
		SYNTAX		INTEGER { disable(0), enable(1) }
		MAX-ACCESS		read-write
		STATUS			current
		DESCRIPTION
				"TYPE: - Checkbox
				 PAGE: - Audio
					Embed 3 Mute L  cmdID= 37344 "
		::= { iqudc00CmdEntry 37344 }


	iqudc00EmbGainEmbedPair3Embed3MuteR OBJECT-TYPE
		SYNTAX		INTEGER { disable(0), enable(1) }
		MAX-ACCESS		read-write
		STATUS			current
		DESCRIPTION
				"TYPE: - Checkbox
				 PAGE: - Audio
					Embed 3 Mute R  cmdID= 37345 "
		::= { iqudc00CmdEntry 37345 }


	iqudc00EmbGainEmbedPair3Embed3LGain OBJECT-TYPE
		SYNTAX		INTEGER
		MAX-ACCESS		read-write
		STATUS			current
		DESCRIPTION
				"TYPE: - Number
				 PAGE: - Audio
					Embed 3 L Gain  cmdID= 37324  min= -360  max= 120  step= 1  format= %0.1f dB  div_scale= 10
					Min = -36.0 dB  Max = 12.0 dB  Step = 0.1 dB "
		::= { iqudc00CmdEntry 37324 }


	iqudc00EmbGainEmbedPair3Embed3RGain OBJECT-TYPE
		SYNTAX		INTEGER
		MAX-ACCESS		read-write
		STATUS			current
		DESCRIPTION
				"TYPE: - Number
				 PAGE: - Audio
					Embed 3 R Gain  cmdID= 37325  min= -360  max= 120  step= 1  format= %0.1f dB  div_scale= 10
					Min = -36.0 dB  Max = 12.0 dB  Step = 0.1 dB "
		::= { iqudc00CmdEntry 37325 }


	iqudc00EmbGainEmbedPair3Stereo OBJECT-TYPE
		SYNTAX		INTEGER { disable(0), enable(1) }
		MAX-ACCESS		read-write
		STATUS			current
		DESCRIPTION
				"TYPE: - Checkbox
				 PAGE: - Audio
					Stereo  cmdID= 37382 "
		::= { iqudc00CmdEntry 37382 }


	iqudc00EmbGainEmbedPair3Embed3InvertL OBJECT-TYPE
		SYNTAX		INTEGER { disable(0), enable(1) }
		MAX-ACCESS		read-write
		STATUS			current
		DESCRIPTION
				"TYPE: - Checkbox
				 PAGE: - Audio
					Embed 3 Invert L  cmdID= 37364 "
		::= { iqudc00CmdEntry 37364 }


	iqudc00EmbGainEmbedPair3Embed3InvertR OBJECT-TYPE
		SYNTAX		INTEGER { disable(0), enable(1) }
		MAX-ACCESS		read-write
		STATUS			current
		DESCRIPTION
				"TYPE: - Checkbox
				 PAGE: - Audio
					Embed 3 Invert R  cmdID= 37365 "
		::= { iqudc00CmdEntry 37365 }


	iqudc00EmbGainEmbedPair3Embed3LClip OBJECT-TYPE
		SYNTAX		RollCallString
		MAX-ACCESS		read-only
		STATUS			current
		DESCRIPTION
				"TYPE: - Display
				 PAGE: - Audio
					Embed 3-L Clip  cmdID= 37544  format=   "
		::= { iqudc00CmdEntry 37544 }


	iqudc00EmbGainEmbedPair3Embed3RClip OBJECT-TYPE
		SYNTAX		RollCallString
		MAX-ACCESS		read-only
		STATUS			current
		DESCRIPTION
				"TYPE: - Display
				 PAGE: - Audio
					Embed 3-R Clip  cmdID= 37545  format=   "
		::= { iqudc00CmdEntry 37545 }


	iqudc00EmbGainEmbedPair4Embed4MuteL OBJECT-TYPE
		SYNTAX		INTEGER { disable(0), enable(1) }
		MAX-ACCESS		read-write
		STATUS			current
		DESCRIPTION
				"TYPE: - Checkbox
				 PAGE: - Audio
					Embed 4 Mute L  cmdID= 37346 "
		::= { iqudc00CmdEntry 37346 }


	iqudc00EmbGainEmbedPair4Embed4MuteR OBJECT-TYPE
		SYNTAX		INTEGER { disable(0), enable(1) }
		MAX-ACCESS		read-write
		STATUS			current
		DESCRIPTION
				"TYPE: - Checkbox
				 PAGE: - Audio
					Embed 4 Mute R  cmdID= 37347 "
		::= { iqudc00CmdEntry 37347 }


	iqudc00EmbGainEmbedPair4Embed4LGain OBJECT-TYPE
		SYNTAX		INTEGER
		MAX-ACCESS		read-write
		STATUS			current
		DESCRIPTION
				"TYPE: - Number
				 PAGE: - Audio
					Embed 4 L Gain  cmdID= 37326  min= -360  max= 120  step= 1  format= %0.1f dB  div_scale= 10
					Min = -36.0 dB  Max = 12.0 dB  Step = 0.1 dB "
		::= { iqudc00CmdEntry 37326 }


	iqudc00EmbGainEmbedPair4Embed4RGain OBJECT-TYPE
		SYNTAX		INTEGER
		MAX-ACCESS		read-write
		STATUS			current
		DESCRIPTION
				"TYPE: - Number
				 PAGE: - Audio
					Embed 4 R Gain  cmdID= 37327  min= -360  max= 120  step= 1  format= %0.1f dB  div_scale= 10
					Min = -36.0 dB  Max = 12.0 dB  Step = 0.1 dB "
		::= { iqudc00CmdEntry 37327 }


	iqudc00EmbGainEmbedPair4Stereo OBJECT-TYPE
		SYNTAX		INTEGER { disable(0), enable(1) }
		MAX-ACCESS		read-write
		STATUS			current
		DESCRIPTION
				"TYPE: - Checkbox
				 PAGE: - Audio
					Stereo  cmdID= 37383 "
		::= { iqudc00CmdEntry 37383 }


	iqudc00EmbGainEmbedPair4Embed4InvertL OBJECT-TYPE
		SYNTAX		INTEGER { disable(0), enable(1) }
		MAX-ACCESS		read-write
		STATUS			current
		DESCRIPTION
				"TYPE: - Checkbox
				 PAGE: - Audio
					Embed 4 Invert L  cmdID= 37366 "
		::= { iqudc00CmdEntry 37366 }


	iqudc00EmbGainEmbedPair4Embed4InvertR OBJECT-TYPE
		SYNTAX		INTEGER { disable(0), enable(1) }
		MAX-ACCESS		read-write
		STATUS			current
		DESCRIPTION
				"TYPE: - Checkbox
				 PAGE: - Audio
					Embed 4 Invert R  cmdID= 37367 "
		::= { iqudc00CmdEntry 37367 }


	iqudc00EmbGainEmbedPair4Embed4LClip OBJECT-TYPE
		SYNTAX		RollCallString
		MAX-ACCESS		read-only
		STATUS			current
		DESCRIPTION
				"TYPE: - Display
				 PAGE: - Audio
					Embed 4-L Clip  cmdID= 37546  format=   "
		::= { iqudc00CmdEntry 37546 }


	iqudc00EmbGainEmbedPair4Embed4RClip OBJECT-TYPE
		SYNTAX		RollCallString
		MAX-ACCESS		read-only
		STATUS			current
		DESCRIPTION
				"TYPE: - Display
				 PAGE: - Audio
					Embed 4-R Clip  cmdID= 37547  format=   "
		::= { iqudc00CmdEntry 37547 }


	iqudc00EmbGainEmbedPair5Embed5MuteL OBJECT-TYPE
		SYNTAX		INTEGER { disable(0), enable(1) }
		MAX-ACCESS		read-write
		STATUS			current
		DESCRIPTION
				"TYPE: - Checkbox
				 PAGE: - Audio
					Embed 5 Mute L  cmdID= 37348 "
		::= { iqudc00CmdEntry 37348 }


	iqudc00EmbGainEmbedPair5Embed5MuteR OBJECT-TYPE
		SYNTAX		INTEGER { disable(0), enable(1) }
		MAX-ACCESS		read-write
		STATUS			current
		DESCRIPTION
				"TYPE: - Checkbox
				 PAGE: - Audio
					Embed 5 Mute R  cmdID= 37349 "
		::= { iqudc00CmdEntry 37349 }


	iqudc00EmbGainEmbedPair5Embed5LGain OBJECT-TYPE
		SYNTAX		INTEGER
		MAX-ACCESS		read-write
		STATUS			current
		DESCRIPTION
				"TYPE: - Number
				 PAGE: - Audio
					Embed 5 L Gain  cmdID= 37328  min= -360  max= 120  step= 1  format= %0.1f dB  div_scale= 10
					Min = -36.0 dB  Max = 12.0 dB  Step = 0.1 dB "
		::= { iqudc00CmdEntry 37328 }


	iqudc00EmbGainEmbedPair5Embed5RGain OBJECT-TYPE
		SYNTAX		INTEGER
		MAX-ACCESS		read-write
		STATUS			current
		DESCRIPTION
				"TYPE: - Number
				 PAGE: - Audio
					Embed 5 R Gain  cmdID= 37329  min= -360  max= 120  step= 1  format= %0.1f dB  div_scale= 10
					Min = -36.0 dB  Max = 12.0 dB  Step = 0.1 dB "
		::= { iqudc00CmdEntry 37329 }


	iqudc00EmbGainEmbedPair5Stereo OBJECT-TYPE
		SYNTAX		INTEGER { disable(0), enable(1) }
		MAX-ACCESS		read-write
		STATUS			current
		DESCRIPTION
				"TYPE: - Checkbox
				 PAGE: - Audio
					Stereo  cmdID= 37384 "
		::= { iqudc00CmdEntry 37384 }


	iqudc00EmbGainEmbedPair5Embed5InvertL OBJECT-TYPE
		SYNTAX		INTEGER { disable(0), enable(1) }
		MAX-ACCESS		read-write
		STATUS			current
		DESCRIPTION
				"TYPE: - Checkbox
				 PAGE: - Audio
					Embed 5 Invert L  cmdID= 37368 "
		::= { iqudc00CmdEntry 37368 }


	iqudc00EmbGainEmbedPair5Embed5InvertR OBJECT-TYPE
		SYNTAX		INTEGER { disable(0), enable(1) }
		MAX-ACCESS		read-write
		STATUS			current
		DESCRIPTION
				"TYPE: - Checkbox
				 PAGE: - Audio
					Embed 5 Invert R  cmdID= 37369 "
		::= { iqudc00CmdEntry 37369 }


	iqudc00EmbGainEmbedPair5Embed5LClip OBJECT-TYPE
		SYNTAX		RollCallString
		MAX-ACCESS		read-only
		STATUS			current
		DESCRIPTION
				"TYPE: - Display
				 PAGE: - Audio
					Embed 5-L Clip  cmdID= 37548  format=   "
		::= { iqudc00CmdEntry 37548 }


	iqudc00EmbGainEmbedPair5Embed5RClip OBJECT-TYPE
		SYNTAX		RollCallString
		MAX-ACCESS		read-only
		STATUS			current
		DESCRIPTION
				"TYPE: - Display
				 PAGE: - Audio
					Embed 5-R Clip  cmdID= 37549  format=   "
		::= { iqudc00CmdEntry 37549 }


	iqudc00EmbGainEmbedPair6Embed6MuteL OBJECT-TYPE
		SYNTAX		INTEGER { disable(0), enable(1) }
		MAX-ACCESS		read-write
		STATUS			current
		DESCRIPTION
				"TYPE: - Checkbox
				 PAGE: - Audio
					Embed 6 Mute L  cmdID= 37350 "
		::= { iqudc00CmdEntry 37350 }


	iqudc00EmbGainEmbedPair6Embed6MuteR OBJECT-TYPE
		SYNTAX		INTEGER { disable(0), enable(1) }
		MAX-ACCESS		read-write
		STATUS			current
		DESCRIPTION
				"TYPE: - Checkbox
				 PAGE: - Audio
					Embed 6 Mute R  cmdID= 37351 "
		::= { iqudc00CmdEntry 37351 }


	iqudc00EmbGainEmbedPair6Embed6LGain OBJECT-TYPE
		SYNTAX		INTEGER
		MAX-ACCESS		read-write
		STATUS			current
		DESCRIPTION
				"TYPE: - Number
				 PAGE: - Audio
					Embed 6 L Gain  cmdID= 37330  min= -360  max= 120  step= 1  format= %0.1f dB  div_scale= 10
					Min = -36.0 dB  Max = 12.0 dB  Step = 0.1 dB "
		::= { iqudc00CmdEntry 37330 }


	iqudc00EmbGainEmbedPair6Embed6RGain OBJECT-TYPE
		SYNTAX		INTEGER
		MAX-ACCESS		read-write
		STATUS			current
		DESCRIPTION
				"TYPE: - Number
				 PAGE: - Audio
					Embed 6 R Gain  cmdID= 37331  min= -360  max= 120  step= 1  format= %0.1f dB  div_scale= 10
					Min = -36.0 dB  Max = 12.0 dB  Step = 0.1 dB "
		::= { iqudc00CmdEntry 37331 }


	iqudc00EmbGainEmbedPair6Stereo OBJECT-TYPE
		SYNTAX		INTEGER { disable(0), enable(1) }
		MAX-ACCESS		read-write
		STATUS			current
		DESCRIPTION
				"TYPE: - Checkbox
				 PAGE: - Audio
					Stereo  cmdID= 37385 "
		::= { iqudc00CmdEntry 37385 }


	iqudc00EmbGainEmbedPair6Embed6InvertL OBJECT-TYPE
		SYNTAX		INTEGER { disable(0), enable(1) }
		MAX-ACCESS		read-write
		STATUS			current
		DESCRIPTION
				"TYPE: - Checkbox
				 PAGE: - Audio
					Embed 6 Invert L  cmdID= 37370 "
		::= { iqudc00CmdEntry 37370 }


	iqudc00EmbGainEmbedPair6Embed6InvertR OBJECT-TYPE
		SYNTAX		INTEGER { disable(0), enable(1) }
		MAX-ACCESS		read-write
		STATUS			current
		DESCRIPTION
				"TYPE: - Checkbox
				 PAGE: - Audio
					Embed 6 Invert R  cmdID= 37371 "
		::= { iqudc00CmdEntry 37371 }


	iqudc00EmbGainEmbedPair6Embed6LClip OBJECT-TYPE
		SYNTAX		RollCallString
		MAX-ACCESS		read-only
		STATUS			current
		DESCRIPTION
				"TYPE: - Display
				 PAGE: - Audio
					Embed 6-L Clip  cmdID= 37550  format=   "
		::= { iqudc00CmdEntry 37550 }


	iqudc00EmbGainEmbedPair6Embed6RClip OBJECT-TYPE
		SYNTAX		RollCallString
		MAX-ACCESS		read-only
		STATUS			current
		DESCRIPTION
				"TYPE: - Display
				 PAGE: - Audio
					Embed 6-R Clip  cmdID= 37551  format=   "
		::= { iqudc00CmdEntry 37551 }


	iqudc00EmbGainEmbedPair7Embed7MuteL OBJECT-TYPE
		SYNTAX		INTEGER { disable(0), enable(1) }
		MAX-ACCESS		read-write
		STATUS			current
		DESCRIPTION
				"TYPE: - Checkbox
				 PAGE: - Audio
					Embed 7 Mute L  cmdID= 37352 "
		::= { iqudc00CmdEntry 37352 }


	iqudc00EmbGainEmbedPair7Embed7MuteR OBJECT-TYPE
		SYNTAX		INTEGER { disable(0), enable(1) }
		MAX-ACCESS		read-write
		STATUS			current
		DESCRIPTION
				"TYPE: - Checkbox
				 PAGE: - Audio
					Embed 7 Mute R  cmdID= 37353 "
		::= { iqudc00CmdEntry 37353 }


	iqudc00EmbGainEmbedPair7Embed7LGain OBJECT-TYPE
		SYNTAX		INTEGER
		MAX-ACCESS		read-write
		STATUS			current
		DESCRIPTION
				"TYPE: - Number
				 PAGE: - Audio
					Embed 7 L Gain  cmdID= 37332  min= -360  max= 120  step= 1  format= %0.1f dB  div_scale= 10
					Min = -36.0 dB  Max = 12.0 dB  Step = 0.1 dB "
		::= { iqudc00CmdEntry 37332 }


	iqudc00EmbGainEmbedPair7Embed7RGain OBJECT-TYPE
		SYNTAX		INTEGER
		MAX-ACCESS		read-write
		STATUS			current
		DESCRIPTION
				"TYPE: - Number
				 PAGE: - Audio
					Embed 7 R Gain  cmdID= 37333  min= -360  max= 120  step= 1  format= %0.1f dB  div_scale= 10
					Min = -36.0 dB  Max = 12.0 dB  Step = 0.1 dB "
		::= { iqudc00CmdEntry 37333 }


	iqudc00EmbGainEmbedPair7Stereo OBJECT-TYPE
		SYNTAX		INTEGER { disable(0), enable(1) }
		MAX-ACCESS		read-write
		STATUS			current
		DESCRIPTION
				"TYPE: - Checkbox
				 PAGE: - Audio
					Stereo  cmdID= 37386 "
		::= { iqudc00CmdEntry 37386 }


	iqudc00EmbGainEmbedPair7Embed7InvertL OBJECT-TYPE
		SYNTAX		INTEGER { disable(0), enable(1) }
		MAX-ACCESS		read-write
		STATUS			current
		DESCRIPTION
				"TYPE: - Checkbox
				 PAGE: - Audio
					Embed 7 Invert L  cmdID= 37372 "
		::= { iqudc00CmdEntry 37372 }


	iqudc00EmbGainEmbedPair7Embed7InvertR OBJECT-TYPE
		SYNTAX		INTEGER { disable(0), enable(1) }
		MAX-ACCESS		read-write
		STATUS			current
		DESCRIPTION
				"TYPE: - Checkbox
				 PAGE: - Audio
					Embed 7 Invert R  cmdID= 37373 "
		::= { iqudc00CmdEntry 37373 }


	iqudc00EmbGainEmbedPair7Embed7LClip OBJECT-TYPE
		SYNTAX		RollCallString
		MAX-ACCESS		read-only
		STATUS			current
		DESCRIPTION
				"TYPE: - Display
				 PAGE: - Audio
					Embed 7-L Clip  cmdID= 37552  format=   "
		::= { iqudc00CmdEntry 37552 }


	iqudc00EmbGainEmbedPair7Embed7RClip OBJECT-TYPE
		SYNTAX		RollCallString
		MAX-ACCESS		read-only
		STATUS			current
		DESCRIPTION
				"TYPE: - Display
				 PAGE: - Audio
					Embed 7-R Clip  cmdID= 37553  format=   "
		::= { iqudc00CmdEntry 37553 }


	iqudc00EmbGainEmbedPair8Embed8MuteL OBJECT-TYPE
		SYNTAX		INTEGER { disable(0), enable(1) }
		MAX-ACCESS		read-write
		STATUS			current
		DESCRIPTION
				"TYPE: - Checkbox
				 PAGE: - Audio
					Embed 8 Mute L  cmdID= 37354 "
		::= { iqudc00CmdEntry 37354 }


	iqudc00EmbGainEmbedPair8Embed8MuteR OBJECT-TYPE
		SYNTAX		INTEGER { disable(0), enable(1) }
		MAX-ACCESS		read-write
		STATUS			current
		DESCRIPTION
				"TYPE: - Checkbox
				 PAGE: - Audio
					Embed 8 Mute R  cmdID= 37355 "
		::= { iqudc00CmdEntry 37355 }


	iqudc00EmbGainEmbedPair8Embed8LGain OBJECT-TYPE
		SYNTAX		INTEGER
		MAX-ACCESS		read-write
		STATUS			current
		DESCRIPTION
				"TYPE: - Number
				 PAGE: - Audio
					Embed 8 L Gain  cmdID= 37334  min= -360  max= 120  step= 1  format= %0.1f dB  div_scale= 10
					Min = -36.0 dB  Max = 12.0 dB  Step = 0.1 dB "
		::= { iqudc00CmdEntry 37334 }


	iqudc00EmbGainEmbedPair8Embed8RGain OBJECT-TYPE
		SYNTAX		INTEGER
		MAX-ACCESS		read-write
		STATUS			current
		DESCRIPTION
				"TYPE: - Number
				 PAGE: - Audio
					Embed 8 R Gain  cmdID= 37335  min= -360  max= 120  step= 1  format= %0.1f dB  div_scale= 10
					Min = -36.0 dB  Max = 12.0 dB  Step = 0.1 dB "
		::= { iqudc00CmdEntry 37335 }


	iqudc00EmbGainEmbedPair8Stereo OBJECT-TYPE
		SYNTAX		INTEGER { disable(0), enable(1) }
		MAX-ACCESS		read-write
		STATUS			current
		DESCRIPTION
				"TYPE: - Checkbox
				 PAGE: - Audio
					Stereo  cmdID= 37387 "
		::= { iqudc00CmdEntry 37387 }


	iqudc00EmbGainEmbedPair8Embed8InvertL OBJECT-TYPE
		SYNTAX		INTEGER { disable(0), enable(1) }
		MAX-ACCESS		read-write
		STATUS			current
		DESCRIPTION
				"TYPE: - Checkbox
				 PAGE: - Audio
					Embed 8 Invert L  cmdID= 37374 "
		::= { iqudc00CmdEntry 37374 }


	iqudc00EmbGainEmbedPair8Embed8InvertR OBJECT-TYPE
		SYNTAX		INTEGER { disable(0), enable(1) }
		MAX-ACCESS		read-write
		STATUS			current
		DESCRIPTION
				"TYPE: - Checkbox
				 PAGE: - Audio
					Embed 8 Invert R  cmdID= 37375 "
		::= { iqudc00CmdEntry 37375 }


	iqudc00EmbGainEmbedPair8Embed8LClip OBJECT-TYPE
		SYNTAX		RollCallString
		MAX-ACCESS		read-only
		STATUS			current
		DESCRIPTION
				"TYPE: - Display
				 PAGE: - Audio
					Embed 8-L Clip  cmdID= 37554  format=   "
		::= { iqudc00CmdEntry 37554 }


	iqudc00EmbGainEmbedPair8Embed8RClip OBJECT-TYPE
		SYNTAX		RollCallString
		MAX-ACCESS		read-only
		STATUS			current
		DESCRIPTION
				"TYPE: - Display
				 PAGE: - Audio
					Embed 8-R Clip  cmdID= 37555  format=   "
		::= { iqudc00CmdEntry 37555 }


	iqudc00EmbOutEmbedPair1Embed1L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Embed 1-L  cmdID= 37300
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37300 }


	iqudc00EmbOutEmbedPair1Embed1R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 1
					Embed 1-R  cmdID= 37301
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37301 }


	iqudc00EmbOutEmbedPair1LinkLRSelection OBJECT-TYPE
		SYNTAX		INTEGER { disable(0), enable(1) }
		MAX-ACCESS		read-write
		STATUS			current
		DESCRIPTION
				"TYPE: - Checkbox
				 PAGE: - Audio- Embed Pair 1
					Link L+R Selection  cmdID= 37390 "
		::= { iqudc00CmdEntry 37390 }


	iqudc00EmbOutEmbedPair2Embed2L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Embed 2-L  cmdID= 37302
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37302 }


	iqudc00EmbOutEmbedPair2Embed2R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 2
					Embed 2-R  cmdID= 37303
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37303 }


	iqudc00EmbOutEmbedPair2LinkLRSelection OBJECT-TYPE
		SYNTAX		INTEGER { disable(0), enable(1) }
		MAX-ACCESS		read-write
		STATUS			current
		DESCRIPTION
				"TYPE: - Checkbox
				 PAGE: - Audio- Embed Pair 2
					Link L+R Selection  cmdID= 37391 "
		::= { iqudc00CmdEntry 37391 }


	iqudc00EmbOutEmbedPair3Embed3L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Embed 3-L  cmdID= 37304
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37304 }


	iqudc00EmbOutEmbedPair3Embed3R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 3
					Embed 3-R  cmdID= 37305
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37305 }


	iqudc00EmbOutEmbedPair3LinkLRSelection OBJECT-TYPE
		SYNTAX		INTEGER { disable(0), enable(1) }
		MAX-ACCESS		read-write
		STATUS			current
		DESCRIPTION
				"TYPE: - Checkbox
				 PAGE: - Audio- Embed Pair 3
					Link L+R Selection  cmdID= 37392 "
		::= { iqudc00CmdEntry 37392 }


	iqudc00EmbOutEmbedPair4Embed4L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Embed 4-L  cmdID= 37306
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37306 }


	iqudc00EmbOutEmbedPair4Embed4R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 4
					Embed 4-R  cmdID= 37307
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37307 }


	iqudc00EmbOutEmbedPair4LinkLRSelection OBJECT-TYPE
		SYNTAX		INTEGER { disable(0), enable(1) }
		MAX-ACCESS		read-write
		STATUS			current
		DESCRIPTION
				"TYPE: - Checkbox
				 PAGE: - Audio- Embed Pair 4
					Link L+R Selection  cmdID= 37393 "
		::= { iqudc00CmdEntry 37393 }


	iqudc00EmbOutEmbedPair5Embed5L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Embed 5-L  cmdID= 37308
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37308 }


	iqudc00EmbOutEmbedPair5Embed5R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 5
					Embed 5-R  cmdID= 37309
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37309 }


	iqudc00EmbOutEmbedPair5LinkLRSelection OBJECT-TYPE
		SYNTAX		INTEGER { disable(0), enable(1) }
		MAX-ACCESS		read-write
		STATUS			current
		DESCRIPTION
				"TYPE: - Checkbox
				 PAGE: - Audio- Embed Pair 5
					Link L+R Selection  cmdID= 37394 "
		::= { iqudc00CmdEntry 37394 }


	iqudc00EmbOutEmbedPair6Embed6L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Embed 6-L  cmdID= 37310
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37310 }


	iqudc00EmbOutEmbedPair6Embed6R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 6
					Embed 6-R  cmdID= 37311
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37311 }


	iqudc00EmbOutEmbedPair6LinkLRSelection OBJECT-TYPE
		SYNTAX		INTEGER { disable(0), enable(1) }
		MAX-ACCESS		read-write
		STATUS			current
		DESCRIPTION
				"TYPE: - Checkbox
				 PAGE: - Audio- Embed Pair 6
					Link L+R Selection  cmdID= 37395 "
		::= { iqudc00CmdEntry 37395 }


	iqudc00EmbOutEmbedPair7Embed7L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Embed 7-L  cmdID= 37312
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37312 }


	iqudc00EmbOutEmbedPair7Embed7R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 7
					Embed 7-R  cmdID= 37313
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37313 }


	iqudc00EmbOutEmbedPair7LinkLRSelection OBJECT-TYPE
		SYNTAX		INTEGER { disable(0), enable(1) }
		MAX-ACCESS		read-write
		STATUS			current
		DESCRIPTION
				"TYPE: - Checkbox
				 PAGE: - Audio- Embed Pair 7
					Link L+R Selection  cmdID= 37396 "
		::= { iqudc00CmdEntry 37396 }


	iqudc00EmbOutEmbedPair8Embed8L OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Embed 8-L  cmdID= 37314
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37314 }


	iqudc00EmbOutEmbedPair8Embed8R OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mixer_1_o_p(23),
							val_Mixer_2_o_p(24),
							val_Mixer_3_o_p(25),
							val_Mixer_4_o_p(26),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Embed Pair 8
					Embed 8-R  cmdID= 37315
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mixer 1 o/p  value= 23
					Mixer 2 o/p  value= 24
					Mixer 3 o/p  value= 25
					Mixer 4 o/p  value= 26
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37315 }


	iqudc00EmbOutEmbedPair8LinkLRSelection OBJECT-TYPE
		SYNTAX		INTEGER { disable(0), enable(1) }
		MAX-ACCESS		read-write
		STATUS			current
		DESCRIPTION
				"TYPE: - Checkbox
				 PAGE: - Audio- Embed Pair 8
					Link L+R Selection  cmdID= 37397 "
		::= { iqudc00CmdEntry 37397 }


	iqudc00AudioEmbDataInput1 OBJECT-TYPE
		SYNTAX		INTEGER { disable(0), enable(1) }
		MAX-ACCESS		read-write
		STATUS			current
		DESCRIPTION
				"TYPE: - Checkbox
				 PAGE: - Audio
					Input 1  cmdID= 37420 "
		::= { iqudc00CmdEntry 37420 }


	iqudc00AudioEmbDataInput2 OBJECT-TYPE
		SYNTAX		INTEGER { disable(0), enable(1) }
		MAX-ACCESS		read-write
		STATUS			current
		DESCRIPTION
				"TYPE: - Checkbox
				 PAGE: - Audio
					Input 2  cmdID= 37421 "
		::= { iqudc00CmdEntry 37421 }


	iqudc00AudioEmbDataInput3 OBJECT-TYPE
		SYNTAX		INTEGER { disable(0), enable(1) }
		MAX-ACCESS		read-write
		STATUS			current
		DESCRIPTION
				"TYPE: - Checkbox
				 PAGE: - Audio
					Input 3  cmdID= 37422 "
		::= { iqudc00CmdEntry 37422 }


	iqudc00AudioEmbDataInput4 OBJECT-TYPE
		SYNTAX		INTEGER { disable(0), enable(1) }
		MAX-ACCESS		read-write
		STATUS			current
		DESCRIPTION
				"TYPE: - Checkbox
				 PAGE: - Audio
					Input 4  cmdID= 37423 "
		::= { iqudc00CmdEntry 37423 }


	iqudc00AudioEmbDataInput5 OBJECT-TYPE
		SYNTAX		INTEGER { disable(0), enable(1) }
		MAX-ACCESS		read-write
		STATUS			current
		DESCRIPTION
				"TYPE: - Checkbox
				 PAGE: - Audio
					Input 5  cmdID= 37424 "
		::= { iqudc00CmdEntry 37424 }


	iqudc00AudioEmbDataInput6 OBJECT-TYPE
		SYNTAX		INTEGER { disable(0), enable(1) }
		MAX-ACCESS		read-write
		STATUS			current
		DESCRIPTION
				"TYPE: - Checkbox
				 PAGE: - Audio
					Input 6  cmdID= 37425 "
		::= { iqudc00CmdEntry 37425 }


	iqudc00AudioEmbDataInput7 OBJECT-TYPE
		SYNTAX		INTEGER { disable(0), enable(1) }
		MAX-ACCESS		read-write
		STATUS			current
		DESCRIPTION
				"TYPE: - Checkbox
				 PAGE: - Audio
					Input 7  cmdID= 37426 "
		::= { iqudc00CmdEntry 37426 }


	iqudc00AudioEmbDataInput8 OBJECT-TYPE
		SYNTAX		INTEGER { disable(0), enable(1) }
		MAX-ACCESS		read-write
		STATUS			current
		DESCRIPTION
				"TYPE: - Checkbox
				 PAGE: - Audio
					Input 8  cmdID= 37427 "
		::= { iqudc00CmdEntry 37427 }


	iqudc00DisembedderNamesDisemb1L OBJECT-TYPE
		SYNTAX		RollCallString
		MAX-ACCESS		read-write
		STATUS			current
		DESCRIPTION
				"TYPE: - Editstring
				 PAGE: - Audio- Names
					Disemb 1L  cmdID= 37500  "
		::= { iqudc00CmdEntry 37500 }


	iqudc00DisembedderNamesDisemb1R OBJECT-TYPE
		SYNTAX		RollCallString
		MAX-ACCESS		read-write
		STATUS			current
		DESCRIPTION
				"TYPE: - Editstring
				 PAGE: - Audio- Names
					Disemb 1R  cmdID= 37501  "
		::= { iqudc00CmdEntry 37501 }


	iqudc00DisembedderNamesDisemb2L OBJECT-TYPE
		SYNTAX		RollCallString
		MAX-ACCESS		read-write
		STATUS			current
		DESCRIPTION
				"TYPE: - Editstring
				 PAGE: - Audio- Names
					Disemb 2L  cmdID= 37502  "
		::= { iqudc00CmdEntry 37502 }


	iqudc00DisembedderNamesDisemb2R OBJECT-TYPE
		SYNTAX		RollCallString
		MAX-ACCESS		read-write
		STATUS			current
		DESCRIPTION
				"TYPE: - Editstring
				 PAGE: - Audio- Names
					Disemb 2R  cmdID= 37503  "
		::= { iqudc00CmdEntry 37503 }


	iqudc00DisembedderNamesDisemb3L OBJECT-TYPE
		SYNTAX		RollCallString
		MAX-ACCESS		read-write
		STATUS			current
		DESCRIPTION
				"TYPE: - Editstring
				 PAGE: - Audio- Names
					Disemb 3L  cmdID= 37504  "
		::= { iqudc00CmdEntry 37504 }


	iqudc00DisembedderNamesDisemb3R OBJECT-TYPE
		SYNTAX		RollCallString
		MAX-ACCESS		read-write
		STATUS			current
		DESCRIPTION
				"TYPE: - Editstring
				 PAGE: - Audio- Names
					Disemb 3R  cmdID= 37505  "
		::= { iqudc00CmdEntry 37505 }


	iqudc00DisembedderNamesDisemb4L OBJECT-TYPE
		SYNTAX		RollCallString
		MAX-ACCESS		read-write
		STATUS			current
		DESCRIPTION
				"TYPE: - Editstring
				 PAGE: - Audio- Names
					Disemb 4L  cmdID= 37506  "
		::= { iqudc00CmdEntry 37506 }


	iqudc00DisembedderNamesDisemb4R OBJECT-TYPE
		SYNTAX		RollCallString
		MAX-ACCESS		read-write
		STATUS			current
		DESCRIPTION
				"TYPE: - Editstring
				 PAGE: - Audio- Names
					Disemb 4R  cmdID= 37507  "
		::= { iqudc00CmdEntry 37507 }


	iqudc00DisembedderNamesDisemb5L OBJECT-TYPE
		SYNTAX		RollCallString
		MAX-ACCESS		read-write
		STATUS			current
		DESCRIPTION
				"TYPE: - Editstring
				 PAGE: - Audio- Names
					Disemb 5L  cmdID= 37508  "
		::= { iqudc00CmdEntry 37508 }


	iqudc00DisembedderNamesDisemb5R OBJECT-TYPE
		SYNTAX		RollCallString
		MAX-ACCESS		read-write
		STATUS			current
		DESCRIPTION
				"TYPE: - Editstring
				 PAGE: - Audio- Names
					Disemb 5R  cmdID= 37509  "
		::= { iqudc00CmdEntry 37509 }


	iqudc00DisembedderNamesDisemb6L OBJECT-TYPE
		SYNTAX		RollCallString
		MAX-ACCESS		read-write
		STATUS			current
		DESCRIPTION
				"TYPE: - Editstring
				 PAGE: - Audio- Names
					Disemb 6L  cmdID= 37510  "
		::= { iqudc00CmdEntry 37510 }


	iqudc00DisembedderNamesDisemb6R OBJECT-TYPE
		SYNTAX		RollCallString
		MAX-ACCESS		read-write
		STATUS			current
		DESCRIPTION
				"TYPE: - Editstring
				 PAGE: - Audio- Names
					Disemb 6R  cmdID= 37511  "
		::= { iqudc00CmdEntry 37511 }


	iqudc00DisembedderNamesDisemb7L OBJECT-TYPE
		SYNTAX		RollCallString
		MAX-ACCESS		read-write
		STATUS			current
		DESCRIPTION
				"TYPE: - Editstring
				 PAGE: - Audio- Names
					Disemb 7L  cmdID= 37512  "
		::= { iqudc00CmdEntry 37512 }


	iqudc00DisembedderNamesDisemb7R OBJECT-TYPE
		SYNTAX		RollCallString
		MAX-ACCESS		read-write
		STATUS			current
		DESCRIPTION
				"TYPE: - Editstring
				 PAGE: - Audio- Names
					Disemb 7R  cmdID= 37513  "
		::= { iqudc00CmdEntry 37513 }


	iqudc00DisembedderNamesDisemb8L OBJECT-TYPE
		SYNTAX		RollCallString
		MAX-ACCESS		read-write
		STATUS			current
		DESCRIPTION
				"TYPE: - Editstring
				 PAGE: - Audio- Names
					Disemb 8L  cmdID= 37514  "
		::= { iqudc00CmdEntry 37514 }


	iqudc00DisembedderNamesDisemb8R OBJECT-TYPE
		SYNTAX		RollCallString
		MAX-ACCESS		read-write
		STATUS			current
		DESCRIPTION
				"TYPE: - Editstring
				 PAGE: - Audio- Names
					Disemb 8R  cmdID= 37515  "
		::= { iqudc00CmdEntry 37515 }


	iqudc00DisembedderNamesEmbeddedOP1L OBJECT-TYPE
		SYNTAX		RollCallString
		MAX-ACCESS		read-write
		STATUS			current
		DESCRIPTION
				"TYPE: - Editstring
				 PAGE: - Audio- Names
					Embed 1L  cmdID= 37520  "
		::= { iqudc00CmdEntry 37520 }


	iqudc00DisembedderNamesEmbeddedOP1R OBJECT-TYPE
		SYNTAX		RollCallString
		MAX-ACCESS		read-write
		STATUS			current
		DESCRIPTION
				"TYPE: - Editstring
				 PAGE: - Audio- Names
					Embed 1R  cmdID= 37521  "
		::= { iqudc00CmdEntry 37521 }


	iqudc00DisembedderNamesEmbeddedOP2L OBJECT-TYPE
		SYNTAX		RollCallString
		MAX-ACCESS		read-write
		STATUS			current
		DESCRIPTION
				"TYPE: - Editstring
				 PAGE: - Audio- Names
					Embed 2L  cmdID= 37522  "
		::= { iqudc00CmdEntry 37522 }


	iqudc00DisembedderNamesEmbeddedOP2R OBJECT-TYPE
		SYNTAX		RollCallString
		MAX-ACCESS		read-write
		STATUS			current
		DESCRIPTION
				"TYPE: - Editstring
				 PAGE: - Audio- Names
					Embed 2R  cmdID= 37523  "
		::= { iqudc00CmdEntry 37523 }


	iqudc00DisembedderNamesEmbeddedOP3L OBJECT-TYPE
		SYNTAX		RollCallString
		MAX-ACCESS		read-write
		STATUS			current
		DESCRIPTION
				"TYPE: - Editstring
				 PAGE: - Audio- Names
					Embed 3L  cmdID= 37524  "
		::= { iqudc00CmdEntry 37524 }


	iqudc00DisembedderNamesEmbeddedOP3R OBJECT-TYPE
		SYNTAX		RollCallString
		MAX-ACCESS		read-write
		STATUS			current
		DESCRIPTION
				"TYPE: - Editstring
				 PAGE: - Audio- Names
					Embed 3R  cmdID= 37525  "
		::= { iqudc00CmdEntry 37525 }


	iqudc00DisembedderNamesEmbeddedOP4L OBJECT-TYPE
		SYNTAX		RollCallString
		MAX-ACCESS		read-write
		STATUS			current
		DESCRIPTION
				"TYPE: - Editstring
				 PAGE: - Audio- Names
					Embed 4L  cmdID= 37526  "
		::= { iqudc00CmdEntry 37526 }


	iqudc00DisembedderNamesEmbeddedOP4R OBJECT-TYPE
		SYNTAX		RollCallString
		MAX-ACCESS		read-write
		STATUS			current
		DESCRIPTION
				"TYPE: - Editstring
				 PAGE: - Audio- Names
					Embed 4R  cmdID= 37527  "
		::= { iqudc00CmdEntry 37527 }


	iqudc00DisembedderNamesEmbeddedOP5L OBJECT-TYPE
		SYNTAX		RollCallString
		MAX-ACCESS		read-write
		STATUS			current
		DESCRIPTION
				"TYPE: - Editstring
				 PAGE: - Audio- Names
					Embed 5L  cmdID= 37528  "
		::= { iqudc00CmdEntry 37528 }


	iqudc00DisembedderNamesEmbeddedOP5R OBJECT-TYPE
		SYNTAX		RollCallString
		MAX-ACCESS		read-write
		STATUS			current
		DESCRIPTION
				"TYPE: - Editstring
				 PAGE: - Audio- Names
					Embed 5R  cmdID= 37529  "
		::= { iqudc00CmdEntry 37529 }


	iqudc00DisembedderNamesEmbeddedOP6L OBJECT-TYPE
		SYNTAX		RollCallString
		MAX-ACCESS		read-write
		STATUS			current
		DESCRIPTION
				"TYPE: - Editstring
				 PAGE: - Audio- Names
					Embed 6L  cmdID= 37530  "
		::= { iqudc00CmdEntry 37530 }


	iqudc00DisembedderNamesEmbeddedOP6R OBJECT-TYPE
		SYNTAX		RollCallString
		MAX-ACCESS		read-write
		STATUS			current
		DESCRIPTION
				"TYPE: - Editstring
				 PAGE: - Audio- Names
					Embed 6R  cmdID= 37531  "
		::= { iqudc00CmdEntry 37531 }


	iqudc00DisembedderNamesEmbeddedOP7L OBJECT-TYPE
		SYNTAX		RollCallString
		MAX-ACCESS		read-write
		STATUS			current
		DESCRIPTION
				"TYPE: - Editstring
				 PAGE: - Audio- Names
					Embed 7L  cmdID= 37532  "
		::= { iqudc00CmdEntry 37532 }


	iqudc00DisembedderNamesEmbeddedOP7R OBJECT-TYPE
		SYNTAX		RollCallString
		MAX-ACCESS		read-write
		STATUS			current
		DESCRIPTION
				"TYPE: - Editstring
				 PAGE: - Audio- Names
					Embed 7R  cmdID= 37533  "
		::= { iqudc00CmdEntry 37533 }


	iqudc00DisembedderNamesEmbeddedOP8L OBJECT-TYPE
		SYNTAX		RollCallString
		MAX-ACCESS		read-write
		STATUS			current
		DESCRIPTION
				"TYPE: - Editstring
				 PAGE: - Audio- Names
					Embed 8L  cmdID= 37534  "
		::= { iqudc00CmdEntry 37534 }


	iqudc00DisembedderNamesEmbeddedOP8R OBJECT-TYPE
		SYNTAX		RollCallString
		MAX-ACCESS		read-write
		STATUS			current
		DESCRIPTION
				"TYPE: - Editstring
				 PAGE: - Audio- Names
					Embed 8R  cmdID= 37535  "
		::= { iqudc00CmdEntry 37535 }


	iqudc00DisembedderNamesIPStereoDisemb1 OBJECT-TYPE
		SYNTAX		INTEGER { disable(0), enable(1) }
		MAX-ACCESS		read-write
		STATUS			current
		DESCRIPTION
				"TYPE: - Checkbox
				 PAGE: - Audio- Names
					Disemb 1  cmdID= 37400 "
		::= { iqudc00CmdEntry 37400 }


	iqudc00DisembedderNamesIPStereoDisemb2 OBJECT-TYPE
		SYNTAX		INTEGER { disable(0), enable(1) }
		MAX-ACCESS		read-write
		STATUS			current
		DESCRIPTION
				"TYPE: - Checkbox
				 PAGE: - Audio- Names
					Disemb 2  cmdID= 37401 "
		::= { iqudc00CmdEntry 37401 }


	iqudc00DisembedderNamesIPStereoDisemb3 OBJECT-TYPE
		SYNTAX		INTEGER { disable(0), enable(1) }
		MAX-ACCESS		read-write
		STATUS			current
		DESCRIPTION
				"TYPE: - Checkbox
				 PAGE: - Audio- Names
					Disemb 3  cmdID= 37402 "
		::= { iqudc00CmdEntry 37402 }


	iqudc00DisembedderNamesIPStereoDisemb4 OBJECT-TYPE
		SYNTAX		INTEGER { disable(0), enable(1) }
		MAX-ACCESS		read-write
		STATUS			current
		DESCRIPTION
				"TYPE: - Checkbox
				 PAGE: - Audio- Names
					Disemb 4  cmdID= 37403 "
		::= { iqudc00CmdEntry 37403 }


	iqudc00DisembedderNamesIPStereoDisemb5 OBJECT-TYPE
		SYNTAX		INTEGER { disable(0), enable(1) }
		MAX-ACCESS		read-write
		STATUS			current
		DESCRIPTION
				"TYPE: - Checkbox
				 PAGE: - Audio- Names
					Disemb 5  cmdID= 37404 "
		::= { iqudc00CmdEntry 37404 }


	iqudc00DisembedderNamesIPStereoDisemb6 OBJECT-TYPE
		SYNTAX		INTEGER { disable(0), enable(1) }
		MAX-ACCESS		read-write
		STATUS			current
		DESCRIPTION
				"TYPE: - Checkbox
				 PAGE: - Audio- Names
					Disemb 6  cmdID= 37405 "
		::= { iqudc00CmdEntry 37405 }


	iqudc00DisembedderNamesIPStereoDisemb7 OBJECT-TYPE
		SYNTAX		INTEGER { disable(0), enable(1) }
		MAX-ACCESS		read-write
		STATUS			current
		DESCRIPTION
				"TYPE: - Checkbox
				 PAGE: - Audio- Names
					Disemb 7  cmdID= 37406 "
		::= { iqudc00CmdEntry 37406 }


	iqudc00DisembedderNamesIPStereoDisemb8 OBJECT-TYPE
		SYNTAX		INTEGER { disable(0), enable(1) }
		MAX-ACCESS		read-write
		STATUS			current
		DESCRIPTION
				"TYPE: - Checkbox
				 PAGE: - Audio- Names
					Disemb 8  cmdID= 37407 "
		::= { iqudc00CmdEntry 37407 }


	iqudc00DisembedderNamesOPStereoEmbed1 OBJECT-TYPE
		SYNTAX		INTEGER { disable(0), enable(1) }
		MAX-ACCESS		read-write
		STATUS			current
		DESCRIPTION
				"TYPE: - Checkbox
				 PAGE: - Audio- Names
					Embed 1  cmdID= 37410 "
		::= { iqudc00CmdEntry 37410 }


	iqudc00DisembedderNamesOPStereoEmbed2 OBJECT-TYPE
		SYNTAX		INTEGER { disable(0), enable(1) }
		MAX-ACCESS		read-write
		STATUS			current
		DESCRIPTION
				"TYPE: - Checkbox
				 PAGE: - Audio- Names
					Embed 2  cmdID= 37411 "
		::= { iqudc00CmdEntry 37411 }


	iqudc00DisembedderNamesOPStereoEmbed3 OBJECT-TYPE
		SYNTAX		INTEGER { disable(0), enable(1) }
		MAX-ACCESS		read-write
		STATUS			current
		DESCRIPTION
				"TYPE: - Checkbox
				 PAGE: - Audio- Names
					Embed 3  cmdID= 37412 "
		::= { iqudc00CmdEntry 37412 }


	iqudc00DisembedderNamesOPStereoEmbed4 OBJECT-TYPE
		SYNTAX		INTEGER { disable(0), enable(1) }
		MAX-ACCESS		read-write
		STATUS			current
		DESCRIPTION
				"TYPE: - Checkbox
				 PAGE: - Audio- Names
					Embed 4  cmdID= 37413 "
		::= { iqudc00CmdEntry 37413 }


	iqudc00DisembedderNamesOPStereoEmbed5 OBJECT-TYPE
		SYNTAX		INTEGER { disable(0), enable(1) }
		MAX-ACCESS		read-write
		STATUS			current
		DESCRIPTION
				"TYPE: - Checkbox
				 PAGE: - Audio- Names
					Embed 5  cmdID= 37414 "
		::= { iqudc00CmdEntry 37414 }


	iqudc00DisembedderNamesOPStereoEmbed6 OBJECT-TYPE
		SYNTAX		INTEGER { disable(0), enable(1) }
		MAX-ACCESS		read-write
		STATUS			current
		DESCRIPTION
				"TYPE: - Checkbox
				 PAGE: - Audio- Names
					Embed 6  cmdID= 37415 "
		::= { iqudc00CmdEntry 37415 }


	iqudc00DisembedderNamesOPStereoEmbed7 OBJECT-TYPE
		SYNTAX		INTEGER { disable(0), enable(1) }
		MAX-ACCESS		read-write
		STATUS			current
		DESCRIPTION
				"TYPE: - Checkbox
				 PAGE: - Audio- Names
					Embed 7  cmdID= 37416 "
		::= { iqudc00CmdEntry 37416 }


	iqudc00DisembedderNamesOPStereoEmbed8 OBJECT-TYPE
		SYNTAX		INTEGER { disable(0), enable(1) }
		MAX-ACCESS		read-write
		STATUS			current
		DESCRIPTION
				"TYPE: - Checkbox
				 PAGE: - Audio- Names
					Embed 8  cmdID= 37417 "
		::= { iqudc00CmdEntry 37417 }


	iqudc00NamesMix1 OBJECT-TYPE
		SYNTAX		RollCallString
		MAX-ACCESS		read-write
		STATUS			current
		DESCRIPTION
				"TYPE: - Editstring
				 PAGE: - Audio- Names
					Mix 1  cmdID= 37810  "
		::= { iqudc00CmdEntry 37810 }


	iqudc00NamesMix2 OBJECT-TYPE
		SYNTAX		RollCallString
		MAX-ACCESS		read-write
		STATUS			current
		DESCRIPTION
				"TYPE: - Editstring
				 PAGE: - Audio- Names
					Mix 2  cmdID= 37811  "
		::= { iqudc00CmdEntry 37811 }


	iqudc00NamesMix3 OBJECT-TYPE
		SYNTAX		RollCallString
		MAX-ACCESS		read-write
		STATUS			current
		DESCRIPTION
				"TYPE: - Editstring
				 PAGE: - Audio- Names
					Mix 3  cmdID= 37812  "
		::= { iqudc00CmdEntry 37812 }


	iqudc00NamesMix4 OBJECT-TYPE
		SYNTAX		RollCallString
		MAX-ACCESS		read-write
		STATUS			current
		DESCRIPTION
				"TYPE: - Editstring
				 PAGE: - Audio- Names
					Mix 4  cmdID= 37813  "
		::= { iqudc00CmdEntry 37813 }


	iqudc00Mix1RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 1  cmdID= 37600
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37600 }


	iqudc00Mix1RoutingInvert1 OBJECT-TYPE
		SYNTAX		INTEGER { disable(0), enable(1) }
		MAX-ACCESS		read-write
		STATUS			current
		DESCRIPTION
				"TYPE: - Checkbox
				 PAGE: - Audio- Mix 1
					Invert 1  cmdID= 37720 "
		::= { iqudc00CmdEntry 37720 }


	iqudc00Mix1RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 2  cmdID= 37601
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37601 }


	iqudc00Mix1RoutingInvert2 OBJECT-TYPE
		SYNTAX		INTEGER { disable(0), enable(1) }
		MAX-ACCESS		read-write
		STATUS			current
		DESCRIPTION
				"TYPE: - Checkbox
				 PAGE: - Audio- Mix 1
					Invert 2  cmdID= 37721 "
		::= { iqudc00CmdEntry 37721 }


	iqudc00Mix1RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 3  cmdID= 37602
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37602 }


	iqudc00Mix1RoutingInvert3 OBJECT-TYPE
		SYNTAX		INTEGER { disable(0), enable(1) }
		MAX-ACCESS		read-write
		STATUS			current
		DESCRIPTION
				"TYPE: - Checkbox
				 PAGE: - Audio- Mix 1
					Invert 3  cmdID= 37722 "
		::= { iqudc00CmdEntry 37722 }


	iqudc00Mix1RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 1
					Source 4  cmdID= 37603
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37603 }


	iqudc00Mix1RoutingInvert4 OBJECT-TYPE
		SYNTAX		INTEGER { disable(0), enable(1) }
		MAX-ACCESS		read-write
		STATUS			current
		DESCRIPTION
				"TYPE: - Checkbox
				 PAGE: - Audio- Mix 1
					Invert 4  cmdID= 37723 "
		::= { iqudc00CmdEntry 37723 }


	iqudc00Mix1GainGain1 OBJECT-TYPE
		SYNTAX		INTEGER
		MAX-ACCESS		read-write
		STATUS			current
		DESCRIPTION
				"TYPE: - Number
				 PAGE: - Audio- Mix 1
					Gain 1  cmdID= 37640  min= -360  max= 120  step= 1  format= %0.1f dB  div_scale= 10
					Min = -36.0 dB  Max = 12.0 dB  Step = 0.1 dB "
		::= { iqudc00CmdEntry 37640 }


	iqudc00Mix1GainMute1 OBJECT-TYPE
		SYNTAX		INTEGER { disable(0), enable(1) }
		MAX-ACCESS		read-write
		STATUS			current
		DESCRIPTION
				"TYPE: - Checkbox
				 PAGE: - Audio- Mix 1
					Mute 1  cmdID= 37680 "
		::= { iqudc00CmdEntry 37680 }


	iqudc00Mix1GainGain2 OBJECT-TYPE
		SYNTAX		INTEGER
		MAX-ACCESS		read-write
		STATUS			current
		DESCRIPTION
				"TYPE: - Number
				 PAGE: - Audio- Mix 1
					Gain 2  cmdID= 37641  min= -360  max= 120  step= 1  format= %0.1f dB  div_scale= 10
					Min = -36.0 dB  Max = 12.0 dB  Step = 0.1 dB "
		::= { iqudc00CmdEntry 37641 }


	iqudc00Mix1GainMute2 OBJECT-TYPE
		SYNTAX		INTEGER { disable(0), enable(1) }
		MAX-ACCESS		read-write
		STATUS			current
		DESCRIPTION
				"TYPE: - Checkbox
				 PAGE: - Audio- Mix 1
					Mute 2  cmdID= 37681 "
		::= { iqudc00CmdEntry 37681 }


	iqudc00Mix1GainGain3 OBJECT-TYPE
		SYNTAX		INTEGER
		MAX-ACCESS		read-write
		STATUS			current
		DESCRIPTION
				"TYPE: - Number
				 PAGE: - Audio- Mix 1
					Gain 3  cmdID= 37642  min= -360  max= 120  step= 1  format= %0.1f dB  div_scale= 10
					Min = -36.0 dB  Max = 12.0 dB  Step = 0.1 dB "
		::= { iqudc00CmdEntry 37642 }


	iqudc00Mix1GainMute3 OBJECT-TYPE
		SYNTAX		INTEGER { disable(0), enable(1) }
		MAX-ACCESS		read-write
		STATUS			current
		DESCRIPTION
				"TYPE: - Checkbox
				 PAGE: - Audio- Mix 1
					Mute 3  cmdID= 37682 "
		::= { iqudc00CmdEntry 37682 }


	iqudc00Mix1GainGain4 OBJECT-TYPE
		SYNTAX		INTEGER
		MAX-ACCESS		read-write
		STATUS			current
		DESCRIPTION
				"TYPE: - Number
				 PAGE: - Audio- Mix 1
					Gain 4  cmdID= 37643  min= -360  max= 120  step= 1  format= %0.1f dB  div_scale= 10
					Min = -36.0 dB  Max = 12.0 dB  Step = 0.1 dB "
		::= { iqudc00CmdEntry 37643 }


	iqudc00Mix1GainMute4 OBJECT-TYPE
		SYNTAX		INTEGER { disable(0), enable(1) }
		MAX-ACCESS		read-write
		STATUS			current
		DESCRIPTION
				"TYPE: - Checkbox
				 PAGE: - Audio- Mix 1
					Mute 4  cmdID= 37683 "
		::= { iqudc00CmdEntry 37683 }


	iqudc00Mix1GainInp1Clip OBJECT-TYPE
		SYNTAX		RollCallString
		MAX-ACCESS		read-only
		STATUS			current
		DESCRIPTION
				"TYPE: - Display
				 PAGE: - Audio- Mix 1
					Inp1 Clip  cmdID= 37760  format=   "
		::= { iqudc00CmdEntry 37760 }


	iqudc00Mix1GainInp2Clip OBJECT-TYPE
		SYNTAX		RollCallString
		MAX-ACCESS		read-only
		STATUS			current
		DESCRIPTION
				"TYPE: - Display
				 PAGE: - Audio- Mix 1
					Inp2 Clip  cmdID= 37761  format=   "
		::= { iqudc00CmdEntry 37761 }


	iqudc00Mix1GainInp3Clip OBJECT-TYPE
		SYNTAX		RollCallString
		MAX-ACCESS		read-only
		STATUS			current
		DESCRIPTION
				"TYPE: - Display
				 PAGE: - Audio- Mix 1
					Inp3 Clip  cmdID= 37762  format=   "
		::= { iqudc00CmdEntry 37762 }


	iqudc00Mix1GainInp4Clip OBJECT-TYPE
		SYNTAX		RollCallString
		MAX-ACCESS		read-only
		STATUS			current
		DESCRIPTION
				"TYPE: - Display
				 PAGE: - Audio- Mix 1
					Inp4 Clip  cmdID= 37763  format=   "
		::= { iqudc00CmdEntry 37763 }


	iqudc00Mix1GainOPClip OBJECT-TYPE
		SYNTAX		RollCallString
		MAX-ACCESS		read-only
		STATUS			current
		DESCRIPTION
				"TYPE: - Display
				 PAGE: - Audio- Mix 1
					O/P Clip  cmdID= 37800  format=   "
		::= { iqudc00CmdEntry 37800 }


	iqudc00Mix2RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 1  cmdID= 37604
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37604 }


	iqudc00Mix2RoutingInvert1 OBJECT-TYPE
		SYNTAX		INTEGER { disable(0), enable(1) }
		MAX-ACCESS		read-write
		STATUS			current
		DESCRIPTION
				"TYPE: - Checkbox
				 PAGE: - Audio- Mix 2
					Invert 1  cmdID= 37724 "
		::= { iqudc00CmdEntry 37724 }


	iqudc00Mix2RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 2  cmdID= 37605
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37605 }


	iqudc00Mix2RoutingInvert2 OBJECT-TYPE
		SYNTAX		INTEGER { disable(0), enable(1) }
		MAX-ACCESS		read-write
		STATUS			current
		DESCRIPTION
				"TYPE: - Checkbox
				 PAGE: - Audio- Mix 2
					Invert 2  cmdID= 37725 "
		::= { iqudc00CmdEntry 37725 }


	iqudc00Mix2RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 3  cmdID= 37606
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37606 }


	iqudc00Mix2RoutingInvert3 OBJECT-TYPE
		SYNTAX		INTEGER { disable(0), enable(1) }
		MAX-ACCESS		read-write
		STATUS			current
		DESCRIPTION
				"TYPE: - Checkbox
				 PAGE: - Audio- Mix 2
					Invert 3  cmdID= 37726 "
		::= { iqudc00CmdEntry 37726 }


	iqudc00Mix2RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 2
					Source 4  cmdID= 37607
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37607 }


	iqudc00Mix2RoutingInvert4 OBJECT-TYPE
		SYNTAX		INTEGER { disable(0), enable(1) }
		MAX-ACCESS		read-write
		STATUS			current
		DESCRIPTION
				"TYPE: - Checkbox
				 PAGE: - Audio- Mix 2
					Invert 4  cmdID= 37727 "
		::= { iqudc00CmdEntry 37727 }


	iqudc00Mix2GainGain1 OBJECT-TYPE
		SYNTAX		INTEGER
		MAX-ACCESS		read-write
		STATUS			current
		DESCRIPTION
				"TYPE: - Number
				 PAGE: - Audio- Mix 2
					Gain 1  cmdID= 37644  min= -360  max= 120  step= 1  format= %0.1f dB  div_scale= 10
					Min = -36.0 dB  Max = 12.0 dB  Step = 0.1 dB "
		::= { iqudc00CmdEntry 37644 }


	iqudc00Mix2GainMute1 OBJECT-TYPE
		SYNTAX		INTEGER { disable(0), enable(1) }
		MAX-ACCESS		read-write
		STATUS			current
		DESCRIPTION
				"TYPE: - Checkbox
				 PAGE: - Audio- Mix 2
					Mute 1  cmdID= 37684 "
		::= { iqudc00CmdEntry 37684 }


	iqudc00Mix2GainGain2 OBJECT-TYPE
		SYNTAX		INTEGER
		MAX-ACCESS		read-write
		STATUS			current
		DESCRIPTION
				"TYPE: - Number
				 PAGE: - Audio- Mix 2
					Gain 2  cmdID= 37645  min= -360  max= 120  step= 1  format= %0.1f dB  div_scale= 10
					Min = -36.0 dB  Max = 12.0 dB  Step = 0.1 dB "
		::= { iqudc00CmdEntry 37645 }


	iqudc00Mix2GainMute2 OBJECT-TYPE
		SYNTAX		INTEGER { disable(0), enable(1) }
		MAX-ACCESS		read-write
		STATUS			current
		DESCRIPTION
				"TYPE: - Checkbox
				 PAGE: - Audio- Mix 2
					Mute 2  cmdID= 37685 "
		::= { iqudc00CmdEntry 37685 }


	iqudc00Mix2GainGain3 OBJECT-TYPE
		SYNTAX		INTEGER
		MAX-ACCESS		read-write
		STATUS			current
		DESCRIPTION
				"TYPE: - Number
				 PAGE: - Audio- Mix 2
					Gain 3  cmdID= 37646  min= -360  max= 120  step= 1  format= %0.1f dB  div_scale= 10
					Min = -36.0 dB  Max = 12.0 dB  Step = 0.1 dB "
		::= { iqudc00CmdEntry 37646 }


	iqudc00Mix2GainMute3 OBJECT-TYPE
		SYNTAX		INTEGER { disable(0), enable(1) }
		MAX-ACCESS		read-write
		STATUS			current
		DESCRIPTION
				"TYPE: - Checkbox
				 PAGE: - Audio- Mix 2
					Mute 3  cmdID= 37686 "
		::= { iqudc00CmdEntry 37686 }


	iqudc00Mix2GainGain4 OBJECT-TYPE
		SYNTAX		INTEGER
		MAX-ACCESS		read-write
		STATUS			current
		DESCRIPTION
				"TYPE: - Number
				 PAGE: - Audio- Mix 2
					Gain 4  cmdID= 37647  min= -360  max= 120  step= 1  format= %0.1f dB  div_scale= 10
					Min = -36.0 dB  Max = 12.0 dB  Step = 0.1 dB "
		::= { iqudc00CmdEntry 37647 }


	iqudc00Mix2GainMute4 OBJECT-TYPE
		SYNTAX		INTEGER { disable(0), enable(1) }
		MAX-ACCESS		read-write
		STATUS			current
		DESCRIPTION
				"TYPE: - Checkbox
				 PAGE: - Audio- Mix 2
					Mute 4  cmdID= 37687 "
		::= { iqudc00CmdEntry 37687 }


	iqudc00Mix2GainInp1Clip OBJECT-TYPE
		SYNTAX		RollCallString
		MAX-ACCESS		read-only
		STATUS			current
		DESCRIPTION
				"TYPE: - Display
				 PAGE: - Audio- Mix 2
					Inp1 Clip  cmdID= 37764  format=   "
		::= { iqudc00CmdEntry 37764 }


	iqudc00Mix2GainInp2Clip OBJECT-TYPE
		SYNTAX		RollCallString
		MAX-ACCESS		read-only
		STATUS			current
		DESCRIPTION
				"TYPE: - Display
				 PAGE: - Audio- Mix 2
					Inp2 Clip  cmdID= 37765  format=   "
		::= { iqudc00CmdEntry 37765 }


	iqudc00Mix2GainInp3Clip OBJECT-TYPE
		SYNTAX		RollCallString
		MAX-ACCESS		read-only
		STATUS			current
		DESCRIPTION
				"TYPE: - Display
				 PAGE: - Audio- Mix 2
					Inp3 Clip  cmdID= 37766  format=   "
		::= { iqudc00CmdEntry 37766 }


	iqudc00Mix2GainInp4Clip OBJECT-TYPE
		SYNTAX		RollCallString
		MAX-ACCESS		read-only
		STATUS			current
		DESCRIPTION
				"TYPE: - Display
				 PAGE: - Audio- Mix 2
					Inp4 Clip  cmdID= 37767  format=   "
		::= { iqudc00CmdEntry 37767 }


	iqudc00Mix2GainOPClip OBJECT-TYPE
		SYNTAX		RollCallString
		MAX-ACCESS		read-only
		STATUS			current
		DESCRIPTION
				"TYPE: - Display
				 PAGE: - Audio- Mix 2
					O/P Clip  cmdID= 37801  format=   "
		::= { iqudc00CmdEntry 37801 }


	iqudc00Mix3RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 1  cmdID= 37608
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37608 }


	iqudc00Mix3RoutingInvert1 OBJECT-TYPE
		SYNTAX		INTEGER { disable(0), enable(1) }
		MAX-ACCESS		read-write
		STATUS			current
		DESCRIPTION
				"TYPE: - Checkbox
				 PAGE: - Audio- Mix 3
					Invert 1  cmdID= 37728 "
		::= { iqudc00CmdEntry 37728 }


	iqudc00Mix3RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 2  cmdID= 37609
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37609 }


	iqudc00Mix3RoutingInvert2 OBJECT-TYPE
		SYNTAX		INTEGER { disable(0), enable(1) }
		MAX-ACCESS		read-write
		STATUS			current
		DESCRIPTION
				"TYPE: - Checkbox
				 PAGE: - Audio- Mix 3
					Invert 2  cmdID= 37729 "
		::= { iqudc00CmdEntry 37729 }


	iqudc00Mix3RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 3  cmdID= 37610
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37610 }


	iqudc00Mix3RoutingInvert3 OBJECT-TYPE
		SYNTAX		INTEGER { disable(0), enable(1) }
		MAX-ACCESS		read-write
		STATUS			current
		DESCRIPTION
				"TYPE: - Checkbox
				 PAGE: - Audio- Mix 3
					Invert 3  cmdID= 37730 "
		::= { iqudc00CmdEntry 37730 }


	iqudc00Mix3RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 3
					Source 4  cmdID= 37611
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37611 }


	iqudc00Mix3RoutingInvert4 OBJECT-TYPE
		SYNTAX		INTEGER { disable(0), enable(1) }
		MAX-ACCESS		read-write
		STATUS			current
		DESCRIPTION
				"TYPE: - Checkbox
				 PAGE: - Audio- Mix 3
					Invert 4  cmdID= 37731 "
		::= { iqudc00CmdEntry 37731 }


	iqudc00Mix3GainGain1 OBJECT-TYPE
		SYNTAX		INTEGER
		MAX-ACCESS		read-write
		STATUS			current
		DESCRIPTION
				"TYPE: - Number
				 PAGE: - Audio- Mix 3
					Gain 1  cmdID= 37648  min= -360  max= 120  step= 1  format= %0.1f dB  div_scale= 10
					Min = -36.0 dB  Max = 12.0 dB  Step = 0.1 dB "
		::= { iqudc00CmdEntry 37648 }


	iqudc00Mix3GainMute1 OBJECT-TYPE
		SYNTAX		INTEGER { disable(0), enable(1) }
		MAX-ACCESS		read-write
		STATUS			current
		DESCRIPTION
				"TYPE: - Checkbox
				 PAGE: - Audio- Mix 3
					Mute 1  cmdID= 37688 "
		::= { iqudc00CmdEntry 37688 }


	iqudc00Mix3GainGain2 OBJECT-TYPE
		SYNTAX		INTEGER
		MAX-ACCESS		read-write
		STATUS			current
		DESCRIPTION
				"TYPE: - Number
				 PAGE: - Audio- Mix 3
					Gain 2  cmdID= 37649  min= -360  max= 120  step= 1  format= %0.1f dB  div_scale= 10
					Min = -36.0 dB  Max = 12.0 dB  Step = 0.1 dB "
		::= { iqudc00CmdEntry 37649 }


	iqudc00Mix3GainMute2 OBJECT-TYPE
		SYNTAX		INTEGER { disable(0), enable(1) }
		MAX-ACCESS		read-write
		STATUS			current
		DESCRIPTION
				"TYPE: - Checkbox
				 PAGE: - Audio- Mix 3
					Mute 2  cmdID= 37689 "
		::= { iqudc00CmdEntry 37689 }


	iqudc00Mix3GainGain3 OBJECT-TYPE
		SYNTAX		INTEGER
		MAX-ACCESS		read-write
		STATUS			current
		DESCRIPTION
				"TYPE: - Number
				 PAGE: - Audio- Mix 3
					Gain 3  cmdID= 37650  min= -360  max= 120  step= 1  format= %0.1f dB  div_scale= 10
					Min = -36.0 dB  Max = 12.0 dB  Step = 0.1 dB "
		::= { iqudc00CmdEntry 37650 }


	iqudc00Mix3GainMute3 OBJECT-TYPE
		SYNTAX		INTEGER { disable(0), enable(1) }
		MAX-ACCESS		read-write
		STATUS			current
		DESCRIPTION
				"TYPE: - Checkbox
				 PAGE: - Audio- Mix 3
					Mute 3  cmdID= 37690 "
		::= { iqudc00CmdEntry 37690 }


	iqudc00Mix3GainGain4 OBJECT-TYPE
		SYNTAX		INTEGER
		MAX-ACCESS		read-write
		STATUS			current
		DESCRIPTION
				"TYPE: - Number
				 PAGE: - Audio- Mix 3
					Gain 4  cmdID= 37651  min= -360  max= 120  step= 1  format= %0.1f dB  div_scale= 10
					Min = -36.0 dB  Max = 12.0 dB  Step = 0.1 dB "
		::= { iqudc00CmdEntry 37651 }


	iqudc00Mix3GainMute4 OBJECT-TYPE
		SYNTAX		INTEGER { disable(0), enable(1) }
		MAX-ACCESS		read-write
		STATUS			current
		DESCRIPTION
				"TYPE: - Checkbox
				 PAGE: - Audio- Mix 3
					Mute 4  cmdID= 37691 "
		::= { iqudc00CmdEntry 37691 }


	iqudc00Mix3GainInp1Clip OBJECT-TYPE
		SYNTAX		RollCallString
		MAX-ACCESS		read-only
		STATUS			current
		DESCRIPTION
				"TYPE: - Display
				 PAGE: - Audio- Mix 3
					Inp1 Clip  cmdID= 37768  format=   "
		::= { iqudc00CmdEntry 37768 }


	iqudc00Mix3GainInp2Clip OBJECT-TYPE
		SYNTAX		RollCallString
		MAX-ACCESS		read-only
		STATUS			current
		DESCRIPTION
				"TYPE: - Display
				 PAGE: - Audio- Mix 3
					Inp2 Clip  cmdID= 37769  format=   "
		::= { iqudc00CmdEntry 37769 }


	iqudc00Mix3GainInp3Clip OBJECT-TYPE
		SYNTAX		RollCallString
		MAX-ACCESS		read-only
		STATUS			current
		DESCRIPTION
				"TYPE: - Display
				 PAGE: - Audio- Mix 3
					Inp3 Clip  cmdID= 37770  format=   "
		::= { iqudc00CmdEntry 37770 }


	iqudc00Mix3GainInp4Clip OBJECT-TYPE
		SYNTAX		RollCallString
		MAX-ACCESS		read-only
		STATUS			current
		DESCRIPTION
				"TYPE: - Display
				 PAGE: - Audio- Mix 3
					Inp4 Clip  cmdID= 37771  format=   "
		::= { iqudc00CmdEntry 37771 }


	iqudc00Mix3GainOPClip OBJECT-TYPE
		SYNTAX		RollCallString
		MAX-ACCESS		read-only
		STATUS			current
		DESCRIPTION
				"TYPE: - Display
				 PAGE: - Audio- Mix 3
					O/P Clip  cmdID= 37802  format=   "
		::= { iqudc00CmdEntry 37802 }


	iqudc00Mix4RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 1  cmdID= 37612
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37612 }


	iqudc00Mix4RoutingInvert1 OBJECT-TYPE
		SYNTAX		INTEGER { disable(0), enable(1) }
		MAX-ACCESS		read-write
		STATUS			current
		DESCRIPTION
				"TYPE: - Checkbox
				 PAGE: - Audio- Mix 4
					Invert 1  cmdID= 37732 "
		::= { iqudc00CmdEntry 37732 }


	iqudc00Mix4RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 2  cmdID= 37613
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37613 }


	iqudc00Mix4RoutingInvert2 OBJECT-TYPE
		SYNTAX		INTEGER { disable(0), enable(1) }
		MAX-ACCESS		read-write
		STATUS			current
		DESCRIPTION
				"TYPE: - Checkbox
				 PAGE: - Audio- Mix 4
					Invert 2  cmdID= 37733 "
		::= { iqudc00CmdEntry 37733 }


	iqudc00Mix4RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 3  cmdID= 37614
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37614 }


	iqudc00Mix4RoutingInvert3 OBJECT-TYPE
		SYNTAX		INTEGER { disable(0), enable(1) }
		MAX-ACCESS		read-write
		STATUS			current
		DESCRIPTION
				"TYPE: - Checkbox
				 PAGE: - Audio- Mix 4
					Invert 3  cmdID= 37734 "
		::= { iqudc00CmdEntry 37734 }


	iqudc00Mix4RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Audio- Mix 4
					Source 4  cmdID= 37615
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqudc00CmdEntry 37615 }


	iqudc00Mix4RoutingInvert4 OBJECT-TYPE
		SYNTAX		INTEGER { disable(0), enable(1) }
		MAX-ACCESS		read-write
		STATUS			current
		DESCRIPTION
				"TYPE: - Checkbox
				 PAGE: - Audio- Mix 4
					Invert 4  cmdID= 37735 "
		::= { iqudc00CmdEntry 37735 }


	iqudc00Mix4GainGain1 OBJECT-TYPE
		SYNTAX		INTEGER
		MAX-ACCESS		read-write
		STATUS			current
		DESCRIPTION
				"TYPE: - Number
				 PAGE: - Audio- Mix 4
					Gain 1  cmdID= 37652  min= -360  max= 120  step= 1  format= %0.1f dB  div_scale= 10
					Min = -36.0 dB  Max = 12.0 dB  Step = 0.1 dB "
		::= { iqudc00CmdEntry 37652 }


	iqudc00Mix4GainMute1 OBJECT-TYPE
		SYNTAX		INTEGER { disable(0), enable(1) }
		MAX-ACCESS		read-write
		STATUS			current
		DESCRIPTION
				"TYPE: - Checkbox
				 PAGE: - Audio- Mix 4
					Mute 1  cmdID= 37692 "
		::= { iqudc00CmdEntry 37692 }


	iqudc00Mix4GainGain2 OBJECT-TYPE
		SYNTAX		INTEGER
		MAX-ACCESS		read-write
		STATUS			current
		DESCRIPTION
				"TYPE: - Number
				 PAGE: - Audio- Mix 4
					Gain 2  cmdID= 37653  min= -360  max= 120  step= 1  format= %0.1f dB  div_scale= 10
					Min = -36.0 dB  Max = 12.0 dB  Step = 0.1 dB "
		::= { iqudc00CmdEntry 37653 }


	iqudc00Mix4GainMute2 OBJECT-TYPE
		SYNTAX		INTEGER { disable(0), enable(1) }
		MAX-ACCESS		read-write
		STATUS			current
		DESCRIPTION
				"TYPE: - Checkbox
				 PAGE: - Audio- Mix 4
					Mute 2  cmdID= 37693 "
		::= { iqudc00CmdEntry 37693 }


	iqudc00Mix4GainGain3 OBJECT-TYPE
		SYNTAX		INTEGER
		MAX-ACCESS		read-write
		STATUS			current
		DESCRIPTION
				"TYPE: - Number
				 PAGE: - Audio- Mix 4
					Gain 3  cmdID= 37654  min= -360  max= 120  step= 1  format= %0.1f dB  div_scale= 10
					Min = -36.0 dB  Max = 12.0 dB  Step = 0.1 dB "
		::= { iqudc00CmdEntry 37654 }


	iqudc00Mix4GainMute3 OBJECT-TYPE
		SYNTAX		INTEGER { disable(0), enable(1) }
		MAX-ACCESS		read-write
		STATUS			current
		DESCRIPTION
				"TYPE: - Checkbox
				 PAGE: - Audio- Mix 4
					Mute 3  cmdID= 37694 "
		::= { iqudc00CmdEntry 37694 }


	iqudc00Mix4GainGain4 OBJECT-TYPE
		SYNTAX		INTEGER
		MAX-ACCESS		read-write
		STATUS			current
		DESCRIPTION
				"TYPE: - Number
				 PAGE: - Audio- Mix 4
					Gain 4  cmdID= 37655  min= -360  max= 120  step= 1  format= %0.1f dB  div_scale= 10
					Min = -36.0 dB  Max = 12.0 dB  Step = 0.1 dB "
		::= { iqudc00CmdEntry 37655 }


	iqudc00Mix4GainMute4 OBJECT-TYPE
		SYNTAX		INTEGER { disable(0), enable(1) }
		MAX-ACCESS		read-write
		STATUS			current
		DESCRIPTION
				"TYPE: - Checkbox
				 PAGE: - Audio- Mix 4
					Mute 4  cmdID= 37695 "
		::= { iqudc00CmdEntry 37695 }


	iqudc00Mix4GainInp1Clip OBJECT-TYPE
		SYNTAX		RollCallString
		MAX-ACCESS		read-only
		STATUS			current
		DESCRIPTION
				"TYPE: - Display
				 PAGE: - Audio- Mix 4
					Inp1 Clip  cmdID= 37772  format=   "
		::= { iqudc00CmdEntry 37772 }


	iqudc00Mix4GainInp2Clip OBJECT-TYPE
		SYNTAX		RollCallString
		MAX-ACCESS		read-only
		STATUS			current
		DESCRIPTION
				"TYPE: - Display
				 PAGE: - Audio- Mix 4
					Inp2 Clip  cmdID= 37773  format=   "
		::= { iqudc00CmdEntry 37773 }


	iqudc00Mix4GainInp3Clip OBJECT-TYPE
		SYNTAX		RollCallString
		MAX-ACCESS		read-only
		STATUS			current
		DESCRIPTION
				"TYPE: - Display
				 PAGE: - Audio- Mix 4
					Inp3 Clip  cmdID= 37774  format=   "
		::= { iqudc00CmdEntry 37774 }


	iqudc00Mix4GainInp4Clip OBJECT-TYPE
		SYNTAX		RollCallString
		MAX-ACCESS		read-only
		STATUS			current
		DESCRIPTION
				"TYPE: - Display
				 PAGE: - Audio- Mix 4
					Inp4 Clip  cmdID= 37775  format=   "
		::= { iqudc00CmdEntry 37775 }


	iqudc00Mix4GainOPClip OBJECT-TYPE
		SYNTAX		RollCallString
		MAX-ACCESS		read-only
		STATUS			current
		DESCRIPTION
				"TYPE: - Display
				 PAGE: - Audio- Mix 4
					O/P Clip  cmdID= 37803  format=   "
		::= { iqudc00CmdEntry 37803 }


	iqudc00AudioDolbyETimingSelAudioPair OBJECT-TYPE
		SYNTAX		INTEGER
		MAX-ACCESS		read-write
		STATUS			current
		DESCRIPTION
				"TYPE: - Number
				 PAGE: - Audio
					Sel Audio Pair  cmdID= 38650  min= 1  max= 8  step= 1  format= %0.0f  div_scale= 1
					Min = 1  Max = 8  Step = 1 "
		::= { iqudc00CmdEntry 38650 }


	iqudc00AudioDolbyETimingRelativeTiming OBJECT-TYPE
		SYNTAX		RollCallString
		MAX-ACCESS		read-only
		STATUS			current
		DESCRIPTION
				"TYPE: - Display
				 PAGE: - Audio
					Relative Timing  cmdID= 38653  format=   "
		::= { iqudc00CmdEntry 38653 }


	iqudc00AudioDolbyETimingLineNumber OBJECT-TYPE
		SYNTAX		RollCallString
		MAX-ACCESS		read-only
		STATUS			current
		DESCRIPTION
				"TYPE: - Display
				 PAGE: - Audio
					Line Number  cmdID= 38651  format=   "
		::= { iqudc00CmdEntry 38651 }


	iqudc00AudioDolbyETimingStatus OBJECT-TYPE
		SYNTAX		RollCallString
		MAX-ACCESS		read-only
		STATUS			current
		DESCRIPTION
				"TYPE: - Display
				 PAGE: - Audio
					Status  cmdID= 38652  format=   "
		::= { iqudc00CmdEntry 38652 }


	iqudc00AudioDolbyETimingError OBJECT-TYPE
		SYNTAX		RollCallString
		MAX-ACCESS		read-only
		STATUS			current
		DESCRIPTION
				"TYPE: - Display
				 PAGE: - Audio
					Error  cmdID= 38654  format=   "
		::= { iqudc00CmdEntry 38654 }


	iqudc00UtilsPatternsPatternEnable OBJECT-TYPE
		SYNTAX		INTEGER { disable(0), enable(1) }
		MAX-ACCESS		read-write
		STATUS			current
		DESCRIPTION
				"TYPE: - Checkbox
				 PAGE: - Utils
					Pattern Enable  cmdID= 33038 "
		::= { iqudc00CmdEntry 33038 }


	iqudc00UtilsPatternsScrollPattern OBJECT-TYPE
		SYNTAX		INTEGER { disable(0), enable(1) }
		MAX-ACCESS		read-write
		STATUS			current
		DESCRIPTION
				"TYPE: - Checkbox
				 PAGE: - Utils
					Scroll Pattern  cmdID= 33040 "
		::= { iqudc00CmdEntry 33040 }


	iqudc00UtilsPatternsPatternType OBJECT-TYPE
		SYNTAX		INTEGER {
							val_100_Color_Bars(1),
							val_75_Color_Bars(2),
							val_SMPTE_Bars(3),
							val_Tartan_Bars(4),
							val_Pluge(5),
							val_Ramp(6),
							val_Sweep(7),
							val_Pulse_Bar(8),
							val_Burst(9)
							}
		MAX-ACCESS		read-write
		STATUS			current
		DESCRIPTION
				"TYPE: - RadiobuttonList
				 PAGE: - Utils
					Pattern Type  cmdID= 33039
					100% Color Bars  value= 1
					75% Color Bars  value= 2
					SMPTE Bars  value= 3
					Tartan Bars  value= 4
					Pluge  value= 5
					Ramp  value= 6
					Sweep  value= 7
					Pulse & Bar  value= 8
					Burst  value= 9  "
		::= { iqudc00CmdEntry 33039 }


	iqudc00UtilsClosedCaptionEnable OBJECT-TYPE
		SYNTAX		INTEGER { disable(0), enable(1) }
		MAX-ACCESS		read-write
		STATUS			current
		DESCRIPTION
				"TYPE: - Checkbox
				 PAGE: - Utils
					Enable  cmdID= 8249 "
		::= { iqudc00CmdEntry 8249 }


	iqudc00UtilsClosedCaptionHDCaptionLine OBJECT-TYPE
		SYNTAX		INTEGER
		MAX-ACCESS		read-write
		STATUS			current
		DESCRIPTION
				"TYPE: - Number
				 PAGE: - Utils
					HD Caption Line  cmdID= 8252  min= 5  max= 22  step= 1  format= %0.0f line  div_scale= 1
					Min = 5 line  Max = 22 line  Step = 1 line "
		::= { iqudc00CmdEntry 8252 }


	iqudc00UtilsClosedCaptionHDFollowIPLine OBJECT-TYPE
		SYNTAX		INTEGER { disable(0), enable(1) }
		MAX-ACCESS		read-write
		STATUS			current
		DESCRIPTION
				"TYPE: - Checkbox
				 PAGE: - Utils
					HD Follow I/P Line  cmdID= 8134 "
		::= { iqudc00CmdEntry 8134 }


	iqudc00UtilsClosedCaptionSDCaptionIPLine OBJECT-TYPE
		SYNTAX		INTEGER
		MAX-ACCESS		read-write
		STATUS			current
		DESCRIPTION
				"TYPE: - Number
				 PAGE: - Utils
					SD Caption I/P Line  cmdID= 8254  min= 7  max= 23  step= 1  format= %0.0f line  div_scale= 1
					Min = 7 line  Max = 23 line  Step = 1 line "
		::= { iqudc00CmdEntry 8254 }


	iqudc00UtilsClosedCaptionSDCaptionOutLine OBJECT-TYPE
		SYNTAX		INTEGER
		MAX-ACCESS		read-write
		STATUS			current
		DESCRIPTION
				"TYPE: - Number
				 PAGE: - Utils
					SD Caption Out Line  cmdID= 8253  min= 7  max= 23  step= 1  format= %0.0f line  div_scale= 1
					Min = 7 line  Max = 23 line  Step = 1 line "
		::= { iqudc00CmdEntry 8253 }


	iqudc00UtilsClosedCaptionSDFollowIPLine OBJECT-TYPE
		SYNTAX		INTEGER { disable(0), enable(1) }
		MAX-ACCESS		read-write
		STATUS			current
		DESCRIPTION
				"TYPE: - Checkbox
				 PAGE: - Utils
					SD Follow I/P Line  cmdID= 8135 "
		::= { iqudc00CmdEntry 8135 }


	iqudc00UtilsMonochrome OBJECT-TYPE
		SYNTAX		INTEGER { disable(0), enable(1) }
		MAX-ACCESS		read-write
		STATUS			current
		DESCRIPTION
				"TYPE: - Checkbox
				 PAGE: - Utils
					Monochrome  cmdID= 33034 "
		::= { iqudc00CmdEntry 33034 }


	iqudc00UtilsMonochromeMonochromeType OBJECT-TYPE
		SYNTAX		INTEGER {
							val_Y_only(0),
							val_C_only(1)
							}
		MAX-ACCESS		read-write
		STATUS			current
		DESCRIPTION
				"TYPE: - RadiobuttonList
				 PAGE: - Utils
					Monochrome Type  cmdID= 33035
					Y only  value= 0
					C only  value= 1  "
		::= { iqudc00CmdEntry 33035 }


	iqudc00GPIGPI1GPIO1Mode OBJECT-TYPE
		SYNTAX		INTEGER {
							val_Unused(0),
							val_Input_GPI1(1),
							val_Output_GPO1(2)
							}
		MAX-ACCESS		read-write
		STATUS			current
		DESCRIPTION
				"TYPE: - RadiobuttonList
				 PAGE: - GPI
					GPI/O 1 Mode  cmdID= 36120
					Unused  value= 0
					Input (GPI1)  value= 1
					Output (GPO1)  value= 2  "
		::= { iqudc00CmdEntry 36120 }


	iqudc00GPIGPI1GPI1ipSelect OBJECT-TYPE
		SYNTAX		INTEGER {
							val_Freeze(0),
							val_Pattern(1),
							val_Black(2),
							val_MonoChrm_Y_Only(4),
							val_MonoChrm_CbCr_Only(5),
							val_Use_I_P_Ref(6),
							val_Use_Ext_Ref(7),
							val_Select_Inp_1(50),
							val_Select_Inp_2(51),
							val_Select_Input(8),
							val_Select_Backup(9),
							val_1(100),
							val_User_Memory_2(101),
							val_User_Memory_3(102),
							val_User_Memory_4(103),
							val_User_Memory_5(104),
							val_User_Memory_6(105),
							val_User_Memory_7(106),
							val_User_Memory_8(107),
							val_User_Memory_9(108),
							val_User_Memory_10(109),
							val_User_Memory_11(110),
							val_User_Memory_12(111),
							val_User_Memory_13(112),
							val_User_Memory_14(113),
							val_User_Memory_15(114),
							val_User_Memory_16(115)
							}
		MAX-ACCESS		read-write
		STATUS			current
		DESCRIPTION
				"TYPE: - RadiobuttonList
				 PAGE: - GPI
					GPI 1-i/p Select  cmdID= 36121
					Freeze  value= 0
					Pattern  value= 1
					Black  value= 2
					MonoChrm Y Only  value= 4
					MonoChrm CbCr Only  value= 5
					Use I/P Ref  value= 6
					Use Ext Ref  value= 7
					Select Inp 1  value= 50
					Select Inp 2  value= 51
					Select Input  value= 8
					Select Backup  value= 9
					 1  value= 100
					User Memory 2  value= 101
					User Memory 3  value= 102
					User Memory 4  value= 103
					User Memory 5  value= 104
					User Memory 6  value= 105
					User Memory 7  value= 106
					User Memory 8  value= 107
					User Memory 9  value= 108
					User Memory 10  value= 109
					User Memory 11  value= 110
					User Memory 12  value= 111
					User Memory 13  value= 112
					User Memory 14  value= 113
					User Memory 15  value= 114
					User Memory 16  value= 115  "
		::= { iqudc00CmdEntry 36121 }


	iqudc00GPIGPI1GPO1opSelect OBJECT-TYPE
		SYNTAX		INTEGER {
							val_Input_1_OK(50),
							val_Input_2_OK(51),
							val_Reference_OK(0),
							val_Freeze(1),
							val_Pattern(2),
							val_Black(3),
							val_Monochrome(4)
							}
		MAX-ACCESS		read-write
		STATUS			current
		DESCRIPTION
				"TYPE: - RadiobuttonList
				 PAGE: - GPI
					GPO 1-o/p Select  cmdID= 36122
					Input 1 OK  value= 50
					Input 2 OK  value= 51
					Reference OK  value= 0
					Freeze  value= 1
					Pattern  value= 2
					Black  value= 3
					Monochrome  value= 4  "
		::= { iqudc00CmdEntry 36122 }


	iqudc00GPIGPI1InvertGPIO1 OBJECT-TYPE
		SYNTAX		INTEGER { disable(0), enable(1) }
		MAX-ACCESS		read-write
		STATUS			current
		DESCRIPTION
				"TYPE: - Checkbox
				 PAGE: - GPI
					Invert GPIO 1  cmdID= 36123 "
		::= { iqudc00CmdEntry 36123 }


	iqudc00GPIGPI2GPIO2Mode OBJECT-TYPE
		SYNTAX		INTEGER {
							val_Unused(0),
							val_Input_GPI2(1),
							val_Output_GPO2(2)
							}
		MAX-ACCESS		read-write
		STATUS			current
		DESCRIPTION
				"TYPE: - RadiobuttonList
				 PAGE: - GPI
					GPI/O 2 Mode  cmdID= 36130
					Unused  value= 0
					Input (GPI2)  value= 1
					Output (GPO2)  value= 2  "
		::= { iqudc00CmdEntry 36130 }


	iqudc00GPIGPI2GPI2ipSelect OBJECT-TYPE
		SYNTAX		INTEGER {
							val_Freeze(0),
							val_Pattern(1),
							val_Black(2),
							val_MonoChrm_Y_Only(4),
							val_MonoChrm_CbCr_Only(5),
							val_Use_I_P_Ref(6),
							val_Use_Ext_Ref(7),
							val_Select_Inp_1(50),
							val_Select_Inp_2(51),
							val_Select_Input(8),
							val_Select_Backup(9),
							val_1(100),
							val_User_Memory_2(101),
							val_User_Memory_3(102),
							val_User_Memory_4(103),
							val_User_Memory_5(104),
							val_User_Memory_6(105),
							val_User_Memory_7(106),
							val_User_Memory_8(107),
							val_User_Memory_9(108),
							val_User_Memory_10(109),
							val_User_Memory_11(110),
							val_User_Memory_12(111),
							val_User_Memory_13(112),
							val_User_Memory_14(113),
							val_User_Memory_15(114),
							val_User_Memory_16(115)
							}
		MAX-ACCESS		read-write
		STATUS			current
		DESCRIPTION
				"TYPE: - RadiobuttonList
				 PAGE: - GPI
					GPI 2-i/p Select  cmdID= 36131
					Freeze  value= 0
					Pattern  value= 1
					Black  value= 2
					MonoChrm Y Only  value= 4
					MonoChrm CbCr Only  value= 5
					Use I/P Ref  value= 6
					Use Ext Ref  value= 7
					Select Inp 1  value= 50
					Select Inp 2  value= 51
					Select Input  value= 8
					Select Backup  value= 9
					 1  value= 100
					User Memory 2  value= 101
					User Memory 3  value= 102
					User Memory 4  value= 103
					User Memory 5  value= 104
					User Memory 6  value= 105
					User Memory 7  value= 106
					User Memory 8  value= 107
					User Memory 9  value= 108
					User Memory 10  value= 109
					User Memory 11  value= 110
					User Memory 12  value= 111
					User Memory 13  value= 112
					User Memory 14  value= 113
					User Memory 15  value= 114
					User Memory 16  value= 115  "
		::= { iqudc00CmdEntry 36131 }


	iqudc00GPIGPI2GPO2opSelect OBJECT-TYPE
		SYNTAX		INTEGER {
							val_Input_1_OK(50),
							val_Input_2_OK(51),
							val_Reference_OK(0),
							val_Freeze(1),
							val_Pattern(2),
							val_Black(3),
							val_Monochrome(4)
							}
		MAX-ACCESS		read-write
		STATUS			current
		DESCRIPTION
				"TYPE: - RadiobuttonList
				 PAGE: - GPI
					GPO 2-o/p Select  cmdID= 36132
					Input 1 OK  value= 50
					Input 2 OK  value= 51
					Reference OK  value= 0
					Freeze  value= 1
					Pattern  value= 2
					Black  value= 3
					Monochrome  value= 4  "
		::= { iqudc00CmdEntry 36132 }


	iqudc00GPIGPI2InvertGPIO2 OBJECT-TYPE
		SYNTAX		INTEGER { disable(0), enable(1) }
		MAX-ACCESS		read-write
		STATUS			current
		DESCRIPTION
				"TYPE: - Checkbox
				 PAGE: - GPI
					Invert GPIO 2  cmdID= 36133 "
		::= { iqudc00CmdEntry 36133 }


	iqudc00GPIGPIPWMDelayTimerTimerSource OBJECT-TYPE
		SYNTAX		INTEGER {
							val_Off(0),
							val_GPI_1(1),
							val_GPI_2(2)
							}
		MAX-ACCESS		read-write
		STATUS			current
		DESCRIPTION
				"TYPE: - RadiobuttonList
				 PAGE: - GPI
					Timer Source  cmdID= 36124
					Off  value= 0
					GPI 1  value= 1
					GPI 2  value= 2  "
		::= { iqudc00CmdEntry 36124 }


	iqudc00GPIGPIPWMDelayTimerActiveHigh OBJECT-TYPE
		SYNTAX		INTEGER { disable(0), enable(1) }
		MAX-ACCESS		read-write
		STATUS			current
		DESCRIPTION
				"TYPE: - Checkbox
				 PAGE: - GPI
					Active High  cmdID= 36125 "
		::= { iqudc00CmdEntry 36125 }


	iqudc00MemoriesRecallMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Recall Memory  cmdID= 37100
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqudc00CmdEntry 37100 }


	iqudc00MemoriesSelMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqudc00CmdEntry 37101 }


	iqudc00MemoriesSaveMemory OBJECT-TYPE
		SYNTAX		INTEGER { noAction(0),val_Save_Memory(1) }
		MAX-ACCESS		read-write
		STATUS			current
		DESCRIPTION
				"TYPE: - Button
				 PAGE: - Memories
					Save Memory  cmdID= 37102  value= 1  "
		::= { iqudc00CmdEntry 37102 }


	iqudc00MemoriesMemoryNameChangeName OBJECT-TYPE
		SYNTAX		RollCallString
		MAX-ACCESS		read-write
		STATUS			current
		DESCRIPTION
				"TYPE: - Editstring
				 PAGE: - Memories
					Change Name  cmdID= 37103  "
		::= { iqudc00CmdEntry 37103 }


	iqudc00MemoriesLastDisplayMemory OBJECT-TYPE
		SYNTAX		RollCallString
		MAX-ACCESS		read-only
		STATUS			current
		DESCRIPTION
				"TYPE: - Display
				 PAGE: - Memories
					Last Display Memory  cmdID= 37104  format=   "
		::= { iqudc00CmdEntry 37104 }


	iqudc00RollCallRollTrackDisableAll OBJECT-TYPE
		SYNTAX		INTEGER { disable(0), enable(1) }
		MAX-ACCESS		read-write
		STATUS			current
		DESCRIPTION
				"TYPE: - Checkbox
					Disable All  cmdID= 36104 "
		::= { iqudc00CmdEntry 36104 }


	iqudc00RollCallRollTrackIndex OBJECT-TYPE
		SYNTAX		INTEGER
		MAX-ACCESS		read-write
		STATUS			current
		DESCRIPTION
				"TYPE: - BarGraph
					Index  cmdID= 36100  min= 1  max= 50   step= 1  format= %0.0f  div_scale= 1
					Min = 1  Max = 50  Step = 1 "
		::= { iqudc00CmdEntry 36100 }


	iqudc00RollCallRollTrackSource OBJECT-TYPE
		SYNTAX		INTEGER {
							val_Unused(-1),
							val_Video_Delay(0),
							val_Input_Present(1),
							val_Input_Loss(2),
							val_Reference_OK(3),
							val_Reference_Lost(4),
							val_O_p_Freeze(5),
							val_O_p_UnFreeze(6),
							val_GPI_1_High(24),
							val_GPI_1_Low(25),
							val_GPI_1_InActive(23),
							val_GPI_2_High(27),
							val_GPI_2_Low(28),
							val_GPI_2_InActive(26),
							val_De_embed_1_Present(7),
							val_De_embed_1_Lost(8),
							val_De_embed_2_Present(9),
							val_De_embed_2_Lost(10),
							val_De_embed_3_Present(11),
							val_De_embed_3_Lost(12),
							val_De_embed_4_Present(13),
							val_De_embed_4_Lost(14),
							val_De_embed_5_Present(15),
							val_De_embed_5_Lost(16),
							val_De_embed_6_Present(17),
							val_De_embed_6_Lost(18),
							val_De_embed_7_Present(19),
							val_De_embed_7_Lost(20),
							val_De_embed_8_Present(21),
							val_De_embed_8_Lost(22),
							val_Input_Std_525(29),
							val_Input_Std_625(30),
							val_Input_Std_720_59(31),
							val_Input_Std_720_50(32),
							val_Input_Std_1080_29(33),
							val_Input_Std_1080_25(34),
							val_Input_4_3(35),
							val_Input_16_9(36),
							val_AFD_Coded_Frame(37),
							val_AFD_4_3(38),
							val_AFD_16_9(39),
							val_AFD_14_9(40),
							val_AFD_reserved(41),
							val_AFD_4_3_SP_14_9(42),
							val_AFD_16_9_SP_14_9(43),
							val_AFD_16_9_SP_4_3(44),
							val_AFD_box_16_9_top(45),
							val_AFD_box_14_9_top(46),
							val_AFD_box_16_9_ctr(47),
							val_4_3_Coded_Frame(48),
							val_4_3_4_3(49),
							val_4_3_16_9(50),
							val_4_3_14_9(51),
							val_4_3_reserved(52),
							val_4_3_4_3_SP_14_9(53),
							val_4_3_16_9_SP_14_9(54),
							val_4_3_16_9_SP_4_3(55),
							val_4_3_box_16_9_top(56),
							val_4_3_box_14_9_top(57),
							val_4_3_box_16_9_ctr(58),
							val_4_3_Unknown(59),
							val_16_9_Coded_Frame(60),
							val_16_9_4_3(61),
							val_16_9_16_9(62),
							val_16_9_14_9(63),
							val_16_9_reserved(64),
							val_16_9_4_3_SP_14_9(65),
							val_16_9_16_9_SP_14_9(66),
							val_16_9_16_9_SP_4_3(67),
							val_16_9_box_16_9_top(68),
							val_16_9_box_14_9_top(69),
							val_16_9_box_16_9_ctr(70),
							val_16_9_Unknown(71)
							}
		MAX-ACCESS		read-write
		STATUS			current
		DESCRIPTION
				"TYPE: - RadiobuttonList
					Source  cmdID= 36101
					Unused  value= -1
					Video Delay  value= 0
					Input Present  value= 1
					Input Loss  value= 2
					Reference OK  value= 3
					Reference Lost  value= 4
					O/p Freeze  value= 5
					O/p UnFreeze  value= 6
					GPI 1 High  value= 24
					GPI 1 Low  value= 25
					GPI 1 InActive  value= 23
					GPI 2 High  value= 27
					GPI 2 Low  value= 28
					GPI 2 InActive  value= 26
					De-embed 1 Present  value= 7
					De-embed 1 Lost  value= 8
					De-embed 2 Present  value= 9
					De-embed 2 Lost  value= 10
					De-embed 3 Present  value= 11
					De-embed 3 Lost  value= 12
					De-embed 4 Present  value= 13
					De-embed 4 Lost  value= 14
					De-embed 5 Present  value= 15
					De-embed 5 Lost  value= 16
					De-embed 6 Present  value= 17
					De-embed 6 Lost  value= 18
					De-embed 7 Present  value= 19
					De-embed 7 Lost  value= 20
					De-embed 8 Present  value= 21
					De-embed 8 Lost  value= 22
					Input Std - 525  value= 29
					Input Std - 625  value= 30
					Input Std - 720/59  value= 31
					Input Std - 720/50  value= 32
					Input Std - 1080/29  value= 33
					Input Std - 1080/25  value= 34
					Input 4:3  value= 35
					Input 16:9  value= 36
					AFD - Coded Frame  value= 37
					AFD - 4:3  value= 38
					AFD - 16:9  value= 39
					AFD - 14:9  value= 40
					AFD reserved  value= 41
					AFD - 4:3 SP 14:9  value= 42
					AFD - 16:9 SP 14:9  value= 43
					AFD - 16:9 SP 4:3  value= 44
					AFD - box 16:9 top  value= 45
					AFD - box 14:9 top  value= 46
					AFD - box>16:9 ctr  value= 47
					4:3 - Coded Frame  value= 48
					4:3 - 4:3  value= 49
					4:3 - 16:9  value= 50
					4:3 - 14:9  value= 51
					4:3 reserved  value= 52
					4:3 - 4:3 SP 14:9  value= 53
					4:3 - 16:9 SP 14:9  value= 54
					4:3 - 16:9 SP 4:3  value= 55
					4:3 - box 16:9 top  value= 56
					4:3 - box 14:9 top  value= 57
					4:3 - box>16:9 ctr  value= 58
					4:3 - Unknown  value= 59
					16:9 - Coded Frame  value= 60
					16:9 - 4:3  value= 61
					16:9 - 16:9  value= 62
					16:9 - 14:9  value= 63
					16:9 reserved  value= 64
					16:9 - 4:3 SP 14:9  value= 65
					16:9 - 16:9 SP 14:9  value= 66
					16:9 - 16:9 SP 4:3  value= 67
					16:9 - box 16:9 top  value= 68
					16:9 - box 14:9 top  value= 69
					16:9 - box>16:9 ctr  value= 70
					16:9 - Unknown  value= 71  "
		::= { iqudc00CmdEntry 36101 }


	iqudc00RollCallRollTrackAddress OBJECT-TYPE
		SYNTAX		RollCallString
		MAX-ACCESS		read-write
		STATUS			current
		DESCRIPTION
				"TYPE: - Editstring
					Address  cmdID= 36102  "
		::= { iqudc00CmdEntry 36102 }


	iqudc00RollCallRollTrackCommand OBJECT-TYPE
		SYNTAX		RollCallString
		MAX-ACCESS		read-write
		STATUS			current
		DESCRIPTION
				"TYPE: - Editstring
					Command  cmdID= 36103  "
		::= { iqudc00CmdEntry 36103 }


	iqudc00RollCallRollTrackStatus OBJECT-TYPE
		SYNTAX		RollCallString
		MAX-ACCESS		read-only
		STATUS			current
		DESCRIPTION
				"TYPE: - Display
					Status  cmdID= 36105  format=   "
		::= { iqudc00CmdEntry 36105 }


	iqudc00RollCallRollTrackSending OBJECT-TYPE
		SYNTAX		RollCallString
		MAX-ACCESS		read-only
		STATUS			current
		DESCRIPTION
				"TYPE: - Display
					Sending  cmdID= 36106  format=   "
		::= { iqudc00CmdEntry 36106 }


	iqudc00LoggingVideoInputLogInput1Type OBJECT-TYPE
		SYNTAX		INTEGER { disable(0), enable(1) }
		MAX-ACCESS		read-write
		STATUS			current
		DESCRIPTION
				"TYPE: - Checkbox
				 PAGE: - Logging- Video Input Logging
					Log Input 1 Type  cmdID= 35017 "
		::= { iqudc00CmdEntry 35017 }


	iqudc00LoggingVideoInputInput1Type OBJECT-TYPE
		SYNTAX		RollCallString
		MAX-ACCESS		read-only
		STATUS			current
		DESCRIPTION
				"TYPE: - Display
				 PAGE: - Logging- Video Input Logging
					Input 1 Type=  cmdID= 36017  format=   "
		::= { iqudc00CmdEntry 36017 }


	iqudc00LoggingVideoInputLogInput1Status OBJECT-TYPE
		SYNTAX		INTEGER { disable(0), enable(1) }
		MAX-ACCESS		read-write
		STATUS			current
		DESCRIPTION
				"TYPE: - Checkbox
				 PAGE: - Logging- Video Input Logging
					Log Input 1 Status  cmdID= 35005 "
		::= { iqudc00CmdEntry 35005 }


	iqudc00LoggingVideoInputInput1Status OBJECT-TYPE
		SYNTAX		RollCallString
		MAX-ACCESS		read-only
		STATUS			current
		DESCRIPTION
				"TYPE: - Display
				 PAGE: - Logging- Video Input Logging
					Input 1 Status=  cmdID= 36005  format=   "
		::= { iqudc00CmdEntry 36005 }


	iqudc00LoggingVideoInputLogInput1Std OBJECT-TYPE
		SYNTAX		INTEGER { disable(0), enable(1) }
		MAX-ACCESS		read-write
		STATUS			current
		DESCRIPTION
				"TYPE: - Checkbox
				 PAGE: - Logging- Video Input Logging
					Log Input 1 Std.  cmdID= 35016 "
		::= { iqudc00CmdEntry 35016 }


	iqudc00LoggingVideoInputInput1Std OBJECT-TYPE
		SYNTAX		RollCallString
		MAX-ACCESS		read-only
		STATUS			current
		DESCRIPTION
				"TYPE: - Display
				 PAGE: - Logging- Video Input Logging
					Input 1 Std.=  cmdID= 36016  format=   "
		::= { iqudc00CmdEntry 36016 }


	iqudc00LoggingVideoInputLogInput1Errors OBJECT-TYPE
		SYNTAX		INTEGER { disable(0), enable(1) }
		MAX-ACCESS		read-write
		STATUS			current
		DESCRIPTION
				"TYPE: - Checkbox
				 PAGE: - Logging- Video Input Logging
					Log Input 1 Errors  cmdID= 35002 "
		::= { iqudc00CmdEntry 35002 }


	iqudc00LoggingVideoInputInput1Errors OBJECT-TYPE
		SYNTAX		RollCallString
		MAX-ACCESS		read-only
		STATUS			current
		DESCRIPTION
				"TYPE: - Display
				 PAGE: - Logging- Video Input Logging
					Input 1 Errors=  cmdID= 36002  format=   "
		::= { iqudc00CmdEntry 36002 }


	iqudc00LoggingVideoInputLogInput1ErrSecs OBJECT-TYPE
		SYNTAX		INTEGER { disable(0), enable(1) }
		MAX-ACCESS		read-write
		STATUS			current
		DESCRIPTION
				"TYPE: - Checkbox
				 PAGE: - Logging- Video Input Logging
					Log Input 1 ErrSecs  cmdID= 35003 "
		::= { iqudc00CmdEntry 35003 }


	iqudc00LoggingVideoInputInput1ErrSecs OBJECT-TYPE
		SYNTAX		RollCallString
		MAX-ACCESS		read-only
		STATUS			current
		DESCRIPTION
				"TYPE: - Display
				 PAGE: - Logging- Video Input Logging
					Input 1 ErrSecs=  cmdID= 36003  format=   "
		::= { iqudc00CmdEntry 36003 }



	iqudc00LoggingVideoInputLogInput1ANCErr OBJECT-TYPE
		SYNTAX		INTEGER { disable(0), enable(1) }
		MAX-ACCESS		read-write
		STATUS			current
		DESCRIPTION
				"TYPE: - Checkbox
				 PAGE: - Logging- Video Input Logging
					Log Input 1 ANC Err  cmdID= 35000 "
		::= { iqudc00CmdEntry 35000 }


	iqudc00LoggingVideoInputInput1ANCErrors OBJECT-TYPE
		SYNTAX		RollCallString
		MAX-ACCESS		read-only
		STATUS			current
		DESCRIPTION
				"TYPE: - Display
				 PAGE: - Logging- Video Input Logging
					Input 1 ANC Errors=  cmdID= 36000  format=   "
		::= { iqudc00CmdEntry 36000 }


	iqudc00LoggingVideoInputLogInput1ANCErrSecs OBJECT-TYPE
		SYNTAX		INTEGER { disable(0), enable(1) }
		MAX-ACCESS		read-write
		STATUS			current
		DESCRIPTION
				"TYPE: - Checkbox
				 PAGE: - Logging- Video Input Logging
					Log Input 1 ANC Err  cmdID= 35001 "
		::= { iqudc00CmdEntry 35001 }


	iqudc00LoggingVideoInputInput1ANCErrSecs OBJECT-TYPE
		SYNTAX		RollCallString
		MAX-ACCESS		read-only
		STATUS			current
		DESCRIPTION
				"TYPE: - Display
				 PAGE: - Logging- Video Input Logging
					Input 1 ANC ErrSecs  cmdID= 36001  format=   "
		::= { iqudc00CmdEntry 36001 }


	iqudc00LoggingVideoInputLogInput2Type OBJECT-TYPE
		SYNTAX		INTEGER { disable(0), enable(1) }
		MAX-ACCESS		read-write
		STATUS			current
		DESCRIPTION
				"TYPE: - Checkbox
				 PAGE: - Logging- Video Input Logging
					Log Input 2 Type  cmdID= 35047 "
		::= { iqudc00CmdEntry 35047 }


	iqudc00LoggingVideoInputInput2Type OBJECT-TYPE
		SYNTAX		RollCallString
		MAX-ACCESS		read-only
		STATUS			current
		DESCRIPTION
				"TYPE: - Display
				 PAGE: - Logging- Video Input Logging
					Input 2 Type=  cmdID= 36047  format=   "
		::= { iqudc00CmdEntry 36047 }


	iqudc00LoggingVideoInputLogInput2Status OBJECT-TYPE
		SYNTAX		INTEGER { disable(0), enable(1) }
		MAX-ACCESS		read-write
		STATUS			current
		DESCRIPTION
				"TYPE: - Checkbox
				 PAGE: - Logging- Video Input Logging
					Log Input 2 Status  cmdID= 35035 "
		::= { iqudc00CmdEntry 35035 }


	iqudc00LoggingVideoInputInput2Status OBJECT-TYPE
		SYNTAX		RollCallString
		MAX-ACCESS		read-only
		STATUS			current
		DESCRIPTION
				"TYPE: - Display
				 PAGE: - Logging- Video Input Logging
					Input 2 Status=  cmdID= 36035  format=   "
		::= { iqudc00CmdEntry 36035 }


	iqudc00LoggingVideoInputLogInput2Std OBJECT-TYPE
		SYNTAX		INTEGER { disable(0), enable(1) }
		MAX-ACCESS		read-write
		STATUS			current
		DESCRIPTION
				"TYPE: - Checkbox
				 PAGE: - Logging- Video Input Logging
					Log Input 2 Std.  cmdID= 35046 "
		::= { iqudc00CmdEntry 35046 }


	iqudc00LoggingVideoInputInput2Std OBJECT-TYPE
		SYNTAX		RollCallString
		MAX-ACCESS		read-only
		STATUS			current
		DESCRIPTION
				"TYPE: - Display
				 PAGE: - Logging- Video Input Logging
					Input 2 Std.=  cmdID= 36046  format=   "
		::= { iqudc00CmdEntry 36046 }


	iqudc00LoggingVideoInputLogInput2Errors OBJECT-TYPE
		SYNTAX		INTEGER { disable(0), enable(1) }
		MAX-ACCESS		read-write
		STATUS			current
		DESCRIPTION
				"TYPE: - Checkbox
				 PAGE: - Logging- Video Input Logging
					Log Input 2 Errors  cmdID= 35032 "
		::= { iqudc00CmdEntry 35032 }


	iqudc00LoggingVideoInputInput2Errors OBJECT-TYPE
		SYNTAX		RollCallString
		MAX-ACCESS		read-only
		STATUS			current
		DESCRIPTION
				"TYPE: - Display
				 PAGE: - Logging- Video Input Logging
					Input 2 Errors=  cmdID= 36032  format=   "
		::= { iqudc00CmdEntry 36032 }


	iqudc00LoggingVideoInputLogInput2ErrSecs OBJECT-TYPE
		SYNTAX		INTEGER { disable(0), enable(1) }
		MAX-ACCESS		read-write
		STATUS			current
		DESCRIPTION
				"TYPE: - Checkbox
				 PAGE: - Logging- Video Input Logging
					Log Input 2 ErrSecs  cmdID= 35033 "
		::= { iqudc00CmdEntry 35033 }


	iqudc00LoggingVideoInputInput2ErrSecs OBJECT-TYPE
		SYNTAX		RollCallString
		MAX-ACCESS		read-only
		STATUS			current
		DESCRIPTION
				"TYPE: - Display
				 PAGE: - Logging- Video Input Logging
					Input 2 ErrSecs=  cmdID= 36033  format=   "
		::= { iqudc00CmdEntry 36033 }


	iqudc00LoggingVideoInputLogInput2ANCErr OBJECT-TYPE
		SYNTAX		INTEGER { disable(0), enable(1) }
		MAX-ACCESS		read-write
		STATUS			current
		DESCRIPTION
				"TYPE: - Checkbox
				 PAGE: - Logging- Video Input Logging
					Log Input 2 ANC Err  cmdID= 35030 "
		::= { iqudc00CmdEntry 35030 }


	iqudc00LoggingVideoInputInput2ANCErrors OBJECT-TYPE
		SYNTAX		RollCallString
		MAX-ACCESS		read-only
		STATUS			current
		DESCRIPTION
				"TYPE: - Display
				 PAGE: - Logging- Video Input Logging
					Input 2 ANC Errors=  cmdID= 36030  format=   "
		::= { iqudc00CmdEntry 36030 }


	iqudc00LoggingVideoInputLogInput2ANCErrSecs OBJECT-TYPE
		SYNTAX		INTEGER { disable(0), enable(1) }
		MAX-ACCESS		read-write
		STATUS			current
		DESCRIPTION
				"TYPE: - Checkbox
				 PAGE: - Logging- Video Input Logging
					Log Input 2 ANC Err  cmdID= 35031 "
		::= { iqudc00CmdEntry 35031 }


	iqudc00LoggingVideoInputInput2ANCErrSecs OBJECT-TYPE
		SYNTAX		RollCallString
		MAX-ACCESS		read-only
		STATUS			current
		DESCRIPTION
				"TYPE: - Display
				 PAGE: - Logging- Video Input Logging
					Input 2 ANC ErrSecs  cmdID= 36031  format=   "
		::= { iqudc00CmdEntry 36031 }


	iqudc00LoggingIn1AudStateLogInp1Emb1stat OBJECT-TYPE
		SYNTAX		INTEGER { disable(0), enable(1) }
		MAX-ACCESS		read-write
		STATUS			current
		DESCRIPTION
				"TYPE: - Checkbox
				 PAGE: - Logging
					Log Inp1 Emb.1 stat  cmdID= 35006 "
		::= { iqudc00CmdEntry 35006 }


	iqudc00LoggingIn1AudStateInp1Emb1state OBJECT-TYPE
		SYNTAX		RollCallString
		MAX-ACCESS		read-only
		STATUS			current
		DESCRIPTION
				"TYPE: - Display
				 PAGE: - Logging
					Inp1 Emb.1 state=  cmdID= 36006  format=   "
		::= { iqudc00CmdEntry 36006 }


	iqudc00LoggingIn1AudStateLogInp1Emb2stat OBJECT-TYPE
		SYNTAX		INTEGER { disable(0), enable(1) }
		MAX-ACCESS		read-write
		STATUS			current
		DESCRIPTION
				"TYPE: - Checkbox
				 PAGE: - Logging
					Log Inp1 Emb.2 stat  cmdID= 35007 "
		::= { iqudc00CmdEntry 35007 }


	iqudc00LoggingIn1AudStateInp1Emb2state OBJECT-TYPE
		SYNTAX		RollCallString
		MAX-ACCESS		read-only
		STATUS			current
		DESCRIPTION
				"TYPE: - Display
				 PAGE: - Logging
					Inp1 Emb.2 state=  cmdID= 36007  format=   "
		::= { iqudc00CmdEntry 36007 }


	iqudc00LoggingIn1AudStateLogInp1Emb3stat OBJECT-TYPE
		SYNTAX		INTEGER { disable(0), enable(1) }
		MAX-ACCESS		read-write
		STATUS			current
		DESCRIPTION
				"TYPE: - Checkbox
				 PAGE: - Logging
					Log Inp1 Emb.3 stat  cmdID= 35008 "
		::= { iqudc00CmdEntry 35008 }


	iqudc00LoggingIn1AudStateInp1Emb3state OBJECT-TYPE
		SYNTAX		RollCallString
		MAX-ACCESS		read-only
		STATUS			current
		DESCRIPTION
				"TYPE: - Display
				 PAGE: - Logging
					Inp1 Emb.3 state=  cmdID= 36008  format=   "
		::= { iqudc00CmdEntry 36008 }


	iqudc00LoggingIn1AudStateLogInp1Emb4stat OBJECT-TYPE
		SYNTAX		INTEGER { disable(0), enable(1) }
		MAX-ACCESS		read-write
		STATUS			current
		DESCRIPTION
				"TYPE: - Checkbox
				 PAGE: - Logging
					Log Inp1 Emb.4 stat  cmdID= 35009 "
		::= { iqudc00CmdEntry 35009 }


	iqudc00LoggingIn1AudStateInp1Emb4state OBJECT-TYPE
		SYNTAX		RollCallString
		MAX-ACCESS		read-only
		STATUS			current
		DESCRIPTION
				"TYPE: - Display
				 PAGE: - Logging
					Inp1 Emb.4 state=  cmdID= 36009  format=   "
		::= { iqudc00CmdEntry 36009 }


	iqudc00LoggingIn1AudStateLogInp1Emb5stat OBJECT-TYPE
		SYNTAX		INTEGER { disable(0), enable(1) }
		MAX-ACCESS		read-write
		STATUS			current
		DESCRIPTION
				"TYPE: - Checkbox
				 PAGE: - Logging
					Log Inp1 Emb.5 stat  cmdID= 35010 "
		::= { iqudc00CmdEntry 35010 }


	iqudc00LoggingIn1AudStateInp1Emb5state OBJECT-TYPE
		SYNTAX		RollCallString
		MAX-ACCESS		read-only
		STATUS			current
		DESCRIPTION
				"TYPE: - Display
				 PAGE: - Logging
					Inp1 Emb.5 state=  cmdID= 36010  format=   "
		::= { iqudc00CmdEntry 36010 }


	iqudc00LoggingIn1AudStateLogInp1Emb6stat OBJECT-TYPE
		SYNTAX		INTEGER { disable(0), enable(1) }
		MAX-ACCESS		read-write
		STATUS			current
		DESCRIPTION
				"TYPE: - Checkbox
				 PAGE: - Logging
					Log Inp1 Emb.6 stat  cmdID= 35011 "
		::= { iqudc00CmdEntry 35011 }


	iqudc00LoggingIn1AudStateInp1Emb6state OBJECT-TYPE
		SYNTAX		RollCallString
		MAX-ACCESS		read-only
		STATUS			current
		DESCRIPTION
				"TYPE: - Display
				 PAGE: - Logging
					Inp1 Emb.6 state=  cmdID= 36011  format=   "
		::= { iqudc00CmdEntry 36011 }


	iqudc00LoggingIn1AudStateLogInp1Emb7stat OBJECT-TYPE
		SYNTAX		INTEGER { disable(0), enable(1) }
		MAX-ACCESS		read-write
		STATUS			current
		DESCRIPTION
				"TYPE: - Checkbox
				 PAGE: - Logging
					Log Inp1 Emb.7 stat  cmdID= 35012 "
		::= { iqudc00CmdEntry 35012 }


	iqudc00LoggingIn1AudStateInp1Emb7state OBJECT-TYPE
		SYNTAX		RollCallString
		MAX-ACCESS		read-only
		STATUS			current
		DESCRIPTION
				"TYPE: - Display
				 PAGE: - Logging
					Inp1 Emb.7 state=  cmdID= 36012  format=   "
		::= { iqudc00CmdEntry 36012 }


	iqudc00LoggingIn1AudStateLogInp1Emb8stat OBJECT-TYPE
		SYNTAX		INTEGER { disable(0), enable(1) }
		MAX-ACCESS		read-write
		STATUS			current
		DESCRIPTION
				"TYPE: - Checkbox
				 PAGE: - Logging
					Log Inp1 Emb.8 stat  cmdID= 35013 "
		::= { iqudc00CmdEntry 35013 }


	iqudc00LoggingIn1AudStateInp1Emb8state OBJECT-TYPE
		SYNTAX		RollCallString
		MAX-ACCESS		read-only
		STATUS			current
		DESCRIPTION
				"TYPE: - Display
				 PAGE: - Logging
					Inp1 Emb.8 state=  cmdID= 36013  format=   "
		::= { iqudc00CmdEntry 36013 }


	iqudc00LoggingIn2AudStateLogInp2Emb1stat OBJECT-TYPE
		SYNTAX		INTEGER { disable(0), enable(1) }
		MAX-ACCESS		read-write
		STATUS			current
		DESCRIPTION
				"TYPE: - Checkbox
				 PAGE: - Logging
					Log Inp2 Emb.1 stat  cmdID= 35036 "
		::= { iqudc00CmdEntry 35036 }


	iqudc00LoggingIn2AudStateInp2Emb1state OBJECT-TYPE
		SYNTAX		RollCallString
		MAX-ACCESS		read-only
		STATUS			current
		DESCRIPTION
				"TYPE: - Display
				 PAGE: - Logging
					Inp2 Emb.1 state=  cmdID= 36036  format=   "
		::= { iqudc00CmdEntry 36036 }


	iqudc00LoggingIn2AudStateLogInp2Emb2stat OBJECT-TYPE
		SYNTAX		INTEGER { disable(0), enable(1) }
		MAX-ACCESS		read-write
		STATUS			current
		DESCRIPTION
				"TYPE: - Checkbox
				 PAGE: - Logging
					Log Inp2 Emb.2 stat  cmdID= 35037 "
		::= { iqudc00CmdEntry 35037 }


	iqudc00LoggingIn2AudStateInp2Emb2state OBJECT-TYPE
		SYNTAX		RollCallString
		MAX-ACCESS		read-only
		STATUS			current
		DESCRIPTION
				"TYPE: - Display
				 PAGE: - Logging
					Inp2 Emb.2 state=  cmdID= 36037  format=   "
		::= { iqudc00CmdEntry 36037 }


	iqudc00LoggingIn2AudStateLogInp2Emb3stat OBJECT-TYPE
		SYNTAX		INTEGER { disable(0), enable(1) }
		MAX-ACCESS		read-write
		STATUS			current
		DESCRIPTION
				"TYPE: - Checkbox
				 PAGE: - Logging
					Log Inp2 Emb.3 stat  cmdID= 35038 "
		::= { iqudc00CmdEntry 35038 }


	iqudc00LoggingIn2AudStateInp2Emb3state OBJECT-TYPE
		SYNTAX		RollCallString
		MAX-ACCESS		read-only
		STATUS			current
		DESCRIPTION
				"TYPE: - Display
				 PAGE: - Logging
					Inp2 Emb.3 state=  cmdID= 36038  format=   "
		::= { iqudc00CmdEntry 36038 }


	iqudc00LoggingIn2AudStateLogInp2Emb4stat OBJECT-TYPE
		SYNTAX		INTEGER { disable(0), enable(1) }
		MAX-ACCESS		read-write
		STATUS			current
		DESCRIPTION
				"TYPE: - Checkbox
				 PAGE: - Logging
					Log Inp2 Emb.4 stat  cmdID= 35039 "
		::= { iqudc00CmdEntry 35039 }


	iqudc00LoggingIn2AudStateInp2Emb4state OBJECT-TYPE
		SYNTAX		RollCallString
		MAX-ACCESS		read-only
		STATUS			current
		DESCRIPTION
				"TYPE: - Display
				 PAGE: - Logging
					Inp2 Emb.4 state=  cmdID= 36039  format=   "
		::= { iqudc00CmdEntry 36039 }


	iqudc00LoggingIn2AudStateLogInp2Emb5stat OBJECT-TYPE
		SYNTAX		INTEGER { disable(0), enable(1) }
		MAX-ACCESS		read-write
		STATUS			current
		DESCRIPTION
				"TYPE: - Checkbox
				 PAGE: - Logging
					Log Inp2 Emb.5 stat  cmdID= 35040 "
		::= { iqudc00CmdEntry 35040 }


	iqudc00LoggingIn2AudStateInp2Emb5state OBJECT-TYPE
		SYNTAX		RollCallString
		MAX-ACCESS		read-only
		STATUS			current
		DESCRIPTION
				"TYPE: - Display
				 PAGE: - Logging
					Inp2 Emb.5 state=  cmdID= 36040  format=   "
		::= { iqudc00CmdEntry 36040 }


	iqudc00LoggingIn2AudStateLogInp2Emb6stat OBJECT-TYPE
		SYNTAX		INTEGER { disable(0), enable(1) }
		MAX-ACCESS		read-write
		STATUS			current
		DESCRIPTION
				"TYPE: - Checkbox
				 PAGE: - Logging
					Log Inp2 Emb.6 stat  cmdID= 35041 "
		::= { iqudc00CmdEntry 35041 }


	iqudc00LoggingIn2AudStateInp2Emb6state OBJECT-TYPE
		SYNTAX		RollCallString
		MAX-ACCESS		read-only
		STATUS			current
		DESCRIPTION
				"TYPE: - Display
				 PAGE: - Logging
					Inp2 Emb.6 state=  cmdID= 36041  format=   "
		::= { iqudc00CmdEntry 36041 }


	iqudc00LoggingIn2AudStateLogInp2Emb7stat OBJECT-TYPE
		SYNTAX		INTEGER { disable(0), enable(1) }
		MAX-ACCESS		read-write
		STATUS			current
		DESCRIPTION
				"TYPE: - Checkbox
				 PAGE: - Logging
					Log Inp2 Emb.7 stat  cmdID= 35042 "
		::= { iqudc00CmdEntry 35042 }


	iqudc00LoggingIn2AudStateInp2Emb7state OBJECT-TYPE
		SYNTAX		RollCallString
		MAX-ACCESS		read-only
		STATUS			current
		DESCRIPTION
				"TYPE: - Display
				 PAGE: - Logging
					Inp2 Emb.7 state=  cmdID= 36042  format=   "
		::= { iqudc00CmdEntry 36042 }


	iqudc00LoggingIn2AudStateLogInp2Emb8stat OBJECT-TYPE
		SYNTAX		INTEGER { disable(0), enable(1) }
		MAX-ACCESS		read-write
		STATUS			current
		DESCRIPTION
				"TYPE: - Checkbox
				 PAGE: - Logging
					Log Inp2 Emb.8 stat  cmdID= 35043 "
		::= { iqudc00CmdEntry 35043 }


	iqudc00LoggingIn2AudStateInp2Emb8state OBJECT-TYPE
		SYNTAX		RollCallString
		MAX-ACCESS		read-only
		STATUS			current
		DESCRIPTION
				"TYPE: - Display
				 PAGE: - Logging
					Inp2 Emb.8 state=  cmdID= 36043  format=   "
		::= { iqudc00CmdEntry 36043 }


	iqudc00LoggingIn1AudTypeLogInp1Emb1type OBJECT-TYPE
		SYNTAX		INTEGER { disable(0), enable(1) }
		MAX-ACCESS		read-write
		STATUS			current
		DESCRIPTION
				"TYPE: - Checkbox
				 PAGE: - Logging
					Log Inp1 Emb.1 type  cmdID= 35018 "
		::= { iqudc00CmdEntry 35018 }


	iqudc00LoggingIn1AudTypeInp1Emb1type OBJECT-TYPE
		SYNTAX		RollCallString
		MAX-ACCESS		read-only
		STATUS			current
		DESCRIPTION
				"TYPE: - Display
				 PAGE: - Logging
					Inp1 Emb.1 type=  cmdID= 36018  format=   "
		::= { iqudc00CmdEntry 36018 }


	iqudc00LoggingIn1AudTypeLogInp1Emb2type OBJECT-TYPE
		SYNTAX		INTEGER { disable(0), enable(1) }
		MAX-ACCESS		read-write
		STATUS			current
		DESCRIPTION
				"TYPE: - Checkbox
				 PAGE: - Logging
					Log Inp1 Emb.2 type  cmdID= 35019 "
		::= { iqudc00CmdEntry 35019 }


	iqudc00LoggingIn1AudTypeInp1Emb2type OBJECT-TYPE
		SYNTAX		RollCallString
		MAX-ACCESS		read-only
		STATUS			current
		DESCRIPTION
				"TYPE: - Display
				 PAGE: - Logging
					Inp1 Emb.2 type=  cmdID= 36019  format=   "
		::= { iqudc00CmdEntry 36019 }


	iqudc00LoggingIn1AudTypeLogInp1Emb3type OBJECT-TYPE
		SYNTAX		INTEGER { disable(0), enable(1) }
		MAX-ACCESS		read-write
		STATUS			current
		DESCRIPTION
				"TYPE: - Checkbox
				 PAGE: - Logging
					Log Inp1 Emb.3 type  cmdID= 35020 "
		::= { iqudc00CmdEntry 35020 }


	iqudc00LoggingIn1AudTypeInp1Emb3type OBJECT-TYPE
		SYNTAX		RollCallString
		MAX-ACCESS		read-only
		STATUS			current
		DESCRIPTION
				"TYPE: - Display
				 PAGE: - Logging
					Inp1 Emb.3 type=  cmdID= 36020  format=   "
		::= { iqudc00CmdEntry 36020 }


	iqudc00LoggingIn1AudTypeLogInp1Emb4type OBJECT-TYPE
		SYNTAX		INTEGER { disable(0), enable(1) }
		MAX-ACCESS		read-write
		STATUS			current
		DESCRIPTION
				"TYPE: - Checkbox
				 PAGE: - Logging
					Log Inp1 Emb.4 type  cmdID= 35021 "
		::= { iqudc00CmdEntry 35021 }


	iqudc00LoggingIn1AudTypeInp1Emb4type OBJECT-TYPE
		SYNTAX		RollCallString
		MAX-ACCESS		read-only
		STATUS			current
		DESCRIPTION
				"TYPE: - Display
				 PAGE: - Logging
					Inp1 Emb.4 type=  cmdID= 36021  format=   "
		::= { iqudc00CmdEntry 36021 }


	iqudc00LoggingIn1AudTypeLogInp1Emb5type OBJECT-TYPE
		SYNTAX		INTEGER { disable(0), enable(1) }
		MAX-ACCESS		read-write
		STATUS			current
		DESCRIPTION
				"TYPE: - Checkbox
				 PAGE: - Logging
					Log Inp1 Emb.5 type  cmdID= 35022 "
		::= { iqudc00CmdEntry 35022 }


	iqudc00LoggingIn1AudTypeInp1Emb5type OBJECT-TYPE
		SYNTAX		RollCallString
		MAX-ACCESS		read-only
		STATUS			current
		DESCRIPTION
				"TYPE: - Display
				 PAGE: - Logging
					Inp1 Emb.5 type=  cmdID= 36022  format=   "
		::= { iqudc00CmdEntry 36022 }


	iqudc00LoggingIn1AudTypeLogInp1Emb6type OBJECT-TYPE
		SYNTAX		INTEGER { disable(0), enable(1) }
		MAX-ACCESS		read-write
		STATUS			current
		DESCRIPTION
				"TYPE: - Checkbox
				 PAGE: - Logging
					Log Inp1 Emb.6 type  cmdID= 35023 "
		::= { iqudc00CmdEntry 35023 }


	iqudc00LoggingIn1AudTypeInp1Emb6type OBJECT-TYPE
		SYNTAX		RollCallString
		MAX-ACCESS		read-only
		STATUS			current
		DESCRIPTION
				"TYPE: - Display
				 PAGE: - Logging
					Inp1 Emb.6 type=  cmdID= 36023  format=   "
		::= { iqudc00CmdEntry 36023 }


	iqudc00LoggingIn1AudTypeLogInp1Emb7type OBJECT-TYPE
		SYNTAX		INTEGER { disable(0), enable(1) }
		MAX-ACCESS		read-write
		STATUS			current
		DESCRIPTION
				"TYPE: - Checkbox
				 PAGE: - Logging
					Log Inp1 Emb.7 type  cmdID= 35024 "
		::= { iqudc00CmdEntry 35024 }


	iqudc00LoggingIn1AudTypeInp1Emb7type OBJECT-TYPE
		SYNTAX		RollCallString
		MAX-ACCESS		read-only
		STATUS			current
		DESCRIPTION
				"TYPE: - Display
				 PAGE: - Logging
					Inp1 Emb.7 type=  cmdID= 36024  format=   "
		::= { iqudc00CmdEntry 36024 }


	iqudc00LoggingIn1AudTypeLogInp1Emb8type OBJECT-TYPE
		SYNTAX		INTEGER { disable(0), enable(1) }
		MAX-ACCESS		read-write
		STATUS			current
		DESCRIPTION
				"TYPE: - Checkbox
				 PAGE: - Logging
					Log Inp1 Emb.8 type  cmdID= 35025 "
		::= { iqudc00CmdEntry 35025 }


	iqudc00LoggingIn1AudTypeInp1Emb8type OBJECT-TYPE
		SYNTAX		RollCallString
		MAX-ACCESS		read-only
		STATUS			current
		DESCRIPTION
				"TYPE: - Display
				 PAGE: - Logging
					Inp1 Emb.8 type=  cmdID= 36025  format=   "
		::= { iqudc00CmdEntry 36025 }


	iqudc00LoggingIn2AudTypeLogInp2Emb1type OBJECT-TYPE
		SYNTAX		INTEGER { disable(0), enable(1) }
		MAX-ACCESS		read-write
		STATUS			current
		DESCRIPTION
				"TYPE: - Checkbox
				 PAGE: - Logging
					Log Inp2 Emb.1 type  cmdID= 35048 "
		::= { iqudc00CmdEntry 35048 }


	iqudc00LoggingIn2AudTypeInp2Emb1type OBJECT-TYPE
		SYNTAX		RollCallString
		MAX-ACCESS		read-only
		STATUS			current
		DESCRIPTION
				"TYPE: - Display
				 PAGE: - Logging
					Inp2 Emb.1 type=  cmdID= 36048  format=   "
		::= { iqudc00CmdEntry 36048 }


	iqudc00LoggingIn2AudTypeLogInp2Emb2type OBJECT-TYPE
		SYNTAX		INTEGER { disable(0), enable(1) }
		MAX-ACCESS		read-write
		STATUS			current
		DESCRIPTION
				"TYPE: - Checkbox
				 PAGE: - Logging
					Log Inp2 Emb.2 type  cmdID= 35049 "
		::= { iqudc00CmdEntry 35049 }


	iqudc00LoggingIn2AudTypeInp2Emb2type OBJECT-TYPE
		SYNTAX		RollCallString
		MAX-ACCESS		read-only
		STATUS			current
		DESCRIPTION
				"TYPE: - Display
				 PAGE: - Logging
					Inp2 Emb.2 type=  cmdID= 36049  format=   "
		::= { iqudc00CmdEntry 36049 }


	iqudc00LoggingIn2AudTypeLogInp2Emb3type OBJECT-TYPE
		SYNTAX		INTEGER { disable(0), enable(1) }
		MAX-ACCESS		read-write
		STATUS			current
		DESCRIPTION
				"TYPE: - Checkbox
				 PAGE: - Logging
					Log Inp2 Emb.3 type  cmdID= 35050 "
		::= { iqudc00CmdEntry 35050 }


	iqudc00LoggingIn2AudTypeInp2Emb3type OBJECT-TYPE
		SYNTAX		RollCallString
		MAX-ACCESS		read-only
		STATUS			current
		DESCRIPTION
				"TYPE: - Display
				 PAGE: - Logging
					Inp2 Emb.3 type=  cmdID= 36050  format=   "
		::= { iqudc00CmdEntry 36050 }


	iqudc00LoggingIn2AudTypeLogInp2Emb4type OBJECT-TYPE
		SYNTAX		INTEGER { disable(0), enable(1) }
		MAX-ACCESS		read-write
		STATUS			current
		DESCRIPTION
				"TYPE: - Checkbox
				 PAGE: - Logging
					Log Inp2 Emb.4 type  cmdID= 35051 "
		::= { iqudc00CmdEntry 35051 }


	iqudc00LoggingIn2AudTypeInp2Emb4type OBJECT-TYPE
		SYNTAX		RollCallString
		MAX-ACCESS		read-only
		STATUS			current
		DESCRIPTION
				"TYPE: - Display
				 PAGE: - Logging
					Inp2 Emb.4 type=  cmdID= 36051  format=   "
		::= { iqudc00CmdEntry 36051 }


	iqudc00LoggingIn2AudTypeLogInp2Emb5type OBJECT-TYPE
		SYNTAX		INTEGER { disable(0), enable(1) }
		MAX-ACCESS		read-write
		STATUS			current
		DESCRIPTION
				"TYPE: - Checkbox
				 PAGE: - Logging
					Log Inp2 Emb.5 type  cmdID= 35052 "
		::= { iqudc00CmdEntry 35052 }


	iqudc00LoggingIn2AudTypeInp2Emb5type OBJECT-TYPE
		SYNTAX		RollCallString
		MAX-ACCESS		read-only
		STATUS			current
		DESCRIPTION
				"TYPE: - Display
				 PAGE: - Logging
					Inp2 Emb.5 type=  cmdID= 36052  format=   "
		::= { iqudc00CmdEntry 36052 }


	iqudc00LoggingIn2AudTypeLogInp2Emb6type OBJECT-TYPE
		SYNTAX		INTEGER { disable(0), enable(1) }
		MAX-ACCESS		read-write
		STATUS			current
		DESCRIPTION
				"TYPE: - Checkbox
				 PAGE: - Logging
					Log Inp2 Emb.6 type  cmdID= 35053 "
		::= { iqudc00CmdEntry 35053 }


	iqudc00LoggingIn2AudTypeInp2Emb6type OBJECT-TYPE
		SYNTAX		RollCallString
		MAX-ACCESS		read-only
		STATUS			current
		DESCRIPTION
				"TYPE: - Display
				 PAGE: - Logging
					Inp2 Emb.6 type=  cmdID= 36053  format=   "
		::= { iqudc00CmdEntry 36053 }


	iqudc00LoggingIn2AudTypeLogInp2Emb7type OBJECT-TYPE
		SYNTAX		INTEGER { disable(0), enable(1) }
		MAX-ACCESS		read-write
		STATUS			current
		DESCRIPTION
				"TYPE: - Checkbox
				 PAGE: - Logging
					Log Inp2 Emb.7 type  cmdID= 35054 "
		::= { iqudc00CmdEntry 35054 }


	iqudc00LoggingIn2AudTypeInp2Emb7type OBJECT-TYPE
		SYNTAX		RollCallString
		MAX-ACCESS		read-only
		STATUS			current
		DESCRIPTION
				"TYPE: - Display
				 PAGE: - Logging
					Inp2 Emb.7 type=  cmdID= 36054  format=   "
		::= { iqudc00CmdEntry 36054 }


	iqudc00LoggingIn2AudTypeLogInp2Emb8type OBJECT-TYPE
		SYNTAX		INTEGER { disable(0), enable(1) }
		MAX-ACCESS		read-write
		STATUS			current
		DESCRIPTION
				"TYPE: - Checkbox
				 PAGE: - Logging
					Log Inp2 Emb.8 type  cmdID= 35055 "
		::= { iqudc00CmdEntry 35055 }


	iqudc00LoggingIn2AudTypeInp2Emb8type OBJECT-TYPE
		SYNTAX		RollCallString
		MAX-ACCESS		read-only
		STATUS			current
		DESCRIPTION
				"TYPE: - Display
				 PAGE: - Logging
					Inp2 Emb.8 type=  cmdID= 36055  format=   "
		::= { iqudc00CmdEntry 36055 }


	iqudc00LoggingOPAudStateLogOutEmb1state OBJECT-TYPE
		SYNTAX		INTEGER { disable(0), enable(1) }
		MAX-ACCESS		read-write
		STATUS			current
		DESCRIPTION
				"TYPE: - Checkbox
				 PAGE: - Logging
					Log Out Emb.1 state  cmdID= 35920 "
		::= { iqudc00CmdEntry 35920 }


	iqudc00LoggingOPAudStateOutEmb1state OBJECT-TYPE
		SYNTAX		RollCallString
		MAX-ACCESS		read-only
		STATUS			current
		DESCRIPTION
				"TYPE: - Display
				 PAGE: - Logging
					Out Emb.1 state=  cmdID= 36920  format=   "
		::= { iqudc00CmdEntry 36920 }


	iqudc00LoggingOPAudStateLogOutEmb2state OBJECT-TYPE
		SYNTAX		INTEGER { disable(0), enable(1) }
		MAX-ACCESS		read-write
		STATUS			current
		DESCRIPTION
				"TYPE: - Checkbox
				 PAGE: - Logging
					Log Out Emb.2 state  cmdID= 35921 "
		::= { iqudc00CmdEntry 35921 }


	iqudc00LoggingOPAudStateOutEmb2state OBJECT-TYPE
		SYNTAX		RollCallString
		MAX-ACCESS		read-only
		STATUS			current
		DESCRIPTION
				"TYPE: - Display
				 PAGE: - Logging
					Out Emb.2 state=  cmdID= 36921  format=   "
		::= { iqudc00CmdEntry 36921 }


	iqudc00LoggingOPAudStateLogOutEmb3state OBJECT-TYPE
		SYNTAX		INTEGER { disable(0), enable(1) }
		MAX-ACCESS		read-write
		STATUS			current
		DESCRIPTION
				"TYPE: - Checkbox
				 PAGE: - Logging
					Log Out Emb.3 state  cmdID= 35922 "
		::= { iqudc00CmdEntry 35922 }


	iqudc00LoggingOPAudStateOutEmb3state OBJECT-TYPE
		SYNTAX		RollCallString
		MAX-ACCESS		read-only
		STATUS			current
		DESCRIPTION
				"TYPE: - Display
				 PAGE: - Logging
					Out Emb.3 state=  cmdID= 36922  format=   "
		::= { iqudc00CmdEntry 36922 }


	iqudc00LoggingOPAudStateLogOutEmb4state OBJECT-TYPE
		SYNTAX		INTEGER { disable(0), enable(1) }
		MAX-ACCESS		read-write
		STATUS			current
		DESCRIPTION
				"TYPE: - Checkbox
				 PAGE: - Logging
					Log Out Emb.4 state  cmdID= 35923 "
		::= { iqudc00CmdEntry 35923 }


	iqudc00LoggingOPAudStateOutEmb4state OBJECT-TYPE
		SYNTAX		RollCallString
		MAX-ACCESS		read-only
		STATUS			current
		DESCRIPTION
				"TYPE: - Display
				 PAGE: - Logging
					Out Emb.4 state=  cmdID= 36923  format=   "
		::= { iqudc00CmdEntry 36923 }


	iqudc00LoggingOPAudStateLogOutEmb5state OBJECT-TYPE
		SYNTAX		INTEGER { disable(0), enable(1) }
		MAX-ACCESS		read-write
		STATUS			current
		DESCRIPTION
				"TYPE: - Checkbox
				 PAGE: - Logging
					Log Out Emb.5 state  cmdID= 35924 "
		::= { iqudc00CmdEntry 35924 }


	iqudc00LoggingOPAudStateOutEmb5state OBJECT-TYPE
		SYNTAX		RollCallString
		MAX-ACCESS		read-only
		STATUS			current
		DESCRIPTION
				"TYPE: - Display
				 PAGE: - Logging
					Out Emb.5 state=  cmdID= 36924  format=   "
		::= { iqudc00CmdEntry 36924 }


	iqudc00LoggingOPAudStateLogOutEmb6state OBJECT-TYPE
		SYNTAX		INTEGER { disable(0), enable(1) }
		MAX-ACCESS		read-write
		STATUS			current
		DESCRIPTION
				"TYPE: - Checkbox
				 PAGE: - Logging
					Log Out Emb.6 state  cmdID= 35925 "
		::= { iqudc00CmdEntry 35925 }


	iqudc00LoggingOPAudStateOutEmb6state OBJECT-TYPE
		SYNTAX		RollCallString
		MAX-ACCESS		read-only
		STATUS			current
		DESCRIPTION
				"TYPE: - Display
				 PAGE: - Logging
					Out Emb.6 state=  cmdID= 36925  format=   "
		::= { iqudc00CmdEntry 36925 }


	iqudc00LoggingOPAudStateLogOutEmb7state OBJECT-TYPE
		SYNTAX		INTEGER { disable(0), enable(1) }
		MAX-ACCESS		read-write
		STATUS			current
		DESCRIPTION
				"TYPE: - Checkbox
				 PAGE: - Logging
					Log Out Emb.7 state  cmdID= 35926 "
		::= { iqudc00CmdEntry 35926 }


	iqudc00LoggingOPAudStateOutEmb7state OBJECT-TYPE
		SYNTAX		RollCallString
		MAX-ACCESS		read-only
		STATUS			current
		DESCRIPTION
				"TYPE: - Display
				 PAGE: - Logging
					Out Emb.7 state=  cmdID= 36926  format=   "
		::= { iqudc00CmdEntry 36926 }


	iqudc00LoggingOPAudStateLogOutEmb8state OBJECT-TYPE
		SYNTAX		INTEGER { disable(0), enable(1) }
		MAX-ACCESS		read-write
		STATUS			current
		DESCRIPTION
				"TYPE: - Checkbox
				 PAGE: - Logging
					Log Out Emb.8 state  cmdID= 35927 "
		::= { iqudc00CmdEntry 35927 }


	iqudc00LoggingOPAudStateOutEmb8state OBJECT-TYPE
		SYNTAX		RollCallString
		MAX-ACCESS		read-only
		STATUS			current
		DESCRIPTION
				"TYPE: - Display
				 PAGE: - Logging
					Out Emb.8 state=  cmdID= 36927  format=   "
		::= { iqudc00CmdEntry 36927 }


	iqudc00LoggingOPAudTypeLogOutEmb1type OBJECT-TYPE
		SYNTAX		INTEGER { disable(0), enable(1) }
		MAX-ACCESS		read-write
		STATUS			current
		DESCRIPTION
				"TYPE: - Checkbox
				 PAGE: - Logging
					Log Out Emb.1 type  cmdID= 35930 "
		::= { iqudc00CmdEntry 35930 }


	iqudc00LoggingOPAudTypeOutEmb1type OBJECT-TYPE
		SYNTAX		RollCallString
		MAX-ACCESS		read-only
		STATUS			current
		DESCRIPTION
				"TYPE: - Display
				 PAGE: - Logging
					Out Emb.1 type=  cmdID= 36930  format=   "
		::= { iqudc00CmdEntry 36930 }


	iqudc00LoggingOPAudTypeLogOutEmb2type OBJECT-TYPE
		SYNTAX		INTEGER { disable(0), enable(1) }
		MAX-ACCESS		read-write
		STATUS			current
		DESCRIPTION
				"TYPE: - Checkbox
				 PAGE: - Logging
					Log Out Emb.2 type  cmdID= 35931 "
		::= { iqudc00CmdEntry 35931 }


	iqudc00LoggingOPAudTypeOutEmb2type OBJECT-TYPE
		SYNTAX		RollCallString
		MAX-ACCESS		read-only
		STATUS			current
		DESCRIPTION
				"TYPE: - Display
				 PAGE: - Logging
					Out Emb.2 type=  cmdID= 36931  format=   "
		::= { iqudc00CmdEntry 36931 }


	iqudc00LoggingOPAudTypeLogOutEmb3type OBJECT-TYPE
		SYNTAX		INTEGER { disable(0), enable(1) }
		MAX-ACCESS		read-write
		STATUS			current
		DESCRIPTION
				"TYPE: - Checkbox
				 PAGE: - Logging
					Log Out Emb.3 type  cmdID= 35932 "
		::= { iqudc00CmdEntry 35932 }


	iqudc00LoggingOPAudTypeOutEmb3type OBJECT-TYPE
		SYNTAX		RollCallString
		MAX-ACCESS		read-only
		STATUS			current
		DESCRIPTION
				"TYPE: - Display
				 PAGE: - Logging
					Out Emb.3 type=  cmdID= 36932  format=   "
		::= { iqudc00CmdEntry 36932 }


	iqudc00LoggingOPAudTypeLogOutEmb4type OBJECT-TYPE
		SYNTAX		INTEGER { disable(0), enable(1) }
		MAX-ACCESS		read-write
		STATUS			current
		DESCRIPTION
				"TYPE: - Checkbox
				 PAGE: - Logging
					Log Out Emb.4 type  cmdID= 35933 "
		::= { iqudc00CmdEntry 35933 }


	iqudc00LoggingOPAudTypeOutEmb4type OBJECT-TYPE
		SYNTAX		RollCallString
		MAX-ACCESS		read-only
		STATUS			current
		DESCRIPTION
				"TYPE: - Display
				 PAGE: - Logging
					Out Emb.4 type=  cmdID= 36933  format=   "
		::= { iqudc00CmdEntry 36933 }


	iqudc00LoggingOPAudTypeLogOutEmb5type OBJECT-TYPE
		SYNTAX		INTEGER { disable(0), enable(1) }
		MAX-ACCESS		read-write
		STATUS			current
		DESCRIPTION
				"TYPE: - Checkbox
				 PAGE: - Logging
					Log Out Emb.5 type  cmdID= 35934 "
		::= { iqudc00CmdEntry 35934 }


	iqudc00LoggingOPAudTypeOutEmb5type OBJECT-TYPE
		SYNTAX		RollCallString
		MAX-ACCESS		read-only
		STATUS			current
		DESCRIPTION
				"TYPE: - Display
				 PAGE: - Logging
					Out Emb.5 type=  cmdID= 36934  format=   "
		::= { iqudc00CmdEntry 36934 }


	iqudc00LoggingOPAudTypeLogOutEmb6type OBJECT-TYPE
		SYNTAX		INTEGER { disable(0), enable(1) }
		MAX-ACCESS		read-write
		STATUS			current
		DESCRIPTION
				"TYPE: - Checkbox
				 PAGE: - Logging
					Log Out Emb.6 type  cmdID= 35935 "
		::= { iqudc00CmdEntry 35935 }


	iqudc00LoggingOPAudTypeOutEmb6type OBJECT-TYPE
		SYNTAX		RollCallString
		MAX-ACCESS		read-only
		STATUS			current
		DESCRIPTION
				"TYPE: - Display
				 PAGE: - Logging
					Out Emb.6 type=  cmdID= 36935  format=   "
		::= { iqudc00CmdEntry 36935 }


	iqudc00LoggingOPAudTypeLogOutEmb7type OBJECT-TYPE
		SYNTAX		INTEGER { disable(0), enable(1) }
		MAX-ACCESS		read-write
		STATUS			current
		DESCRIPTION
				"TYPE: - Checkbox
				 PAGE: - Logging
					Log Out Emb.7 type  cmdID= 35936 "
		::= { iqudc00CmdEntry 35936 }


	iqudc00LoggingOPAudTypeOutEmb7type OBJECT-TYPE
		SYNTAX		RollCallString
		MAX-ACCESS		read-only
		STATUS			current
		DESCRIPTION
				"TYPE: - Display
				 PAGE: - Logging
					Out Emb.7 type=  cmdID= 36936  format=   "
		::= { iqudc00CmdEntry 36936 }


	iqudc00LoggingOPAudTypeLogOutEmb8type OBJECT-TYPE
		SYNTAX		INTEGER { disable(0), enable(1) }
		MAX-ACCESS		read-write
		STATUS			current
		DESCRIPTION
				"TYPE: - Checkbox
				 PAGE: - Logging
					Log Out Emb.8 type  cmdID= 35937 "
		::= { iqudc00CmdEntry 35937 }


	iqudc00LoggingOPAudTypeOutEmb8type OBJECT-TYPE
		SYNTAX		RollCallString
		MAX-ACCESS		read-only
		STATUS			current
		DESCRIPTION
				"TYPE: - Display
				 PAGE: - Logging
					Out Emb.8 type=  cmdID= 36937  format=   "
		::= { iqudc00CmdEntry 36937 }


	iqudc00LoggingOPAudLevelLogOutEmb1LLev OBJECT-TYPE
		SYNTAX		INTEGER { disable(0), enable(1) }
		MAX-ACCESS		read-write
		STATUS			current
		DESCRIPTION
				"TYPE: - Checkbox
				 PAGE: - Logging
					Log Out Emb.1-L Lev  cmdID= 35900 "
		::= { iqudc00CmdEntry 35900 }


	iqudc00LoggingOPAudLevelOutEmb1LLevel OBJECT-TYPE
		SYNTAX		RollCallString
		MAX-ACCESS		read-only
		STATUS			current
		DESCRIPTION
				"TYPE: - Display
				 PAGE: - Logging
					Out Emb.1-L Level=  cmdID= 36900  format=   "
		::= { iqudc00CmdEntry 36900 }


	iqudc00LoggingOPAudLevelLogOutEmb1RLev OBJECT-TYPE
		SYNTAX		INTEGER { disable(0), enable(1) }
		MAX-ACCESS		read-write
		STATUS			current
		DESCRIPTION
				"TYPE: - Checkbox
				 PAGE: - Logging
					Log Out Emb.1-R Lev  cmdID= 35901 "
		::= { iqudc00CmdEntry 35901 }


	iqudc00LoggingOPAudLevelOutEmb1RLevel OBJECT-TYPE
		SYNTAX		RollCallString
		MAX-ACCESS		read-only
		STATUS			current
		DESCRIPTION
				"TYPE: - Display
				 PAGE: - Logging
					Out Emb.1-R Level=  cmdID= 36901  format=   "
		::= { iqudc00CmdEntry 36901 }


	iqudc00LoggingOPAudLevelLogOutEmb2LLev OBJECT-TYPE
		SYNTAX		INTEGER { disable(0), enable(1) }
		MAX-ACCESS		read-write
		STATUS			current
		DESCRIPTION
				"TYPE: - Checkbox
				 PAGE: - Logging
					Log Out Emb.2-L Lev  cmdID= 35902 "
		::= { iqudc00CmdEntry 35902 }


	iqudc00LoggingOPAudLevelOutEmb2LLevel OBJECT-TYPE
		SYNTAX		RollCallString
		MAX-ACCESS		read-only
		STATUS			current
		DESCRIPTION
				"TYPE: - Display
				 PAGE: - Logging
					Out Emb.2-L Level=  cmdID= 36902  format=   "
		::= { iqudc00CmdEntry 36902 }


	iqudc00LoggingOPAudLevelLogOutEmb2RLev OBJECT-TYPE
		SYNTAX		INTEGER { disable(0), enable(1) }
		MAX-ACCESS		read-write
		STATUS			current
		DESCRIPTION
				"TYPE: - Checkbox
				 PAGE: - Logging
					Log Out Emb.2-R Lev  cmdID= 35903 "
		::= { iqudc00CmdEntry 35903 }


	iqudc00LoggingOPAudLevelOutEmb2RLevel OBJECT-TYPE
		SYNTAX		RollCallString
		MAX-ACCESS		read-only
		STATUS			current
		DESCRIPTION
				"TYPE: - Display
				 PAGE: - Logging
					Out Emb.2-R Level=  cmdID= 36903  format=   "
		::= { iqudc00CmdEntry 36903 }


	iqudc00LoggingOPAudLevelLogOutEmb3LLev OBJECT-TYPE
		SYNTAX		INTEGER { disable(0), enable(1) }
		MAX-ACCESS		read-write
		STATUS			current
		DESCRIPTION
				"TYPE: - Checkbox
				 PAGE: - Logging
					Log Out Emb.3-L Lev  cmdID= 35904 "
		::= { iqudc00CmdEntry 35904 }


	iqudc00LoggingOPAudLevelOutEmb3LLevel OBJECT-TYPE
		SYNTAX		RollCallString
		MAX-ACCESS		read-only
		STATUS			current
		DESCRIPTION
				"TYPE: - Display
				 PAGE: - Logging
					Out Emb.3-L Level=  cmdID= 36904  format=   "
		::= { iqudc00CmdEntry 36904 }


	iqudc00LoggingOPAudLevelLogOutEmb3RLev OBJECT-TYPE
		SYNTAX		INTEGER { disable(0), enable(1) }
		MAX-ACCESS		read-write
		STATUS			current
		DESCRIPTION
				"TYPE: - Checkbox
				 PAGE: - Logging
					Log Out Emb.3-R Lev  cmdID= 35905 "
		::= { iqudc00CmdEntry 35905 }


	iqudc00LoggingOPAudLevelOutEmb3RLevel OBJECT-TYPE
		SYNTAX		RollCallString
		MAX-ACCESS		read-only
		STATUS			current
		DESCRIPTION
				"TYPE: - Display
				 PAGE: - Logging
					Out Emb.3-R Level=  cmdID= 36905  format=   "
		::= { iqudc00CmdEntry 36905 }


	iqudc00LoggingOPAudLevelLogOutEmb4LLev OBJECT-TYPE
		SYNTAX		INTEGER { disable(0), enable(1) }
		MAX-ACCESS		read-write
		STATUS			current
		DESCRIPTION
				"TYPE: - Checkbox
				 PAGE: - Logging
					Log Out Emb.4-L Lev  cmdID= 35906 "
		::= { iqudc00CmdEntry 35906 }


	iqudc00LoggingOPAudLevelOutEmb4LLevel OBJECT-TYPE
		SYNTAX		RollCallString
		MAX-ACCESS		read-only
		STATUS			current
		DESCRIPTION
				"TYPE: - Display
				 PAGE: - Logging
					Out Emb.4-L Level=  cmdID= 36906  format=   "
		::= { iqudc00CmdEntry 36906 }


	iqudc00LoggingOPAudLevelLogOutEmb4RLev OBJECT-TYPE
		SYNTAX		INTEGER { disable(0), enable(1) }
		MAX-ACCESS		read-write
		STATUS			current
		DESCRIPTION
				"TYPE: - Checkbox
				 PAGE: - Logging
					Log Out Emb.4-R Lev  cmdID= 35907 "
		::= { iqudc00CmdEntry 35907 }


	iqudc00LoggingOPAudLevelOutEmb4RLevel OBJECT-TYPE
		SYNTAX		RollCallString
		MAX-ACCESS		read-only
		STATUS			current
		DESCRIPTION
				"TYPE: - Display
				 PAGE: - Logging
					Out Emb.4-R Level=  cmdID= 36907  format=   "
		::= { iqudc00CmdEntry 36907 }


	iqudc00LoggingOPAudLevelLogOutEmb5LLev OBJECT-TYPE
		SYNTAX		INTEGER { disable(0), enable(1) }
		MAX-ACCESS		read-write
		STATUS			current
		DESCRIPTION
				"TYPE: - Checkbox
				 PAGE: - Logging
					Log Out Emb.5-L Lev  cmdID= 35908 "
		::= { iqudc00CmdEntry 35908 }


	iqudc00LoggingOPAudLevelOutEmb5LLevel OBJECT-TYPE
		SYNTAX		RollCallString
		MAX-ACCESS		read-only
		STATUS			current
		DESCRIPTION
				"TYPE: - Display
				 PAGE: - Logging
					Out Emb.5-L Level=  cmdID= 36908  format=   "
		::= { iqudc00CmdEntry 36908 }


	iqudc00LoggingOPAudLevelLogOutEmb5RLev OBJECT-TYPE
		SYNTAX		INTEGER { disable(0), enable(1) }
		MAX-ACCESS		read-write
		STATUS			current
		DESCRIPTION
				"TYPE: - Checkbox
				 PAGE: - Logging
					Log Out Emb.5-R Lev  cmdID= 35909 "
		::= { iqudc00CmdEntry 35909 }


	iqudc00LoggingOPAudLevelOutEmb5RLevel OBJECT-TYPE
		SYNTAX		RollCallString
		MAX-ACCESS		read-only
		STATUS			current
		DESCRIPTION
				"TYPE: - Display
				 PAGE: - Logging
					Out Emb.5-R Level=  cmdID= 36909  format=   "
		::= { iqudc00CmdEntry 36909 }


	iqudc00LoggingOPAudLevelLogOutEmb6LLev OBJECT-TYPE
		SYNTAX		INTEGER { disable(0), enable(1) }
		MAX-ACCESS		read-write
		STATUS			current
		DESCRIPTION
				"TYPE: - Checkbox
				 PAGE: - Logging
					Log Out Emb.6-L Lev  cmdID= 35910 "
		::= { iqudc00CmdEntry 35910 }


	iqudc00LoggingOPAudLevelOutEmb6LLevel OBJECT-TYPE
		SYNTAX		RollCallString
		MAX-ACCESS		read-only
		STATUS			current
		DESCRIPTION
				"TYPE: - Display
				 PAGE: - Logging
					Out Emb.6-L Level=  cmdID= 36910  format=   "
		::= { iqudc00CmdEntry 36910 }


	iqudc00LoggingOPAudLevelLogOutEmb6RLev OBJECT-TYPE
		SYNTAX		INTEGER { disable(0), enable(1) }
		MAX-ACCESS		read-write
		STATUS			current
		DESCRIPTION
				"TYPE: - Checkbox
				 PAGE: - Logging
					Log Out Emb.6-R Lev  cmdID= 35911 "
		::= { iqudc00CmdEntry 35911 }


	iqudc00LoggingOPAudLevelOutEmb6RLevel OBJECT-TYPE
		SYNTAX		RollCallString
		MAX-ACCESS		read-only
		STATUS			current
		DESCRIPTION
				"TYPE: - Display
				 PAGE: - Logging
					Out Emb.6-R Level=  cmdID= 36911  format=   "
		::= { iqudc00CmdEntry 36911 }


	iqudc00LoggingOPAudLevelLogOutEmb7LLev OBJECT-TYPE
		SYNTAX		INTEGER { disable(0), enable(1) }
		MAX-ACCESS		read-write
		STATUS			current
		DESCRIPTION
				"TYPE: - Checkbox
				 PAGE: - Logging
					Log Out Emb.7-L Lev  cmdID= 35912 "
		::= { iqudc00CmdEntry 35912 }


	iqudc00LoggingOPAudLevelOutEmb7LLevel OBJECT-TYPE
		SYNTAX		RollCallString
		MAX-ACCESS		read-only
		STATUS			current
		DESCRIPTION
				"TYPE: - Display
				 PAGE: - Logging
					Out Emb.7-L Level=  cmdID= 36912  format=   "
		::= { iqudc00CmdEntry 36912 }


	iqudc00LoggingOPAudLevelLogOutEmb7RLev OBJECT-TYPE
		SYNTAX		INTEGER { disable(0), enable(1) }
		MAX-ACCESS		read-write
		STATUS			current
		DESCRIPTION
				"TYPE: - Checkbox
				 PAGE: - Logging
					Log Out Emb.7-R Lev  cmdID= 35913 "
		::= { iqudc00CmdEntry 35913 }


	iqudc00LoggingOPAudLevelOutEmb7RLevel OBJECT-TYPE
		SYNTAX		RollCallString
		MAX-ACCESS		read-only
		STATUS			current
		DESCRIPTION
				"TYPE: - Display
				 PAGE: - Logging
					Out Emb.7-R Level=  cmdID= 36913  format=   "
		::= { iqudc00CmdEntry 36913 }


	iqudc00LoggingOPAudLevelLogOutEmb8LLev OBJECT-TYPE
		SYNTAX		INTEGER { disable(0), enable(1) }
		MAX-ACCESS		read-write
		STATUS			current
		DESCRIPTION
				"TYPE: - Checkbox
				 PAGE: - Logging
					Log Out Emb.8-L Lev  cmdID= 35914 "
		::= { iqudc00CmdEntry 35914 }


	iqudc00LoggingOPAudLevelOutEmb8LLevel OBJECT-TYPE
		SYNTAX		RollCallString
		MAX-ACCESS		read-only
		STATUS			current
		DESCRIPTION
				"TYPE: - Display
				 PAGE: - Logging
					Out Emb.8-L Level=  cmdID= 36914  format=   "
		::= { iqudc00CmdEntry 36914 }


	iqudc00LoggingOPAudLevelLogOutEmb8RLev OBJECT-TYPE
		SYNTAX		INTEGER { disable(0), enable(1) }
		MAX-ACCESS		read-write
		STATUS			current
		DESCRIPTION
				"TYPE: - Checkbox
				 PAGE: - Logging
					Log Out Emb.8-R Lev  cmdID= 35915 "
		::= { iqudc00CmdEntry 35915 }


	iqudc00LoggingOPAudLevelOutEmb8RLevel OBJECT-TYPE
		SYNTAX		RollCallString
		MAX-ACCESS		read-only
		STATUS			current
		DESCRIPTION
				"TYPE: - Display
				 PAGE: - Logging
					Out Emb.8-R Level=  cmdID= 36915  format=   "
		::= { iqudc00CmdEntry 36915 }


	iqudc00LoggingRefOutputLogOutputState OBJECT-TYPE
		SYNTAX		INTEGER { disable(0), enable(1) }
		MAX-ACCESS		read-write
		STATUS			current
		DESCRIPTION
				"TYPE: - Checkbox
				 PAGE: - Logging
					Log Output State  cmdID= 35941 "
		::= { iqudc00CmdEntry 35941 }


	iqudc00LoggingRefOutputOutputState OBJECT-TYPE
		SYNTAX		RollCallString
		MAX-ACCESS		read-only
		STATUS			current
		DESCRIPTION
				"TYPE: - Display
				 PAGE: - Logging
					Output State=  cmdID= 36941  format=   "
		::= { iqudc00CmdEntry 36941 }


	iqudc00LoggingRefOutputLogOutputType OBJECT-TYPE
		SYNTAX		INTEGER { disable(0), enable(1) }
		MAX-ACCESS		read-write
		STATUS			current
		DESCRIPTION
				"TYPE: - Checkbox
				 PAGE: - Logging
					Log Output Type  cmdID= 35942 "
		::= { iqudc00CmdEntry 35942 }


	iqudc00LoggingRefOutputOutputType OBJECT-TYPE
		SYNTAX		RollCallString
		MAX-ACCESS		read-only
		STATUS			current
		DESCRIPTION
				"TYPE: - Display
				 PAGE: - Logging
					Output Type=  cmdID= 36942  format=   "
		::= { iqudc00CmdEntry 36942 }


	iqudc00LoggingRefOutputLogOutputStandard OBJECT-TYPE
		SYNTAX		INTEGER { disable(0), enable(1) }
		MAX-ACCESS		read-write
		STATUS			current
		DESCRIPTION
				"TYPE: - Checkbox
				 PAGE: - Logging
					Log Output Standard  cmdID= 35940 "
		::= { iqudc00CmdEntry 35940 }


	iqudc00LoggingRefOutputOutputStandard OBJECT-TYPE
		SYNTAX		RollCallString
		MAX-ACCESS		read-only
		STATUS			current
		DESCRIPTION
				"TYPE: - Display
				 PAGE: - Logging
					Output Standard=  cmdID= 36940  format=   "
		::= { iqudc00CmdEntry 36940 }


	iqudc00LoggingRefOutputLogOutputSource OBJECT-TYPE
		SYNTAX		INTEGER { disable(0), enable(1) }
		MAX-ACCESS		read-write
		STATUS			current
		DESCRIPTION
				"TYPE: - Checkbox
				 PAGE: - Logging
					Log Output Source  cmdID= 35943 "
		::= { iqudc00CmdEntry 35943 }


	iqudc00LoggingRefOutputOutputSource OBJECT-TYPE
		SYNTAX		RollCallString
		MAX-ACCESS		read-only
		STATUS			current
		DESCRIPTION
				"TYPE: - Display
				 PAGE: - Logging
					Output Source=  cmdID= 36943  format=   "
		::= { iqudc00CmdEntry 36943 }


	iqudc00LoggingRefOutputLogReferenceType OBJECT-TYPE
		SYNTAX		INTEGER { disable(0), enable(1) }
		MAX-ACCESS		read-write
		STATUS			current
		DESCRIPTION
				"TYPE: - Checkbox
				 PAGE: - Logging
					Log Reference Type  cmdID= 35995 "
		::= { iqudc00CmdEntry 35995 }


	iqudc00LoggingRefOutputReferenceType OBJECT-TYPE
		SYNTAX		RollCallString
		MAX-ACCESS		read-only
		STATUS			current
		DESCRIPTION
				"TYPE: - Display
				 PAGE: - Logging
					Reference Type=  cmdID= 36995  format=   "
		::= { iqudc00CmdEntry 36995 }


	iqudc00LoggingRefOutputLogReferenceState OBJECT-TYPE
		SYNTAX		INTEGER { disable(0), enable(1) }
		MAX-ACCESS		read-write
		STATUS			current
		DESCRIPTION
				"TYPE: - Checkbox
				 PAGE: - Logging
					Log Reference State  cmdID= 35004 "
		::= { iqudc00CmdEntry 35004 }


	iqudc00LoggingRefOutputReferenceState OBJECT-TYPE
		SYNTAX		RollCallString
		MAX-ACCESS		read-only
		STATUS			current
		DESCRIPTION
				"TYPE: - Display
				 PAGE: - Logging
					Reference State=  cmdID= 36004  format=   "
		::= { iqudc00CmdEntry 36004 }


	iqudc00LoggingRefOutputLogReferenceStand OBJECT-TYPE
		SYNTAX		INTEGER { disable(0), enable(1) }
		MAX-ACCESS		read-write
		STATUS			current
		DESCRIPTION
				"TYPE: - Checkbox
				 PAGE: - Logging
					Log Reference Stand  cmdID= 35014 "
		::= { iqudc00CmdEntry 35014 }


	iqudc00LoggingRefOutputReferenceStandard OBJECT-TYPE
		SYNTAX		RollCallString
		MAX-ACCESS		read-only
		STATUS			current
		DESCRIPTION
				"TYPE: - Display
				 PAGE: - Logging
					Reference Standard=  cmdID= 36014  format=   "
		::= { iqudc00CmdEntry 36014 }


	iqudc00LoggingMiscLogSerialNo OBJECT-TYPE
		SYNTAX		INTEGER { disable(0), enable(1) }
		MAX-ACCESS		read-write
		STATUS			current
		DESCRIPTION
				"TYPE: - Checkbox
				 PAGE: - Logging
					Log Serial No.  cmdID= 35015 "
		::= { iqudc00CmdEntry 35015 }


	iqudc00LoggingMiscSerialNo OBJECT-TYPE
		SYNTAX		RollCallString
		MAX-ACCESS		read-only
		STATUS			current
		DESCRIPTION
				"TYPE: - Display
				 PAGE: - Logging
					Serial No.=  cmdID= 36015  format=   "
		::= { iqudc00CmdEntry 36015 }


	iqudc00LoggingMiscLogOSVersion OBJECT-TYPE
		SYNTAX		INTEGER { disable(0), enable(1) }
		MAX-ACCESS		read-write
		STATUS			current
		DESCRIPTION
				"TYPE: - Checkbox
				 PAGE: - Logging
					Log OS Version  cmdID= 35993 "
		::= { iqudc00CmdEntry 35993 }


	iqudc00LoggingMiscOSVersion OBJECT-TYPE
		SYNTAX		RollCallString
		MAX-ACCESS		read-only
		STATUS			current
		DESCRIPTION
				"TYPE: - Display
				 PAGE: - Logging
					OS Version=  cmdID= 36993  format=   "
		::= { iqudc00CmdEntry 36993 }


	iqudc00LoggingMiscLogBuildNo OBJECT-TYPE
		SYNTAX		INTEGER { disable(0), enable(1) }
		MAX-ACCESS		read-write
		STATUS			current
		DESCRIPTION
				"TYPE: - Checkbox
				 PAGE: - Logging
					Log Build No.  cmdID= 35990 "
		::= { iqudc00CmdEntry 35990 }


	iqudc00LoggingMiscBuildNo OBJECT-TYPE
		SYNTAX		RollCallString
		MAX-ACCESS		read-only
		STATUS			current
		DESCRIPTION
				"TYPE: - Display
				 PAGE: - Logging
					Build No.=  cmdID= 36990  format=   "
		::= { iqudc00CmdEntry 36990 }


	iqudc00LoggingMiscLogHardwareVer OBJECT-TYPE
		SYNTAX		INTEGER { disable(0), enable(1) }
		MAX-ACCESS		read-write
		STATUS			current
		DESCRIPTION
				"TYPE: - Checkbox
				 PAGE: - Logging
					Log Hardware Ver.  cmdID= 35992 "
		::= { iqudc00CmdEntry 35992 }


	iqudc00LoggingMiscHardwareVer OBJECT-TYPE
		SYNTAX		RollCallString
		MAX-ACCESS		read-only
		STATUS			current
		DESCRIPTION
				"TYPE: - Display
				 PAGE: - Logging
					Hardware Ver.=  cmdID= 36992  format=   "
		::= { iqudc00CmdEntry 36992 }


	iqudc00LoggingMiscLogFirmwareVer OBJECT-TYPE
		SYNTAX		INTEGER { disable(0), enable(1) }
		MAX-ACCESS		read-write
		STATUS			current
		DESCRIPTION
				"TYPE: - Checkbox
				 PAGE: - Logging
					Log Firmware Ver.  cmdID= 35991 "
		::= { iqudc00CmdEntry 35991 }


	iqudc00LoggingMiscFirmwareVer OBJECT-TYPE
		SYNTAX		RollCallString
		MAX-ACCESS		read-only
		STATUS			current
		DESCRIPTION
				"TYPE: - Display
				 PAGE: - Logging
					Firmware Ver.=  cmdID= 36991  format=   "
		::= { iqudc00CmdEntry 36991 }


	iqudc00LoggingMiscLogUpTime OBJECT-TYPE
		SYNTAX		INTEGER { disable(0), enable(1) }
		MAX-ACCESS		read-write
		STATUS			current
		DESCRIPTION
				"TYPE: - Checkbox
				 PAGE: - Logging
					Log Up Time  cmdID= 35994 "
		::= { iqudc00CmdEntry 35994 }


	iqudc00LoggingMiscUpTime OBJECT-TYPE
		SYNTAX		RollCallString
		MAX-ACCESS		read-only
		STATUS			current
		DESCRIPTION
				"TYPE: - Display
				 PAGE: - Logging
					Up Time=  cmdID= 36994  format=   "
		::= { iqudc00CmdEntry 36994 }


	iqudc00LoggingWideScreenLogInput1Aspect OBJECT-TYPE
		SYNTAX		INTEGER { disable(0), enable(1) }
		MAX-ACCESS		read-write
		STATUS			current
		DESCRIPTION
				"TYPE: - Checkbox
				 PAGE: - Logging- WideScreen Logging
					Log Input 1 Aspect  cmdID= 35026 "
		::= { iqudc00CmdEntry 35026 }


	iqudc00LoggingWideScreenInput1Aspect OBJECT-TYPE
		SYNTAX		RollCallString
		MAX-ACCESS		read-only
		STATUS			current
		DESCRIPTION
				"TYPE: - Display
				 PAGE: - Logging- WideScreen Logging
					Input 1 Aspect=  cmdID= 36026  format=   "
		::= { iqudc00CmdEntry 36026 }


	iqudc00LoggingWideScreenLogInput1AFD OBJECT-TYPE
		SYNTAX		INTEGER { disable(0), enable(1) }
		MAX-ACCESS		read-write
		STATUS			current
		DESCRIPTION
				"TYPE: - Checkbox
				 PAGE: - Logging- WideScreen Logging
					Log Input 1 AFD  cmdID= 35027 "
		::= { iqudc00CmdEntry 35027 }


	iqudc00LoggingWideScreenInput1AFD OBJECT-TYPE
		SYNTAX		RollCallString
		MAX-ACCESS		read-only
		STATUS			current
		DESCRIPTION
				"TYPE: - Display
				 PAGE: - Logging- WideScreen Logging
					Input 1 AFD=  cmdID= 36027  format=   "
		::= { iqudc00CmdEntry 36027 }


	iqudc00LoggingWideScreenLogInput1WSS OBJECT-TYPE
		SYNTAX		INTEGER { disable(0), enable(1) }
		MAX-ACCESS		read-write
		STATUS			current
		DESCRIPTION
				"TYPE: - Checkbox
				 PAGE: - Logging- WideScreen Logging
					Log Input 1 WSS  cmdID= 35059 "
		::= { iqudc00CmdEntry 35059 }


	iqudc00LoggingWideScreenInput1WSS OBJECT-TYPE
		SYNTAX		RollCallString
		MAX-ACCESS		read-only
		STATUS			current
		DESCRIPTION
				"TYPE: - Display
				 PAGE: - Logging- WideScreen Logging
					Input 1 WSS=  cmdID= 36029  format=   "
		::= { iqudc00CmdEntry 36029 }


	iqudc00LoggingWideScreenLogInput1VI OBJECT-TYPE
		SYNTAX		INTEGER { disable(0), enable(1) }
		MAX-ACCESS		read-write
		STATUS			current
		DESCRIPTION
				"TYPE: - Checkbox
				 PAGE: - Logging- WideScreen Logging
					Log Input 1 VI  cmdID= 35058 "
		::= { iqudc00CmdEntry 35058 }


	iqudc00LoggingWideScreenInput1VI OBJECT-TYPE
		SYNTAX		RollCallString
		MAX-ACCESS		read-only
		STATUS			current
		DESCRIPTION
				"TYPE: - Display
				 PAGE: - Logging- WideScreen Logging
					Input 1 VI=  cmdID= 36028  format=   "
		::= { iqudc00CmdEntry 36028 }


	iqudc00LoggingWideScreenLogInput2Aspect OBJECT-TYPE
		SYNTAX		INTEGER { disable(0), enable(1) }
		MAX-ACCESS		read-write
		STATUS			current
		DESCRIPTION
				"TYPE: - Checkbox
				 PAGE: - Logging- WideScreen Logging
					Log Input 2 Aspect  cmdID= 35056 "
		::= { iqudc00CmdEntry 35056 }


	iqudc00LoggingWideScreenInput2Aspect OBJECT-TYPE
		SYNTAX		RollCallString
		MAX-ACCESS		read-only
		STATUS			current
		DESCRIPTION
				"TYPE: - Display
				 PAGE: - Logging- WideScreen Logging
					Input 2 Aspect=  cmdID= 36056  format=   "
		::= { iqudc00CmdEntry 36056 }


	iqudc00LoggingWideScreenLogInput2AFD OBJECT-TYPE
		SYNTAX		INTEGER { disable(0), enable(1) }
		MAX-ACCESS		read-write
		STATUS			current
		DESCRIPTION
				"TYPE: - Checkbox
				 PAGE: - Logging- WideScreen Logging
					Log Input 2 AFD  cmdID= 35057 "
		::= { iqudc00CmdEntry 35057 }


	iqudc00LoggingWideScreenInput2AFD OBJECT-TYPE
		SYNTAX		RollCallString
		MAX-ACCESS		read-only
		STATUS			current
		DESCRIPTION
				"TYPE: - Display
				 PAGE: - Logging- WideScreen Logging
					Input 2 AFD=  cmdID= 36057  format=   "
		::= { iqudc00CmdEntry 36057 }


	iqudc00LoggingWideScreenLogInput2WSS OBJECT-TYPE
		SYNTAX		INTEGER { disable(0), enable(1) }
		MAX-ACCESS		read-write
		STATUS			current
		DESCRIPTION
				"TYPE: - Checkbox
				 PAGE: - Logging- WideScreen Logging
					Log Input 2 WSS  cmdID= 35029 "
		::= { iqudc00CmdEntry 35029 }


	iqudc00LoggingWideScreenInput2WSS OBJECT-TYPE
		SYNTAX		RollCallString
		MAX-ACCESS		read-only
		STATUS			current
		DESCRIPTION
				"TYPE: - Display
				 PAGE: - Logging- WideScreen Logging
					Input 2 WSS=  cmdID= 36059  format=   "
		::= { iqudc00CmdEntry 36059 }


	iqudc00LoggingWideScreenLogInput2VI OBJECT-TYPE
		SYNTAX		INTEGER { disable(0), enable(1) }
		MAX-ACCESS		read-write
		STATUS			current
		DESCRIPTION
				"TYPE: - Checkbox
				 PAGE: - Logging- WideScreen Logging
					Log Input 2 VI  cmdID= 35028 "
		::= { iqudc00CmdEntry 35028 }


	iqudc00LoggingWideScreenInput2VI OBJECT-TYPE
		SYNTAX		RollCallString
		MAX-ACCESS		read-only
		STATUS			current
		DESCRIPTION
				"TYPE: - Display
				 PAGE: - Logging- WideScreen Logging
					Input 2 VI=  cmdID= 36058  format=   "
		::= { iqudc00CmdEntry 36058 }


	iqudc00LoggingWideScreenLogOutputAspect OBJECT-TYPE
		SYNTAX		INTEGER { disable(0), enable(1) }
		MAX-ACCESS		read-write
		STATUS			current
		DESCRIPTION
				"TYPE: - Checkbox
				 PAGE: - Logging- WideScreen Logging
					Log Output AFD  cmdID= 35944 "
		::= { iqudc00CmdEntry 35944 }


	iqudc00LoggingWideScreenOutputAspect OBJECT-TYPE
		SYNTAX		RollCallString
		MAX-ACCESS		read-only
		STATUS			current
		DESCRIPTION
				"TYPE: - Display
				 PAGE: - Logging- WideScreen Logging
					Output AFD=  cmdID= 36944  format=   "
		::= { iqudc00CmdEntry 36944 }


	iqudc00LoggingWideScreenLogOutputAFD OBJECT-TYPE
		SYNTAX		INTEGER { disable(0), enable(1) }
		MAX-ACCESS		read-write
		STATUS			current
		DESCRIPTION
				"TYPE: - Checkbox
				 PAGE: - Logging- WideScreen Logging
					Log Output AFD  cmdID= 35945 "
		::= { iqudc00CmdEntry 35945 }


	iqudc00LoggingWideScreenOutputAFD OBJECT-TYPE
		SYNTAX		RollCallString
		MAX-ACCESS		read-only
		STATUS			current
		DESCRIPTION
				"TYPE: - Display
				 PAGE: - Logging- WideScreen Logging
					Output AFD=  cmdID= 36945  format=   "
		::= { iqudc00CmdEntry 36945 }


	iqudc00LoggingOPDolbyELogEmbDolbyE1 OBJECT-TYPE
		SYNTAX		INTEGER { disable(0), enable(1) }
		MAX-ACCESS		read-write
		STATUS			current
		DESCRIPTION
				"TYPE: - Checkbox
				 PAGE: - Logging
					Log Emb DolbyE 1  cmdID= 35950 "
		::= { iqudc00CmdEntry 35950 }


	iqudc00LoggingOPDolbyEEmbDolbyE1 OBJECT-TYPE
		SYNTAX		RollCallString
		MAX-ACCESS		read-only
		STATUS			current
		DESCRIPTION
				"TYPE: - Display
				 PAGE: - Logging
					Emb DolbyE 1=  cmdID= 36950  format=   "
		::= { iqudc00CmdEntry 36950 }


	iqudc00LoggingOPDolbyELogEmbDolbyE2 OBJECT-TYPE
		SYNTAX		INTEGER { disable(0), enable(1) }
		MAX-ACCESS		read-write
		STATUS			current
		DESCRIPTION
				"TYPE: - Checkbox
				 PAGE: - Logging
					Log Emb DolbyE 2  cmdID= 35951 "
		::= { iqudc00CmdEntry 35951 }


	iqudc00LoggingOPDolbyEEmbDolbyE2 OBJECT-TYPE
		SYNTAX		RollCallString
		MAX-ACCESS		read-only
		STATUS			current
		DESCRIPTION
				"TYPE: - Display
				 PAGE: - Logging
					Emb DolbyE 2=  cmdID= 36951  format=   "
		::= { iqudc00CmdEntry 36951 }


	iqudc00LoggingOPDolbyELogEmbDolbyE3 OBJECT-TYPE
		SYNTAX		INTEGER { disable(0), enable(1) }
		MAX-ACCESS		read-write
		STATUS			current
		DESCRIPTION
				"TYPE: - Checkbox
				 PAGE: - Logging
					Log Emb DolbyE 3  cmdID= 35952 "
		::= { iqudc00CmdEntry 35952 }


	iqudc00LoggingOPDolbyEEmbDolbyE3 OBJECT-TYPE
		SYNTAX		RollCallString
		MAX-ACCESS		read-only
		STATUS			current
		DESCRIPTION
				"TYPE: - Display
				 PAGE: - Logging
					Emb DolbyE 3=  cmdID= 36952  format=   "
		::= { iqudc00CmdEntry 36952 }


	iqudc00LoggingOPDolbyELogEmbDolbyE4 OBJECT-TYPE
		SYNTAX		INTEGER { disable(0), enable(1) }
		MAX-ACCESS		read-write
		STATUS			current
		DESCRIPTION
				"TYPE: - Checkbox
				 PAGE: - Logging
					Log Emb DolbyE 4  cmdID= 35953 "
		::= { iqudc00CmdEntry 35953 }


	iqudc00LoggingOPDolbyEEmbDolbyE4 OBJECT-TYPE
		SYNTAX		RollCallString
		MAX-ACCESS		read-only
		STATUS			current
		DESCRIPTION
				"TYPE: - Display
				 PAGE: - Logging
					Emb DolbyE 4=  cmdID= 36953  format=   "
		::= { iqudc00CmdEntry 36953 }


	iqudc00LoggingOPDolbyELogEmbDolbyE5 OBJECT-TYPE
		SYNTAX		INTEGER { disable(0), enable(1) }
		MAX-ACCESS		read-write
		STATUS			current
		DESCRIPTION
				"TYPE: - Checkbox
				 PAGE: - Logging
					Log Emb DolbyE 5  cmdID= 35954 "
		::= { iqudc00CmdEntry 35954 }


	iqudc00LoggingOPDolbyEEmbDolbyE5 OBJECT-TYPE
		SYNTAX		RollCallString
		MAX-ACCESS		read-only
		STATUS			current
		DESCRIPTION
				"TYPE: - Display
				 PAGE: - Logging
					Emb DolbyE 5=  cmdID= 36954  format=   "
		::= { iqudc00CmdEntry 36954 }


	iqudc00LoggingOPDolbyELogEmbDolbyE6 OBJECT-TYPE
		SYNTAX		INTEGER { disable(0), enable(1) }
		MAX-ACCESS		read-write
		STATUS			current
		DESCRIPTION
				"TYPE: - Checkbox
				 PAGE: - Logging
					Log Emb DolbyE 6  cmdID= 35955 "
		::= { iqudc00CmdEntry 35955 }


	iqudc00LoggingOPDolbyEEmbDolbyE6 OBJECT-TYPE
		SYNTAX		RollCallString
		MAX-ACCESS		read-only
		STATUS			current
		DESCRIPTION
				"TYPE: - Display
				 PAGE: - Logging
					Emb DolbyE 6=  cmdID= 36955  format=   "
		::= { iqudc00CmdEntry 36955 }


	iqudc00LoggingOPDolbyELogEmbDolbyE7 OBJECT-TYPE
		SYNTAX		INTEGER { disable(0), enable(1) }
		MAX-ACCESS		read-write
		STATUS			current
		DESCRIPTION
				"TYPE: - Checkbox
				 PAGE: - Logging
					Log Emb DolbyE 7  cmdID= 35956 "
		::= { iqudc00CmdEntry 35956 }


	iqudc00LoggingOPDolbyEEmbDolbyE7 OBJECT-TYPE
		SYNTAX		RollCallString
		MAX-ACCESS		read-only
		STATUS			current
		DESCRIPTION
				"TYPE: - Display
				 PAGE: - Logging
					Emb DolbyE 7=  cmdID= 36956  format=   "
		::= { iqudc00CmdEntry 36956 }


	iqudc00LoggingOPDolbyELogEmbDolbyE8 OBJECT-TYPE
		SYNTAX		INTEGER { disable(0), enable(1) }
		MAX-ACCESS		read-write
		STATUS			current
		DESCRIPTION
				"TYPE: - Checkbox
				 PAGE: - Logging
					Log Emb DolbyE 8  cmdID= 35957 "
		::= { iqudc00CmdEntry 35957 }


	iqudc00LoggingOPDolbyEEmbDolbyE8 OBJECT-TYPE
		SYNTAX		RollCallString
		MAX-ACCESS		read-only
		STATUS			current
		DESCRIPTION
				"TYPE: - Display
				 PAGE: - Logging
					Emb DolbyE 8=  cmdID= 36957  format=   "
		::= { iqudc00CmdEntry 36957 }


	iqudc00SetupProduct OBJECT-TYPE
		SYNTAX		RollCallString
		MAX-ACCESS		read-only
		STATUS			current
		DESCRIPTION
				"TYPE: - Display
					Product  cmdID= 32771  format=   "
		::= { iqudc00CmdEntry 32771 }


	iqudc00SetupProductSerial OBJECT-TYPE
		SYNTAX		RollCallString
		MAX-ACCESS		read-only
		STATUS			current
		DESCRIPTION
				"TYPE: - Display
					Serial  cmdID= 1  format=   "
		::= { iqudc00CmdEntry 1 }


	iqudc00SetupProductPCB OBJECT-TYPE
		SYNTAX		RollCallString
		MAX-ACCESS		read-only
		STATUS			current
		DESCRIPTION
				"TYPE: - Display
					PCB  cmdID= 32770  format=   "
		::= { iqudc00CmdEntry 32770 }


	iqudc00SetupRestart OBJECT-TYPE
		SYNTAX		INTEGER { noAction(0),val_Restart(1) }
		MAX-ACCESS		read-write
		STATUS			current
		DESCRIPTION
				"TYPE: - Button
					Restart  cmdID= 4  value= 1  "
		::= { iqudc00CmdEntry 4 }


	iqudc00SetupSoftwareRelease OBJECT-TYPE
		SYNTAX		RollCallString
		MAX-ACCESS		read-only
		STATUS			current
		DESCRIPTION
				"TYPE: - Display
					Release  cmdID= 2  format=   "
		::= { iqudc00CmdEntry 2 }


	iqudc00SetupSoftwareBuild OBJECT-TYPE
		SYNTAX		RollCallString
		MAX-ACCESS		read-only
		STATUS			current
		DESCRIPTION
				"TYPE: - Display
					Build  cmdID= 5  format=   "
		::= { iqudc00CmdEntry 5 }


	iqudc00SetupSoftwareKOS OBJECT-TYPE
		SYNTAX		RollCallString
		MAX-ACCESS		read-only
		STATUS			current
		DESCRIPTION
				"TYPE: - Display
					KOS  cmdID= 32772  format=   "
		::= { iqudc00CmdEntry 32772 }


	iqudc00SetupFactory OBJECT-TYPE
		SYNTAX		INTEGER { noAction(0),val_Factory(1) }
		MAX-ACCESS		read-write
		STATUS			current
		DESCRIPTION
				"TYPE: - Button
					Factory  cmdID= 37002  value= 1  "
		::= { iqudc00CmdEntry 37002 }


	iqudc00SetupFirmwareMIO OBJECT-TYPE
		SYNTAX		RollCallString
		MAX-ACCESS		read-only
		STATUS			current
		DESCRIPTION
				"TYPE: - Display
					MIO  cmdID= 32769  format=   "
		::= { iqudc00CmdEntry 32769 }


	iqudc00SetupFirmwareMV OBJECT-TYPE
		SYNTAX		RollCallString
		MAX-ACCESS		read-only
		STATUS			current
		DESCRIPTION
				"TYPE: - Display
					MV  cmdID= 32780  format=   "
		::= { iqudc00CmdEntry 32780 }


	iqudc00SetupFirmwareMH OBJECT-TYPE
		SYNTAX		RollCallString
		MAX-ACCESS		read-only
		STATUS			current
		DESCRIPTION
				"TYPE: - Display
					MH  cmdID= 32781  format=   "
		::= { iqudc00CmdEntry 32781 }


	iqudc00SetupDisplay OBJECT-TYPE
		SYNTAX		INTEGER {
							val_Video_Status(0),
							val_Wide_Screen_Signal(2),
							val_Audio_Status(1)
							}
		MAX-ACCESS		read-write
		STATUS			current
		DESCRIPTION
				"TYPE: - RadiobuttonList
					Display  cmdID= 32773
					Video Status  value= 0
					Wide Screen Signal  value= 2
					Audio Status  value= 1  "
		::= { iqudc00CmdEntry 32773 }


	iqudc00DiagnosticsSelectTestVideoMemtest OBJECT-TYPE
		SYNTAX		INTEGER {
							val_GPIO_test(1),
							val_Video_Mem_test(3),
							val_SDI_1_1_test(4),
							val_SDI_2_1_test(5),
							val_SDI_3_2_test(6),
							val_SDI_4_2_test(7),
							val_SRC_test(8),
							val_LVDS_test(9)
							}
		MAX-ACCESS		read-write
		STATUS			current
		DESCRIPTION
				"TYPE: - Button
					GPIO test  cmdID= 36500  value= 1
					Video Mem test  cmdID= 36500  value= 3
					SDI 1-1 test  cmdID= 36500  value= 4
					SDI 2-1 test  cmdID= 36500  value= 5
					SDI 3-2 test  cmdID= 36500  value= 6
					SDI 4-2 test  cmdID= 36500  value= 7
					SRC test  cmdID= 36500  value= 8
					LVDS test  cmdID= 36500  value= 9  "
		::= { iqudc00CmdEntry 36500 }


	iqudc00DiagnosticsSelectTestVideoMemloop OBJECT-TYPE
		SYNTAX		INTEGER {
							val_GPIO_loop(1),
							val_Video_Mem_loop(3),
							val_SDI_1_1_loop(4),
							val_SDI_2_1_loop(5),
							val_SDI_3_2_loop(6),
							val_SDI_4_2_loop(7),
							val_SRC_loop(8),
							val_LVDS_loop(9)
							}
		MAX-ACCESS		read-write
		STATUS			current
		DESCRIPTION
				"TYPE: - Button
					GPIO loop  cmdID= 36501  value= 1
					Video Mem loop  cmdID= 36501  value= 3
					SDI 1-1 loop  cmdID= 36501  value= 4
					SDI 2-1 loop  cmdID= 36501  value= 5
					SDI 3-2 loop  cmdID= 36501  value= 6
					SDI 4-2 loop  cmdID= 36501  value= 7
					SRC loop  cmdID= 36501  value= 8
					LVDS loop  cmdID= 36501  value= 9  "
		::= { iqudc00CmdEntry 36501 }


	iqudc00DiagnosticsDiagnosticErrorsLoopCount OBJECT-TYPE
		SYNTAX		RollCallString
		MAX-ACCESS		read-only
		STATUS			current
		DESCRIPTION
				"TYPE: - Display
					Loop Count  cmdID= 36526  format=   "
		::= { iqudc00CmdEntry 36526 }


	iqudc00DiagnosticsDiagnosticErrorsProgress OBJECT-TYPE
		SYNTAX		RollCallString
		MAX-ACCESS		read-only
		STATUS			current
		DESCRIPTION
				"TYPE: - Display
					Progress  cmdID= 36505  format=   "
		::= { iqudc00CmdEntry 36505 }


	iqudc00DiagnosticsDiagnosticErrorsGpIoErrs OBJECT-TYPE
		SYNTAX		RollCallString
		MAX-ACCESS		read-only
		STATUS			current
		DESCRIPTION
				"TYPE: - Display
					GpIo Errs  cmdID= 36520  format=   "
		::= { iqudc00CmdEntry 36520 }


	iqudc00DiagnosticsDiagnosticErrorsVideoMemErrs OBJECT-TYPE
		SYNTAX		RollCallString
		MAX-ACCESS		read-only
		STATUS			current
		DESCRIPTION
				"TYPE: - Display
					Video Mem Errs  cmdID= 36521  format=   "
		::= { iqudc00CmdEntry 36521 }


	iqudc00DiagnosticsDiagnosticErrorsSDI1Errs OBJECT-TYPE
		SYNTAX		RollCallString
		MAX-ACCESS		read-only
		STATUS			current
		DESCRIPTION
				"TYPE: - Display
					SDI1 Errs  cmdID= 36522  format=   "
		::= { iqudc00CmdEntry 36522 }


	iqudc00DiagnosticsDiagnosticErrorsSDI2Errs OBJECT-TYPE
		SYNTAX		RollCallString
		MAX-ACCESS		read-only
		STATUS			current
		DESCRIPTION
				"TYPE: - Display
					SDI2 Errs  cmdID= 36523  format=   "
		::= { iqudc00CmdEntry 36523 }


	iqudc00DiagnosticsDiagnosticErrorsSDI3Errs OBJECT-TYPE
		SYNTAX		RollCallString
		MAX-ACCESS		read-only
		STATUS			current
		DESCRIPTION
				"TYPE: - Display
					SDI3 Errs  cmdID= 36524  format=   "
		::= { iqudc00CmdEntry 36524 }


	iqudc00DiagnosticsDiagnosticErrorsSDI4Errs OBJECT-TYPE
		SYNTAX		RollCallString
		MAX-ACCESS		read-only
		STATUS			current
		DESCRIPTION
				"TYPE: - Display
					SDI4 Errs  cmdID= 36525  format=   "
		::= { iqudc00CmdEntry 36525 }


	iqudc00DiagnosticsDiagnosticErrorsSRCErrs OBJECT-TYPE
		SYNTAX		RollCallString
		MAX-ACCESS		read-only
		STATUS			current
		DESCRIPTION
				"TYPE: - Display
					SRC Errs  cmdID= 36527  format=   "
		::= { iqudc00CmdEntry 36527 }


	iqudc00DiagnosticsDiagnosticErrorsLVDSErrs OBJECT-TYPE
		SYNTAX		RollCallString
		MAX-ACCESS		read-only
		STATUS			current
		DESCRIPTION
				"TYPE: - Display
					LVDS Errs  cmdID= 36529  format=   "
		::= { iqudc00CmdEntry 36529 }


	iqudc00DiagnosticsSTOPTests OBJECT-TYPE
		SYNTAX		INTEGER { noAction(0),val_STOP_Tests(1) }
		MAX-ACCESS		read-write
		STATUS			current
		DESCRIPTION
				"TYPE: - Button
					STOP Tests  cmdID= 36502  value= 1  "
		::= { iqudc00CmdEntry 36502 }


	iqudc00DiagnosticsTestId OBJECT-TYPE
		SYNTAX		RollCallString
		MAX-ACCESS		read-only
		STATUS			current
		DESCRIPTION
				"TYPE: - Display
					Test Id:  cmdID= 36506  format=   "
		::= { iqudc00CmdEntry 36506 }


	iqudc00DiagnosticsLastError OBJECT-TYPE
		SYNTAX		RollCallString
		MAX-ACCESS		read-only
		STATUS			current
		DESCRIPTION
				"TYPE: - Display
					Last Error  cmdID= 36507  format=   "
		::= { iqudc00CmdEntry 36507 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: s35122541
--				:
-- Comments		:
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 00-00-00 01:30Z
--				:
-- Comments		: Uptime in formated date-time string
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: INP 1
--				: INP 2
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number of current control sessions
--
---------------------------------------------------------------------------------------------------
-- Header		: INPUT_1_VI
--
-- MIB ref		: swCardEventLogSlotXX       .10.73.78.80.85.84.95.49.95.86.73
-- absolute OID	: 1.3.6.1.4.1.7995.2.6.1.1.XX.10.73.78.80.85.84.95.49.95.86.73
-- Vary			: YES
--
-- Value(s)		: NONE
--				: OK
--				: ERROR
--				: Unknown
-- Comments		:
--
---------------------------------------------------------------------------------------------------
-- Header		: INPUT_2_VI
--
-- MIB ref		: swCardEventLogSlotXX       .10.73.78.80.85.84.95.50.95.86.73
-- absolute OID	: 1.3.6.1.4.1.7995.2.6.1.1.XX.10.73.78.80.85.84.95.50.95.86.73
-- Vary			: YES
--
-- Value(s)		: NONE
--				: OK
--				: ERROR
--				: Unknown
-- Comments		:
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: K_OS: V115 Release
--				:
-- Comments		: String
--
---------------------------------------------------------------------------------------------------
-- Header		: INPUT_1_AFD
--
-- MIB ref		: swCardEventLogSlotXX       .11.73.78.80.85.84.95.49.95.65.70.68
-- absolute OID	: 1.3.6.1.4.1.7995.2.6.1.1.XX.11.73.78.80.85.84.95.49.95.65.70.68
-- Vary			: YES
--
-- Value(s)		: <Disabled>
--              : Reserved (0)
--              : Reserved (1)
--              : Box 16:9(top)
--              : Box 14:9(top)
--              : Box>16:9(ctr)
--              : Reserved (5)
--              : Reserved (6)
--              : Reserved (7)
--              : Coded Frame
--              : 4:3 (center)
--              : 16:9 (center)
--              : 14:9 (center)
--              : Reserved (12)
--              : 4:3 SP 14:9
--              : 16:9 SP 14:9
--              : 16:9 SP 4:3
--              : Unknown
-- Comments		:
--
---------------------------------------------------------------------------------------------------
-- Header		: INPUT_1_WSS
--
-- MIB ref		: swCardEventLogSlotXX       .11.73.78.80.85.84.95.49.95.87.83.83
-- absolute OID	: 1.3.6.1.4.1.7995.2.6.1.1.XX.11.73.78.80.85.84.95.49.95.87.83.83
-- Vary			: YES
--
-- Value(s)		: NONE
--				: OK
--				: ERROR
--				: Unknown
-- Comments		:
--
---------------------------------------------------------------------------------------------------
-- Header		: INPUT_2_AFD
--
-- MIB ref		: swCardEventLogSlotXX       .11.73.78.80.85.84.95.50.95.65.70.68
-- absolute OID	: 1.3.6.1.4.1.7995.2.6.1.1.XX.11.73.78.80.85.84.95.50.95.65.70.68
-- Vary			: YES
--
-- Value(s)		: <Disabled>
--              : Reserved (0)
--              : Reserved (1)
--              : Box 16:9(top)
--              : Box 14:9(top)
--              : Box>16:9(ctr)
--              : Reserved (5)
--              : Reserved (6)
--              : Reserved (7)
--              : Coded Frame
--              : 4:3 (center)
--              : 16:9 (center)
--              : 14:9 (center)
--              : Reserved (12)
--              : 4:3 SP 14:9
--              : 16:9 SP 14:9
--              : 16:9 SP 4:3
--              : Unknown
-- Comments		:
--
---------------------------------------------------------------------------------------------------
-- Header		: INPUT_2_WSS
--
-- MIB ref		: swCardEventLogSlotXX       .11.73.78.80.85.84.95.50.95.87.83.83
-- absolute OID	: 1.3.6.1.4.1.7995.2.6.1.1.XX.11.73.78.80.85.84.95.50.95.87.83.83
-- Vary			: YES
--
-- Value(s)		: NONE
--				: OK
--				: ERROR
--				: Unknown
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 0010501685
--				:
-- Comments		: String of current Software build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: NO
--
-- Value(s)		: HD / SD SDI
--				:
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: NO
--
-- Value(s)		: HD / SD SDI
--				:
-- Comments		:
--
---------------------------------------------------------------------------------------------------
-- Header		: OUTPUT_1_AFD
--
-- MIB ref		: swCardEventLogSlotXX       .12.79.85.84.80.85.84.95.49.95.65.70.68
-- absolute OID	: 1.3.6.1.4.1.7995.2.6.1.1.XX.12.79.85.84.80.85.84.95.49.95.65.70.68
-- Vary			: YES
--
-- Value(s)		: <Disabled>
--              : Reserved (0)
--              : Reserved (1)
--              : Box 16:9(top)
--              : Box 14:9(top)
--              : Box>16:9(ctr)
--              : Reserved (5)
--              : Reserved (6)
--              : Reserved (7)
--              : Coded Frame
--              : 4:3 (center)
--              : 16:9 (center)
--              : 14:9 (center)
--              : Reserved (12)
--              : 4:3 SP 14:9
--              : 16:9 SP 14:9
--              : 16:9 SP 4:3
--              : Unknown
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2008-01-10T10:08:38Z
--				:
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
--              : FAIL:Error
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: OK
--              : FAIL:Error
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2008-01-10T10:12:06Z
--				:
-- Comments		: Time of last control modify command
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: NO
--
-- Value(s)		: HD / SD SDI
--				:
-- Comments		:
--
---------------------------------------------------------------------------------------------------
-- Header		: INPUT_1_ASPECT
--
-- MIB ref		: swCardEventLogSlotXX       .14.73.78.80.85.84.95.49.95.65.83.80.69.67.84
-- absolute OID	: 1.3.6.1.4.1.7995.2.6.1.1.XX.14.73.78.80.85.84.95.49.95.65.83.80.69.67.84
-- Vary			: YES
--
-- Value(s)		: 16:9
--				: 4:3
--				: Unknown
-- Comments		:
--
---------------------------------------------------------------------------------------------------
-- Header		: INPUT_2_ASPECT
--
-- MIB ref		: swCardEventLogSlotXX       .14.73.78.80.85.84.95.50.95.65.83.80.69.67.84
-- absolute OID	: 1.3.6.1.4.1.7995.2.6.1.1.XX.14.73.78.80.85.84.95.50.95.65.83.80.69.67.84
-- Vary			: YES
--
-- Value(s)		: 16:9
--				: 4:3
--				: Unknown
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: NO
--
-- Value(s)		: OK
--				:
-- Comments		:
--
---------------------------------------------------------------------------------------------------
-- Header		: OUTPUT_1_ASPECT
--
-- MIB ref		: swCardEventLogSlotXX       .15.79.85.84.80.85.84.95.49.95.65.83.80.69.67.84
-- absolute OID	: 1.3.6.1.4.1.7995.2.6.1.1.XX.15.79.85.84.80.85.84.95.49.95.65.83.80.69.67.84
-- Vary			: YES
--
-- Value(s)		: 16:9
--				: 4:3
--				: Unknown
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 2.122
--				:
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: NO
--
-- Value(s)		: 1
--				:
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: NONE
--              : WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
-- Vary			: YES
--
-- Value(s)		: OK
--				: NONE
--              : WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
-- Vary			: YES
--
-- Value(s)		: Tri/Bi-Level
--				: TriLevel
--              : BiLevel
--              : BlackBurst
--              : Analog
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
-- Vary			: YES
--
-- Value(s)		: OK
--              : FAIL:Lost
--              : FAIL:Error
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				:
-- Comments		: Number
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
-- Vary			: YES
--
-- Value(s)		: 0
--				:
-- Comments		: Number
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: NONE
--              : WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
-- Vary			: YES
--
-- Value(s)		: OK
--				: NONE
--              : WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				:
-- Comments		: Number
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
-- Vary			: YES
--
-- Value(s)		: 0
--				:
-- Comments		: Number
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
-- Vary			: YES
--
-- Value(s)		: WARN: No Input
--              : PCM
--              : NONPCM
--              : Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
-- Vary			: YES
--
-- Value(s)		: WARN: No Input
--              : PCM
--              : NONPCM
--              : Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
-- Vary			: YES
--
-- Value(s)		: WARN: No Input
--              : PCM
--              : NONPCM
--              : Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
-- Vary			: YES
--
-- Value(s)		: WARN: No Input
--              : PCM
--              : NONPCM
--              : Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
-- Vary			: YES
--
-- Value(s)		: WARN: No Input
--              : PCM
--              : NONPCM
--              : Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
-- Vary			: YES
--
-- Value(s)		: WARN: No Input
--              : PCM
--              : NONPCM
--              : Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
-- Vary			: YES
--
-- Value(s)		: WARN: No Input
--              : PCM
--              : NONPCM
--              : Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
-- Vary			: YES
--
-- Value(s)		: WARN: No Input
--              : PCM
--              : NONPCM
--              : Unknown
-- Comments		:
--
---------------------------------------------------------------------------------------------------
-- Header		: INPUT_2_EMBEDDED_AUDIO_1_TYPE
--
-- MIB ref		: swCardEventLogSlotXX       .29.73.78.80.85.84.95.50.95.69.77.66.69.68.68.69.68.95.65.85.68.73.79.95.49.95.84.89.80.69
-- absolute OID	: 1.3.6.1.4.1.7995.2.6.1.1.XX.29.73.78.80.85.84.95.50.95.69.77.66.69.68.68.69.68.95.65.85.68.73.79.95.49.95.84.89.80.69
-- Vary			: YES
--
-- Value(s)		: WARN: No Input
--              : PCM
--              : NONPCM
--              : Unknown
-- Comments		:
--
---------------------------------------------------------------------------------------------------
-- Header		: INPUT_2_EMBEDDED_AUDIO_2_TYPE
--
-- MIB ref		: swCardEventLogSlotXX       .29.73.78.80.85.84.95.50.95.69.77.66.69.68.68.69.68.95.65.85.68.73.79.95.50.95.84.89.80.69
-- absolute OID	: 1.3.6.1.4.1.7995.2.6.1.1.XX.29.73.78.80.85.84.95.50.95.69.77.66.69.68.68.69.68.95.65.85.68.73.79.95.50.95.84.89.80.69
-- Vary			: YES
--
-- Value(s)		: WARN: No Input
--              : PCM
--              : NONPCM
--              : Unknown
-- Comments		:
--
---------------------------------------------------------------------------------------------------
-- Header		: INPUT_2_EMBEDDED_AUDIO_3_TYPE
--
-- MIB ref		: swCardEventLogSlotXX       .29.73.78.80.85.84.95.50.95.69.77.66.69.68.68.69.68.95.65.85.68.73.79.95.51.95.84.89.80.69
-- absolute OID	: 1.3.6.1.4.1.7995.2.6.1.1.XX.29.73.78.80.85.84.95.50.95.69.77.66.69.68.68.69.68.95.65.85.68.73.79.95.51.95.84.89.80.69
-- Vary			: YES
--
-- Value(s)		: WARN: No Input
--              : PCM
--              : NONPCM
--              : Unknown
-- Comments		:
--
---------------------------------------------------------------------------------------------------
-- Header		: INPUT_2_EMBEDDED_AUDIO_4_TYPE
--
-- MIB ref		: swCardEventLogSlotXX       .29.73.78.80.85.84.95.50.95.69.77.66.69.68.68.69.68.95.65.85.68.73.79.95.52.95.84.89.80.69
-- absolute OID	: 1.3.6.1.4.1.7995.2.6.1.1.XX.29.73.78.80.85.84.95.50.95.69.77.66.69.68.68.69.68.95.65.85.68.73.79.95.52.95.84.89.80.69
-- Vary			: YES
--
-- Value(s)		: WARN: No Input
--              : PCM
--              : NONPCM
--              : Unknown
-- Comments		:
--
---------------------------------------------------------------------------------------------------
-- Header		: INPUT_2_EMBEDDED_AUDIO_5_TYPE
--
-- MIB ref		: swCardEventLogSlotXX       .29.73.78.80.85.84.95.50.95.69.77.66.69.68.68.69.68.95.65.85.68.73.79.95.53.95.84.89.80.69
-- absolute OID	: 1.3.6.1.4.1.7995.2.6.1.1.XX.29.73.78.80.85.84.95.50.95.69.77.66.69.68.68.69.68.95.65.85.68.73.79.95.53.95.84.89.80.69
-- Vary			: YES
--
-- Value(s)		: WARN: No Input
--              : PCM
--              : NONPCM
--              : Unknown
-- Comments		:
--
---------------------------------------------------------------------------------------------------
-- Header		: INPUT_2_EMBEDDED_AUDIO_6_TYPE
--
-- MIB ref		: swCardEventLogSlotXX       .29.73.78.80.85.84.95.50.95.69.77.66.69.68.68.69.68.95.65.85.68.73.79.95.54.95.84.89.80.69
-- absolute OID	: 1.3.6.1.4.1.7995.2.6.1.1.XX.29.73.78.80.85.84.95.50.95.69.77.66.69.68.68.69.68.95.65.85.68.73.79.95.54.95.84.89.80.69
-- Vary			: YES
--
-- Value(s)		: WARN: No Input
--              : PCM
--              : NONPCM
--              : Unknown
-- Comments		:
--
---------------------------------------------------------------------------------------------------
-- Header		: INPUT_2_EMBEDDED_AUDIO_7_TYPE
--
-- MIB ref		: swCardEventLogSlotXX       .29.73.78.80.85.84.95.50.95.69.77.66.69.68.68.69.68.95.65.85.68.73.79.95.55.95.84.89.80.69
-- absolute OID	: 1.3.6.1.4.1.7995.2.6.1.1.XX.29.73.78.80.85.84.95.50.95.69.77.66.69.68.68.69.68.95.65.85.68.73.79.95.55.95.84.89.80.69
-- Vary			: YES
--
-- Value(s)		: WARN: No Input
--              : PCM
--              : NONPCM
--              : Unknown
-- Comments		:
--
---------------------------------------------------------------------------------------------------
-- Header		: INPUT_2_EMBEDDED_AUDIO_8_TYPE
--
-- MIB ref		: swCardEventLogSlotXX       .29.73.78.80.85.84.95.50.95.69.77.66.69.68.68.69.68.95.65.85.68.73.79.95.56.95.84.89.80.69
-- absolute OID	: 1.3.6.1.4.1.7995.2.6.1.1.XX.29.73.78.80.85.84.95.50.95.69.77.66.69.68.68.69.68.95.65.85.68.73.79.95.56.95.84.89.80.69
-- Vary			: YES
--
-- Value(s)		: WARN: No Input
--              : PCM
--              : NONPCM
--              : Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: WARN: No Input
--              : PCM
--              : NONPCM
--              : Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: WARN: No Input
--              : PCM
--              : NONPCM
--              : Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: WARN: No Input
--              : PCM
--              : NONPCM
--              : Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: WARN: No Input
--              : PCM
--              : NONPCM
--              : Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: WARN: No Input
--              : PCM
--              : NONPCM
--              : Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: WARN: No Input
--              : PCM
--              : NONPCM
--              : Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: WARN: No Input
--              : PCM
--              : NONPCM
--              : Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: WARN: No Input
--              : PCM
--              : NONPCM
--              : Unknown
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_1_DOLBY_E
--
-- MIB ref		: swCardEventLogSlotXX       .33.79.85.84.80.85.84.95.49.95.69.77.66.69.68.68.69.68.95.65.85.68.73.79.95.49.95.68.79.76.66.89.95.69
-- absolute OID	: 1.3.6.1.4.1.7995.2.6.1.1.XX.33.79.85.84.80.85.84.95.49.95.69.77.66.69.68.68.69.68.95.65.85.68.73.79.95.49.95.68.79.76.66.89.95.69
-- Vary			: YES
--
-- Value(s)		: NONE
--				: OK
--				: EARLY
--				: LATE
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_2_DOLBY_E
--
-- MIB ref		: swCardEventLogSlotXX       .33.79.85.84.80.85.84.95.49.95.69.77.66.69.68.68.69.68.95.65.85.68.73.79.95.50.95.68.79.76.66.89.95.69
-- absolute OID	: 1.3.6.1.4.1.7995.2.6.1.1.XX.33.79.85.84.80.85.84.95.49.95.69.77.66.69.68.68.69.68.95.65.85.68.73.79.95.50.95.68.79.76.66.89.95.69
-- Vary			: YES
--
-- Value(s)		: NONE
--				: OK
--				: EARLY
--				: LATE
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_3_DOLBY_E
--
-- MIB ref		: swCardEventLogSlotXX       .33.79.85.84.80.85.84.95.49.95.69.77.66.69.68.68.69.68.95.65.85.68.73.79.95.51.95.68.79.76.66.89.95.69
-- absolute OID	: 1.3.6.1.4.1.7995.2.6.1.1.XX.33.79.85.84.80.85.84.95.49.95.69.77.66.69.68.68.69.68.95.65.85.68.73.79.95.51.95.68.79.76.66.89.95.69
-- Vary			: YES
--
-- Value(s)		: NONE
--				: OK
--				: EARLY
--				: LATE
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_4_DOLBY_E
--
-- MIB ref		: swCardEventLogSlotXX       .33.79.85.84.80.85.84.95.49.95.69.77.66.69.68.68.69.68.95.65.85.68.73.79.95.52.95.68.79.76.66.89.95.69
-- absolute OID	: 1.3.6.1.4.1.7995.2.6.1.1.XX.33.79.85.84.80.85.84.95.49.95.69.77.66.69.68.68.69.68.95.65.85.68.73.79.95.52.95.68.79.76.66.89.95.69
-- Vary			: YES
--
-- Value(s)		: NONE
--				: OK
--				: EARLY
--				: LATE
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_5_DOLBY_E
--
-- MIB ref		: swCardEventLogSlotXX       .33.79.85.84.80.85.84.95.49.95.69.77.66.69.68.68.69.68.95.65.85.68.73.79.95.53.95.68.79.76.66.89.95.69
-- absolute OID	: 1.3.6.1.4.1.7995.2.6.1.1.XX.33.79.85.84.80.85.84.95.49.95.69.77.66.69.68.68.69.68.95.65.85.68.73.79.95.53.95.68.79.76.66.89.95.69
-- Vary			: YES
--
-- Value(s)		: NONE
--				: OK
--				: EARLY
--				: LATE
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_6_DOLBY_E
--
-- MIB ref		: swCardEventLogSlotXX       .33.79.85.84.80.85.84.95.49.95.69.77.66.69.68.68.69.68.95.65.85.68.73.79.95.54.95.68.79.76.66.89.95.69
-- absolute OID	: 1.3.6.1.4.1.7995.2.6.1.1.XX.33.79.85.84.80.85.84.95.49.95.69.77.66.69.68.68.69.68.95.65.85.68.73.79.95.54.95.68.79.76.66.89.95.69
-- Vary			: YES
--
-- Value(s)		: NONE
--				: OK
--				: EARLY
--				: LATE
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_7_DOLBY_E
--
-- MIB ref		: swCardEventLogSlotXX       .33.79.85.84.80.85.84.95.49.95.69.77.66.69.68.68.69.68.95.65.85.68.73.79.95.55.95.68.79.76.66.89.95.69
-- absolute OID	: 1.3.6.1.4.1.7995.2.6.1.1.XX.33.79.85.84.80.85.84.95.49.95.69.77.66.69.68.68.69.68.95.65.85.68.73.79.95.55.95.68.79.76.66.89.95.69
-- Vary			: YES
--
-- Value(s)		: NONE
--				: OK
--				: EARLY
--				: LATE
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
-- Vary			: YES
--
-- Value(s)		: OK
--				: WARN:Overflow
--              : WARN:Silent
--              : WARN:Quiet
--              : WARN:Loud
-- Comments		:
--
---------------------------------------------------------------------------------------------------
-- Header		: OUTPUT_1_EMBEDDED_AUDIO_8_DOLBY_E
--
-- MIB ref		: swCardEventLogSlotXX       .33.79.85.84.80.85.84.95.49.95.69.77.66.69.68.68.69.68.95.65.85.68.73.79.95.56.95.68.79.76.66.89.95.69
-- absolute OID	: 1.3.6.1.4.1.7995.2.6.1.1.XX.33.79.85.84.80.85.84.95.49.95.69.77.66.69.68.68.69.68.95.65.85.68.73.79.95.56.95.68.79.76.66.89.95.69
-- Vary			: YES
--
-- Value(s)		: NONE
--				: OK
--				: EARLY
--				: LATE
-- Comments		:
--
---------------------------------------------------------------------------------------------------
