-- ************************************************************************************
-- Snell Card:IQDBE00
--        Module Id#:562
--       Command Set:7
--          Filename:SNELL-IQDBE00-CMD-MIB.mib
--            Author:Jonathan Riches
--              Date:22/04/2010
--              Time:10:00
--
-- Copyright (c) 2010 Snell Ltd
-- All rights reserved.
--
-- ************************************************************************************

SNELL-IQDBE00-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDBE00,
    moduleIQDBE00MIB
        FROM SNELL-WILCOX-PRODUCT-REG;

 moduleIQDBE00CmdMi MODULE-IDENTITY
    LAST-UPDATED "1004221000Z"
    ORGANIZATION "Snell Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell card, command set  translations."
    ::= { moduleIQDBE00MIB 1 }




--********************************************************************************
--*
--*  Snell Card:
--*  command set:
--*  list commands/menus:
--*
--******************************************************************************
	iqdbe00CmdTable OBJECT-TYPE
		SYNTAX			SEQUENCE OF Iqdbe00CmdEntry
		MAX-ACCESS		not-accessible
		STATUS			current
		DESCRIPTION
				"Note the instance of this table is relected in the command set Version"
		::= { moduleIQDBE00 1 }

	iqdbe00CmdEntry OBJECT-TYPE
		SYNTAX		Iqdbe00CmdEntry
		MAX-ACCESS		not-accessible
		STATUS			current
		DESCRIPTION
				"Entry in command table."
		INDEX	{ iqdbe00SlotIndex }
		::= { iqdbe00CmdTable 1 }

	Iqdbe00CmdEntry ::=
		SEQUENCE {
			iqdbe00SlotIndex
				Unsigned32,
			iqdbe00MenuInputIPLoss
				INTEGER,
			iqdbe00InputValidStdsAllValid
				INTEGER,
			iqdbe00InputValidStdsAllInvalid
				INTEGER,
			iqdbe00InputValidStds108023sF
				INTEGER,
			iqdbe00InputValidStds108023p
				INTEGER,
			iqdbe00InputValidStds108024sF
				INTEGER,
			iqdbe00InputValidStds108024p
				INTEGER,
			iqdbe00InputValidStds108025i
				INTEGER,
			iqdbe00InputValidStds108025p
				INTEGER,
			iqdbe00InputValidStds103529i
				INTEGER,
			iqdbe00InputValidStds108029i
				INTEGER,
			iqdbe00InputValidStds108029p
				INTEGER,
			iqdbe00InputValidStds103530i
				INTEGER,
			iqdbe00InputValidStds108030i
				INTEGER,
			iqdbe00InputValidStds108030p
				INTEGER,
			iqdbe00InputValidStds72050p
				INTEGER,
			iqdbe00InputValidStds72059p
				INTEGER,
			iqdbe00InputValidStds72060p
				INTEGER,
			iqdbe00InputValidStds62525i
				INTEGER,
			iqdbe00InputValidStds52529i
				INTEGER,
			iqdbe00InputErrorsCRCErrs
				RollCallString,
			iqdbe00InputErrorsCRCErrSec
				RollCallString,
			iqdbe00InputErrorsANCErrs
				RollCallString,
			iqdbe00InputErrorsANCErrSec
				RollCallString,
			iqdbe00InputErrorsResetSec
				RollCallString,
			iqdbe00InputErrorsErrorReset
				INTEGER,
			iqdbe00AudioOutputOutputStandard
				INTEGER,
			iqdbe00AudioOutputSelectStandard
				INTEGER,
			iqdbe00OutputVideoProcAmpsMasterGain
				INTEGER,
			iqdbe00OutputVideoProcAmpsYGain
				INTEGER,
			iqdbe00OutputVideoProcAmpsCGain
				INTEGER,
			iqdbe00OutputVideoProcAmpsBlackLevel
				INTEGER,
			iqdbe00AudioOutputDefaultOutput
				INTEGER,
			iqdbe00AudioOutputDefaultOPStd
				INTEGER,
			iqdbe00AudioDelayASourcesManual
				INTEGER,
			iqdbe00AudioDelayASourcesGPIPWM
				INTEGER,
			iqdbe00AudioDelayASourcesRollTrack14
				INTEGER,
			iqdbe00AudioDelayASourcesRollTrack15
				INTEGER,
			iqdbe00AudioDelayASourcesRollTrack16
				INTEGER,
			iqdbe00AudioDelayASourcesRollTrack17
				INTEGER,
			iqdbe00AudDelaysAudioDelayAAdjustCoarseDelay
				INTEGER,
			iqdbe00AudDelaysAudioDelayACurrentAudioDelay
				RollCallString,
			iqdbe00AudioDelayBSourcesManual
				INTEGER,
			iqdbe00AudioDelayBSourcesGPIPWM
				INTEGER,
			iqdbe00AudioDelayBSourcesRollTrack14
				INTEGER,
			iqdbe00AudioDelayBSourcesRollTrack15
				INTEGER,
			iqdbe00AudioDelayBSourcesRollTrack16
				INTEGER,
			iqdbe00AudioDelayBSourcesRollTrack17
				INTEGER,
			iqdbe00AudDelaysAudioDelayBAdjustCoarseDelay
				INTEGER,
			iqdbe00AudDelaysAudioDelayBCurrentAudioDelay
				RollCallString,
			iqdbe00AudDelaysAESDelaySelectDelay1
				INTEGER,
			iqdbe00AudDelaysAESDelaySelectInternal1
				INTEGER,
			iqdbe00AudDelaysAESDelaySelectAutoDolbyEPhase1
				INTEGER,
			iqdbe00AudDelaysAESDelaySelectDelayLimit1
				RollCallString,
			iqdbe00AudDelaysAESDelaySelectAES1FineDelay
				INTEGER,
			iqdbe00AudDelaysAESDelaySelectDelay2
				INTEGER,
			iqdbe00AudDelaysAESDelaySelectInternal2
				INTEGER,
			iqdbe00AudDelaysAESDelaySelectAutoDolbyEPhase2
				INTEGER,
			iqdbe00AudDelaysAESDelaySelectDelayLimit2
				RollCallString,
			iqdbe00AudDelaysAESDelaySelectAES2FineDelay
				INTEGER,
			iqdbe00AudDelaysAESDelaySelectDelay3
				INTEGER,
			iqdbe00AudDelaysAESDelaySelectInternal3
				INTEGER,
			iqdbe00AudDelaysAESDelaySelectAutoDolbyEPhase3
				INTEGER,
			iqdbe00AudDelaysAESDelaySelectDelayLimit3
				RollCallString,
			iqdbe00AudDelaysAESDelaySelectAES3FineDelay
				INTEGER,
			iqdbe00AudDelaysAESDelaySelectDelay4
				INTEGER,
			iqdbe00AudDelaysAESDelaySelectInternal4
				INTEGER,
			iqdbe00AudDelaysAESDelaySelectAutoDolbyEPhase4
				INTEGER,
			iqdbe00AudDelaysAESDelaySelectDelayLimit4
				RollCallString,
			iqdbe00AudDelaysAESDelaySelectAES4FineDelay
				INTEGER,
			iqdbe00AudDelaysAESDelaySelectDelay5
				INTEGER,
			iqdbe00AudDelaysAESDelaySelectInternal5
				INTEGER,
			iqdbe00AudDelaysAESDelaySelectAutoDolbyEPhase5
				INTEGER,
			iqdbe00AudDelaysAESDelaySelectDelayLimit5
				RollCallString,
			iqdbe00AudDelaysAESDelaySelectAES5FineDelay
				INTEGER,
			iqdbe00AudDelaysAESDelaySelectDelay6
				INTEGER,
			iqdbe00AudDelaysAESDelaySelectInternal6
				INTEGER,
			iqdbe00AudDelaysAESDelaySelectAutoDolbyEPhase6
				INTEGER,
			iqdbe00AudDelaysAESDelaySelectDelayLimit6
				RollCallString,
			iqdbe00AudDelaysAESDelaySelectAES6FineDelay
				INTEGER,
			iqdbe00AudDelaysAESDelaySelectDelay7
				INTEGER,
			iqdbe00AudDelaysAESDelaySelectInternal7
				INTEGER,
			iqdbe00AudDelaysAESDelaySelectAutoDolbyEPhase7
				INTEGER,
			iqdbe00AudDelaysAESDelaySelectDelayLimit7
				RollCallString,
			iqdbe00AudDelaysAESDelaySelectAES7FineDelay
				INTEGER,
			iqdbe00AudDelaysAESDelaySelectDolbyEncoder
				INTEGER,
			iqdbe00AudDelaysAESDelaySelectInternal
				INTEGER,
			iqdbe00AudDelaysAESDelaySelectAutoDolbyEPhase8
				INTEGER,
			iqdbe00AudDelaysAESDelaySelectDelayLimit8
				RollCallString,
			iqdbe00AudDelaysAESDelaySelectDolbyEncFineDela
				INTEGER,
			iqdbe00AudDelaysEMBDelaySelectDelay1
				INTEGER,
			iqdbe00AudDelaysEMBDelaySelectInternal1
				INTEGER,
			iqdbe00AudDelaysEMBDelaySelectAutoDolbyEPhase1
				INTEGER,
			iqdbe00AudDelaysEMBDelaySelectDelayLimit1
				RollCallString,
			iqdbe00AudDelaysEMBDelaySelectEMB1FineDelay
				INTEGER,
			iqdbe00AudDelaysEMBDelaySelectDelay2
				INTEGER,
			iqdbe00AudDelaysEMBDelaySelectInternal2
				INTEGER,
			iqdbe00AudDelaysEMBDelaySelectAutoDolbyEPhase2
				INTEGER,
			iqdbe00AudDelaysEMBDelaySelectDelayLimit2
				RollCallString,
			iqdbe00AudDelaysEMBDelaySelectEMB2FineDelay
				INTEGER,
			iqdbe00AudDelaysEMBDelaySelectDelay3
				INTEGER,
			iqdbe00AudDelaysEMBDelaySelectInternal3
				INTEGER,
			iqdbe00AudDelaysEMBDelaySelectAutoDolbyEPhase3
				INTEGER,
			iqdbe00AudDelaysEMBDelaySelectDelayLimit3
				RollCallString,
			iqdbe00AudDelaysEMBDelaySelectEMB3FineDelay
				INTEGER,
			iqdbe00AudDelaysEMBDelaySelectDelay4
				INTEGER,
			iqdbe00AudDelaysEMBDelaySelectInternal4
				INTEGER,
			iqdbe00AudDelaysEMBDelaySelectAutoDolbyEPhase4
				INTEGER,
			iqdbe00AudDelaysEMBDelaySelectDelayLimit4
				RollCallString,
			iqdbe00AudDelaysEMBDelaySelectEMB4FineDelay
				INTEGER,
			iqdbe00AudDelaysEMBDelaySelectDelay5
				INTEGER,
			iqdbe00AudDelaysEMBDelaySelectInternal5
				INTEGER,
			iqdbe00AudDelaysEMBDelaySelectAutoDolbyEPhase5
				INTEGER,
			iqdbe00AudDelaysEMBDelaySelectDelayLimit5
				RollCallString,
			iqdbe00AudDelaysEMBDelaySelectEMB5FineDelay
				INTEGER,
			iqdbe00AudDelaysEMBDelaySelectDelay6
				INTEGER,
			iqdbe00AudDelaysEMBDelaySelectInternal6
				INTEGER,
			iqdbe00AudDelaysEMBDelaySelectAutoDolbyEPhase6
				INTEGER,
			iqdbe00AudDelaysEMBDelaySelectDelayLimit6
				RollCallString,
			iqdbe00AudDelaysEMBDelaySelectEMB6FineDelay
				INTEGER,
			iqdbe00AudDelaysEMBDelaySelectDelay7
				INTEGER,
			iqdbe00AudDelaysEMBDelaySelectInternal7
				INTEGER,
			iqdbe00AudDelaysEMBDelaySelectAutoDolbyEPhase7
				INTEGER,
			iqdbe00AudDelaysEMBDelaySelectDelayLimit7
				RollCallString,
			iqdbe00AudDelaysEMBDelaySelectEMB7FineDelay
				INTEGER,
			iqdbe00AudDelaysEMBDelaySelectDelay8
				INTEGER,
			iqdbe00AudDelaysEMBDelaySelectInternal8
				INTEGER,
			iqdbe00AudDelaysEMBDelaySelectDelayLimit8
				RollCallString,
			iqdbe00AudDelaysEMBDelaySelectAutoDolbyEPhase8
				INTEGER,
			iqdbe00AudDelaysEMBDelaySelectEMB8FineDelay
				INTEGER,
			iqdbe00AudioAudDelaysRollTrack14
				RollCallString,
			iqdbe00AudioAudDelaysRollTrack15
				RollCallString,
			iqdbe00AudioAudDelaysRollTrack16
				RollCallString,
			iqdbe00AudioAudDelaysRollTrack17
				RollCallString,
			iqdbe00AudioAudDelaysCrashSRCLimit
				INTEGER,
			iqdbe00EmbCtrlGroupGroup1Audio
				INTEGER,
			iqdbe00EmbCtrlGroupGroup2Audio
				INTEGER,
			iqdbe00EmbCtrlGroupGroup3Audio
				INTEGER,
			iqdbe00EmbCtrlGroupGroup4Audio
				INTEGER,
			iqdbe00EmbCtrlChannelPair1LActive
				INTEGER,
			iqdbe00EmbCtrlChannelPair1RActive
				INTEGER,
			iqdbe00EmbCtrlChannelPair2LActive
				INTEGER,
			iqdbe00EmbCtrlChannelPair2RActive
				INTEGER,
			iqdbe00EmbCtrlChannelPair3LActive
				INTEGER,
			iqdbe00EmbCtrlChannelPair3RActive
				INTEGER,
			iqdbe00EmbCtrlChannelPair4LActive
				INTEGER,
			iqdbe00EmbCtrlChannelPair4RActive
				INTEGER,
			iqdbe00EmbCtrlChannelPair5LActive
				INTEGER,
			iqdbe00EmbCtrlChannelPair5RActive
				INTEGER,
			iqdbe00EmbCtrlChannelPair6LActive
				INTEGER,
			iqdbe00EmbCtrlChannelPair6RActive
				INTEGER,
			iqdbe00EmbCtrlChannelPair7LActive
				INTEGER,
			iqdbe00EmbCtrlChannelPair7RActive
				INTEGER,
			iqdbe00EmbCtrlChannelPair8LActive
				INTEGER,
			iqdbe00EmbCtrlChannelPair8RActive
				INTEGER,
			iqdbe00AudioEmbCtrlEmbedderPriority
				INTEGER,
			iqdbe00EmbGainEmbedPair1Embed1MuteL
				INTEGER,
			iqdbe00EmbGainEmbedPair1Embed1MuteR
				INTEGER,
			iqdbe00EmbGainEmbedPair1Embed1LGain
				INTEGER,
			iqdbe00EmbGainEmbedPair1Embed1RGain
				INTEGER,
			iqdbe00EmbGainEmbedPair1Stereo
				INTEGER,
			iqdbe00EmbGainEmbedPair1Embed1InvertL
				INTEGER,
			iqdbe00EmbGainEmbedPair1Embed1InvertR
				INTEGER,
			iqdbe00EmbGainEmbedPair1Embed1LClip
				RollCallString,
			iqdbe00EmbGainEmbedPair1Embed1RClip
				RollCallString,
			iqdbe00EmbGainEmbedPair2Embed2MuteL
				INTEGER,
			iqdbe00EmbGainEmbedPair2Embed2MuteR
				INTEGER,
			iqdbe00EmbGainEmbedPair2Embed2LGain
				INTEGER,
			iqdbe00EmbGainEmbedPair2Embed2RGain
				INTEGER,
			iqdbe00EmbGainEmbedPair2Stereo
				INTEGER,
			iqdbe00EmbGainEmbedPair2Embed2InvertL
				INTEGER,
			iqdbe00EmbGainEmbedPair2Embed2InvertR
				INTEGER,
			iqdbe00EmbGainEmbedPair2Embed2LClip
				RollCallString,
			iqdbe00EmbGainEmbedPair2Embed2RClip
				RollCallString,
			iqdbe00EmbGainEmbedPair3Embed3MuteL
				INTEGER,
			iqdbe00EmbGainEmbedPair3Embed3MuteR
				INTEGER,
			iqdbe00EmbGainEmbedPair3Embed3LGain
				INTEGER,
			iqdbe00EmbGainEmbedPair3Embed3RGain
				INTEGER,
			iqdbe00EmbGainEmbedPair3Stereo
				INTEGER,
			iqdbe00EmbGainEmbedPair3Embed3InvertL
				INTEGER,
			iqdbe00EmbGainEmbedPair3Embed3InvertR
				INTEGER,
			iqdbe00EmbGainEmbedPair3Embed3LClip
				RollCallString,
			iqdbe00EmbGainEmbedPair3Embed3RClip
				RollCallString,
			iqdbe00EmbGainEmbedPair4Embed4MuteL
				INTEGER,
			iqdbe00EmbGainEmbedPair4Embed4MuteR
				INTEGER,
			iqdbe00EmbGainEmbedPair4Embed4LGain
				INTEGER,
			iqdbe00EmbGainEmbedPair4Embed4RGain
				INTEGER,
			iqdbe00EmbGainEmbedPair4Stereo
				INTEGER,
			iqdbe00EmbGainEmbedPair4Embed4InvertL
				INTEGER,
			iqdbe00EmbGainEmbedPair4Embed4InvertR
				INTEGER,
			iqdbe00EmbGainEmbedPair4Embed4LClip
				RollCallString,
			iqdbe00EmbGainEmbedPair4Embed4RClip
				RollCallString,
			iqdbe00EmbGainEmbedPair5Embed5MuteL
				INTEGER,
			iqdbe00EmbGainEmbedPair5Embed5MuteR
				INTEGER,
			iqdbe00EmbGainEmbedPair5Embed5LGain
				INTEGER,
			iqdbe00EmbGainEmbedPair5Embed5RGain
				INTEGER,
			iqdbe00EmbGainEmbedPair5Stereo
				INTEGER,
			iqdbe00EmbGainEmbedPair5Embed5InvertL
				INTEGER,
			iqdbe00EmbGainEmbedPair5Embed5InvertR
				INTEGER,
			iqdbe00EmbGainEmbedPair5Embed5LClip
				RollCallString,
			iqdbe00EmbGainEmbedPair5Embed5RClip
				RollCallString,
			iqdbe00EmbGainEmbedPair6Embed6MuteL
				INTEGER,
			iqdbe00EmbGainEmbedPair6Embed6MuteR
				INTEGER,
			iqdbe00EmbGainEmbedPair6Embed6LGain
				INTEGER,
			iqdbe00EmbGainEmbedPair6Embed6RGain
				INTEGER,
			iqdbe00EmbGainEmbedPair6Stereo
				INTEGER,
			iqdbe00EmbGainEmbedPair6Embed6InvertL
				INTEGER,
			iqdbe00EmbGainEmbedPair6Embed6InvertR
				INTEGER,
			iqdbe00EmbGainEmbedPair6Embed6LClip
				RollCallString,
			iqdbe00EmbGainEmbedPair6Embed6RClip
				RollCallString,
			iqdbe00EmbGainEmbedPair7Embed7MuteL
				INTEGER,
			iqdbe00EmbGainEmbedPair7Embed7MuteR
				INTEGER,
			iqdbe00EmbGainEmbedPair7Embed7LGain
				INTEGER,
			iqdbe00EmbGainEmbedPair7Embed7RGain
				INTEGER,
			iqdbe00EmbGainEmbedPair7Stereo
				INTEGER,
			iqdbe00EmbGainEmbedPair7Embed7InvertL
				INTEGER,
			iqdbe00EmbGainEmbedPair7Embed7InvertR
				INTEGER,
			iqdbe00EmbGainEmbedPair7Embed7LClip
				RollCallString,
			iqdbe00EmbGainEmbedPair7Embed7RClip
				RollCallString,
			iqdbe00EmbGainEmbedPair8Embed8MuteL
				INTEGER,
			iqdbe00EmbGainEmbedPair8Embed8MuteR
				INTEGER,
			iqdbe00EmbGainEmbedPair8Embed8LGain
				INTEGER,
			iqdbe00EmbGainEmbedPair8Embed8RGain
				INTEGER,
			iqdbe00EmbGainEmbedPair8Stereo
				INTEGER,
			iqdbe00EmbGainEmbedPair8Embed8InvertL
				INTEGER,
			iqdbe00EmbGainEmbedPair8Embed8InvertR
				INTEGER,
			iqdbe00EmbGainEmbedPair8Embed8LClip
				RollCallString,
			iqdbe00EmbGainEmbedPair8Embed8RClip
				RollCallString,
			iqdbe00EmbOutEmbedPair1Left
				INTEGER,
			iqdbe00EmbOutEmbedPair1Right
				INTEGER,
			iqdbe00EmbOutEmbedPair1LinkLRSelection
				INTEGER,
			iqdbe00EmbOutEmbedPair2Left
				INTEGER,
			iqdbe00EmbOutEmbedPair2Right
				INTEGER,
			iqdbe00EmbOutEmbedPair2LinkLRSelection
				INTEGER,
			iqdbe00EmbOutEmbedPair3Left
				INTEGER,
			iqdbe00EmbOutEmbedPair3Right
				INTEGER,
			iqdbe00EmbOutEmbedPair3LinkLRSelection
				INTEGER,
			iqdbe00EmbOutEmbedPair4Left
				INTEGER,
			iqdbe00EmbOutEmbedPair4Right
				INTEGER,
			iqdbe00EmbOutEmbedPair4LinkLRSelection
				INTEGER,
			iqdbe00EmbOutEmbedPair5Left
				INTEGER,
			iqdbe00EmbOutEmbedPair5Right
				INTEGER,
			iqdbe00EmbOutEmbedPair5LinkLRSelection
				INTEGER,
			iqdbe00EmbOutEmbedPair6Left
				INTEGER,
			iqdbe00EmbOutEmbedPair6Right
				INTEGER,
			iqdbe00EmbOutEmbedPair6LinkLRSelection
				INTEGER,
			iqdbe00EmbOutEmbedPair7Left
				INTEGER,
			iqdbe00EmbOutEmbedPair7Right
				INTEGER,
			iqdbe00EmbOutEmbedPair7LinkLRSelection
				INTEGER,
			iqdbe00EmbOutEmbedPair8Left
				INTEGER,
			iqdbe00EmbOutEmbedPair8Right
				INTEGER,
			iqdbe00EmbOutEmbedPair8LinkLRSelection
				INTEGER,
			iqdbe00AudioEmbModeInput1
				INTEGER,
			iqdbe00AudioEmbModeInput2
				INTEGER,
			iqdbe00AudioEmbModeInput3
				INTEGER,
			iqdbe00AudioEmbModeInput4
				INTEGER,
			iqdbe00AudioEmbModeInput5
				INTEGER,
			iqdbe00AudioEmbModeInput6
				INTEGER,
			iqdbe00AudioEmbModeInput7
				INTEGER,
			iqdbe00AudioEmbModeInput8
				INTEGER,
			iqdbe00EmbNamesDisembederNamesDisembed1
				RollCallString,
			iqdbe00EmbNamesDisembederNamesDisembed1R
				RollCallString,
			iqdbe00EmbNamesDisembederNamesDisembed2
				RollCallString,
			iqdbe00EmbNamesDisembederNamesDisembed2R
				RollCallString,
			iqdbe00EmbNamesDisembederNamesDisembed3
				RollCallString,
			iqdbe00EmbNamesDisembederNamesDisembed3R
				RollCallString,
			iqdbe00EmbNamesDisembederNamesDisembed4
				RollCallString,
			iqdbe00EmbNamesDisembederNamesDisembed4R
				RollCallString,
			iqdbe00EmbNamesDisembederNamesDisembed5
				RollCallString,
			iqdbe00EmbNamesDisembederNamesDisembed5R
				RollCallString,
			iqdbe00EmbNamesDisembederNamesDisembed6
				RollCallString,
			iqdbe00EmbNamesDisembederNamesDisembed6R
				RollCallString,
			iqdbe00EmbNamesDisembederNamesDisembed7
				RollCallString,
			iqdbe00EmbNamesDisembederNamesDisembed7R
				RollCallString,
			iqdbe00EmbNamesDisembederNamesDisembed8
				RollCallString,
			iqdbe00EmbNamesDisembederNamesDisembed8R
				RollCallString,
			iqdbe00EmbNamesEmbeddedOPNamesEmbed1
				RollCallString,
			iqdbe00EmbNamesEmbeddedOPNamesEmbed1R
				RollCallString,
			iqdbe00EmbNamesEmbeddedOPNamesEmbed2
				RollCallString,
			iqdbe00EmbNamesEmbeddedOPNamesEmbed2R
				RollCallString,
			iqdbe00EmbNamesEmbeddedOPNamesEmbed3
				RollCallString,
			iqdbe00EmbNamesEmbeddedOPNamesEmbed3R
				RollCallString,
			iqdbe00EmbNamesEmbeddedOPNamesEmbed4
				RollCallString,
			iqdbe00EmbNamesEmbeddedOPNamesEmbed4R
				RollCallString,
			iqdbe00EmbNamesEmbeddedOPNamesEmbed5
				RollCallString,
			iqdbe00EmbNamesEmbeddedOPNamesEmbed5R
				RollCallString,
			iqdbe00EmbNamesEmbeddedOPNamesEmbed6
				RollCallString,
			iqdbe00EmbNamesEmbeddedOPNamesEmbed6R
				RollCallString,
			iqdbe00EmbNamesEmbeddedOPNamesEmbed7
				RollCallString,
			iqdbe00EmbNamesEmbeddedOPNamesEmbed7R
				RollCallString,
			iqdbe00EmbNamesEmbeddedOPNamesEmbed8
				RollCallString,
			iqdbe00EmbNamesEmbeddedOPNamesEmbed8R
				RollCallString,
			iqdbe00EmbNamesIPNamesStereoDisemb1
				INTEGER,
			iqdbe00EmbNamesIPNamesStereoDisemb2
				INTEGER,
			iqdbe00EmbNamesIPNamesStereoDisemb3
				INTEGER,
			iqdbe00EmbNamesIPNamesStereoDisemb4
				INTEGER,
			iqdbe00EmbNamesIPNamesStereoDisemb5
				INTEGER,
			iqdbe00EmbNamesIPNamesStereoDisemb6
				INTEGER,
			iqdbe00EmbNamesIPNamesStereoDisemb7
				INTEGER,
			iqdbe00EmbNamesIPNamesStereoDisemb8
				INTEGER,
			iqdbe00EmbNamesOPNamesStereoEmbed1
				INTEGER,
			iqdbe00EmbNamesOPNamesStereoEmbed2
				INTEGER,
			iqdbe00EmbNamesOPNamesStereoEmbed3
				INTEGER,
			iqdbe00EmbNamesOPNamesStereoEmbed4
				INTEGER,
			iqdbe00EmbNamesOPNamesStereoEmbed5
				INTEGER,
			iqdbe00EmbNamesOPNamesStereoEmbed6
				INTEGER,
			iqdbe00EmbNamesOPNamesStereoEmbed7
				INTEGER,
			iqdbe00EmbNamesOPNamesStereoEmbed8
				INTEGER,
			iqdbe00AudioMixNamesMix1
				RollCallString,
			iqdbe00AudioMixNamesMix2
				RollCallString,
			iqdbe00AudioMixNamesMix3
				RollCallString,
			iqdbe00AudioMixNamesMix4
				RollCallString,
			iqdbe00Mix1RoutingSource1
				INTEGER,
			iqdbe00Mix1RoutingInvert1
				INTEGER,
			iqdbe00Mix1RoutingSource2
				INTEGER,
			iqdbe00Mix1RoutingInvert2
				INTEGER,
			iqdbe00Mix1RoutingSource3
				INTEGER,
			iqdbe00Mix1RoutingInvert3
				INTEGER,
			iqdbe00Mix1RoutingSource4
				INTEGER,
			iqdbe00Mix1RoutingInvert4
				INTEGER,
			iqdbe00Mix1GainGain1
				INTEGER,
			iqdbe00Mix1GainMute1
				INTEGER,
			iqdbe00Mix1GainGain2
				INTEGER,
			iqdbe00Mix1GainMute2
				INTEGER,
			iqdbe00Mix1GainGain3
				INTEGER,
			iqdbe00Mix1GainMute3
				INTEGER,
			iqdbe00Mix1GainGain4
				INTEGER,
			iqdbe00Mix1GainMute4
				INTEGER,
			iqdbe00Mix1GainInp1Clip
				RollCallString,
			iqdbe00Mix1GainInp2Clip
				RollCallString,
			iqdbe00Mix1GainInp3Clip
				RollCallString,
			iqdbe00Mix1GainInp4Clip
				RollCallString,
			iqdbe00Mix1GainOPClip
				RollCallString,
			iqdbe00Mix2RoutingSource1
				INTEGER,
			iqdbe00Mix2RoutingInvert1
				INTEGER,
			iqdbe00Mix2RoutingSource2
				INTEGER,
			iqdbe00Mix2RoutingInvert2
				INTEGER,
			iqdbe00Mix2RoutingSource3
				INTEGER,
			iqdbe00Mix2RoutingInvert3
				INTEGER,
			iqdbe00Mix2RoutingSource4
				INTEGER,
			iqdbe00Mix2RoutingInvert4
				INTEGER,
			iqdbe00Mix2GainGain1
				INTEGER,
			iqdbe00Mix2GainMute1
				INTEGER,
			iqdbe00Mix2GainGain2
				INTEGER,
			iqdbe00Mix2GainMute2
				INTEGER,
			iqdbe00Mix2GainGain3
				INTEGER,
			iqdbe00Mix2GainMute3
				INTEGER,
			iqdbe00Mix2GainGain4
				INTEGER,
			iqdbe00Mix2GainMute4
				INTEGER,
			iqdbe00Mix2GainInp1Clip
				RollCallString,
			iqdbe00Mix2GainInp2Clip
				RollCallString,
			iqdbe00Mix2GainInp3Clip
				RollCallString,
			iqdbe00Mix2GainInp4Clip
				RollCallString,
			iqdbe00Mix2GainOPClip
				RollCallString,
			iqdbe00Mix3RoutingSource1
				INTEGER,
			iqdbe00Mix3RoutingInvert1
				INTEGER,
			iqdbe00Mix3RoutingSource2
				INTEGER,
			iqdbe00Mix3RoutingInvert2
				INTEGER,
			iqdbe00Mix3RoutingSource3
				INTEGER,
			iqdbe00Mix3RoutingInvert3
				INTEGER,
			iqdbe00Mix3RoutingSource4
				INTEGER,
			iqdbe00Mix3RoutingInvert4
				INTEGER,
			iqdbe00Mix3GainGain1
				INTEGER,
			iqdbe00Mix3GainMute1
				INTEGER,
			iqdbe00Mix3GainGain2
				INTEGER,
			iqdbe00Mix3GainMute2
				INTEGER,
			iqdbe00Mix3GainGain3
				INTEGER,
			iqdbe00Mix3GainMute3
				INTEGER,
			iqdbe00Mix3GainGain4
				INTEGER,
			iqdbe00Mix3GainMute4
				INTEGER,
			iqdbe00Mix3GainInp1Clip
				RollCallString,
			iqdbe00Mix3GainInp2Clip
				RollCallString,
			iqdbe00Mix3GainInp3Clip
				RollCallString,
			iqdbe00Mix3GainInp4Clip
				RollCallString,
			iqdbe00Mix3GainOPClip
				RollCallString,
			iqdbe00Mix4RoutingSource1
				INTEGER,
			iqdbe00Mix4RoutingInvert1
				INTEGER,
			iqdbe00Mix4RoutingSource2
				INTEGER,
			iqdbe00Mix4RoutingInvert2
				INTEGER,
			iqdbe00Mix4RoutingSource3
				INTEGER,
			iqdbe00Mix4RoutingInvert3
				INTEGER,
			iqdbe00Mix4RoutingSource4
				INTEGER,
			iqdbe00Mix4RoutingInvert4
				INTEGER,
			iqdbe00Mix4GainGain1
				INTEGER,
			iqdbe00Mix4GainMute1
				INTEGER,
			iqdbe00Mix4GainGain2
				INTEGER,
			iqdbe00Mix4GainMute2
				INTEGER,
			iqdbe00Mix4GainGain3
				INTEGER,
			iqdbe00Mix4GainMute3
				INTEGER,
			iqdbe00Mix4GainGain4
				INTEGER,
			iqdbe00Mix4GainMute4
				INTEGER,
			iqdbe00Mix4GainInp1Clip
				RollCallString,
			iqdbe00Mix4GainInp2Clip
				RollCallString,
			iqdbe00Mix4GainInp3Clip
				RollCallString,
			iqdbe00Mix4GainInp4Clip
				RollCallString,
			iqdbe00Mix4GainOPClip
				RollCallString,
			iqdbe00AESGainAESOut1AESOut1MuteL
				INTEGER,
			iqdbe00AESGainAESOut1AESOut1MuteR
				INTEGER,
			iqdbe00AESGainAESOut1AESOut1LGain
				INTEGER,
			iqdbe00AESGainAESOut1AESOut1RGain
				INTEGER,
			iqdbe00AESGainAESOut1Stereo
				INTEGER,
			iqdbe00AESGainAESOut1AESOut1InvertL
				INTEGER,
			iqdbe00AESGainAESOut1AESOut1InvertR
				INTEGER,
			iqdbe00AESGainAESOut1AESOut1LClip
				RollCallString,
			iqdbe00AESGainAESOut1AESOut1RClip
				RollCallString,
			iqdbe00AESGainAESOut2AESOut2MuteL
				INTEGER,
			iqdbe00AESGainAESOut2AESOut2MuteR
				INTEGER,
			iqdbe00AESGainAESOut2AESOut2LGain
				INTEGER,
			iqdbe00AESGainAESOut2AESOut2RGain
				INTEGER,
			iqdbe00AESGainAESOut2Stereo
				INTEGER,
			iqdbe00AESGainAESOut2AESOut2InvertL
				INTEGER,
			iqdbe00AESGainAESOut2AESOut2InvertR
				INTEGER,
			iqdbe00AESGainAESOut2AESOut2LClip
				RollCallString,
			iqdbe00AESGainAESOut2AESOut2RClip
				RollCallString,
			iqdbe00AESGainAESOut3AESOut3MuteL
				INTEGER,
			iqdbe00AESGainAESOut3AESOut3MuteR
				INTEGER,
			iqdbe00AESGainAESOut3AESOut3LGain
				INTEGER,
			iqdbe00AESGainAESOut3AESOut3RGain
				INTEGER,
			iqdbe00AESGainAESOut3Stereo
				INTEGER,
			iqdbe00AESGainAESOut3AESOut3InvertL
				INTEGER,
			iqdbe00AESGainAESOut3AESOut3InvertR
				INTEGER,
			iqdbe00AESGainAESOut3AESOut3LClip
				RollCallString,
			iqdbe00AESGainAESOut3AESOut3RClip
				RollCallString,
			iqdbe00AESGainAESOut4AESOut4MuteL
				INTEGER,
			iqdbe00AESGainAESOut4AESOut4MuteR
				INTEGER,
			iqdbe00AESGainAESOut4AESOut4LGain
				INTEGER,
			iqdbe00AESGainAESOut4AESOut4RGain
				INTEGER,
			iqdbe00AESGainAESOut4Stereo
				INTEGER,
			iqdbe00AESGainAESOut4AESOut4InvertL
				INTEGER,
			iqdbe00AESGainAESOut4AESOut4InvertR
				INTEGER,
			iqdbe00AESGainAESOut4AESOut4LClip
				RollCallString,
			iqdbe00AESGainAESOut4AESOut4RClip
				RollCallString,
			iqdbe00AESGainAESOut5AESOut5MuteL
				INTEGER,
			iqdbe00AESGainAESOut5AESOut5MuteR
				INTEGER,
			iqdbe00AESGainAESOut5AESOut5LGain
				INTEGER,
			iqdbe00AESGainAESOut5AESOut5RGain
				INTEGER,
			iqdbe00AESGainAESOut5Stereo
				INTEGER,
			iqdbe00AESGainAESOut5AESOut5InvertL
				INTEGER,
			iqdbe00AESGainAESOut5AESOut5InvertR
				INTEGER,
			iqdbe00AESGainAESOut5AESOut5LClip
				RollCallString,
			iqdbe00AESGainAESOut5AESOut5RClip
				RollCallString,
			iqdbe00AESGainAESOut6AESOut6MuteL
				INTEGER,
			iqdbe00AESGainAESOut6AESOut6MuteR
				INTEGER,
			iqdbe00AESGainAESOut6AESOut6LGain
				INTEGER,
			iqdbe00AESGainAESOut6AESOut6RGain
				INTEGER,
			iqdbe00AESGainAESOut6Stereo
				INTEGER,
			iqdbe00AESGainAESOut6AESOut6InvertL
				INTEGER,
			iqdbe00AESGainAESOut6AESOut6InvertR
				INTEGER,
			iqdbe00AESGainAESOut6AESOut6LClip
				RollCallString,
			iqdbe00AESGainAESOut6AESOut6RClip
				RollCallString,
			iqdbe00AESGainAESOut7AESOut7MuteL
				INTEGER,
			iqdbe00AESGainAESOut7AESOut7MuteR
				INTEGER,
			iqdbe00AESGainAESOut7AESOut7LGain
				INTEGER,
			iqdbe00AESGainAESOut7AESOut7RGain
				INTEGER,
			iqdbe00AESGainAESOut7Stereo
				INTEGER,
			iqdbe00AESGainAESOut7AESOut7InvertL
				INTEGER,
			iqdbe00AESGainAESOut7AESOut7InvertR
				INTEGER,
			iqdbe00AESGainAESOut7AESOut7LClip
				RollCallString,
			iqdbe00AESGainAESOut7AESOut7RClip
				RollCallString,
			iqdbe00AESGainAESOut8AESOut8MuteL
				INTEGER,
			iqdbe00AESGainAESOut8AESOut8MuteR
				INTEGER,
			iqdbe00AESGainAESOut8AESOut8LGain
				INTEGER,
			iqdbe00AESGainAESOut8AESOut8RGain
				INTEGER,
			iqdbe00AESGainAESOut8Stereo
				INTEGER,
			iqdbe00AESGainAESOut8AESOut8InvertL
				INTEGER,
			iqdbe00AESGainAESOut8AESOut8InvertR
				INTEGER,
			iqdbe00AESGainAESOut8AESOut8LClip
				RollCallString,
			iqdbe00AESGainAESOut8AESOut8RClip
				RollCallString,
			iqdbe00AESOutAESOut1Left
				INTEGER,
			iqdbe00AESOutAESOut1Right
				INTEGER,
			iqdbe00AESOutAESOut1LinkLRSelection
				INTEGER,
			iqdbe00AESOutAESOut2Left
				INTEGER,
			iqdbe00AESOutAESOut2Right
				INTEGER,
			iqdbe00AESOutAESOut2LinkLRSelection
				INTEGER,
			iqdbe00AESOutAESOut3Left
				INTEGER,
			iqdbe00AESOutAESOut3Right
				INTEGER,
			iqdbe00AESOutAESOut3LinkLRSelection
				INTEGER,
			iqdbe00AESOutAESOut4Left
				INTEGER,
			iqdbe00AESOutAESOut4Right
				INTEGER,
			iqdbe00AESOutAESOut4LinkLRSelection
				INTEGER,
			iqdbe00AESOutAESOut5Left
				INTEGER,
			iqdbe00AESOutAESOut5Right
				INTEGER,
			iqdbe00AESOutAESOut5LinkLRSelection
				INTEGER,
			iqdbe00AESOutAESOut6Left
				INTEGER,
			iqdbe00AESOutAESOut6Right
				INTEGER,
			iqdbe00AESOutAESOut6LinkLRSelection
				INTEGER,
			iqdbe00AESOutAESOut7Left
				INTEGER,
			iqdbe00AESOutAESOut7Right
				INTEGER,
			iqdbe00AESOutAESOut7LinkLRSelection
				INTEGER,
			iqdbe00AESOutAESOut8Left
				INTEGER,
			iqdbe00AESOutAESOut8Right
				INTEGER,
			iqdbe00AESOutAESOut8LinkLRSelection
				INTEGER,
			iqdbe00AESOutMonitoropLeft
				INTEGER,
			iqdbe00AESOutMonitoropRight
				INTEGER,
			iqdbe00AESOutMonitoropLinkLRSelection
				INTEGER,
			iqdbe00AESOutAESPortNamesAESPort1Stereo
				INTEGER,
			iqdbe00AESOutAESPortNamesAESPort1L
				RollCallString,
			iqdbe00AESOutAESPortNamesAESPort1R
				RollCallString,
			iqdbe00AESOutAESPortNamesAESPort2Stereo
				INTEGER,
			iqdbe00AESOutAESPortNamesAESPort2L
				RollCallString,
			iqdbe00AESOutAESPortNamesAESPort2R
				RollCallString,
			iqdbe00AESOutAESPortNamesAESPort3Stereo
				INTEGER,
			iqdbe00AESOutAESPortNamesAESPort3L
				RollCallString,
			iqdbe00AESOutAESPortNamesAESPort3R
				RollCallString,
			iqdbe00AESOutAESPortNamesAESPort4Stereo
				INTEGER,
			iqdbe00AESOutAESPortNamesAESPort4L
				RollCallString,
			iqdbe00AESOutAESPortNamesAESPort4R
				RollCallString,
			iqdbe00AESOutAESPortNamesAESPort5Stereo
				INTEGER,
			iqdbe00AESOutAESPortNamesAESPort5L
				RollCallString,
			iqdbe00AESOutAESPortNamesAESPort5R
				RollCallString,
			iqdbe00AESOutAESPortNamesAESPort6Stereo
				INTEGER,
			iqdbe00AESOutAESPortNamesAESPort6L
				RollCallString,
			iqdbe00AESOutAESPortNamesAESPort6R
				RollCallString,
			iqdbe00AESOutAESPortNamesAESPort7Stereo
				INTEGER,
			iqdbe00AESOutAESPortNamesAESPort7L
				RollCallString,
			iqdbe00AESOutAESPortNamesAESPort7R
				RollCallString,
			iqdbe00AESOutAESPortNamesAESPort8Stereo
				INTEGER,
			iqdbe00AESOutAESPortNamesAESPort8L
				RollCallString,
			iqdbe00AESOutAESPortNamesAESPort8R
				RollCallString,
			iqdbe00AESBusAESDataModeInput1
				INTEGER,
			iqdbe00AESBusAESDataModeInput2
				INTEGER,
			iqdbe00AESBusAESDataModeInput3
				INTEGER,
			iqdbe00AESBusAESDataModeInput4
				INTEGER,
			iqdbe00AESBusAESDataModeInput5
				INTEGER,
			iqdbe00AESBusAESDataModeInput6
				INTEGER,
			iqdbe00AESBusAESDataModeInput7
				INTEGER,
			iqdbe00AESBusAESDataModeInput8
				INTEGER,
			iqdbe00AESBusAESBusNamesAESBus1Stereo
				INTEGER,
			iqdbe00AESBusAESBusNamesAESBus1
				RollCallString,
			iqdbe00AESBusAESBusNamesAESBus1R
				RollCallString,
			iqdbe00AESBusAESBusNamesAESBus2Stereo
				INTEGER,
			iqdbe00AESBusAESBusNamesAESBus2
				RollCallString,
			iqdbe00AESBusAESBusNamesAESBus2R
				RollCallString,
			iqdbe00AESBusAESBusNamesAESBus3Stereo
				INTEGER,
			iqdbe00AESBusAESBusNamesAESBus3
				RollCallString,
			iqdbe00AESBusAESBusNamesAESBus3R
				RollCallString,
			iqdbe00AESBusAESBusNamesAESBus4Stereo
				INTEGER,
			iqdbe00AESBusAESBusNamesAESBus4
				RollCallString,
			iqdbe00AESBusAESBusNamesAESBus4R
				RollCallString,
			iqdbe00AESBusAESBusNamesAESBus5Stereo
				INTEGER,
			iqdbe00AESBusAESBusNamesAESBus5
				RollCallString,
			iqdbe00AESBusAESBusNamesAESBus5R
				RollCallString,
			iqdbe00AESBusAESBusNamesAESBus6Stereo
				INTEGER,
			iqdbe00AESBusAESBusNamesAESBus6
				RollCallString,
			iqdbe00AESBusAESBusNamesAESBus6R
				RollCallString,
			iqdbe00AESBusAESBusNamesAESBus7Stereo
				INTEGER,
			iqdbe00AESBusAESBusNamesAESBus7
				RollCallString,
			iqdbe00AESBusAESBusNamesAESBus7R
				RollCallString,
			iqdbe00AESBusAESBusNamesAESBus8Stereo
				INTEGER,
			iqdbe00AESBusAESBusNamesAESBus8
				RollCallString,
			iqdbe00AESBusAESBusNamesAESBus8R
				RollCallString,
			iqdbe00AESBusAESBusRoutingSource1
				INTEGER,
			iqdbe00AESBusAESBusRoutingSource2
				INTEGER,
			iqdbe00AESBusAESBusRoutingSource3
				INTEGER,
			iqdbe00AESBusAESBusRoutingSource4
				INTEGER,
			iqdbe00AESBusAESBusRoutingSource5
				INTEGER,
			iqdbe00AESBusAESBusRoutingSource6
				INTEGER,
			iqdbe00AESBusAESBusRoutingSource7
				INTEGER,
			iqdbe00AESBusAESBusRoutingSource8
				INTEGER,
			iqdbe00AESPortsAESDirectionAESPort1Dir
				INTEGER,
			iqdbe00AESPortsAESDirectionAESPort2Dir
				INTEGER,
			iqdbe00AESPortsAESDirectionAESPort3Dir
				INTEGER,
			iqdbe00AESPortsAESDirectionAESPort4Dir
				INTEGER,
			iqdbe00AESPortsAESDirectionAESPort5Dir
				INTEGER,
			iqdbe00AESPortsAESDirectionAESPort6Dir
				INTEGER,
			iqdbe00AESPortsAESDirectionAESPort7Dir
				INTEGER,
			iqdbe00AESPortsAESDirectionAESPort8Dir
				INTEGER,
			iqdbe00AudioDolbyETimingSelAudioPair
				INTEGER,
			iqdbe00AudioDolbyETimingRelativeTiming
				RollCallString,
			iqdbe00AudioDolbyETimingStatus
				RollCallString,
			iqdbe00AudioDolbyETimingError
				RollCallString,
			iqdbe00DolbyETimingDolbyELineStandard
				INTEGER,
			iqdbe00DolbyETimingDolbyELineAutoLineNo
				INTEGER,
			iqdbe00DolbyELineUserDolbyELinePair1
				INTEGER,
			iqdbe00DolbyELineUserDolbyELinePair2
				INTEGER,
			iqdbe00DolbyELineUserDolbyELinePair3
				INTEGER,
			iqdbe00DolbyELineUserDolbyELinePair4
				INTEGER,
			iqdbe00DolbyELineUserDolbyELinePair5
				INTEGER,
			iqdbe00DolbyELineUserDolbyELinePair6
				INTEGER,
			iqdbe00DolbyELineUserDolbyELinePair7
				INTEGER,
			iqdbe00DolbyELineUserDolbyELinePair8
				INTEGER,
			iqdbe00InputChanAssignInputAA1
				INTEGER,
			iqdbe00InputChanAssignInputAA2
				INTEGER,
			iqdbe00InputChanAssignInputALinkLR
				INTEGER,
			iqdbe00InputChanAssignInputBB3
				INTEGER,
			iqdbe00InputChanAssignInputBB4
				INTEGER,
			iqdbe00InputChanAssignInputBLinkLR
				INTEGER,
			iqdbe00InputChanAssignInputCC5
				INTEGER,
			iqdbe00InputChanAssignInputCC6
				INTEGER,
			iqdbe00InputChanAssignInputCLinkLR
				INTEGER,
			iqdbe00InputChanAssignInputDD7
				INTEGER,
			iqdbe00InputChanAssignInputDD8
				INTEGER,
			iqdbe00InputChanAssignInputDLinkLR
				INTEGER,
			iqdbe00AudioDolbyEncoderBitDepth
				INTEGER,
			iqdbe00AudioDolbyEncoderMetadataSource
				INTEGER,
			iqdbe00AudioDolbyEncoderEncodingMode
				INTEGER,
			iqdbe00AudioDolbyEncoderReversionMode
				INTEGER,
			iqdbe00DolbyEncoderInternalMetadataProgramConfig
				INTEGER,
			iqdbe00DolbyEncoderInternalMetadataProgramSel
				INTEGER,
			iqdbe00DolbyEncoderInternalMetadataDialogueNorm
				INTEGER,
			iqdbe00DolbyEncoderInternalMetadataInputAssignAB
				RollCallString,
			iqdbe00DolbyEncoderInternalMetadataInputAssignCD
				RollCallString,
			iqdbe00DolbyEncoderInternalMetadataChannelMode
				INTEGER,
			iqdbe00DolbyEncoderInternalMetadataLFEChannel
				INTEGER,
			iqdbe00DolbyEncoderInternalMetadataBitstreamMode
				INTEGER,
			iqdbe00DolbyEncoderInternalMetadataRFMode
				INTEGER,
			iqdbe00DolbyEncoderInternalMetadataLineMode
				INTEGER,
			iqdbe00InternalMetadataAudioProdInfoExists
				INTEGER,
			iqdbe00InternalMetadataAudioProdInfoMixLevel
				INTEGER,
			iqdbe00InternalMetadataAudioProdInfoRoomType
				INTEGER,
			iqdbe00DolbyEncoderInternalMetadataSurroundMode
				INTEGER,
			iqdbe00DolbyEncoderInternalMetadataCenterMixLevel
				INTEGER,
			iqdbe00DolbyEncoderInternalMetadataSurroundMixLevel
				INTEGER,
			iqdbe00InternalMetadataExtendedBSI1ExtBSI1Exists
				INTEGER,
			iqdbe00InternalMetadataExtendedBSI1StereoDownmixMode
				INTEGER,
			iqdbe00InternalMetadataExtendedBSI1LtRtCenterDownmix
				INTEGER,
			iqdbe00InternalMetadataExtendedBSI1LoRoCenterDownmix
				INTEGER,
			iqdbe00InternalMetadataExtendedBSI1LtRtSurroundDownm
				INTEGER,
			iqdbe00InternalMetadataExtendedBSI1LoRoSurroundDownm
				INTEGER,
			iqdbe00InternalMetadataExtendedBSI2ExtBSI2Exists
				INTEGER,
			iqdbe00InternalMetadataExtendedBSI2SurroundExMode
				INTEGER,
			iqdbe00InternalMetadataExtendedBSI2LowpassFilter
				INTEGER,
			iqdbe00InternalMetadataExtendedBSI2LFEFilter
				INTEGER,
			iqdbe00InternalMetadataExtendedBSI2SurrPhaseShiftFi
				INTEGER,
			iqdbe00InternalMetadataExtendedBSI2Surr3dBAttenuator
				INTEGER,
			iqdbe00DolbyEncoderInternalMetadataProgDescpt1
				RollCallString,
			iqdbe00DolbyEncoderInternalMetadataProgDescpt2
				RollCallString,
			iqdbe00DolbyEncoderInternalMetadataDolbyEncReset
				INTEGER,
			iqdbe00InternalMetadataProgPresetIntMD
				INTEGER,
			iqdbe00ProgPresetIntMDSaveUserPresetSelUserPreset
				INTEGER,
			iqdbe00ProgPresetIntMDSaveUserPresetSavePreset
				INTEGER,
			iqdbe00ProgPresetIntMDSaveUserPresetNamePreset
				RollCallString,
			iqdbe00DolbyEncoderOutputMetadataProgramSel
				INTEGER,
			iqdbe00DolbyEncoderOutputMetadataProgramConfig
				RollCallString,
			iqdbe00DolbyEncoderOutputMetadataProgramNamept1
				RollCallString,
			iqdbe00DolbyEncoderOutputMetadataProgramNamept2
				RollCallString,
			iqdbe00DolbyEncoderOutputMetadataDialogueNorm
				RollCallString,
			iqdbe00DolbyEncoderOutputMetadataChannelMode
				RollCallString,
			iqdbe00DolbyEncoderOutputMetadataLFEChannel
				RollCallString,
			iqdbe00DolbyEncoderOutputMetadataBitstreamMode
				RollCallString,
			iqdbe00DolbyEncoderOutputMetadataRFMode
				RollCallString,
			iqdbe00DolbyEncoderOutputMetadataLineMode
				RollCallString,
			iqdbe00DolbyEncoderOutputMetadataCenterMixLevel
				RollCallString,
			iqdbe00DolbyEncoderOutputMetadataSurroundMixLevel
				RollCallString,
			iqdbe00DolbyEncoderOutputMetadataSurrondMode
				RollCallString,
			iqdbe00OutputMetadataAudioProdInfoExists
				RollCallString,
			iqdbe00OutputMetadataAudioProdInfoMixLevel
				RollCallString,
			iqdbe00OutputMetadataAudioProdInfoRoomType
				RollCallString,
			iqdbe00OutputMetadataExtendedBSI1Exists
				RollCallString,
			iqdbe00OutputMetadataExtendedBSI1StereoDownmixMode
				RollCallString,
			iqdbe00OutputMetadataExtendedBSI1LtRtCenMixLevel
				RollCallString,
			iqdbe00OutputMetadataExtendedBSI1LtRtSurMixLevel
				RollCallString,
			iqdbe00OutputMetadataExtendedBSI1LoRoCenMixLevel
				RollCallString,
			iqdbe00OutputMetadataExtendedBSI1LoRoSurMixLevel
				RollCallString,
			iqdbe00OutputMetadataExtendedBSI2Exists
				RollCallString,
			iqdbe00OutputMetadataExtendedBSI2SurExMode
				RollCallString,
			iqdbe00OutputMetadataExtendedBSI2LowpassFilter
				RollCallString,
			iqdbe00OutputMetadataExtendedBSI2LFEFilter
				RollCallString,
			iqdbe00OutputMetadataExtendedBSI2SurPhshiftFilter
				RollCallString,
			iqdbe00OutputMetadataExtendedBSI2Sur3dBAttenuator
				RollCallString,
			iqdbe00AudioDolbyEncoderFirmwareVersion
				RollCallString,
			iqdbe00AudioVidDelayInternalDelay
				RollCallString,
			iqdbe00AudioVidDelayDelayMode
				INTEGER,
			iqdbe00VidDelaySetDelayDelayFrames
				INTEGER,
			iqdbe00VidDelaySetDelayVerticalTiming
				INTEGER,
			iqdbe00VidDelaySetDelayHorizontalTiming
				INTEGER,
			iqdbe00VidDelaySetDelayDelayms
				INTEGER,
			iqdbe00UtilsPatternsPatternEnable
				INTEGER,
			iqdbe00UtilsPatternsScrollPattern
				INTEGER,
			iqdbe00UtilsPatternsPatternType
				INTEGER,
			iqdbe00AudioUtilsANCblankonMismat
				INTEGER,
			iqdbe00UtilsFreezeForceFreeze
				INTEGER,
			iqdbe00UtilsFreezeFreezeType
				INTEGER,
			iqdbe00UtilsMonochrome
				INTEGER,
			iqdbe00UtilsMonochromeMonochromeType
				INTEGER,
			iqdbe00UtilsVBIBlankingANCMode
				INTEGER,
			iqdbe00UtilsVBIBlankingStandard
				INTEGER,
			iqdbe00UtilsVBIBlankingBlankAll
				INTEGER,
			iqdbe00UtilsVBIBlankingPassAll
				INTEGER,
			iqdbe00UtilsVBIBlankingBlank1
				INTEGER,
			iqdbe00UtilsVBIBlankingBlank2
				INTEGER,
			iqdbe00UtilsVBIBlankingBlank3
				INTEGER,
			iqdbe00UtilsVBIBlankingBlank4
				INTEGER,
			iqdbe00UtilsVBIBlankingBlank5
				INTEGER,
			iqdbe00UtilsVBIBlankingBlank6
				INTEGER,
			iqdbe00UtilsVBIBlankingBlank7
				INTEGER,
			iqdbe00UtilsVBIBlankingBlank8
				INTEGER,
			iqdbe00UtilsVBIBlankingBlank9
				INTEGER,
			iqdbe00UtilsVBIBlankingBlank10
				INTEGER,
			iqdbe00UtilsVBIBlankingBlank11
				INTEGER,
			iqdbe00UtilsVBIBlankingBlank12
				INTEGER,
			iqdbe00UtilsVBIBlankingBlank13
				INTEGER,
			iqdbe00UtilsVBIBlankingBlank14
				INTEGER,
			iqdbe00UtilsVBIBlankingBlank15
				INTEGER,
			iqdbe00UtilsVBIBlankingBlank16
				INTEGER,
			iqdbe00UtilsVBIBlankingBlank17
				INTEGER,
			iqdbe00UtilsVBIBlankingBlank18
				INTEGER,
			iqdbe00UtilsVBIBlankingBlank19
				INTEGER,
			iqdbe00UtilsVBIBlankingBlank20
				INTEGER,
			iqdbe00UtilsVBIBlankingBlank21
				INTEGER,
			iqdbe00UtilsVBIBlankingBlank22
				INTEGER,
			iqdbe00UtilsVBIBlankingBlank23
				INTEGER,
			iqdbe00UtilsVBIBlankingBlank24
				INTEGER,
			iqdbe00UtilsVBIBlankingBlank25
				INTEGER,
			iqdbe00UtilsVBIBlankingBlank26
				INTEGER,
			iqdbe00UtilsVBIBlankingBlank27
				INTEGER,
			iqdbe00UtilsVBIBlankingBlank28
				INTEGER,
			iqdbe00UtilsVBIBlankingBlank29
				INTEGER,
			iqdbe00UtilsVBIBlankingBlank30
				INTEGER,
			iqdbe00UtilsVBIBlankingBlank31
				INTEGER,
			iqdbe00UtilsVBIBlankingBlank32
				INTEGER,
			iqdbe00UtilsVBIBlankingBlank33
				INTEGER,
			iqdbe00UtilsVBIBlankingBlank34
				INTEGER,
			iqdbe00RecallMemory
				INTEGER,
			iqdbe00SelMemory
				INTEGER,
			iqdbe00SaveMemory
				INTEGER,
			iqdbe00ClearMemory
				INTEGER,
			iqdbe00MemoryNameChangeName
				RollCallString,
			iqdbe00MemoryNameLastUserMemory
				RollCallString,
			iqdbe00MemoryName1
				RollCallString,
			iqdbe00MemoryName2
				RollCallString,
			iqdbe00MemoryName3
				RollCallString,
			iqdbe00MemoryName4
				RollCallString,
			iqdbe00MemoryName5
				RollCallString,
			iqdbe00MemoryName6
				RollCallString,
			iqdbe00MemoryName7
				RollCallString,
			iqdbe00MemoryName8
				RollCallString,
			iqdbe00MemoryName9
				RollCallString,
			iqdbe00MemoryName10
				RollCallString,
			iqdbe00MemoryName11
				RollCallString,
			iqdbe00MemoryName12
				RollCallString,
			iqdbe00MemoryName13
				RollCallString,
			iqdbe00MemoryName14
				RollCallString,
			iqdbe00MemoryName15
				RollCallString,
			iqdbe00MemoryName16
				RollCallString,
			iqdbe00LoggingVideoLoggingLogInput1Type
				INTEGER,
			iqdbe00LoggingVideoLoggingInput1Type
				RollCallString,
			iqdbe00LoggingVideoLoggingLogInput1Status
				INTEGER,
			iqdbe00LoggingVideoLoggingInput1Status
				RollCallString,
			iqdbe00LoggingVideoLoggingLogInput1Std
				INTEGER,
			iqdbe00LoggingVideoLoggingInput1Std
				RollCallString,
			iqdbe00LoggingVideoLoggingLogInput1Errors
				INTEGER,
			iqdbe00LoggingVideoLoggingInput1Errors
				RollCallString,
			iqdbe00LoggingVideoLoggingLogInput1ErrSecs
				INTEGER,
			iqdbe00LoggingVideoLoggingInput1ErrSecs
				RollCallString,
			iqdbe00LoggingVideoLoggingLogInput1ANCErr
				INTEGER,
			iqdbe00LoggingVideoLoggingInput1ANCErrors
				RollCallString,
			iqdbe00LoggingVideoLoggingLogInput1ANCErrSec
				INTEGER,
			iqdbe00LoggingVideoLoggingInput1ANCErrSecs
				RollCallString,
			iqdbe00LoggingVideoLoggingLogOutputState
				INTEGER,
			iqdbe00LoggingVideoLoggingOutputState
				RollCallString,
			iqdbe00LoggingVideoLoggingLogOutputType
				INTEGER,
			iqdbe00LoggingVideoLoggingOutputType
				RollCallString,
			iqdbe00LoggingVideoLoggingLogOutputStandard
				INTEGER,
			iqdbe00LoggingVideoLoggingOutputStandard
				RollCallString,
			iqdbe00LoggingVideoLoggingLogoutputANCstat
				INTEGER,
			iqdbe00LoggingVideoLoggingOutputANCstate
				RollCallString,
			iqdbe00LoggingEmbAudLoggingLogInp1Emb1stat
				INTEGER,
			iqdbe00LoggingEmbAudLoggingInp1Emb1state
				RollCallString,
			iqdbe00LoggingEmbAudLoggingLogInp1Emb2stat
				INTEGER,
			iqdbe00LoggingEmbAudLoggingInp1Emb2state
				RollCallString,
			iqdbe00LoggingEmbAudLoggingLogInp1Emb3stat
				INTEGER,
			iqdbe00LoggingEmbAudLoggingInp1Emb3state
				RollCallString,
			iqdbe00LoggingEmbAudLoggingLogInp1Emb4stat
				INTEGER,
			iqdbe00LoggingEmbAudLoggingInp1Emb4state
				RollCallString,
			iqdbe00LoggingEmbAudLoggingLogInp1Emb5stat
				INTEGER,
			iqdbe00LoggingEmbAudLoggingInp1Emb5state
				RollCallString,
			iqdbe00LoggingEmbAudLoggingLogInp1Emb6stat
				INTEGER,
			iqdbe00LoggingEmbAudLoggingInp1Emb6state
				RollCallString,
			iqdbe00LoggingEmbAudLoggingLogInp1Emb7stat
				INTEGER,
			iqdbe00LoggingEmbAudLoggingInp1Emb7state
				RollCallString,
			iqdbe00LoggingEmbAudLoggingLogInp1Emb8stat
				INTEGER,
			iqdbe00LoggingEmbAudLoggingInp1Emb8state
				RollCallString,
			iqdbe00LoggingEmbAudLoggingLogInp1Emb1type
				INTEGER,
			iqdbe00LoggingEmbAudLoggingInp1Emb1type
				RollCallString,
			iqdbe00LoggingEmbAudLoggingLogInp1Emb2type
				INTEGER,
			iqdbe00LoggingEmbAudLoggingInp1Emb2type
				RollCallString,
			iqdbe00LoggingEmbAudLoggingLogInp1Emb3type
				INTEGER,
			iqdbe00LoggingEmbAudLoggingInp1Emb3type
				RollCallString,
			iqdbe00LoggingEmbAudLoggingLogInp1Emb4type
				INTEGER,
			iqdbe00LoggingEmbAudLoggingInp1Emb4type
				RollCallString,
			iqdbe00LoggingEmbAudLoggingLogInp1Emb5type
				INTEGER,
			iqdbe00LoggingEmbAudLoggingInp1Emb5type
				RollCallString,
			iqdbe00LoggingEmbAudLoggingLogInp1Emb6type
				INTEGER,
			iqdbe00LoggingEmbAudLoggingInp1Emb6type
				RollCallString,
			iqdbe00LoggingEmbAudLoggingLogInp1Emb7type
				INTEGER,
			iqdbe00LoggingEmbAudLoggingInp1Emb7type
				RollCallString,
			iqdbe00LoggingEmbAudLoggingLogInp1Emb8type
				INTEGER,
			iqdbe00LoggingEmbAudLoggingInp1Emb8type
				RollCallString,
			iqdbe00LoggingOPAudLoggingLogOutEmb1state
				INTEGER,
			iqdbe00LoggingOPAudLoggingOutEmb1state
				RollCallString,
			iqdbe00LoggingOPAudLoggingLogOutEmb2state
				INTEGER,
			iqdbe00LoggingOPAudLoggingOutEmb2state
				RollCallString,
			iqdbe00LoggingOPAudLoggingLogOutEmb3state
				INTEGER,
			iqdbe00LoggingOPAudLoggingOutEmb3state
				RollCallString,
			iqdbe00LoggingOPAudLoggingLogOutEmb4state
				INTEGER,
			iqdbe00LoggingOPAudLoggingOutEmb4state
				RollCallString,
			iqdbe00LoggingOPAudLoggingLogOutEmb5state
				INTEGER,
			iqdbe00LoggingOPAudLoggingOutEmb5state
				RollCallString,
			iqdbe00LoggingOPAudLoggingLogOutEmb6state
				INTEGER,
			iqdbe00LoggingOPAudLoggingOutEmb6state
				RollCallString,
			iqdbe00LoggingOPAudLoggingLogOutEmb7state
				INTEGER,
			iqdbe00LoggingOPAudLoggingOutEmb7state
				RollCallString,
			iqdbe00LoggingOPAudLoggingLogOutEmb8state
				INTEGER,
			iqdbe00LoggingOPAudLoggingOutEmb8state
				RollCallString,
			iqdbe00LoggingOPAudLoggingLogOutEmb1type
				INTEGER,
			iqdbe00LoggingOPAudLoggingOutEmb1type
				RollCallString,
			iqdbe00LoggingOPAudLoggingLogOutEmb2type
				INTEGER,
			iqdbe00LoggingOPAudLoggingOutEmb2type
				RollCallString,
			iqdbe00LoggingOPAudLoggingLogOutEmb3type
				INTEGER,
			iqdbe00LoggingOPAudLoggingOutEmb3type
				RollCallString,
			iqdbe00LoggingOPAudLoggingLogOutEmb4type
				INTEGER,
			iqdbe00LoggingOPAudLoggingOutEmb4type
				RollCallString,
			iqdbe00LoggingOPAudLoggingLogOutEmb5type
				INTEGER,
			iqdbe00LoggingOPAudLoggingOutEmb5type
				RollCallString,
			iqdbe00LoggingOPAudLoggingLogOutEmb6type
				INTEGER,
			iqdbe00LoggingOPAudLoggingOutEmb6type
				RollCallString,
			iqdbe00LoggingOPAudLoggingLogOutEmb7type
				INTEGER,
			iqdbe00LoggingOPAudLoggingOutEmb7type
				RollCallString,
			iqdbe00LoggingOPAudLoggingLogOutEmb8type
				INTEGER,
			iqdbe00LoggingOPAudLoggingOutEmb8type
				RollCallString,
			iqdbe00LoggingOPAudLevelLoggiLogOutEmb1LLev
				INTEGER,
			iqdbe00LoggingOPAudLevelLoggiOutEmb1LLevel
				RollCallString,
			iqdbe00LoggingOPAudLevelLoggiLogOutEmb1RLev
				INTEGER,
			iqdbe00LoggingOPAudLevelLoggiOutEmb1RLevel
				RollCallString,
			iqdbe00LoggingOPAudLevelLoggiLogOutEmb2LLev
				INTEGER,
			iqdbe00LoggingOPAudLevelLoggiOutEmb2LLevel
				RollCallString,
			iqdbe00LoggingOPAudLevelLoggiLogOutEmb2RLev
				INTEGER,
			iqdbe00LoggingOPAudLevelLoggiOutEmb2RLevel
				RollCallString,
			iqdbe00LoggingOPAudLevelLoggiLogOutEmb3LLev
				INTEGER,
			iqdbe00LoggingOPAudLevelLoggiOutEmb3LLevel
				RollCallString,
			iqdbe00LoggingOPAudLevelLoggiLogOutEmb3RLev
				INTEGER,
			iqdbe00LoggingOPAudLevelLoggiOutEmb3RLevel
				RollCallString,
			iqdbe00LoggingOPAudLevelLoggiLogOutEmb4LLev
				INTEGER,
			iqdbe00LoggingOPAudLevelLoggiOutEmb4LLevel
				RollCallString,
			iqdbe00LoggingOPAudLevelLoggiLogOutEmb4RLev
				INTEGER,
			iqdbe00LoggingOPAudLevelLoggiOutEmb4RLevel
				RollCallString,
			iqdbe00LoggingOPAudLevelLoggiLogOutEmb5LLev
				INTEGER,
			iqdbe00LoggingOPAudLevelLoggiOutEmb5LLevel
				RollCallString,
			iqdbe00LoggingOPAudLevelLoggiLogOutEmb5RLev
				INTEGER,
			iqdbe00LoggingOPAudLevelLoggiOutEmb5RLevel
				RollCallString,
			iqdbe00LoggingOPAudLevelLoggiLogOutEmb6LLev
				INTEGER,
			iqdbe00LoggingOPAudLevelLoggiOutEmb6LLevel
				RollCallString,
			iqdbe00LoggingOPAudLevelLoggiLogOutEmb6RLev
				INTEGER,
			iqdbe00LoggingOPAudLevelLoggiOutEmb6RLevel
				RollCallString,
			iqdbe00LoggingOPAudLevelLoggiLogOutEmb7LLev
				INTEGER,
			iqdbe00LoggingOPAudLevelLoggiOutEmb7LLevel
				RollCallString,
			iqdbe00LoggingOPAudLevelLoggiLogOutEmb7RLev
				INTEGER,
			iqdbe00LoggingOPAudLevelLoggiOutEmb7RLevel
				RollCallString,
			iqdbe00LoggingOPAudLevelLoggiLogOutEmb8LLev
				INTEGER,
			iqdbe00LoggingOPAudLevelLoggiOutEmb8LLevel
				RollCallString,
			iqdbe00LoggingOPAudLevelLoggiLogOutEmb8RLev
				INTEGER,
			iqdbe00LoggingOPAudLevelLoggiOutEmb8RLevel
				RollCallString,
			iqdbe00LoggingOPDolbyELoggingLogEmbDolbyE1
				INTEGER,
			iqdbe00LoggingOPDolbyELoggingEmbDolbyE1
				RollCallString,
			iqdbe00LoggingOPDolbyELoggingLogEmbDolbyE2
				INTEGER,
			iqdbe00LoggingOPDolbyELoggingEmbDolbyE2
				RollCallString,
			iqdbe00LoggingOPDolbyELoggingLogEmbDolbyE3
				INTEGER,
			iqdbe00LoggingOPDolbyELoggingEmbDolbyE3
				RollCallString,
			iqdbe00LoggingOPDolbyELoggingLogEmbDolbyE4
				INTEGER,
			iqdbe00LoggingOPDolbyELoggingEmbDolbyE4
				RollCallString,
			iqdbe00LoggingOPDolbyELoggingLogEmbDolbyE5
				INTEGER,
			iqdbe00LoggingOPDolbyELoggingEmbDolbyE5
				RollCallString,
			iqdbe00LoggingOPDolbyELoggingLogEmbDolbyE6
				INTEGER,
			iqdbe00LoggingOPDolbyELoggingEmbDolbyE6
				RollCallString,
			iqdbe00LoggingOPDolbyELoggingLogEmbDolbyE7
				INTEGER,
			iqdbe00LoggingOPDolbyELoggingEmbDolbyE7
				RollCallString,
			iqdbe00LoggingOPDolbyELoggingLogEmbDolbyE8
				INTEGER,
			iqdbe00LoggingOPDolbyELoggingEmbDolbyE8
				RollCallString,
			iqdbe00LoggingAESInputLoggingLogAESInput1sta
				INTEGER,
			iqdbe00LoggingAESInputLoggingAESInput1state
				RollCallString,
			iqdbe00LoggingAESInputLoggingLogAESInput2sta
				INTEGER,
			iqdbe00LoggingAESInputLoggingAESInput2state
				RollCallString,
			iqdbe00LoggingAESInputLoggingLogAESInput3sta
				INTEGER,
			iqdbe00LoggingAESInputLoggingAESInput3state
				RollCallString,
			iqdbe00LoggingAESInputLoggingLogAESInput4sta
				INTEGER,
			iqdbe00LoggingAESInputLoggingAESInput4state
				RollCallString,
			iqdbe00LoggingAESInputLoggingLogAESInput5sta
				INTEGER,
			iqdbe00LoggingAESInputLoggingAESInput5state
				RollCallString,
			iqdbe00LoggingAESInputLoggingLogAESInput6sta
				INTEGER,
			iqdbe00LoggingAESInputLoggingAESInput6state
				RollCallString,
			iqdbe00LoggingAESInputLoggingLogAESInput7sta
				INTEGER,
			iqdbe00LoggingAESInputLoggingAESInput7state
				RollCallString,
			iqdbe00LoggingAESInputLoggingLogAESInput8sta
				INTEGER,
			iqdbe00LoggingAESInputLoggingAESInput8state
				RollCallString,
			iqdbe00LoggingAESInputLoggingLogAESInput1typ
				INTEGER,
			iqdbe00LoggingAESInputLoggingAESInput1type
				RollCallString,
			iqdbe00LoggingAESInputLoggingLogAESInput2typ
				INTEGER,
			iqdbe00LoggingAESInputLoggingAESInput2type
				RollCallString,
			iqdbe00LoggingAESInputLoggingLogAESInput3typ
				INTEGER,
			iqdbe00LoggingAESInputLoggingAESInput3type
				RollCallString,
			iqdbe00LoggingAESInputLoggingLogAESInput4typ
				INTEGER,
			iqdbe00LoggingAESInputLoggingAESInput4type
				RollCallString,
			iqdbe00LoggingAESInputLoggingLogAESInput5typ
				INTEGER,
			iqdbe00LoggingAESInputLoggingAESInput5type
				RollCallString,
			iqdbe00LoggingAESInputLoggingLogAESInput6typ
				INTEGER,
			iqdbe00LoggingAESInputLoggingAESInput6type
				RollCallString,
			iqdbe00LoggingAESInputLoggingLogAESInput7typ
				INTEGER,
			iqdbe00LoggingAESInputLoggingAESInput7type
				RollCallString,
			iqdbe00LoggingAESInputLoggingLogAESInput8typ
				INTEGER,
			iqdbe00LoggingAESInputLoggingAESInput8type
				RollCallString,
			iqdbe00LoggingAESOutputLoggingLogAESOutput1st
				INTEGER,
			iqdbe00LoggingAESOutputLoggingAESOutput1state
				RollCallString,
			iqdbe00LoggingAESOutputLoggingLogAESOutput2st
				INTEGER,
			iqdbe00LoggingAESOutputLoggingAESOutput2state
				RollCallString,
			iqdbe00LoggingAESOutputLoggingLogAESOutput3st
				INTEGER,
			iqdbe00LoggingAESOutputLoggingAESOutput3state
				RollCallString,
			iqdbe00LoggingAESOutputLoggingLogAESOutput4st
				INTEGER,
			iqdbe00LoggingAESOutputLoggingAESOutput4state
				RollCallString,
			iqdbe00LoggingAESOutputLoggingLogAESOutput5st
				INTEGER,
			iqdbe00LoggingAESOutputLoggingAESOutput5state
				RollCallString,
			iqdbe00LoggingAESOutputLoggingLogAESOutput6st
				INTEGER,
			iqdbe00LoggingAESOutputLoggingAESOutput6state
				RollCallString,
			iqdbe00LoggingAESOutputLoggingLogAESOutput7st
				INTEGER,
			iqdbe00LoggingAESOutputLoggingAESOutput7state
				RollCallString,
			iqdbe00LoggingAESOutputLoggingLogAESOutput8st
				INTEGER,
			iqdbe00LoggingAESOutputLoggingAESOutput8state
				RollCallString,
			iqdbe00LoggingAESOutputLoggingLogAESOutput1ty
				INTEGER,
			iqdbe00LoggingAESOutputLoggingAESOutput1type
				RollCallString,
			iqdbe00LoggingAESOutputLoggingLogAESOutput2ty
				INTEGER,
			iqdbe00LoggingAESOutputLoggingAESOutput2type
				RollCallString,
			iqdbe00LoggingAESOutputLoggingLogAESOutput3ty
				INTEGER,
			iqdbe00LoggingAESOutputLoggingAESOutput3type
				RollCallString,
			iqdbe00LoggingAESOutputLoggingLogAESOutput4ty
				INTEGER,
			iqdbe00LoggingAESOutputLoggingAESOutput4type
				RollCallString,
			iqdbe00LoggingAESOutputLoggingLogAESOutput5ty
				INTEGER,
			iqdbe00LoggingAESOutputLoggingAESOutput5type
				RollCallString,
			iqdbe00LoggingAESOutputLoggingLogAESOutput6ty
				INTEGER,
			iqdbe00LoggingAESOutputLoggingAESOutput6type
				RollCallString,
			iqdbe00LoggingAESOutputLoggingLogAESOutput7ty
				INTEGER,
			iqdbe00LoggingAESOutputLoggingAESOutput7type
				RollCallString,
			iqdbe00LoggingAESOutputLoggingLogAESOutput8ty
				INTEGER,
			iqdbe00LoggingAESOutputLoggingAESOutput8type
				RollCallString,
			iqdbe00LoggingDolbyEncoderLogProgConfig
				INTEGER,
			iqdbe00LoggingDolbyEncoderProgramConfig
				RollCallString,
			iqdbe00LoggingDolbyEncoderLogSource
				INTEGER,
			iqdbe00LoggingDolbyEncoderSource
				RollCallString,
			iqdbe00LoggingDolbyEncoderLogStatus
				INTEGER,
			iqdbe00LoggingDolbyEncoderStatus
				RollCallString,
			iqdbe00LoggingDolbyEncoderLogAC3
				INTEGER,
			iqdbe00LoggingDolbyEncoderAC3
				RollCallString,
			iqdbe00LoggingDolbyEncoderLogExBSI
				INTEGER,
			iqdbe00LoggingDolbyEncoderExBSI
				RollCallString,
			iqdbe00LoggingDolbyEncoderLogVFS
				INTEGER,
			iqdbe00LoggingDolbyEncoderVFS
				RollCallString,
			iqdbe00LoggingDolbyEncoderLogFramerate
				INTEGER,
			iqdbe00LoggingDolbyEncoderFramerate
				RollCallString,
			iqdbe00LoggingDolbyEncoderLogProg1DescTxt
				INTEGER,
			iqdbe00LoggingDolbyEncoderProg1DescTxt
				RollCallString,
			iqdbe00LoggingDolbyEncoderProg1DescTxtpt2
				RollCallString,
			iqdbe00LoggingDolbyEncoderLogProg2DescTxt
				INTEGER,
			iqdbe00LoggingDolbyEncoderProg2DescTxt
				RollCallString,
			iqdbe00LoggingDolbyEncoderProg2DescTxtpt2
				RollCallString,
			iqdbe00LoggingDolbyEncoderLogProg3DescTxt
				INTEGER,
			iqdbe00LoggingDolbyEncoderProg3DescTxt
				RollCallString,
			iqdbe00LoggingDolbyEncoderProg3DescTxtpt2
				RollCallString,
			iqdbe00LoggingDolbyEncoderLogProg4DescTxt
				INTEGER,
			iqdbe00LoggingDolbyEncoderProg4DescTxt
				RollCallString,
			iqdbe00LoggingDolbyEncoderProg4DescTxtpt2
				RollCallString,
			iqdbe00LoggingDolbyEncoderLogProg5DescTxt
				INTEGER,
			iqdbe00LoggingDolbyEncoderProg5DescTxt
				RollCallString,
			iqdbe00LoggingDolbyEncoderProg5DescTxtpt2
				RollCallString,
			iqdbe00LoggingDolbyEncoderLogProg6DescTxt
				INTEGER,
			iqdbe00LoggingDolbyEncoderProg6DescTxt
				RollCallString,
			iqdbe00LoggingDolbyEncoderProg6DescTxtpt2
				RollCallString,
			iqdbe00LoggingDolbyEncoderLogProg7DescTxt
				INTEGER,
			iqdbe00LoggingDolbyEncoderProg7DescTxt
				RollCallString,
			iqdbe00LoggingDolbyEncoderProg7DescTxtpt2
				RollCallString,
			iqdbe00LoggingDolbyEncoderLogProg8DescTxt
				INTEGER,
			iqdbe00LoggingDolbyEncoderLogProg8DescTxt
				RollCallString,
			iqdbe00LoggingDolbyEncoderProg8DescTxtpt2
				RollCallString,
			iqdbe00LoggingMiscLoggingLogSerialNo
				INTEGER,
			iqdbe00LoggingMiscLoggingSerialNo
				RollCallString,
			iqdbe00LoggingMiscLoggingLogOSVersion
				INTEGER,
			iqdbe00LoggingMiscLoggingOSVersion
				RollCallString,
			iqdbe00LoggingMiscLoggingLogBuildNo
				INTEGER,
			iqdbe00LoggingMiscLoggingBuildNo
				RollCallString,
			iqdbe00LoggingMiscLoggingLogHardwareVer
				INTEGER,
			iqdbe00LoggingMiscLoggingHardwareVer
				RollCallString,
			iqdbe00LoggingMiscLoggingLogFirmwareVer
				INTEGER,
			iqdbe00LoggingMiscLoggingFirmwareVer
				RollCallString,
			iqdbe00LoggingMiscLoggingLogUpTime
				INTEGER,
			iqdbe00LoggingMiscLoggingUpTime
				RollCallString,
			iqdbe00RollCallRollTrackDisableAll
				INTEGER,
			iqdbe00RollCallRollTrackIndex
				INTEGER,
			iqdbe00RollCallRollTrackSource
				INTEGER,
			iqdbe00RollCallRollTrackAddress
				RollCallString,
			iqdbe00RollCallRollTrackCommand
				RollCallString,
			iqdbe00RollCallRollTrackStatus
				RollCallString,
			iqdbe00RollCallRollTrackSending
				RollCallString,
			iqdbe00AudioSetupUnitStatusDisplay
				INTEGER,
			iqdbe00AudioSetupProduct
				RollCallString,
			iqdbe00AudioSetupRelease
				RollCallString,
			iqdbe00AudioSetupBuild
				RollCallString,
			iqdbe00AudioSetupKOS
				RollCallString,
			iqdbe00AudioSetupSerialNo
				RollCallString,
			iqdbe00AudioSetupFirmware
				RollCallString,
			iqdbe00AudioSetupPCB
				RollCallString,
			iqdbe00AudioSetupFactoryDefault
				INTEGER,
			iqdbe00AudioSetupRestart
				INTEGER,
			iqdbe00AudioSetupDefaultSettings
				INTEGER,
			iqdbe00AudioSetupSerialNumber
				RollCallString,
			iqdbe00AudioSetupBoardID
				INTEGER,
			iqdbe00AudioSetupSaveID
				INTEGER,
			iqdbe00AudioEngineerEngineerPassword
				RollCallString,
			iqdbe00AudioEngineerShowEngineer
				INTEGER,
			iqdbe00EngineerPageOptions1
				INTEGER,
			iqdbe00EngineerPageOptions2
				INTEGER,
			iqdbe00EngineerPageOptions3
				INTEGER,
			iqdbe00EngineerEngineerPageUndoChanges
				INTEGER,
			iqdbe00EngineerEngineerPageLineNumber
				RollCallString,
			iqdbe00EngineerEngineerPageSampleNumber
				RollCallString,
			iqdbe00EngineerEngineerPageDolbyModuleUpdate
				INTEGER,
			iqdbe00EngineerPaAutoalignEmbeddedInputs
				INTEGER,
			iqdbe00EngineerPaAutoalignAESInputs
				INTEGER,
			iqdbe00MenuAudioShowEngineer2
				INTEGER,
			iqdbe00MenuAudioUseEmbDelayFbac
				INTEGER
		}

	iqdbe00SlotIndex OBJECT-TYPE
		SYNTAX		Unsigned32
		MAX-ACCESS		not-accessible
		STATUS			current
		DESCRIPTION
				"The unique Index value for each slot.  Its value
					ranges between 1 and the value of slotNumber."
		::= { iqdbe00CmdEntry 0 }


	iqdbe00MenuInputIPLoss OBJECT-TYPE
		SYNTAX		INTEGER {
							val_No_Input(0),
							val_In_Out_Std_Mismatch(1)
							}
		MAX-ACCESS		read-write
		STATUS			current
		DESCRIPTION
				"TYPE: - RadiobuttonList
				 PAGE: - Input
					I/P Loss  cmdID= 33030
					No Input  value= 0
					In/Out Std.Mismatch  value= 1  "
		::= { iqdbe00CmdEntry 33030 }


	iqdbe00InputValidStdsAllValid OBJECT-TYPE
		SYNTAX		INTEGER { noAction(0),val_All_Valid(1) }
		MAX-ACCESS		read-write
		STATUS			current
		DESCRIPTION
				"TYPE: - Button
				 PAGE: - Input
					All Valid  cmdID= 32900  value= 1  "
		::= { iqdbe00CmdEntry 32900 }


	iqdbe00InputValidStdsAllInvalid OBJECT-TYPE
		SYNTAX		INTEGER { noAction(0),val_All_Invalid(1) }
		MAX-ACCESS		read-write
		STATUS			current
		DESCRIPTION
				"TYPE: - Button
				 PAGE: - Input
					All Invalid  cmdID= 32901  value= 1  "
		::= { iqdbe00CmdEntry 32901 }


	iqdbe00InputValidStds108023sF OBJECT-TYPE
		SYNTAX		INTEGER { disable(0), enable(1) }
		MAX-ACCESS		read-write
		STATUS			current
		DESCRIPTION
				"TYPE: - Checkbox
				 PAGE: - Input
					1080/23sF  cmdID= 32916 "
		::= { iqdbe00CmdEntry 32916 }


	iqdbe00InputValidStds108023p OBJECT-TYPE
		SYNTAX		INTEGER { disable(0), enable(1) }
		MAX-ACCESS		read-write
		STATUS			current
		DESCRIPTION
				"TYPE: - Checkbox
				 PAGE: - Input
					1080/23p  cmdID= 32915 "
		::= { iqdbe00CmdEntry 32915 }


	iqdbe00InputValidStds108024sF OBJECT-TYPE
		SYNTAX		INTEGER { disable(0), enable(1) }
		MAX-ACCESS		read-write
		STATUS			current
		DESCRIPTION
				"TYPE: - Checkbox
				 PAGE: - Input
					1080/24sF  cmdID= 32917 "
		::= { iqdbe00CmdEntry 32917 }


	iqdbe00InputValidStds108024p OBJECT-TYPE
		SYNTAX		INTEGER { disable(0), enable(1) }
		MAX-ACCESS		read-write
		STATUS			current
		DESCRIPTION
				"TYPE: - Checkbox
				 PAGE: - Input
					1080/24p  cmdID= 32914 "
		::= { iqdbe00CmdEntry 32914 }


	iqdbe00InputValidStds108025i OBJECT-TYPE
		SYNTAX		INTEGER { disable(0), enable(1) }
		MAX-ACCESS		read-write
		STATUS			current
		DESCRIPTION
				"TYPE: - Checkbox
				 PAGE: - Input
					1080/25i  cmdID= 32910 "
		::= { iqdbe00CmdEntry 32910 }


	iqdbe00InputValidStds108025p OBJECT-TYPE
		SYNTAX		INTEGER { disable(0), enable(1) }
		MAX-ACCESS		read-write
		STATUS			current
		DESCRIPTION
				"TYPE: - Checkbox
				 PAGE: - Input
					1080/25p  cmdID= 32911 "
		::= { iqdbe00CmdEntry 32911 }


	iqdbe00InputValidStds103529i OBJECT-TYPE
		SYNTAX		INTEGER { disable(0), enable(1) }
		MAX-ACCESS		read-write
		STATUS			current
		DESCRIPTION
				"TYPE: - Checkbox
				 PAGE: - Input
					1035/29i  cmdID= 32921 "
		::= { iqdbe00CmdEntry 32921 }


	iqdbe00InputValidStds108029i OBJECT-TYPE
		SYNTAX		INTEGER { disable(0), enable(1) }
		MAX-ACCESS		read-write
		STATUS			current
		DESCRIPTION
				"TYPE: - Checkbox
				 PAGE: - Input
					1080/29i  cmdID= 32919 "
		::= { iqdbe00CmdEntry 32919 }


	iqdbe00InputValidStds108029p OBJECT-TYPE
		SYNTAX		INTEGER { disable(0), enable(1) }
		MAX-ACCESS		read-write
		STATUS			current
		DESCRIPTION
				"TYPE: - Checkbox
				 PAGE: - Input
					1080/29p  cmdID= 32918 "
		::= { iqdbe00CmdEntry 32918 }


	iqdbe00InputValidStds103530i OBJECT-TYPE
		SYNTAX		INTEGER { disable(0), enable(1) }
		MAX-ACCESS		read-write
		STATUS			current
		DESCRIPTION
				"TYPE: - Checkbox
				 PAGE: - Input
					1035/30i  cmdID= 32920 "
		::= { iqdbe00CmdEntry 32920 }


	iqdbe00InputValidStds108030i OBJECT-TYPE
		SYNTAX		INTEGER { disable(0), enable(1) }
		MAX-ACCESS		read-write
		STATUS			current
		DESCRIPTION
				"TYPE: - Checkbox
				 PAGE: - Input
					1080/30i  cmdID= 32912 "
		::= { iqdbe00CmdEntry 32912 }


	iqdbe00InputValidStds108030p OBJECT-TYPE
		SYNTAX		INTEGER { disable(0), enable(1) }
		MAX-ACCESS		read-write
		STATUS			current
		DESCRIPTION
				"TYPE: - Checkbox
				 PAGE: - Input
					1080/30p  cmdID= 32913 "
		::= { iqdbe00CmdEntry 32913 }


	iqdbe00InputValidStds72050p OBJECT-TYPE
		SYNTAX		INTEGER { disable(0), enable(1) }
		MAX-ACCESS		read-write
		STATUS			current
		DESCRIPTION
				"TYPE: - Checkbox
				 PAGE: - Input
					720/50p  cmdID= 32922 "
		::= { iqdbe00CmdEntry 32922 }


	iqdbe00InputValidStds72059p OBJECT-TYPE
		SYNTAX		INTEGER { disable(0), enable(1) }
		MAX-ACCESS		read-write
		STATUS			current
		DESCRIPTION
				"TYPE: - Checkbox
				 PAGE: - Input
					720/59p  cmdID= 32924 "
		::= { iqdbe00CmdEntry 32924 }


	iqdbe00InputValidStds72060p OBJECT-TYPE
		SYNTAX		INTEGER { disable(0), enable(1) }
		MAX-ACCESS		read-write
		STATUS			current
		DESCRIPTION
				"TYPE: - Checkbox
				 PAGE: - Input
					720/60p  cmdID= 32923 "
		::= { iqdbe00CmdEntry 32923 }


	iqdbe00InputValidStds62525i OBJECT-TYPE
		SYNTAX		INTEGER { disable(0), enable(1) }
		MAX-ACCESS		read-write
		STATUS			current
		DESCRIPTION
				"TYPE: - Checkbox
				 PAGE: - Input
					625/25i  cmdID= 32925 "
		::= { iqdbe00CmdEntry 32925 }


	iqdbe00InputValidStds52529i OBJECT-TYPE
		SYNTAX		INTEGER { disable(0), enable(1) }
		MAX-ACCESS		read-write
		STATUS			current
		DESCRIPTION
				"TYPE: - Checkbox
				 PAGE: - Input
					525/29i  cmdID= 32926 "
		::= { iqdbe00CmdEntry 32926 }


	iqdbe00InputErrorsCRCErrs OBJECT-TYPE
		SYNTAX		RollCallString
		MAX-ACCESS		read-only
		STATUS			current
		DESCRIPTION
				"TYPE: - Display
				 PAGE: - Input
					CRC Errs  cmdID= 33050  format=   "
		::= { iqdbe00CmdEntry 33050 }


	iqdbe00InputErrorsCRCErrSec OBJECT-TYPE
		SYNTAX		RollCallString
		MAX-ACCESS		read-only
		STATUS			current
		DESCRIPTION
				"TYPE: - Display
				 PAGE: - Input
					CRC ErrSec  cmdID= 33051  format=   "
		::= { iqdbe00CmdEntry 33051 }


	iqdbe00InputErrorsANCErrs OBJECT-TYPE
		SYNTAX		RollCallString
		MAX-ACCESS		read-only
		STATUS			current
		DESCRIPTION
				"TYPE: - Display
				 PAGE: - Input
					ANC Errs  cmdID= 33053  format=   "
		::= { iqdbe00CmdEntry 33053 }


	iqdbe00InputErrorsANCErrSec OBJECT-TYPE
		SYNTAX		RollCallString
		MAX-ACCESS		read-only
		STATUS			current
		DESCRIPTION
				"TYPE: - Display
				 PAGE: - Input
					ANC ErrSec  cmdID= 33054  format=   "
		::= { iqdbe00CmdEntry 33054 }


	iqdbe00InputErrorsResetSec OBJECT-TYPE
		SYNTAX		RollCallString
		MAX-ACCESS		read-only
		STATUS			current
		DESCRIPTION
				"TYPE: - Display
				 PAGE: - Input
					ResetSec  cmdID= 33055  format=   "
		::= { iqdbe00CmdEntry 33055 }


	iqdbe00InputErrorsErrorReset OBJECT-TYPE
		SYNTAX		INTEGER { noAction(0),val_Error_Reset(1) }
		MAX-ACCESS		read-write
		STATUS			current
		DESCRIPTION
				"TYPE: - Button
				 PAGE: - Input
					Error Reset  cmdID= 33052  value= 1  "
		::= { iqdbe00CmdEntry 33052 }


	iqdbe00AudioOutputOutputStandard OBJECT-TYPE
		SYNTAX		INTEGER {
							val_Manual(0),
							val_Follows_Input(1)
							}
		MAX-ACCESS		read-write
		STATUS			current
		DESCRIPTION
				"TYPE: - RadiobuttonList
					Output Standard  cmdID= 33011
					Manual  value= 0
					Follows Input  value= 1  "
		::= { iqdbe00CmdEntry 33011 }


	iqdbe00AudioOutputSelectStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Select Standard  cmdID= 33010
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe00CmdEntry 33010 }


	iqdbe00OutputVideoProcAmpsMasterGain OBJECT-TYPE
		SYNTAX		INTEGER
		MAX-ACCESS		read-write
		STATUS			current
		DESCRIPTION
				"TYPE: - Number
					Master Gain  cmdID= 33000  min= -600  max= 600  step= 10  format= %0.1f dB  div_scale= 100
					Min = -6.0 dB  Max = 6.0 dB  Step = 0.1 dB "
		::= { iqdbe00CmdEntry 33000 }


	iqdbe00OutputVideoProcAmpsYGain OBJECT-TYPE
		SYNTAX		INTEGER
		MAX-ACCESS		read-write
		STATUS			current
		DESCRIPTION
				"TYPE: - Number
					Y Gain  cmdID= 33001  min= -600  max= 600  step= 10  format= %0.1f dB  div_scale= 100
					Min = -6.0 dB  Max = 6.0 dB  Step = 0.1 dB "
		::= { iqdbe00CmdEntry 33001 }


	iqdbe00OutputVideoProcAmpsCGain OBJECT-TYPE
		SYNTAX		INTEGER
		MAX-ACCESS		read-write
		STATUS			current
		DESCRIPTION
				"TYPE: - Number
					C Gain  cmdID= 33003  min= -600  max= 600  step= 10  format= %0.1f dB  div_scale= 100
					Min = -6.0 dB  Max = 6.0 dB  Step = 0.1 dB "
		::= { iqdbe00CmdEntry 33003 }


	iqdbe00OutputVideoProcAmpsBlackLevel OBJECT-TYPE
		SYNTAX		INTEGER
		MAX-ACCESS		read-write
		STATUS			current
		DESCRIPTION
				"TYPE: - Number
					Black Level  cmdID= 33002  min= -200  max= 200  step= 1  format= %0.0f mV  div_scale= 1
					Min = -200 mV  Max = 200 mV  Step = 1 mV "
		::= { iqdbe00CmdEntry 33002 }


	iqdbe00AudioOutputDefaultOutput OBJECT-TYPE
		SYNTAX		INTEGER {
							val_Freeze_Frame(1),
							val_Freeze_Field(5),
							val_Black(2),
							val_Input(3),
							val_Out_Pattern(4)
							}
		MAX-ACCESS		read-write
		STATUS			current
		DESCRIPTION
				"TYPE: - RadiobuttonList
					Default Output  cmdID= 33031
					Freeze Frame  value= 1
					Freeze Field  value= 5
					Black  value= 2
					Input  value= 3
					Out Pattern  value= 4  "
		::= { iqdbe00CmdEntry 33031 }


	iqdbe00AudioOutputDefaultOPStd OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Default O/P Std.  cmdID= 33012
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe00CmdEntry 33012 }


	iqdbe00AudioDelayASourcesManual OBJECT-TYPE
		SYNTAX		INTEGER { disable(0), enable(1) }
		MAX-ACCESS		read-write
		STATUS			current
		DESCRIPTION
				"TYPE: - Checkbox
				 PAGE: - Aud.Delays
					Manual  cmdID= 38041 "
		::= { iqdbe00CmdEntry 38041 }


	iqdbe00AudioDelayASourcesGPIPWM OBJECT-TYPE
		SYNTAX		INTEGER { disable(0), enable(1) }
		MAX-ACCESS		read-write
		STATUS			current
		DESCRIPTION
				"TYPE: - Checkbox
				 PAGE: - Aud.Delays
					GPI PWM  cmdID= 38042 "
		::= { iqdbe00CmdEntry 38042 }


	iqdbe00AudioDelayASourcesRollTrack14 OBJECT-TYPE
		SYNTAX		INTEGER { disable(0), enable(1) }
		MAX-ACCESS		read-write
		STATUS			current
		DESCRIPTION
				"TYPE: - Checkbox
				 PAGE: - Aud.Delays
					RollTrack14  cmdID= 38044 "
		::= { iqdbe00CmdEntry 38044 }


	iqdbe00AudioDelayASourcesRollTrack15 OBJECT-TYPE
		SYNTAX		INTEGER { disable(0), enable(1) }
		MAX-ACCESS		read-write
		STATUS			current
		DESCRIPTION
				"TYPE: - Checkbox
				 PAGE: - Aud.Delays
					RollTrack15  cmdID= 38045 "
		::= { iqdbe00CmdEntry 38045 }


	iqdbe00AudioDelayASourcesRollTrack16 OBJECT-TYPE
		SYNTAX		INTEGER { disable(0), enable(1) }
		MAX-ACCESS		read-write
		STATUS			current
		DESCRIPTION
				"TYPE: - Checkbox
				 PAGE: - Aud.Delays
					RollTrack16  cmdID= 38046 "
		::= { iqdbe00CmdEntry 38046 }


	iqdbe00AudioDelayASourcesRollTrack17 OBJECT-TYPE
		SYNTAX		INTEGER { disable(0), enable(1) }
		MAX-ACCESS		read-write
		STATUS			current
		DESCRIPTION
				"TYPE: - Checkbox
				 PAGE: - Aud.Delays
					RollTrack17  cmdID= 38047 "
		::= { iqdbe00CmdEntry 38047 }


	iqdbe00AudDelaysAudioDelayAAdjustCoarseDelay OBJECT-TYPE
		SYNTAX		INTEGER
		MAX-ACCESS		read-write
		STATUS			current
		DESCRIPTION
				"TYPE: - Number
				 PAGE: - Aud.Delays
					Adjust Coarse Delay  cmdID= 38043  min= -4000  max= 200000  step= 25  format= %0.2f ms  div_scale= 100
					Min = -40.00 ms  Max = 2000.00 ms  Step = 0.25 ms "
		::= { iqdbe00CmdEntry 38043 }


	iqdbe00AudDelaysAudioDelayACurrentAudioDelay OBJECT-TYPE
		SYNTAX		RollCallString
		MAX-ACCESS		read-only
		STATUS			current
		DESCRIPTION
				"TYPE: - Display
				 PAGE: - Aud.Delays
					Current Audio Delay  cmdID= 38048  format=   "
		::= { iqdbe00CmdEntry 38048 }


	iqdbe00AudioDelayBSourcesManual OBJECT-TYPE
		SYNTAX		INTEGER { disable(0), enable(1) }
		MAX-ACCESS		read-write
		STATUS			current
		DESCRIPTION
				"TYPE: - Checkbox
				 PAGE: - Aud.Delays
					Manual  cmdID= 38061 "
		::= { iqdbe00CmdEntry 38061 }


	iqdbe00AudioDelayBSourcesGPIPWM OBJECT-TYPE
		SYNTAX		INTEGER { disable(0), enable(1) }
		MAX-ACCESS		read-write
		STATUS			current
		DESCRIPTION
				"TYPE: - Checkbox
				 PAGE: - Aud.Delays
					GPI PWM  cmdID= 38062 "
		::= { iqdbe00CmdEntry 38062 }


	iqdbe00AudioDelayBSourcesRollTrack14 OBJECT-TYPE
		SYNTAX		INTEGER { disable(0), enable(1) }
		MAX-ACCESS		read-write
		STATUS			current
		DESCRIPTION
				"TYPE: - Checkbox
				 PAGE: - Aud.Delays
					RollTrack14  cmdID= 38064 "
		::= { iqdbe00CmdEntry 38064 }


	iqdbe00AudioDelayBSourcesRollTrack15 OBJECT-TYPE
		SYNTAX		INTEGER { disable(0), enable(1) }
		MAX-ACCESS		read-write
		STATUS			current
		DESCRIPTION
				"TYPE: - Checkbox
				 PAGE: - Aud.Delays
					RollTrack15  cmdID= 38065 "
		::= { iqdbe00CmdEntry 38065 }


	iqdbe00AudioDelayBSourcesRollTrack16 OBJECT-TYPE
		SYNTAX		INTEGER { disable(0), enable(1) }
		MAX-ACCESS		read-write
		STATUS			current
		DESCRIPTION
				"TYPE: - Checkbox
				 PAGE: - Aud.Delays
					RollTrack16  cmdID= 38066 "
		::= { iqdbe00CmdEntry 38066 }


	iqdbe00AudioDelayBSourcesRollTrack17 OBJECT-TYPE
		SYNTAX		INTEGER { disable(0), enable(1) }
		MAX-ACCESS		read-write
		STATUS			current
		DESCRIPTION
				"TYPE: - Checkbox
				 PAGE: - Aud.Delays
					RollTrack17  cmdID= 38067 "
		::= { iqdbe00CmdEntry 38067 }


	iqdbe00AudDelaysAudioDelayBAdjustCoarseDelay OBJECT-TYPE
		SYNTAX		INTEGER
		MAX-ACCESS		read-write
		STATUS			current
		DESCRIPTION
				"TYPE: - Number
				 PAGE: - Aud.Delays
					Adjust Coarse Delay  cmdID= 38063  min= -4000  max= 200000  step= 25  format= %0.2f ms  div_scale= 100
					Min = -40.00 ms  Max = 2000.00 ms  Step = 0.25 ms "
		::= { iqdbe00CmdEntry 38063 }


	iqdbe00AudDelaysAudioDelayBCurrentAudioDelay OBJECT-TYPE
		SYNTAX		RollCallString
		MAX-ACCESS		read-only
		STATUS			current
		DESCRIPTION
				"TYPE: - Display
				 PAGE: - Aud.Delays
					Current Audio Delay  cmdID= 38068  format=   "
		::= { iqdbe00CmdEntry 38068 }


	iqdbe00AudDelaysAESDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-1  cmdID= 38600
					Min  value= 0
					Delay A  value= 1
					Delay B  value= 2  "
		::= { iqdbe00CmdEntry 38600 }


	iqdbe00AudDelaysAESDelaySelectInternal1 OBJECT-TYPE
		SYNTAX		INTEGER { disable(0), enable(1) }
		MAX-ACCESS		read-write
		STATUS			current
		DESCRIPTION
				"TYPE: - Checkbox
				 PAGE: - Aud.Delays
					Internal-1  cmdID= 38620 "
		::= { iqdbe00CmdEntry 38620 }


	iqdbe00AudDelaysAESDelaySelectAutoDolbyEPhase1 OBJECT-TYPE
		SYNTAX		INTEGER { disable(0), enable(1) }
		MAX-ACCESS		read-write
		STATUS			current
		DESCRIPTION
				"TYPE: - Checkbox
				 PAGE: - Aud.Delays
					Auto Dolby-E Phase  cmdID= 38118 "
		::= { iqdbe00CmdEntry 38118 }


	iqdbe00AudDelaysAESDelaySelectDelayLimit1 OBJECT-TYPE
		SYNTAX		RollCallString
		MAX-ACCESS		read-only
		STATUS			current
		DESCRIPTION
				"TYPE: - Display
				 PAGE: - Aud.Delays
					Delay Limit  cmdID= 38300  format=   "
		::= { iqdbe00CmdEntry 38300 }


	iqdbe00AudDelaysAESDelaySelectAES1FineDelay OBJECT-TYPE
		SYNTAX		INTEGER
		MAX-ACCESS		read-write
		STATUS			current
		DESCRIPTION
				"TYPE: - Number
				 PAGE: - Aud.Delays
					AES 1 Fine Delay  cmdID= 38130  min= -2450  max= 2450  step= 52  format= %0.3f ms  div_scale= 10000
					Min = -0.245 ms  Max = 0.245 ms  Step = 0.005 ms "
		::= { iqdbe00CmdEntry 38130 }


	iqdbe00AudDelaysAESDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-2  cmdID= 38601
					Min  value= 0
					Delay A  value= 1
					Delay B  value= 2  "
		::= { iqdbe00CmdEntry 38601 }


	iqdbe00AudDelaysAESDelaySelectInternal2 OBJECT-TYPE
		SYNTAX		INTEGER { disable(0), enable(1) }
		MAX-ACCESS		read-write
		STATUS			current
		DESCRIPTION
				"TYPE: - Checkbox
				 PAGE: - Aud.Delays
					Internal-2  cmdID= 38621 "
		::= { iqdbe00CmdEntry 38621 }


	iqdbe00AudDelaysAESDelaySelectAutoDolbyEPhase2 OBJECT-TYPE
		SYNTAX		INTEGER { disable(0), enable(1) }
		MAX-ACCESS		read-write
		STATUS			current
		DESCRIPTION
				"TYPE: - Checkbox
				 PAGE: - Aud.Delays
					Auto Dolby-E Phase  cmdID= 38119 "
		::= { iqdbe00CmdEntry 38119 }


	iqdbe00AudDelaysAESDelaySelectDelayLimit2 OBJECT-TYPE
		SYNTAX		RollCallString
		MAX-ACCESS		read-only
		STATUS			current
		DESCRIPTION
				"TYPE: - Display
				 PAGE: - Aud.Delays
					Delay Limit  cmdID= 38301  format=   "
		::= { iqdbe00CmdEntry 38301 }


	iqdbe00AudDelaysAESDelaySelectAES2FineDelay OBJECT-TYPE
		SYNTAX		INTEGER
		MAX-ACCESS		read-write
		STATUS			current
		DESCRIPTION
				"TYPE: - Number
				 PAGE: - Aud.Delays
					AES 2 Fine Delay  cmdID= 38131  min= -2450  max= 2450  step= 52  format= %0.3f ms  div_scale= 10000
					Min = -0.245 ms  Max = 0.245 ms  Step = 0.005 ms "
		::= { iqdbe00CmdEntry 38131 }


	iqdbe00AudDelaysAESDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-3  cmdID= 38602
					Min  value= 0
					Delay A  value= 1
					Delay B  value= 2  "
		::= { iqdbe00CmdEntry 38602 }


	iqdbe00AudDelaysAESDelaySelectInternal3 OBJECT-TYPE
		SYNTAX		INTEGER { disable(0), enable(1) }
		MAX-ACCESS		read-write
		STATUS			current
		DESCRIPTION
				"TYPE: - Checkbox
				 PAGE: - Aud.Delays
					Internal-3  cmdID= 38622 "
		::= { iqdbe00CmdEntry 38622 }


	iqdbe00AudDelaysAESDelaySelectAutoDolbyEPhase3 OBJECT-TYPE
		SYNTAX		INTEGER { disable(0), enable(1) }
		MAX-ACCESS		read-write
		STATUS			current
		DESCRIPTION
				"TYPE: - Checkbox
				 PAGE: - Aud.Delays
					Auto Dolby-E Phase  cmdID= 38120 "
		::= { iqdbe00CmdEntry 38120 }


	iqdbe00AudDelaysAESDelaySelectDelayLimit3 OBJECT-TYPE
		SYNTAX		RollCallString
		MAX-ACCESS		read-only
		STATUS			current
		DESCRIPTION
				"TYPE: - Display
				 PAGE: - Aud.Delays
					Delay Limit  cmdID= 38302  format=   "
		::= { iqdbe00CmdEntry 38302 }


	iqdbe00AudDelaysAESDelaySelectAES3FineDelay OBJECT-TYPE
		SYNTAX		INTEGER
		MAX-ACCESS		read-write
		STATUS			current
		DESCRIPTION
				"TYPE: - Number
				 PAGE: - Aud.Delays
					AES 3 Fine Delay  cmdID= 38132  min= -2450  max= 2450  step= 52  format= %0.3f ms  div_scale= 10000
					Min = -0.245 ms  Max = 0.245 ms  Step = 0.005 ms "
		::= { iqdbe00CmdEntry 38132 }


	iqdbe00AudDelaysAESDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-4  cmdID= 38603
					Min  value= 0
					Delay A  value= 1
					Delay B  value= 2  "
		::= { iqdbe00CmdEntry 38603 }


	iqdbe00AudDelaysAESDelaySelectInternal4 OBJECT-TYPE
		SYNTAX		INTEGER { disable(0), enable(1) }
		MAX-ACCESS		read-write
		STATUS			current
		DESCRIPTION
				"TYPE: - Checkbox
				 PAGE: - Aud.Delays
					Internal-4  cmdID= 38623 "
		::= { iqdbe00CmdEntry 38623 }


	iqdbe00AudDelaysAESDelaySelectAutoDolbyEPhase4 OBJECT-TYPE
		SYNTAX		INTEGER { disable(0), enable(1) }
		MAX-ACCESS		read-write
		STATUS			current
		DESCRIPTION
				"TYPE: - Checkbox
				 PAGE: - Aud.Delays
					Auto Dolby-E Phase  cmdID= 38121 "
		::= { iqdbe00CmdEntry 38121 }


	iqdbe00AudDelaysAESDelaySelectDelayLimit4 OBJECT-TYPE
		SYNTAX		RollCallString
		MAX-ACCESS		read-only
		STATUS			current
		DESCRIPTION
				"TYPE: - Display
				 PAGE: - Aud.Delays
					Delay Limit  cmdID= 38303  format=   "
		::= { iqdbe00CmdEntry 38303 }


	iqdbe00AudDelaysAESDelaySelectAES4FineDelay OBJECT-TYPE
		SYNTAX		INTEGER
		MAX-ACCESS		read-write
		STATUS			current
		DESCRIPTION
				"TYPE: - Number
				 PAGE: - Aud.Delays
					AES 4 Fine Delay  cmdID= 38133  min= -2450  max= 2450  step= 52  format= %0.3f ms  div_scale= 10000
					Min = -0.245 ms  Max = 0.245 ms  Step = 0.005 ms "
		::= { iqdbe00CmdEntry 38133 }


	iqdbe00AudDelaysAESDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-5  cmdID= 38604
					Min  value= 0
					Delay A  value= 1
					Delay B  value= 2  "
		::= { iqdbe00CmdEntry 38604 }


	iqdbe00AudDelaysAESDelaySelectInternal5 OBJECT-TYPE
		SYNTAX		INTEGER { disable(0), enable(1) }
		MAX-ACCESS		read-write
		STATUS			current
		DESCRIPTION
				"TYPE: - Checkbox
				 PAGE: - Aud.Delays
					Internal-5  cmdID= 38624 "
		::= { iqdbe00CmdEntry 38624 }


	iqdbe00AudDelaysAESDelaySelectAutoDolbyEPhase5 OBJECT-TYPE
		SYNTAX		INTEGER { disable(0), enable(1) }
		MAX-ACCESS		read-write
		STATUS			current
		DESCRIPTION
				"TYPE: - Checkbox
				 PAGE: - Aud.Delays
					Auto Dolby-E Phase  cmdID= 38122 "
		::= { iqdbe00CmdEntry 38122 }


	iqdbe00AudDelaysAESDelaySelectDelayLimit5 OBJECT-TYPE
		SYNTAX		RollCallString
		MAX-ACCESS		read-only
		STATUS			current
		DESCRIPTION
				"TYPE: - Display
				 PAGE: - Aud.Delays
					Delay Limit  cmdID= 38304  format=   "
		::= { iqdbe00CmdEntry 38304 }


	iqdbe00AudDelaysAESDelaySelectAES5FineDelay OBJECT-TYPE
		SYNTAX		INTEGER
		MAX-ACCESS		read-write
		STATUS			current
		DESCRIPTION
				"TYPE: - Number
				 PAGE: - Aud.Delays
					AES 5 Fine Delay  cmdID= 38134  min= -2450  max= 2450  step= 52  format= %0.3f ms  div_scale= 10000
					Min = -0.245 ms  Max = 0.245 ms  Step = 0.005 ms "
		::= { iqdbe00CmdEntry 38134 }


	iqdbe00AudDelaysAESDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-6  cmdID= 38605
					Min  value= 0
					Delay A  value= 1
					Delay B  value= 2  "
		::= { iqdbe00CmdEntry 38605 }


	iqdbe00AudDelaysAESDelaySelectInternal6 OBJECT-TYPE
		SYNTAX		INTEGER { disable(0), enable(1) }
		MAX-ACCESS		read-write
		STATUS			current
		DESCRIPTION
				"TYPE: - Checkbox
				 PAGE: - Aud.Delays
					Internal-6  cmdID= 38625 "
		::= { iqdbe00CmdEntry 38625 }


	iqdbe00AudDelaysAESDelaySelectAutoDolbyEPhase6 OBJECT-TYPE
		SYNTAX		INTEGER { disable(0), enable(1) }
		MAX-ACCESS		read-write
		STATUS			current
		DESCRIPTION
				"TYPE: - Checkbox
				 PAGE: - Aud.Delays
					Auto Dolby-E Phase  cmdID= 38123 "
		::= { iqdbe00CmdEntry 38123 }


	iqdbe00AudDelaysAESDelaySelectDelayLimit6 OBJECT-TYPE
		SYNTAX		RollCallString
		MAX-ACCESS		read-only
		STATUS			current
		DESCRIPTION
				"TYPE: - Display
				 PAGE: - Aud.Delays
					Delay Limit  cmdID= 38305  format=   "
		::= { iqdbe00CmdEntry 38305 }


	iqdbe00AudDelaysAESDelaySelectAES6FineDelay OBJECT-TYPE
		SYNTAX		INTEGER
		MAX-ACCESS		read-write
		STATUS			current
		DESCRIPTION
				"TYPE: - Number
				 PAGE: - Aud.Delays
					AES 6 Fine Delay  cmdID= 38135  min= -2450  max= 2450  step= 52  format= %0.3f ms  div_scale= 10000
					Min = -0.245 ms  Max = 0.245 ms  Step = 0.005 ms "
		::= { iqdbe00CmdEntry 38135 }


	iqdbe00AudDelaysAESDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-7  cmdID= 38606
					Min  value= 0
					Delay A  value= 1
					Delay B  value= 2  "
		::= { iqdbe00CmdEntry 38606 }


	iqdbe00AudDelaysAESDelaySelectInternal7 OBJECT-TYPE
		SYNTAX		INTEGER { disable(0), enable(1) }
		MAX-ACCESS		read-write
		STATUS			current
		DESCRIPTION
				"TYPE: - Checkbox
				 PAGE: - Aud.Delays
					Internal-7  cmdID= 38626 "
		::= { iqdbe00CmdEntry 38626 }


	iqdbe00AudDelaysAESDelaySelectAutoDolbyEPhase7 OBJECT-TYPE
		SYNTAX		INTEGER { disable(0), enable(1) }
		MAX-ACCESS		read-write
		STATUS			current
		DESCRIPTION
				"TYPE: - Checkbox
				 PAGE: - Aud.Delays
					Auto Dolby-E Phase  cmdID= 38124 "
		::= { iqdbe00CmdEntry 38124 }


	iqdbe00AudDelaysAESDelaySelectDelayLimit7 OBJECT-TYPE
		SYNTAX		RollCallString
		MAX-ACCESS		read-only
		STATUS			current
		DESCRIPTION
				"TYPE: - Display
				 PAGE: - Aud.Delays
					Delay Limit  cmdID= 38306  format=   "
		::= { iqdbe00CmdEntry 38306 }


	iqdbe00AudDelaysAESDelaySelectAES7FineDelay OBJECT-TYPE
		SYNTAX		INTEGER
		MAX-ACCESS		read-write
		STATUS			current
		DESCRIPTION
				"TYPE: - Number
				 PAGE: - Aud.Delays
					AES 7 Fine Delay  cmdID= 38136  min= -2450  max= 2450  step= 52  format= %0.3f ms  div_scale= 10000
					Min = -0.245 ms  Max = 0.245 ms  Step = 0.005 ms "
		::= { iqdbe00CmdEntry 38136 }


	iqdbe00AudDelaysAESDelaySelectDolbyEncoder OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Dolby Encoder  cmdID= 38607
					Min  value= 0
					Delay A  value= 1
					Delay B  value= 2  "
		::= { iqdbe00CmdEntry 38607 }


	iqdbe00AudDelaysAESDelaySelectInternal OBJECT-TYPE
		SYNTAX		INTEGER { disable(0), enable(1) }
		MAX-ACCESS		read-write
		STATUS			current
		DESCRIPTION
				"TYPE: - Checkbox
				 PAGE: - Aud.Delays
					Internal  cmdID= 38627 "
		::= { iqdbe00CmdEntry 38627 }


	iqdbe00AudDelaysAESDelaySelectAutoDolbyEPhase8 OBJECT-TYPE
		SYNTAX		INTEGER { disable(0), enable(1) }
		MAX-ACCESS		read-write
		STATUS			current
		DESCRIPTION
				"TYPE: - Checkbox
				 PAGE: - Aud.Delays
					Auto Dolby-E Phase  cmdID= 38125 "
		::= { iqdbe00CmdEntry 38125 }


	iqdbe00AudDelaysAESDelaySelectDelayLimit8 OBJECT-TYPE
		SYNTAX		RollCallString
		MAX-ACCESS		read-only
		STATUS			current
		DESCRIPTION
				"TYPE: - Display
				 PAGE: - Aud.Delays
					Delay Limit  cmdID= 38307  format=   "
		::= { iqdbe00CmdEntry 38307 }


	iqdbe00AudDelaysAESDelaySelectDolbyEncFineDela OBJECT-TYPE
		SYNTAX		INTEGER
		MAX-ACCESS		read-write
		STATUS			current
		DESCRIPTION
				"TYPE: - Number
				 PAGE: - Aud.Delays
					Dolby Enc Fine Dela  cmdID= 38137  min= -2450  max= 2450  step= 52  format= %0.3f ms  div_scale= 10000
					Min = -0.245 ms  Max = 0.245 ms  Step = 0.005 ms "
		::= { iqdbe00CmdEntry 38137 }


	iqdbe00AudDelaysEMBDelaySelectDelay1 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-1  cmdID= 38080
					Min  value= 0
					Delay A  value= 1
					Delay B  value= 2  "
		::= { iqdbe00CmdEntry 38080 }


	iqdbe00AudDelaysEMBDelaySelectInternal1 OBJECT-TYPE
		SYNTAX		INTEGER { disable(0), enable(1) }
		MAX-ACCESS		read-write
		STATUS			current
		DESCRIPTION
				"TYPE: - Checkbox
				 PAGE: - Aud.Delays
					Internal-1  cmdID= 38100 "
		::= { iqdbe00CmdEntry 38100 }


	iqdbe00AudDelaysEMBDelaySelectAutoDolbyEPhase1 OBJECT-TYPE
		SYNTAX		INTEGER { disable(0), enable(1) }
		MAX-ACCESS		read-write
		STATUS			current
		DESCRIPTION
				"TYPE: - Checkbox
				 PAGE: - Aud.Delays
					Auto Dolby-E Phase  cmdID= 38110 "
		::= { iqdbe00CmdEntry 38110 }


	iqdbe00AudDelaysEMBDelaySelectDelayLimit1 OBJECT-TYPE
		SYNTAX		RollCallString
		MAX-ACCESS		read-only
		STATUS			current
		DESCRIPTION
				"TYPE: - Display
				 PAGE: - Aud.Delays
					Delay Limit  cmdID= 38308  format=   "
		::= { iqdbe00CmdEntry 38308 }


	iqdbe00AudDelaysEMBDelaySelectEMB1FineDelay OBJECT-TYPE
		SYNTAX		INTEGER
		MAX-ACCESS		read-write
		STATUS			current
		DESCRIPTION
				"TYPE: - Number
				 PAGE: - Aud.Delays
					EMB 1 Fine Delay  cmdID= 38138  min= -2450  max= 2450  step= 52  format= %0.3f ms  div_scale= 10000
					Min = -0.245 ms  Max = 0.245 ms  Step = 0.005 ms "
		::= { iqdbe00CmdEntry 38138 }


	iqdbe00AudDelaysEMBDelaySelectDelay2 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-2  cmdID= 38081
					Min  value= 0
					Delay A  value= 1
					Delay B  value= 2  "
		::= { iqdbe00CmdEntry 38081 }


	iqdbe00AudDelaysEMBDelaySelectInternal2 OBJECT-TYPE
		SYNTAX		INTEGER { disable(0), enable(1) }
		MAX-ACCESS		read-write
		STATUS			current
		DESCRIPTION
				"TYPE: - Checkbox
				 PAGE: - Aud.Delays
					Internal-2  cmdID= 38101 "
		::= { iqdbe00CmdEntry 38101 }


	iqdbe00AudDelaysEMBDelaySelectAutoDolbyEPhase2 OBJECT-TYPE
		SYNTAX		INTEGER { disable(0), enable(1) }
		MAX-ACCESS		read-write
		STATUS			current
		DESCRIPTION
				"TYPE: - Checkbox
				 PAGE: - Aud.Delays
					Auto Dolby-E Phase  cmdID= 38111 "
		::= { iqdbe00CmdEntry 38111 }


	iqdbe00AudDelaysEMBDelaySelectDelayLimit2 OBJECT-TYPE
		SYNTAX		RollCallString
		MAX-ACCESS		read-only
		STATUS			current
		DESCRIPTION
				"TYPE: - Display
				 PAGE: - Aud.Delays
					Delay Limit  cmdID= 38309  format=   "
		::= { iqdbe00CmdEntry 38309 }


	iqdbe00AudDelaysEMBDelaySelectEMB2FineDelay OBJECT-TYPE
		SYNTAX		INTEGER
		MAX-ACCESS		read-write
		STATUS			current
		DESCRIPTION
				"TYPE: - Number
				 PAGE: - Aud.Delays
					EMB 2 Fine Delay  cmdID= 38139  min= -2450  max= 2450  step= 52  format= %0.3f ms  div_scale= 10000
					Min = -0.245 ms  Max = 0.245 ms  Step = 0.005 ms "
		::= { iqdbe00CmdEntry 38139 }


	iqdbe00AudDelaysEMBDelaySelectDelay3 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-3  cmdID= 38082
					Min  value= 0
					Delay A  value= 1
					Delay B  value= 2  "
		::= { iqdbe00CmdEntry 38082 }


	iqdbe00AudDelaysEMBDelaySelectInternal3 OBJECT-TYPE
		SYNTAX		INTEGER { disable(0), enable(1) }
		MAX-ACCESS		read-write
		STATUS			current
		DESCRIPTION
				"TYPE: - Checkbox
				 PAGE: - Aud.Delays
					Internal-3  cmdID= 38102 "
		::= { iqdbe00CmdEntry 38102 }


	iqdbe00AudDelaysEMBDelaySelectAutoDolbyEPhase3 OBJECT-TYPE
		SYNTAX		INTEGER { disable(0), enable(1) }
		MAX-ACCESS		read-write
		STATUS			current
		DESCRIPTION
				"TYPE: - Checkbox
				 PAGE: - Aud.Delays
					Auto Dolby-E Phase  cmdID= 38112 "
		::= { iqdbe00CmdEntry 38112 }


	iqdbe00AudDelaysEMBDelaySelectDelayLimit3 OBJECT-TYPE
		SYNTAX		RollCallString
		MAX-ACCESS		read-only
		STATUS			current
		DESCRIPTION
				"TYPE: - Display
				 PAGE: - Aud.Delays
					Delay Limit  cmdID= 38310  format=   "
		::= { iqdbe00CmdEntry 38310 }


	iqdbe00AudDelaysEMBDelaySelectEMB3FineDelay OBJECT-TYPE
		SYNTAX		INTEGER
		MAX-ACCESS		read-write
		STATUS			current
		DESCRIPTION
				"TYPE: - Number
				 PAGE: - Aud.Delays
					EMB 3 Fine Delay  cmdID= 38140  min= -2450  max= 2450  step= 52  format= %0.3f ms  div_scale= 10000
					Min = -0.245 ms  Max = 0.245 ms  Step = 0.005 ms "
		::= { iqdbe00CmdEntry 38140 }


	iqdbe00AudDelaysEMBDelaySelectDelay4 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-4  cmdID= 38083
					Min  value= 0
					Delay A  value= 1
					Delay B  value= 2  "
		::= { iqdbe00CmdEntry 38083 }


	iqdbe00AudDelaysEMBDelaySelectInternal4 OBJECT-TYPE
		SYNTAX		INTEGER { disable(0), enable(1) }
		MAX-ACCESS		read-write
		STATUS			current
		DESCRIPTION
				"TYPE: - Checkbox
				 PAGE: - Aud.Delays
					Internal-4  cmdID= 38103 "
		::= { iqdbe00CmdEntry 38103 }


	iqdbe00AudDelaysEMBDelaySelectAutoDolbyEPhase4 OBJECT-TYPE
		SYNTAX		INTEGER { disable(0), enable(1) }
		MAX-ACCESS		read-write
		STATUS			current
		DESCRIPTION
				"TYPE: - Checkbox
				 PAGE: - Aud.Delays
					Auto Dolby-E Phase  cmdID= 38113 "
		::= { iqdbe00CmdEntry 38113 }


	iqdbe00AudDelaysEMBDelaySelectDelayLimit4 OBJECT-TYPE
		SYNTAX		RollCallString
		MAX-ACCESS		read-only
		STATUS			current
		DESCRIPTION
				"TYPE: - Display
				 PAGE: - Aud.Delays
					Delay Limit  cmdID= 38311  format=   "
		::= { iqdbe00CmdEntry 38311 }


	iqdbe00AudDelaysEMBDelaySelectEMB4FineDelay OBJECT-TYPE
		SYNTAX		INTEGER
		MAX-ACCESS		read-write
		STATUS			current
		DESCRIPTION
				"TYPE: - Number
				 PAGE: - Aud.Delays
					EMB 4 Fine Delay  cmdID= 38141  min= -2450  max= 2450  step= 52  format= %0.3f ms  div_scale= 10000
					Min = -0.245 ms  Max = 0.245 ms  Step = 0.005 ms "
		::= { iqdbe00CmdEntry 38141 }


	iqdbe00AudDelaysEMBDelaySelectDelay5 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-5  cmdID= 38084
					Min  value= 0
					Delay A  value= 1
					Delay B  value= 2  "
		::= { iqdbe00CmdEntry 38084 }


	iqdbe00AudDelaysEMBDelaySelectInternal5 OBJECT-TYPE
		SYNTAX		INTEGER { disable(0), enable(1) }
		MAX-ACCESS		read-write
		STATUS			current
		DESCRIPTION
				"TYPE: - Checkbox
				 PAGE: - Aud.Delays
					Internal-5  cmdID= 38104 "
		::= { iqdbe00CmdEntry 38104 }


	iqdbe00AudDelaysEMBDelaySelectAutoDolbyEPhase5 OBJECT-TYPE
		SYNTAX		INTEGER { disable(0), enable(1) }
		MAX-ACCESS		read-write
		STATUS			current
		DESCRIPTION
				"TYPE: - Checkbox
				 PAGE: - Aud.Delays
					Auto Dolby-E Phase  cmdID= 38114 "
		::= { iqdbe00CmdEntry 38114 }


	iqdbe00AudDelaysEMBDelaySelectDelayLimit5 OBJECT-TYPE
		SYNTAX		RollCallString
		MAX-ACCESS		read-only
		STATUS			current
		DESCRIPTION
				"TYPE: - Display
				 PAGE: - Aud.Delays
					Delay Limit  cmdID= 38312  format=   "
		::= { iqdbe00CmdEntry 38312 }


	iqdbe00AudDelaysEMBDelaySelectEMB5FineDelay OBJECT-TYPE
		SYNTAX		INTEGER
		MAX-ACCESS		read-write
		STATUS			current
		DESCRIPTION
				"TYPE: - Number
				 PAGE: - Aud.Delays
					EMB 5 Fine Delay  cmdID= 38142  min= -2450  max= 2450  step= 52  format= %0.3f ms  div_scale= 10000
					Min = -0.245 ms  Max = 0.245 ms  Step = 0.005 ms "
		::= { iqdbe00CmdEntry 38142 }


	iqdbe00AudDelaysEMBDelaySelectDelay6 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-6  cmdID= 38085
					Min  value= 0
					Delay A  value= 1
					Delay B  value= 2  "
		::= { iqdbe00CmdEntry 38085 }


	iqdbe00AudDelaysEMBDelaySelectInternal6 OBJECT-TYPE
		SYNTAX		INTEGER { disable(0), enable(1) }
		MAX-ACCESS		read-write
		STATUS			current
		DESCRIPTION
				"TYPE: - Checkbox
				 PAGE: - Aud.Delays
					Internal-6  cmdID= 38105 "
		::= { iqdbe00CmdEntry 38105 }


	iqdbe00AudDelaysEMBDelaySelectAutoDolbyEPhase6 OBJECT-TYPE
		SYNTAX		INTEGER { disable(0), enable(1) }
		MAX-ACCESS		read-write
		STATUS			current
		DESCRIPTION
				"TYPE: - Checkbox
				 PAGE: - Aud.Delays
					Auto Dolby-E Phase  cmdID= 38115 "
		::= { iqdbe00CmdEntry 38115 }


	iqdbe00AudDelaysEMBDelaySelectDelayLimit6 OBJECT-TYPE
		SYNTAX		RollCallString
		MAX-ACCESS		read-only
		STATUS			current
		DESCRIPTION
				"TYPE: - Display
				 PAGE: - Aud.Delays
					Delay Limit  cmdID= 38313  format=   "
		::= { iqdbe00CmdEntry 38313 }


	iqdbe00AudDelaysEMBDelaySelectEMB6FineDelay OBJECT-TYPE
		SYNTAX		INTEGER
		MAX-ACCESS		read-write
		STATUS			current
		DESCRIPTION
				"TYPE: - Number
				 PAGE: - Aud.Delays
					EMB 6 Fine Delay  cmdID= 38143  min= -2450  max= 2450  step= 52  format= %0.3f ms  div_scale= 10000
					Min = -0.245 ms  Max = 0.245 ms  Step = 0.005 ms "
		::= { iqdbe00CmdEntry 38143 }


	iqdbe00AudDelaysEMBDelaySelectDelay7 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-7  cmdID= 38086
					Min  value= 0
					Delay A  value= 1
					Delay B  value= 2  "
		::= { iqdbe00CmdEntry 38086 }


	iqdbe00AudDelaysEMBDelaySelectInternal7 OBJECT-TYPE
		SYNTAX		INTEGER { disable(0), enable(1) }
		MAX-ACCESS		read-write
		STATUS			current
		DESCRIPTION
				"TYPE: - Checkbox
				 PAGE: - Aud.Delays
					Internal-7  cmdID= 38106 "
		::= { iqdbe00CmdEntry 38106 }


	iqdbe00AudDelaysEMBDelaySelectAutoDolbyEPhase7 OBJECT-TYPE
		SYNTAX		INTEGER { disable(0), enable(1) }
		MAX-ACCESS		read-write
		STATUS			current
		DESCRIPTION
				"TYPE: - Checkbox
				 PAGE: - Aud.Delays
					Auto Dolby-E Phase  cmdID= 38116 "
		::= { iqdbe00CmdEntry 38116 }


	iqdbe00AudDelaysEMBDelaySelectDelayLimit7 OBJECT-TYPE
		SYNTAX		RollCallString
		MAX-ACCESS		read-only
		STATUS			current
		DESCRIPTION
				"TYPE: - Display
				 PAGE: - Aud.Delays
					Delay Limit  cmdID= 38314  format=   "
		::= { iqdbe00CmdEntry 38314 }


	iqdbe00AudDelaysEMBDelaySelectEMB7FineDelay OBJECT-TYPE
		SYNTAX		INTEGER
		MAX-ACCESS		read-write
		STATUS			current
		DESCRIPTION
				"TYPE: - Number
				 PAGE: - Aud.Delays
					EMB 7 Fine Delay  cmdID= 38144  min= -2450  max= 2450  step= 52  format= %0.3f ms  div_scale= 10000
					Min = -0.245 ms  Max = 0.245 ms  Step = 0.005 ms "
		::= { iqdbe00CmdEntry 38144 }


	iqdbe00AudDelaysEMBDelaySelectDelay8 OBJECT-TYPE
		SYNTAX		INTEGER {
							val_Min(0),
							val_Delay_A(1),
							val_Delay_B(2)
							}
		MAX-ACCESS		read-write
		STATUS			current
		DESCRIPTION
				"TYPE: - RadiobuttonList
				 PAGE: - Aud.Delays
					Delay-8  cmdID= 38087
					Min  value= 0
					Delay A  value= 1
					Delay B  value= 2  "
		::= { iqdbe00CmdEntry 38087 }


	iqdbe00AudDelaysEMBDelaySelectInternal8 OBJECT-TYPE
		SYNTAX		INTEGER { disable(0), enable(1) }
		MAX-ACCESS		read-write
		STATUS			current
		DESCRIPTION
				"TYPE: - Checkbox
				 PAGE: - Aud.Delays
					Internal-8  cmdID= 38107 "
		::= { iqdbe00CmdEntry 38107 }


	iqdbe00AudDelaysEMBDelaySelectDelayLimit8 OBJECT-TYPE
		SYNTAX		RollCallString
		MAX-ACCESS		read-only
		STATUS			current
		DESCRIPTION
				"TYPE: - Display
				 PAGE: - Aud.Delays
					Delay Limit  cmdID= 38315  format=   "
		::= { iqdbe00CmdEntry 38315 }


	iqdbe00AudDelaysEMBDelaySelectAutoDolbyEPhase8 OBJECT-TYPE
		SYNTAX		INTEGER { disable(0), enable(1) }
		MAX-ACCESS		read-write
		STATUS			current
		DESCRIPTION
				"TYPE: - Checkbox
				 PAGE: - Aud.Delays
					Auto Dolby-E Phase  cmdID= 38117 "
		::= { iqdbe00CmdEntry 38117 }


	iqdbe00AudDelaysEMBDelaySelectEMB8FineDelay OBJECT-TYPE
		SYNTAX		INTEGER
		MAX-ACCESS		read-write
		STATUS			current
		DESCRIPTION
				"TYPE: - Number
				 PAGE: - Aud.Delays
					EMB 8 Fine Delay  cmdID= 38145  min= -2450  max= 2450  step= 52  format= %0.3f ms  div_scale= 10000
					Min = -0.245 ms  Max = 0.245 ms  Step = 0.005 ms "
		::= { iqdbe00CmdEntry 38145 }


	iqdbe00AudioAudDelaysRollTrack14 OBJECT-TYPE
		SYNTAX		RollCallString
		MAX-ACCESS		read-only
		STATUS			current
		DESCRIPTION
				"TYPE: - Display
				 PAGE: - Aud.Delays
					RollTrack14  cmdID= 14  format=   "
		::= { iqdbe00CmdEntry 14 }


	iqdbe00AudioAudDelaysRollTrack15 OBJECT-TYPE
		SYNTAX		RollCallString
		MAX-ACCESS		read-only
		STATUS			current
		DESCRIPTION
				"TYPE: - Display
				 PAGE: - Aud.Delays
					RollTrack15  cmdID= 15  format=   "
		::= { iqdbe00CmdEntry 15 }


	iqdbe00AudioAudDelaysRollTrack16 OBJECT-TYPE
		SYNTAX		RollCallString
		MAX-ACCESS		read-only
		STATUS			current
		DESCRIPTION
				"TYPE: - Display
				 PAGE: - Aud.Delays
					RollTrack16  cmdID= 16  format=   "
		::= { iqdbe00CmdEntry 16 }


	iqdbe00AudioAudDelaysRollTrack17 OBJECT-TYPE
		SYNTAX		RollCallString
		MAX-ACCESS		read-only
		STATUS			current
		DESCRIPTION
				"TYPE: - Display
				 PAGE: - Aud.Delays
					RollTrack17  cmdID= 17  format=   "
		::= { iqdbe00CmdEntry 17 }


	iqdbe00AudioAudDelaysCrashSRCLimit OBJECT-TYPE
		SYNTAX		INTEGER
		MAX-ACCESS		read-write
		STATUS			current
		DESCRIPTION
				"TYPE: - Number
				 PAGE: - Aud.Delays
					Crash SRC Limit  cmdID= 38678  min= 0  max= 80  step= 1  format= %0.0f ms  div_scale= 1
					Min = 0 ms  Max = 80 ms  Step = 1 ms "
		::= { iqdbe00CmdEntry 38678 }


	iqdbe00EmbCtrlGroupGroup1Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 1 Audio  cmdID= 37450
					Pass  value= 0
					Blank  value= 2
					Embed  value= 1  "
		::= { iqdbe00CmdEntry 37450 }


	iqdbe00EmbCtrlGroupGroup2Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 2 Audio  cmdID= 37451
					Pass  value= 0
					Blank  value= 2
					Embed  value= 1  "
		::= { iqdbe00CmdEntry 37451 }


	iqdbe00EmbCtrlGroupGroup3Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 3 Audio  cmdID= 37452
					Pass  value= 0
					Blank  value= 2
					Embed  value= 1  "
		::= { iqdbe00CmdEntry 37452 }


	iqdbe00EmbCtrlGroupGroup4Audio OBJECT-TYPE
		SYNTAX		INTEGER {
							val_Pass(0),
							val_Blank(2),
							val_Embed(1)
							}
		MAX-ACCESS		read-write
		STATUS			current
		DESCRIPTION
				"TYPE: - RadiobuttonList
				 PAGE: - Emb.Ctrl
					Group 4 Audio  cmdID= 37453
					Pass  value= 0
					Blank  value= 2
					Embed  value= 1  "
		::= { iqdbe00CmdEntry 37453 }


	iqdbe00EmbCtrlChannelPair1LActive OBJECT-TYPE
		SYNTAX		INTEGER { disable(0), enable(1) }
		MAX-ACCESS		read-write
		STATUS			current
		DESCRIPTION
				"TYPE: - Checkbox
				 PAGE: - Emb.Ctrl
					Pair 1-L Active  cmdID= 37431 "
		::= { iqdbe00CmdEntry 37431 }


	iqdbe00EmbCtrlChannelPair1RActive OBJECT-TYPE
		SYNTAX		INTEGER { disable(0), enable(1) }
		MAX-ACCESS		read-write
		STATUS			current
		DESCRIPTION
				"TYPE: - Checkbox
				 PAGE: - Emb.Ctrl
					Pair 1-R Active  cmdID= 37432 "
		::= { iqdbe00CmdEntry 37432 }


	iqdbe00EmbCtrlChannelPair2LActive OBJECT-TYPE
		SYNTAX		INTEGER { disable(0), enable(1) }
		MAX-ACCESS		read-write
		STATUS			current
		DESCRIPTION
				"TYPE: - Checkbox
				 PAGE: - Emb.Ctrl
					Pair 2-L Active  cmdID= 37433 "
		::= { iqdbe00CmdEntry 37433 }


	iqdbe00EmbCtrlChannelPair2RActive OBJECT-TYPE
		SYNTAX		INTEGER { disable(0), enable(1) }
		MAX-ACCESS		read-write
		STATUS			current
		DESCRIPTION
				"TYPE: - Checkbox
				 PAGE: - Emb.Ctrl
					Pair 2-R Active  cmdID= 37434 "
		::= { iqdbe00CmdEntry 37434 }


	iqdbe00EmbCtrlChannelPair3LActive OBJECT-TYPE
		SYNTAX		INTEGER { disable(0), enable(1) }
		MAX-ACCESS		read-write
		STATUS			current
		DESCRIPTION
				"TYPE: - Checkbox
				 PAGE: - Emb.Ctrl
					Pair 3-L Active  cmdID= 37435 "
		::= { iqdbe00CmdEntry 37435 }


	iqdbe00EmbCtrlChannelPair3RActive OBJECT-TYPE
		SYNTAX		INTEGER { disable(0), enable(1) }
		MAX-ACCESS		read-write
		STATUS			current
		DESCRIPTION
				"TYPE: - Checkbox
				 PAGE: - Emb.Ctrl
					Pair 3-R Active  cmdID= 37436 "
		::= { iqdbe00CmdEntry 37436 }


	iqdbe00EmbCtrlChannelPair4LActive OBJECT-TYPE
		SYNTAX		INTEGER { disable(0), enable(1) }
		MAX-ACCESS		read-write
		STATUS			current
		DESCRIPTION
				"TYPE: - Checkbox
				 PAGE: - Emb.Ctrl
					Pair 4-L Active  cmdID= 37437 "
		::= { iqdbe00CmdEntry 37437 }


	iqdbe00EmbCtrlChannelPair4RActive OBJECT-TYPE
		SYNTAX		INTEGER { disable(0), enable(1) }
		MAX-ACCESS		read-write
		STATUS			current
		DESCRIPTION
				"TYPE: - Checkbox
				 PAGE: - Emb.Ctrl
					Pair 4-R Active  cmdID= 37438 "
		::= { iqdbe00CmdEntry 37438 }


	iqdbe00EmbCtrlChannelPair5LActive OBJECT-TYPE
		SYNTAX		INTEGER { disable(0), enable(1) }
		MAX-ACCESS		read-write
		STATUS			current
		DESCRIPTION
				"TYPE: - Checkbox
				 PAGE: - Emb.Ctrl
					Pair 5-L Active  cmdID= 37439 "
		::= { iqdbe00CmdEntry 37439 }


	iqdbe00EmbCtrlChannelPair5RActive OBJECT-TYPE
		SYNTAX		INTEGER { disable(0), enable(1) }
		MAX-ACCESS		read-write
		STATUS			current
		DESCRIPTION
				"TYPE: - Checkbox
				 PAGE: - Emb.Ctrl
					Pair 5-R Active  cmdID= 37440 "
		::= { iqdbe00CmdEntry 37440 }


	iqdbe00EmbCtrlChannelPair6LActive OBJECT-TYPE
		SYNTAX		INTEGER { disable(0), enable(1) }
		MAX-ACCESS		read-write
		STATUS			current
		DESCRIPTION
				"TYPE: - Checkbox
				 PAGE: - Emb.Ctrl
					Pair 6-L Active  cmdID= 37441 "
		::= { iqdbe00CmdEntry 37441 }


	iqdbe00EmbCtrlChannelPair6RActive OBJECT-TYPE
		SYNTAX		INTEGER { disable(0), enable(1) }
		MAX-ACCESS		read-write
		STATUS			current
		DESCRIPTION
				"TYPE: - Checkbox
				 PAGE: - Emb.Ctrl
					Pair 6-R Active  cmdID= 37442 "
		::= { iqdbe00CmdEntry 37442 }


	iqdbe00EmbCtrlChannelPair7LActive OBJECT-TYPE
		SYNTAX		INTEGER { disable(0), enable(1) }
		MAX-ACCESS		read-write
		STATUS			current
		DESCRIPTION
				"TYPE: - Checkbox
				 PAGE: - Emb.Ctrl
					Pair 7-L Active  cmdID= 37443 "
		::= { iqdbe00CmdEntry 37443 }


	iqdbe00EmbCtrlChannelPair7RActive OBJECT-TYPE
		SYNTAX		INTEGER { disable(0), enable(1) }
		MAX-ACCESS		read-write
		STATUS			current
		DESCRIPTION
				"TYPE: - Checkbox
				 PAGE: - Emb.Ctrl
					Pair 7-R Active  cmdID= 37444 "
		::= { iqdbe00CmdEntry 37444 }


	iqdbe00EmbCtrlChannelPair8LActive OBJECT-TYPE
		SYNTAX		INTEGER { disable(0), enable(1) }
		MAX-ACCESS		read-write
		STATUS			current
		DESCRIPTION
				"TYPE: - Checkbox
				 PAGE: - Emb.Ctrl
					Pair 8-L Active  cmdID= 37445 "
		::= { iqdbe00CmdEntry 37445 }


	iqdbe00EmbCtrlChannelPair8RActive OBJECT-TYPE
		SYNTAX		INTEGER { disable(0), enable(1) }
		MAX-ACCESS		read-write
		STATUS			current
		DESCRIPTION
				"TYPE: - Checkbox
				 PAGE: - Emb.Ctrl
					Pair 8-R Active  cmdID= 37446 "
		::= { iqdbe00CmdEntry 37446 }


	iqdbe00AudioEmbCtrlEmbedderPriority OBJECT-TYPE
		SYNTAX		INTEGER {
							val_Normal(0),
							val_Audio_Dolby_E(1)
							}
		MAX-ACCESS		read-write
		STATUS			current
		DESCRIPTION
				"TYPE: - RadiobuttonList
				 PAGE: - Emb.Ctrl
					Embedder Priority  cmdID= 37460
					Normal  value= 0
					Audio (Dolby-E)  value= 1  "
		::= { iqdbe00CmdEntry 37460 }


	iqdbe00EmbGainEmbedPair1Embed1MuteL OBJECT-TYPE
		SYNTAX		INTEGER { disable(0), enable(1) }
		MAX-ACCESS		read-write
		STATUS			current
		DESCRIPTION
				"TYPE: - Checkbox
				 PAGE: - Emb.Gain
					Embed 1 Mute L  cmdID= 37340 "
		::= { iqdbe00CmdEntry 37340 }


	iqdbe00EmbGainEmbedPair1Embed1MuteR OBJECT-TYPE
		SYNTAX		INTEGER { disable(0), enable(1) }
		MAX-ACCESS		read-write
		STATUS			current
		DESCRIPTION
				"TYPE: - Checkbox
				 PAGE: - Emb.Gain
					Embed 1 Mute R  cmdID= 37341 "
		::= { iqdbe00CmdEntry 37341 }


	iqdbe00EmbGainEmbedPair1Embed1LGain OBJECT-TYPE
		SYNTAX		INTEGER
		MAX-ACCESS		read-write
		STATUS			current
		DESCRIPTION
				"TYPE: - Number
				 PAGE: - Emb.Gain
					Embed 1 L Gain  cmdID= 37320  min= -661  max= 120  step= 1  format= %0.1f dB  div_scale= 10
					Min = -66.1 dB  Max = 12.0 dB  Step = 0.1 dB "
		::= { iqdbe00CmdEntry 37320 }


	iqdbe00EmbGainEmbedPair1Embed1RGain OBJECT-TYPE
		SYNTAX		INTEGER
		MAX-ACCESS		read-write
		STATUS			current
		DESCRIPTION
				"TYPE: - Number
				 PAGE: - Emb.Gain
					Embed 1 R Gain  cmdID= 37321  min= -661  max= 120  step= 1  format= %0.1f dB  div_scale= 10
					Min = -66.1 dB  Max = 12.0 dB  Step = 0.1 dB "
		::= { iqdbe00CmdEntry 37321 }


	iqdbe00EmbGainEmbedPair1Stereo OBJECT-TYPE
		SYNTAX		INTEGER { disable(0), enable(1) }
		MAX-ACCESS		read-write
		STATUS			current
		DESCRIPTION
				"TYPE: - Checkbox
				 PAGE: - Emb.Gain
					Stereo  cmdID= 37380 "
		::= { iqdbe00CmdEntry 37380 }


	iqdbe00EmbGainEmbedPair1Embed1InvertL OBJECT-TYPE
		SYNTAX		INTEGER { disable(0), enable(1) }
		MAX-ACCESS		read-write
		STATUS			current
		DESCRIPTION
				"TYPE: - Checkbox
				 PAGE: - Emb.Gain
					Embed 1 Invert L  cmdID= 37360 "
		::= { iqdbe00CmdEntry 37360 }


	iqdbe00EmbGainEmbedPair1Embed1InvertR OBJECT-TYPE
		SYNTAX		INTEGER { disable(0), enable(1) }
		MAX-ACCESS		read-write
		STATUS			current
		DESCRIPTION
				"TYPE: - Checkbox
				 PAGE: - Emb.Gain
					Embed 1 Invert R  cmdID= 37361 "
		::= { iqdbe00CmdEntry 37361 }


	iqdbe00EmbGainEmbedPair1Embed1LClip OBJECT-TYPE
		SYNTAX		RollCallString
		MAX-ACCESS		read-only
		STATUS			current
		DESCRIPTION
				"TYPE: - Display
				 PAGE: - Emb.Gain
					Embed 1-L Clip  cmdID= 37540  format=   "
		::= { iqdbe00CmdEntry 37540 }


	iqdbe00EmbGainEmbedPair1Embed1RClip OBJECT-TYPE
		SYNTAX		RollCallString
		MAX-ACCESS		read-only
		STATUS			current
		DESCRIPTION
				"TYPE: - Display
				 PAGE: - Emb.Gain
					Embed 1-R Clip  cmdID= 37541  format=   "
		::= { iqdbe00CmdEntry 37541 }


	iqdbe00EmbGainEmbedPair2Embed2MuteL OBJECT-TYPE
		SYNTAX		INTEGER { disable(0), enable(1) }
		MAX-ACCESS		read-write
		STATUS			current
		DESCRIPTION
				"TYPE: - Checkbox
				 PAGE: - Emb.Gain
					Embed 2 Mute L  cmdID= 37342 "
		::= { iqdbe00CmdEntry 37342 }


	iqdbe00EmbGainEmbedPair2Embed2MuteR OBJECT-TYPE
		SYNTAX		INTEGER { disable(0), enable(1) }
		MAX-ACCESS		read-write
		STATUS			current
		DESCRIPTION
				"TYPE: - Checkbox
				 PAGE: - Emb.Gain
					Embed 2 Mute R  cmdID= 37343 "
		::= { iqdbe00CmdEntry 37343 }


	iqdbe00EmbGainEmbedPair2Embed2LGain OBJECT-TYPE
		SYNTAX		INTEGER
		MAX-ACCESS		read-write
		STATUS			current
		DESCRIPTION
				"TYPE: - Number
				 PAGE: - Emb.Gain
					Embed 2 L Gain  cmdID= 37322  min= -661  max= 120  step= 1  format= %0.1f dB  div_scale= 10
					Min = -66.1 dB  Max = 12.0 dB  Step = 0.1 dB "
		::= { iqdbe00CmdEntry 37322 }


	iqdbe00EmbGainEmbedPair2Embed2RGain OBJECT-TYPE
		SYNTAX		INTEGER
		MAX-ACCESS		read-write
		STATUS			current
		DESCRIPTION
				"TYPE: - Number
				 PAGE: - Emb.Gain
					Embed 2 R Gain  cmdID= 37323  min= -661  max= 120  step= 1  format= %0.1f dB  div_scale= 10
					Min = -66.1 dB  Max = 12.0 dB  Step = 0.1 dB "
		::= { iqdbe00CmdEntry 37323 }


	iqdbe00EmbGainEmbedPair2Stereo OBJECT-TYPE
		SYNTAX		INTEGER { disable(0), enable(1) }
		MAX-ACCESS		read-write
		STATUS			current
		DESCRIPTION
				"TYPE: - Checkbox
				 PAGE: - Emb.Gain
					Stereo  cmdID= 37381 "
		::= { iqdbe00CmdEntry 37381 }


	iqdbe00EmbGainEmbedPair2Embed2InvertL OBJECT-TYPE
		SYNTAX		INTEGER { disable(0), enable(1) }
		MAX-ACCESS		read-write
		STATUS			current
		DESCRIPTION
				"TYPE: - Checkbox
				 PAGE: - Emb.Gain
					Embed 2 Invert L  cmdID= 37362 "
		::= { iqdbe00CmdEntry 37362 }


	iqdbe00EmbGainEmbedPair2Embed2InvertR OBJECT-TYPE
		SYNTAX		INTEGER { disable(0), enable(1) }
		MAX-ACCESS		read-write
		STATUS			current
		DESCRIPTION
				"TYPE: - Checkbox
				 PAGE: - Emb.Gain
					Embed 2 Invert R  cmdID= 37363 "
		::= { iqdbe00CmdEntry 37363 }


	iqdbe00EmbGainEmbedPair2Embed2LClip OBJECT-TYPE
		SYNTAX		RollCallString
		MAX-ACCESS		read-only
		STATUS			current
		DESCRIPTION
				"TYPE: - Display
				 PAGE: - Emb.Gain
					Embed 2-L Clip  cmdID= 37542  format=   "
		::= { iqdbe00CmdEntry 37542 }


	iqdbe00EmbGainEmbedPair2Embed2RClip OBJECT-TYPE
		SYNTAX		RollCallString
		MAX-ACCESS		read-only
		STATUS			current
		DESCRIPTION
				"TYPE: - Display
				 PAGE: - Emb.Gain
					Embed 2-R Clip  cmdID= 37543  format=   "
		::= { iqdbe00CmdEntry 37543 }


	iqdbe00EmbGainEmbedPair3Embed3MuteL OBJECT-TYPE
		SYNTAX		INTEGER { disable(0), enable(1) }
		MAX-ACCESS		read-write
		STATUS			current
		DESCRIPTION
				"TYPE: - Checkbox
				 PAGE: - Emb.Gain
					Embed 3 Mute L  cmdID= 37344 "
		::= { iqdbe00CmdEntry 37344 }


	iqdbe00EmbGainEmbedPair3Embed3MuteR OBJECT-TYPE
		SYNTAX		INTEGER { disable(0), enable(1) }
		MAX-ACCESS		read-write
		STATUS			current
		DESCRIPTION
				"TYPE: - Checkbox
				 PAGE: - Emb.Gain
					Embed 3 Mute R  cmdID= 37345 "
		::= { iqdbe00CmdEntry 37345 }


	iqdbe00EmbGainEmbedPair3Embed3LGain OBJECT-TYPE
		SYNTAX		INTEGER
		MAX-ACCESS		read-write
		STATUS			current
		DESCRIPTION
				"TYPE: - Number
				 PAGE: - Emb.Gain
					Embed 3 L Gain  cmdID= 37324  min= -661  max= 120  step= 1  format= %0.1f dB  div_scale= 10
					Min = -66.1 dB  Max = 12.0 dB  Step = 0.1 dB "
		::= { iqdbe00CmdEntry 37324 }


	iqdbe00EmbGainEmbedPair3Embed3RGain OBJECT-TYPE
		SYNTAX		INTEGER
		MAX-ACCESS		read-write
		STATUS			current
		DESCRIPTION
				"TYPE: - Number
				 PAGE: - Emb.Gain
					Embed 3 R Gain  cmdID= 37325  min= -661  max= 120  step= 1  format= %0.1f dB  div_scale= 10
					Min = -66.1 dB  Max = 12.0 dB  Step = 0.1 dB "
		::= { iqdbe00CmdEntry 37325 }


	iqdbe00EmbGainEmbedPair3Stereo OBJECT-TYPE
		SYNTAX		INTEGER { disable(0), enable(1) }
		MAX-ACCESS		read-write
		STATUS			current
		DESCRIPTION
				"TYPE: - Checkbox
				 PAGE: - Emb.Gain
					Stereo  cmdID= 37382 "
		::= { iqdbe00CmdEntry 37382 }


	iqdbe00EmbGainEmbedPair3Embed3InvertL OBJECT-TYPE
		SYNTAX		INTEGER { disable(0), enable(1) }
		MAX-ACCESS		read-write
		STATUS			current
		DESCRIPTION
				"TYPE: - Checkbox
				 PAGE: - Emb.Gain
					Embed 3 Invert L  cmdID= 37364 "
		::= { iqdbe00CmdEntry 37364 }


	iqdbe00EmbGainEmbedPair3Embed3InvertR OBJECT-TYPE
		SYNTAX		INTEGER { disable(0), enable(1) }
		MAX-ACCESS		read-write
		STATUS			current
		DESCRIPTION
				"TYPE: - Checkbox
				 PAGE: - Emb.Gain
					Embed 3 Invert R  cmdID= 37365 "
		::= { iqdbe00CmdEntry 37365 }


	iqdbe00EmbGainEmbedPair3Embed3LClip OBJECT-TYPE
		SYNTAX		RollCallString
		MAX-ACCESS		read-only
		STATUS			current
		DESCRIPTION
				"TYPE: - Display
				 PAGE: - Emb.Gain
					Embed 3-L Clip  cmdID= 37544  format=   "
		::= { iqdbe00CmdEntry 37544 }


	iqdbe00EmbGainEmbedPair3Embed3RClip OBJECT-TYPE
		SYNTAX		RollCallString
		MAX-ACCESS		read-only
		STATUS			current
		DESCRIPTION
				"TYPE: - Display
				 PAGE: - Emb.Gain
					Embed 3-R Clip  cmdID= 37545  format=   "
		::= { iqdbe00CmdEntry 37545 }


	iqdbe00EmbGainEmbedPair4Embed4MuteL OBJECT-TYPE
		SYNTAX		INTEGER { disable(0), enable(1) }
		MAX-ACCESS		read-write
		STATUS			current
		DESCRIPTION
				"TYPE: - Checkbox
				 PAGE: - Emb.Gain
					Embed 4 Mute L  cmdID= 37346 "
		::= { iqdbe00CmdEntry 37346 }


	iqdbe00EmbGainEmbedPair4Embed4MuteR OBJECT-TYPE
		SYNTAX		INTEGER { disable(0), enable(1) }
		MAX-ACCESS		read-write
		STATUS			current
		DESCRIPTION
				"TYPE: - Checkbox
				 PAGE: - Emb.Gain
					Embed 4 Mute R  cmdID= 37347 "
		::= { iqdbe00CmdEntry 37347 }


	iqdbe00EmbGainEmbedPair4Embed4LGain OBJECT-TYPE
		SYNTAX		INTEGER
		MAX-ACCESS		read-write
		STATUS			current
		DESCRIPTION
				"TYPE: - Number
				 PAGE: - Emb.Gain
					Embed 4 L Gain  cmdID= 37326  min= -661  max= 120  step= 1  format= %0.1f dB  div_scale= 10
					Min = -66.1 dB  Max = 12.0 dB  Step = 0.1 dB "
		::= { iqdbe00CmdEntry 37326 }


	iqdbe00EmbGainEmbedPair4Embed4RGain OBJECT-TYPE
		SYNTAX		INTEGER
		MAX-ACCESS		read-write
		STATUS			current
		DESCRIPTION
				"TYPE: - Number
				 PAGE: - Emb.Gain
					Embed 4 R Gain  cmdID= 37327  min= -661  max= 120  step= 1  format= %0.1f dB  div_scale= 10
					Min = -66.1 dB  Max = 12.0 dB  Step = 0.1 dB "
		::= { iqdbe00CmdEntry 37327 }


	iqdbe00EmbGainEmbedPair4Stereo OBJECT-TYPE
		SYNTAX		INTEGER { disable(0), enable(1) }
		MAX-ACCESS		read-write
		STATUS			current
		DESCRIPTION
				"TYPE: - Checkbox
				 PAGE: - Emb.Gain
					Stereo  cmdID= 37383 "
		::= { iqdbe00CmdEntry 37383 }


	iqdbe00EmbGainEmbedPair4Embed4InvertL OBJECT-TYPE
		SYNTAX		INTEGER { disable(0), enable(1) }
		MAX-ACCESS		read-write
		STATUS			current
		DESCRIPTION
				"TYPE: - Checkbox
				 PAGE: - Emb.Gain
					Embed 4 Invert L  cmdID= 37366 "
		::= { iqdbe00CmdEntry 37366 }


	iqdbe00EmbGainEmbedPair4Embed4InvertR OBJECT-TYPE
		SYNTAX		INTEGER { disable(0), enable(1) }
		MAX-ACCESS		read-write
		STATUS			current
		DESCRIPTION
				"TYPE: - Checkbox
				 PAGE: - Emb.Gain
					Embed 4 Invert R  cmdID= 37367 "
		::= { iqdbe00CmdEntry 37367 }


	iqdbe00EmbGainEmbedPair4Embed4LClip OBJECT-TYPE
		SYNTAX		RollCallString
		MAX-ACCESS		read-only
		STATUS			current
		DESCRIPTION
				"TYPE: - Display
				 PAGE: - Emb.Gain
					Embed 4-L Clip  cmdID= 37546  format=   "
		::= { iqdbe00CmdEntry 37546 }


	iqdbe00EmbGainEmbedPair4Embed4RClip OBJECT-TYPE
		SYNTAX		RollCallString
		MAX-ACCESS		read-only
		STATUS			current
		DESCRIPTION
				"TYPE: - Display
				 PAGE: - Emb.Gain
					Embed 4-R Clip  cmdID= 37547  format=   "
		::= { iqdbe00CmdEntry 37547 }


	iqdbe00EmbGainEmbedPair5Embed5MuteL OBJECT-TYPE
		SYNTAX		INTEGER { disable(0), enable(1) }
		MAX-ACCESS		read-write
		STATUS			current
		DESCRIPTION
				"TYPE: - Checkbox
				 PAGE: - Emb.Gain
					Embed 5 Mute L  cmdID= 37348 "
		::= { iqdbe00CmdEntry 37348 }


	iqdbe00EmbGainEmbedPair5Embed5MuteR OBJECT-TYPE
		SYNTAX		INTEGER { disable(0), enable(1) }
		MAX-ACCESS		read-write
		STATUS			current
		DESCRIPTION
				"TYPE: - Checkbox
				 PAGE: - Emb.Gain
					Embed 5 Mute R  cmdID= 37349 "
		::= { iqdbe00CmdEntry 37349 }


	iqdbe00EmbGainEmbedPair5Embed5LGain OBJECT-TYPE
		SYNTAX		INTEGER
		MAX-ACCESS		read-write
		STATUS			current
		DESCRIPTION
				"TYPE: - Number
				 PAGE: - Emb.Gain
					Embed 5 L Gain  cmdID= 37328  min= -661  max= 120  step= 1  format= %0.1f dB  div_scale= 10
					Min = -66.1 dB  Max = 12.0 dB  Step = 0.1 dB "
		::= { iqdbe00CmdEntry 37328 }


	iqdbe00EmbGainEmbedPair5Embed5RGain OBJECT-TYPE
		SYNTAX		INTEGER
		MAX-ACCESS		read-write
		STATUS			current
		DESCRIPTION
				"TYPE: - Number
				 PAGE: - Emb.Gain
					Embed 5 R Gain  cmdID= 37329  min= -661  max= 120  step= 1  format= %0.1f dB  div_scale= 10
					Min = -66.1 dB  Max = 12.0 dB  Step = 0.1 dB "
		::= { iqdbe00CmdEntry 37329 }


	iqdbe00EmbGainEmbedPair5Stereo OBJECT-TYPE
		SYNTAX		INTEGER { disable(0), enable(1) }
		MAX-ACCESS		read-write
		STATUS			current
		DESCRIPTION
				"TYPE: - Checkbox
				 PAGE: - Emb.Gain
					Stereo  cmdID= 37384 "
		::= { iqdbe00CmdEntry 37384 }


	iqdbe00EmbGainEmbedPair5Embed5InvertL OBJECT-TYPE
		SYNTAX		INTEGER { disable(0), enable(1) }
		MAX-ACCESS		read-write
		STATUS			current
		DESCRIPTION
				"TYPE: - Checkbox
				 PAGE: - Emb.Gain
					Embed 5 Invert L  cmdID= 37368 "
		::= { iqdbe00CmdEntry 37368 }


	iqdbe00EmbGainEmbedPair5Embed5InvertR OBJECT-TYPE
		SYNTAX		INTEGER { disable(0), enable(1) }
		MAX-ACCESS		read-write
		STATUS			current
		DESCRIPTION
				"TYPE: - Checkbox
				 PAGE: - Emb.Gain
					Embed 5 Invert R  cmdID= 37369 "
		::= { iqdbe00CmdEntry 37369 }


	iqdbe00EmbGainEmbedPair5Embed5LClip OBJECT-TYPE
		SYNTAX		RollCallString
		MAX-ACCESS		read-only
		STATUS			current
		DESCRIPTION
				"TYPE: - Display
				 PAGE: - Emb.Gain
					Embed 5-L Clip  cmdID= 37548  format=   "
		::= { iqdbe00CmdEntry 37548 }


	iqdbe00EmbGainEmbedPair5Embed5RClip OBJECT-TYPE
		SYNTAX		RollCallString
		MAX-ACCESS		read-only
		STATUS			current
		DESCRIPTION
				"TYPE: - Display
				 PAGE: - Emb.Gain
					Embed 5-R Clip  cmdID= 37549  format=   "
		::= { iqdbe00CmdEntry 37549 }


	iqdbe00EmbGainEmbedPair6Embed6MuteL OBJECT-TYPE
		SYNTAX		INTEGER { disable(0), enable(1) }
		MAX-ACCESS		read-write
		STATUS			current
		DESCRIPTION
				"TYPE: - Checkbox
				 PAGE: - Emb.Gain
					Embed 6 Mute L  cmdID= 37350 "
		::= { iqdbe00CmdEntry 37350 }


	iqdbe00EmbGainEmbedPair6Embed6MuteR OBJECT-TYPE
		SYNTAX		INTEGER { disable(0), enable(1) }
		MAX-ACCESS		read-write
		STATUS			current
		DESCRIPTION
				"TYPE: - Checkbox
				 PAGE: - Emb.Gain
					Embed 6 Mute R  cmdID= 37351 "
		::= { iqdbe00CmdEntry 37351 }


	iqdbe00EmbGainEmbedPair6Embed6LGain OBJECT-TYPE
		SYNTAX		INTEGER
		MAX-ACCESS		read-write
		STATUS			current
		DESCRIPTION
				"TYPE: - Number
				 PAGE: - Emb.Gain
					Embed 6 L Gain  cmdID= 37330  min= -661  max= 120  step= 1  format= %0.1f dB  div_scale= 10
					Min = -66.1 dB  Max = 12.0 dB  Step = 0.1 dB "
		::= { iqdbe00CmdEntry 37330 }


	iqdbe00EmbGainEmbedPair6Embed6RGain OBJECT-TYPE
		SYNTAX		INTEGER
		MAX-ACCESS		read-write
		STATUS			current
		DESCRIPTION
				"TYPE: - Number
				 PAGE: - Emb.Gain
					Embed 6 R Gain  cmdID= 37331  min= -661  max= 120  step= 1  format= %0.1f dB  div_scale= 10
					Min = -66.1 dB  Max = 12.0 dB  Step = 0.1 dB "
		::= { iqdbe00CmdEntry 37331 }


	iqdbe00EmbGainEmbedPair6Stereo OBJECT-TYPE
		SYNTAX		INTEGER { disable(0), enable(1) }
		MAX-ACCESS		read-write
		STATUS			current
		DESCRIPTION
				"TYPE: - Checkbox
				 PAGE: - Emb.Gain
					Stereo  cmdID= 37385 "
		::= { iqdbe00CmdEntry 37385 }


	iqdbe00EmbGainEmbedPair6Embed6InvertL OBJECT-TYPE
		SYNTAX		INTEGER { disable(0), enable(1) }
		MAX-ACCESS		read-write
		STATUS			current
		DESCRIPTION
				"TYPE: - Checkbox
				 PAGE: - Emb.Gain
					Embed 6 Invert L  cmdID= 37370 "
		::= { iqdbe00CmdEntry 37370 }


	iqdbe00EmbGainEmbedPair6Embed6InvertR OBJECT-TYPE
		SYNTAX		INTEGER { disable(0), enable(1) }
		MAX-ACCESS		read-write
		STATUS			current
		DESCRIPTION
				"TYPE: - Checkbox
				 PAGE: - Emb.Gain
					Embed 6 Invert R  cmdID= 37371 "
		::= { iqdbe00CmdEntry 37371 }


	iqdbe00EmbGainEmbedPair6Embed6LClip OBJECT-TYPE
		SYNTAX		RollCallString
		MAX-ACCESS		read-only
		STATUS			current
		DESCRIPTION
				"TYPE: - Display
				 PAGE: - Emb.Gain
					Embed 6-L Clip  cmdID= 37550  format=   "
		::= { iqdbe00CmdEntry 37550 }


	iqdbe00EmbGainEmbedPair6Embed6RClip OBJECT-TYPE
		SYNTAX		RollCallString
		MAX-ACCESS		read-only
		STATUS			current
		DESCRIPTION
				"TYPE: - Display
				 PAGE: - Emb.Gain
					Embed 6-R Clip  cmdID= 37551  format=   "
		::= { iqdbe00CmdEntry 37551 }


	iqdbe00EmbGainEmbedPair7Embed7MuteL OBJECT-TYPE
		SYNTAX		INTEGER { disable(0), enable(1) }
		MAX-ACCESS		read-write
		STATUS			current
		DESCRIPTION
				"TYPE: - Checkbox
				 PAGE: - Emb.Gain
					Embed 7 Mute L  cmdID= 37352 "
		::= { iqdbe00CmdEntry 37352 }


	iqdbe00EmbGainEmbedPair7Embed7MuteR OBJECT-TYPE
		SYNTAX		INTEGER { disable(0), enable(1) }
		MAX-ACCESS		read-write
		STATUS			current
		DESCRIPTION
				"TYPE: - Checkbox
				 PAGE: - Emb.Gain
					Embed 7 Mute R  cmdID= 37353 "
		::= { iqdbe00CmdEntry 37353 }


	iqdbe00EmbGainEmbedPair7Embed7LGain OBJECT-TYPE
		SYNTAX		INTEGER
		MAX-ACCESS		read-write
		STATUS			current
		DESCRIPTION
				"TYPE: - Number
				 PAGE: - Emb.Gain
					Embed 7 L Gain  cmdID= 37332  min= -661  max= 120  step= 1  format= %0.1f dB  div_scale= 10
					Min = -66.1 dB  Max = 12.0 dB  Step = 0.1 dB "
		::= { iqdbe00CmdEntry 37332 }


	iqdbe00EmbGainEmbedPair7Embed7RGain OBJECT-TYPE
		SYNTAX		INTEGER
		MAX-ACCESS		read-write
		STATUS			current
		DESCRIPTION
				"TYPE: - Number
				 PAGE: - Emb.Gain
					Embed 7 R Gain  cmdID= 37333  min= -661  max= 120  step= 1  format= %0.1f dB  div_scale= 10
					Min = -66.1 dB  Max = 12.0 dB  Step = 0.1 dB "
		::= { iqdbe00CmdEntry 37333 }


	iqdbe00EmbGainEmbedPair7Stereo OBJECT-TYPE
		SYNTAX		INTEGER { disable(0), enable(1) }
		MAX-ACCESS		read-write
		STATUS			current
		DESCRIPTION
				"TYPE: - Checkbox
				 PAGE: - Emb.Gain
					Stereo  cmdID= 37386 "
		::= { iqdbe00CmdEntry 37386 }


	iqdbe00EmbGainEmbedPair7Embed7InvertL OBJECT-TYPE
		SYNTAX		INTEGER { disable(0), enable(1) }
		MAX-ACCESS		read-write
		STATUS			current
		DESCRIPTION
				"TYPE: - Checkbox
				 PAGE: - Emb.Gain
					Embed 7 Invert L  cmdID= 37372 "
		::= { iqdbe00CmdEntry 37372 }


	iqdbe00EmbGainEmbedPair7Embed7InvertR OBJECT-TYPE
		SYNTAX		INTEGER { disable(0), enable(1) }
		MAX-ACCESS		read-write
		STATUS			current
		DESCRIPTION
				"TYPE: - Checkbox
				 PAGE: - Emb.Gain
					Embed 7 Invert R  cmdID= 37373 "
		::= { iqdbe00CmdEntry 37373 }


	iqdbe00EmbGainEmbedPair7Embed7LClip OBJECT-TYPE
		SYNTAX		RollCallString
		MAX-ACCESS		read-only
		STATUS			current
		DESCRIPTION
				"TYPE: - Display
				 PAGE: - Emb.Gain
					Embed 7-L Clip  cmdID= 37552  format=   "
		::= { iqdbe00CmdEntry 37552 }


	iqdbe00EmbGainEmbedPair7Embed7RClip OBJECT-TYPE
		SYNTAX		RollCallString
		MAX-ACCESS		read-only
		STATUS			current
		DESCRIPTION
				"TYPE: - Display
				 PAGE: - Emb.Gain
					Embed 7-R Clip  cmdID= 37553  format=   "
		::= { iqdbe00CmdEntry 37553 }


	iqdbe00EmbGainEmbedPair8Embed8MuteL OBJECT-TYPE
		SYNTAX		INTEGER { disable(0), enable(1) }
		MAX-ACCESS		read-write
		STATUS			current
		DESCRIPTION
				"TYPE: - Checkbox
				 PAGE: - Emb.Gain
					Embed 8 Mute L  cmdID= 37354 "
		::= { iqdbe00CmdEntry 37354 }


	iqdbe00EmbGainEmbedPair8Embed8MuteR OBJECT-TYPE
		SYNTAX		INTEGER { disable(0), enable(1) }
		MAX-ACCESS		read-write
		STATUS			current
		DESCRIPTION
				"TYPE: - Checkbox
				 PAGE: - Emb.Gain
					Embed 8 Mute R  cmdID= 37355 "
		::= { iqdbe00CmdEntry 37355 }


	iqdbe00EmbGainEmbedPair8Embed8LGain OBJECT-TYPE
		SYNTAX		INTEGER
		MAX-ACCESS		read-write
		STATUS			current
		DESCRIPTION
				"TYPE: - Number
				 PAGE: - Emb.Gain
					Embed 8 L Gain  cmdID= 37334  min= -661  max= 120  step= 1  format= %0.1f dB  div_scale= 10
					Min = -66.1 dB  Max = 12.0 dB  Step = 0.1 dB "
		::= { iqdbe00CmdEntry 37334 }


	iqdbe00EmbGainEmbedPair8Embed8RGain OBJECT-TYPE
		SYNTAX		INTEGER
		MAX-ACCESS		read-write
		STATUS			current
		DESCRIPTION
				"TYPE: - Number
				 PAGE: - Emb.Gain
					Embed 8 R Gain  cmdID= 37335  min= -661  max= 120  step= 1  format= %0.1f dB  div_scale= 10
					Min = -66.1 dB  Max = 12.0 dB  Step = 0.1 dB "
		::= { iqdbe00CmdEntry 37335 }


	iqdbe00EmbGainEmbedPair8Stereo OBJECT-TYPE
		SYNTAX		INTEGER { disable(0), enable(1) }
		MAX-ACCESS		read-write
		STATUS			current
		DESCRIPTION
				"TYPE: - Checkbox
				 PAGE: - Emb.Gain
					Stereo  cmdID= 37387 "
		::= { iqdbe00CmdEntry 37387 }


	iqdbe00EmbGainEmbedPair8Embed8InvertL OBJECT-TYPE
		SYNTAX		INTEGER { disable(0), enable(1) }
		MAX-ACCESS		read-write
		STATUS			current
		DESCRIPTION
				"TYPE: - Checkbox
				 PAGE: - Emb.Gain
					Embed 8 Invert L  cmdID= 37374 "
		::= { iqdbe00CmdEntry 37374 }


	iqdbe00EmbGainEmbedPair8Embed8InvertR OBJECT-TYPE
		SYNTAX		INTEGER { disable(0), enable(1) }
		MAX-ACCESS		read-write
		STATUS			current
		DESCRIPTION
				"TYPE: - Checkbox
				 PAGE: - Emb.Gain
					Embed 8 Invert R  cmdID= 37375 "
		::= { iqdbe00CmdEntry 37375 }


	iqdbe00EmbGainEmbedPair8Embed8LClip OBJECT-TYPE
		SYNTAX		RollCallString
		MAX-ACCESS		read-only
		STATUS			current
		DESCRIPTION
				"TYPE: - Display
				 PAGE: - Emb.Gain
					Embed 8-L Clip  cmdID= 37554  format=   "
		::= { iqdbe00CmdEntry 37554 }


	iqdbe00EmbGainEmbedPair8Embed8RClip OBJECT-TYPE
		SYNTAX		RollCallString
		MAX-ACCESS		read-only
		STATUS			current
		DESCRIPTION
				"TYPE: - Display
				 PAGE: - Emb.Gain
					Embed 8-R Clip  cmdID= 37555  format=   "
		::= { iqdbe00CmdEntry 37555 }


	iqdbe00EmbOutEmbedPair1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 1
					Left  cmdID= 37300
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37300 }


	iqdbe00EmbOutEmbedPair1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 1
					Right  cmdID= 37301
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37301 }


	iqdbe00EmbOutEmbedPair1LinkLRSelection OBJECT-TYPE
		SYNTAX		INTEGER { disable(0), enable(1) }
		MAX-ACCESS		read-write
		STATUS			current
		DESCRIPTION
				"TYPE: - Checkbox
				 PAGE: - Embed Pair 1
					Link L+R Selection  cmdID= 37390 "
		::= { iqdbe00CmdEntry 37390 }


	iqdbe00EmbOutEmbedPair2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 2
					Left  cmdID= 37302
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37302 }


	iqdbe00EmbOutEmbedPair2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 2
					Right  cmdID= 37303
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37303 }


	iqdbe00EmbOutEmbedPair2LinkLRSelection OBJECT-TYPE
		SYNTAX		INTEGER { disable(0), enable(1) }
		MAX-ACCESS		read-write
		STATUS			current
		DESCRIPTION
				"TYPE: - Checkbox
				 PAGE: - Embed Pair 2
					Link L+R Selection  cmdID= 37391 "
		::= { iqdbe00CmdEntry 37391 }


	iqdbe00EmbOutEmbedPair3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 3
					Left  cmdID= 37304
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37304 }


	iqdbe00EmbOutEmbedPair3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 3
					Right  cmdID= 37305
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37305 }


	iqdbe00EmbOutEmbedPair3LinkLRSelection OBJECT-TYPE
		SYNTAX		INTEGER { disable(0), enable(1) }
		MAX-ACCESS		read-write
		STATUS			current
		DESCRIPTION
				"TYPE: - Checkbox
				 PAGE: - Embed Pair 3
					Link L+R Selection  cmdID= 37392 "
		::= { iqdbe00CmdEntry 37392 }


	iqdbe00EmbOutEmbedPair4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 4
					Left  cmdID= 37306
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37306 }


	iqdbe00EmbOutEmbedPair4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 4
					Right  cmdID= 37307
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37307 }


	iqdbe00EmbOutEmbedPair4LinkLRSelection OBJECT-TYPE
		SYNTAX		INTEGER { disable(0), enable(1) }
		MAX-ACCESS		read-write
		STATUS			current
		DESCRIPTION
				"TYPE: - Checkbox
				 PAGE: - Embed Pair 4
					Link L+R Selection  cmdID= 37393 "
		::= { iqdbe00CmdEntry 37393 }


	iqdbe00EmbOutEmbedPair5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 5
					Left  cmdID= 37308
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37308 }


	iqdbe00EmbOutEmbedPair5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 5
					Right  cmdID= 37309
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37309 }


	iqdbe00EmbOutEmbedPair5LinkLRSelection OBJECT-TYPE
		SYNTAX		INTEGER { disable(0), enable(1) }
		MAX-ACCESS		read-write
		STATUS			current
		DESCRIPTION
				"TYPE: - Checkbox
				 PAGE: - Embed Pair 5
					Link L+R Selection  cmdID= 37394 "
		::= { iqdbe00CmdEntry 37394 }


	iqdbe00EmbOutEmbedPair6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 6
					Left  cmdID= 37310
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37310 }


	iqdbe00EmbOutEmbedPair6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 6
					Right  cmdID= 37311
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37311 }


	iqdbe00EmbOutEmbedPair6LinkLRSelection OBJECT-TYPE
		SYNTAX		INTEGER { disable(0), enable(1) }
		MAX-ACCESS		read-write
		STATUS			current
		DESCRIPTION
				"TYPE: - Checkbox
				 PAGE: - Embed Pair 6
					Link L+R Selection  cmdID= 37395 "
		::= { iqdbe00CmdEntry 37395 }


	iqdbe00EmbOutEmbedPair7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 7
					Left  cmdID= 37312
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37312 }


	iqdbe00EmbOutEmbedPair7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 7
					Right  cmdID= 37313
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37313 }


	iqdbe00EmbOutEmbedPair7LinkLRSelection OBJECT-TYPE
		SYNTAX		INTEGER { disable(0), enable(1) }
		MAX-ACCESS		read-write
		STATUS			current
		DESCRIPTION
				"TYPE: - Checkbox
				 PAGE: - Embed Pair 7
					Link L+R Selection  cmdID= 37396 "
		::= { iqdbe00CmdEntry 37396 }


	iqdbe00EmbOutEmbedPair8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 8
					Left  cmdID= 37314
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37314 }


	iqdbe00EmbOutEmbedPair8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Embed Pair 8
					Right  cmdID= 37315
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37315 }


	iqdbe00EmbOutEmbedPair8LinkLRSelection OBJECT-TYPE
		SYNTAX		INTEGER { disable(0), enable(1) }
		MAX-ACCESS		read-write
		STATUS			current
		DESCRIPTION
				"TYPE: - Checkbox
				 PAGE: - Embed Pair 8
					Link L+R Selection  cmdID= 37397 "
		::= { iqdbe00CmdEntry 37397 }


	iqdbe00AudioEmbModeInput1 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 1  cmdID= 37420
					PCM  value= 0
					Data  value= 1
					Mixed  value= 2  "
		::= { iqdbe00CmdEntry 37420 }


	iqdbe00AudioEmbModeInput2 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 2  cmdID= 37421
					PCM  value= 0
					Data  value= 1
					Mixed  value= 2  "
		::= { iqdbe00CmdEntry 37421 }


	iqdbe00AudioEmbModeInput3 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 3  cmdID= 37422
					PCM  value= 0
					Data  value= 1
					Mixed  value= 2  "
		::= { iqdbe00CmdEntry 37422 }


	iqdbe00AudioEmbModeInput4 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 4  cmdID= 37423
					PCM  value= 0
					Data  value= 1
					Mixed  value= 2  "
		::= { iqdbe00CmdEntry 37423 }


	iqdbe00AudioEmbModeInput5 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 5  cmdID= 37424
					PCM  value= 0
					Data  value= 1
					Mixed  value= 2  "
		::= { iqdbe00CmdEntry 37424 }


	iqdbe00AudioEmbModeInput6 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 6  cmdID= 37425
					PCM  value= 0
					Data  value= 1
					Mixed  value= 2  "
		::= { iqdbe00CmdEntry 37425 }


	iqdbe00AudioEmbModeInput7 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 7  cmdID= 37426
					PCM  value= 0
					Data  value= 1
					Mixed  value= 2  "
		::= { iqdbe00CmdEntry 37426 }


	iqdbe00AudioEmbModeInput8 OBJECT-TYPE
		SYNTAX		INTEGER {
							val_PCM(0),
							val_Data(1),
							val_Mixed(2)
							}
		MAX-ACCESS		read-write
		STATUS			current
		DESCRIPTION
				"TYPE: - RadiobuttonList
				 PAGE: - Emb.Mode
					Input 8  cmdID= 37427
					PCM  value= 0
					Data  value= 1
					Mixed  value= 2  "
		::= { iqdbe00CmdEntry 37427 }


	iqdbe00EmbNamesDisembederNamesDisembed1 OBJECT-TYPE
		SYNTAX		RollCallString
		MAX-ACCESS		read-write
		STATUS			current
		DESCRIPTION
				"TYPE: - Editstring
				 PAGE: - Emb.Names
					Disembed 1  cmdID= 37500  "
		::= { iqdbe00CmdEntry 37500 }


	iqdbe00EmbNamesDisembederNamesDisembed1R OBJECT-TYPE
		SYNTAX		RollCallString
		MAX-ACCESS		read-write
		STATUS			current
		DESCRIPTION
				"TYPE: - Editstring
				 PAGE: - Emb.Names
					Disembed 1-R  cmdID= 37501  "
		::= { iqdbe00CmdEntry 37501 }


	iqdbe00EmbNamesDisembederNamesDisembed2 OBJECT-TYPE
		SYNTAX		RollCallString
		MAX-ACCESS		read-write
		STATUS			current
		DESCRIPTION
				"TYPE: - Editstring
				 PAGE: - Emb.Names
					Disembed 2  cmdID= 37502  "
		::= { iqdbe00CmdEntry 37502 }


	iqdbe00EmbNamesDisembederNamesDisembed2R OBJECT-TYPE
		SYNTAX		RollCallString
		MAX-ACCESS		read-write
		STATUS			current
		DESCRIPTION
				"TYPE: - Editstring
				 PAGE: - Emb.Names
					Disembed 2-R  cmdID= 37503  "
		::= { iqdbe00CmdEntry 37503 }


	iqdbe00EmbNamesDisembederNamesDisembed3 OBJECT-TYPE
		SYNTAX		RollCallString
		MAX-ACCESS		read-write
		STATUS			current
		DESCRIPTION
				"TYPE: - Editstring
				 PAGE: - Emb.Names
					Disembed 3  cmdID= 37504  "
		::= { iqdbe00CmdEntry 37504 }


	iqdbe00EmbNamesDisembederNamesDisembed3R OBJECT-TYPE
		SYNTAX		RollCallString
		MAX-ACCESS		read-write
		STATUS			current
		DESCRIPTION
				"TYPE: - Editstring
				 PAGE: - Emb.Names
					Disembed 3-R  cmdID= 37505  "
		::= { iqdbe00CmdEntry 37505 }


	iqdbe00EmbNamesDisembederNamesDisembed4 OBJECT-TYPE
		SYNTAX		RollCallString
		MAX-ACCESS		read-write
		STATUS			current
		DESCRIPTION
				"TYPE: - Editstring
				 PAGE: - Emb.Names
					Disembed 4  cmdID= 37506  "
		::= { iqdbe00CmdEntry 37506 }


	iqdbe00EmbNamesDisembederNamesDisembed4R OBJECT-TYPE
		SYNTAX		RollCallString
		MAX-ACCESS		read-write
		STATUS			current
		DESCRIPTION
				"TYPE: - Editstring
				 PAGE: - Emb.Names
					Disembed 4-R  cmdID= 37507  "
		::= { iqdbe00CmdEntry 37507 }


	iqdbe00EmbNamesDisembederNamesDisembed5 OBJECT-TYPE
		SYNTAX		RollCallString
		MAX-ACCESS		read-write
		STATUS			current
		DESCRIPTION
				"TYPE: - Editstring
				 PAGE: - Emb.Names
					Disembed 5  cmdID= 37508  "
		::= { iqdbe00CmdEntry 37508 }


	iqdbe00EmbNamesDisembederNamesDisembed5R OBJECT-TYPE
		SYNTAX		RollCallString
		MAX-ACCESS		read-write
		STATUS			current
		DESCRIPTION
				"TYPE: - Editstring
				 PAGE: - Emb.Names
					Disembed 5-R  cmdID= 37509  "
		::= { iqdbe00CmdEntry 37509 }


	iqdbe00EmbNamesDisembederNamesDisembed6 OBJECT-TYPE
		SYNTAX		RollCallString
		MAX-ACCESS		read-write
		STATUS			current
		DESCRIPTION
				"TYPE: - Editstring
				 PAGE: - Emb.Names
					Disembed 6  cmdID= 37510  "
		::= { iqdbe00CmdEntry 37510 }


	iqdbe00EmbNamesDisembederNamesDisembed6R OBJECT-TYPE
		SYNTAX		RollCallString
		MAX-ACCESS		read-write
		STATUS			current
		DESCRIPTION
				"TYPE: - Editstring
				 PAGE: - Emb.Names
					Disembed 6-R  cmdID= 37511  "
		::= { iqdbe00CmdEntry 37511 }


	iqdbe00EmbNamesDisembederNamesDisembed7 OBJECT-TYPE
		SYNTAX		RollCallString
		MAX-ACCESS		read-write
		STATUS			current
		DESCRIPTION
				"TYPE: - Editstring
				 PAGE: - Emb.Names
					Disembed 7  cmdID= 37512  "
		::= { iqdbe00CmdEntry 37512 }


	iqdbe00EmbNamesDisembederNamesDisembed7R OBJECT-TYPE
		SYNTAX		RollCallString
		MAX-ACCESS		read-write
		STATUS			current
		DESCRIPTION
				"TYPE: - Editstring
				 PAGE: - Emb.Names
					Disembed 7-R  cmdID= 37513  "
		::= { iqdbe00CmdEntry 37513 }


	iqdbe00EmbNamesDisembederNamesDisembed8 OBJECT-TYPE
		SYNTAX		RollCallString
		MAX-ACCESS		read-write
		STATUS			current
		DESCRIPTION
				"TYPE: - Editstring
				 PAGE: - Emb.Names
					Disembed 8  cmdID= 37514  "
		::= { iqdbe00CmdEntry 37514 }


	iqdbe00EmbNamesDisembederNamesDisembed8R OBJECT-TYPE
		SYNTAX		RollCallString
		MAX-ACCESS		read-write
		STATUS			current
		DESCRIPTION
				"TYPE: - Editstring
				 PAGE: - Emb.Names
					Disembed 8-R  cmdID= 37515  "
		::= { iqdbe00CmdEntry 37515 }


	iqdbe00EmbNamesEmbeddedOPNamesEmbed1 OBJECT-TYPE
		SYNTAX		RollCallString
		MAX-ACCESS		read-write
		STATUS			current
		DESCRIPTION
				"TYPE: - Editstring
				 PAGE: - Emb.Names
					Embed 1  cmdID= 37520  "
		::= { iqdbe00CmdEntry 37520 }


	iqdbe00EmbNamesEmbeddedOPNamesEmbed1R OBJECT-TYPE
		SYNTAX		RollCallString
		MAX-ACCESS		read-write
		STATUS			current
		DESCRIPTION
				"TYPE: - Editstring
				 PAGE: - Emb.Names
					Embed 1-R  cmdID= 37521  "
		::= { iqdbe00CmdEntry 37521 }


	iqdbe00EmbNamesEmbeddedOPNamesEmbed2 OBJECT-TYPE
		SYNTAX		RollCallString
		MAX-ACCESS		read-write
		STATUS			current
		DESCRIPTION
				"TYPE: - Editstring
				 PAGE: - Emb.Names
					Embed 2  cmdID= 37522  "
		::= { iqdbe00CmdEntry 37522 }


	iqdbe00EmbNamesEmbeddedOPNamesEmbed2R OBJECT-TYPE
		SYNTAX		RollCallString
		MAX-ACCESS		read-write
		STATUS			current
		DESCRIPTION
				"TYPE: - Editstring
				 PAGE: - Emb.Names
					Embed 2-R  cmdID= 37523  "
		::= { iqdbe00CmdEntry 37523 }


	iqdbe00EmbNamesEmbeddedOPNamesEmbed3 OBJECT-TYPE
		SYNTAX		RollCallString
		MAX-ACCESS		read-write
		STATUS			current
		DESCRIPTION
				"TYPE: - Editstring
				 PAGE: - Emb.Names
					Embed 3  cmdID= 37524  "
		::= { iqdbe00CmdEntry 37524 }


	iqdbe00EmbNamesEmbeddedOPNamesEmbed3R OBJECT-TYPE
		SYNTAX		RollCallString
		MAX-ACCESS		read-write
		STATUS			current
		DESCRIPTION
				"TYPE: - Editstring
				 PAGE: - Emb.Names
					Embed 3-R  cmdID= 37525  "
		::= { iqdbe00CmdEntry 37525 }


	iqdbe00EmbNamesEmbeddedOPNamesEmbed4 OBJECT-TYPE
		SYNTAX		RollCallString
		MAX-ACCESS		read-write
		STATUS			current
		DESCRIPTION
				"TYPE: - Editstring
				 PAGE: - Emb.Names
					Embed 4  cmdID= 37526  "
		::= { iqdbe00CmdEntry 37526 }


	iqdbe00EmbNamesEmbeddedOPNamesEmbed4R OBJECT-TYPE
		SYNTAX		RollCallString
		MAX-ACCESS		read-write
		STATUS			current
		DESCRIPTION
				"TYPE: - Editstring
				 PAGE: - Emb.Names
					Embed 4-R  cmdID= 37527  "
		::= { iqdbe00CmdEntry 37527 }


	iqdbe00EmbNamesEmbeddedOPNamesEmbed5 OBJECT-TYPE
		SYNTAX		RollCallString
		MAX-ACCESS		read-write
		STATUS			current
		DESCRIPTION
				"TYPE: - Editstring
				 PAGE: - Emb.Names
					Embed 5  cmdID= 37528  "
		::= { iqdbe00CmdEntry 37528 }


	iqdbe00EmbNamesEmbeddedOPNamesEmbed5R OBJECT-TYPE
		SYNTAX		RollCallString
		MAX-ACCESS		read-write
		STATUS			current
		DESCRIPTION
				"TYPE: - Editstring
				 PAGE: - Emb.Names
					Embed 5-R  cmdID= 37529  "
		::= { iqdbe00CmdEntry 37529 }


	iqdbe00EmbNamesEmbeddedOPNamesEmbed6 OBJECT-TYPE
		SYNTAX		RollCallString
		MAX-ACCESS		read-write
		STATUS			current
		DESCRIPTION
				"TYPE: - Editstring
				 PAGE: - Emb.Names
					Embed 6  cmdID= 37530  "
		::= { iqdbe00CmdEntry 37530 }


	iqdbe00EmbNamesEmbeddedOPNamesEmbed6R OBJECT-TYPE
		SYNTAX		RollCallString
		MAX-ACCESS		read-write
		STATUS			current
		DESCRIPTION
				"TYPE: - Editstring
				 PAGE: - Emb.Names
					Embed 6-R  cmdID= 37531  "
		::= { iqdbe00CmdEntry 37531 }


	iqdbe00EmbNamesEmbeddedOPNamesEmbed7 OBJECT-TYPE
		SYNTAX		RollCallString
		MAX-ACCESS		read-write
		STATUS			current
		DESCRIPTION
				"TYPE: - Editstring
				 PAGE: - Emb.Names
					Embed 7  cmdID= 37532  "
		::= { iqdbe00CmdEntry 37532 }


	iqdbe00EmbNamesEmbeddedOPNamesEmbed7R OBJECT-TYPE
		SYNTAX		RollCallString
		MAX-ACCESS		read-write
		STATUS			current
		DESCRIPTION
				"TYPE: - Editstring
				 PAGE: - Emb.Names
					Embed 7-R  cmdID= 37533  "
		::= { iqdbe00CmdEntry 37533 }


	iqdbe00EmbNamesEmbeddedOPNamesEmbed8 OBJECT-TYPE
		SYNTAX		RollCallString
		MAX-ACCESS		read-write
		STATUS			current
		DESCRIPTION
				"TYPE: - Editstring
				 PAGE: - Emb.Names
					Embed 8  cmdID= 37534  "
		::= { iqdbe00CmdEntry 37534 }


	iqdbe00EmbNamesEmbeddedOPNamesEmbed8R OBJECT-TYPE
		SYNTAX		RollCallString
		MAX-ACCESS		read-write
		STATUS			current
		DESCRIPTION
				"TYPE: - Editstring
				 PAGE: - Emb.Names
					Embed 8-R  cmdID= 37535  "
		::= { iqdbe00CmdEntry 37535 }


	iqdbe00EmbNamesIPNamesStereoDisemb1 OBJECT-TYPE
		SYNTAX		INTEGER { disable(0), enable(1) }
		MAX-ACCESS		read-write
		STATUS			current
		DESCRIPTION
				"TYPE: - Checkbox
				 PAGE: - Emb.Names
					Disemb 1  cmdID= 37400 "
		::= { iqdbe00CmdEntry 37400 }


	iqdbe00EmbNamesIPNamesStereoDisemb2 OBJECT-TYPE
		SYNTAX		INTEGER { disable(0), enable(1) }
		MAX-ACCESS		read-write
		STATUS			current
		DESCRIPTION
				"TYPE: - Checkbox
				 PAGE: - Emb.Names
					Disemb 2  cmdID= 37401 "
		::= { iqdbe00CmdEntry 37401 }


	iqdbe00EmbNamesIPNamesStereoDisemb3 OBJECT-TYPE
		SYNTAX		INTEGER { disable(0), enable(1) }
		MAX-ACCESS		read-write
		STATUS			current
		DESCRIPTION
				"TYPE: - Checkbox
				 PAGE: - Emb.Names
					Disemb 3  cmdID= 37402 "
		::= { iqdbe00CmdEntry 37402 }


	iqdbe00EmbNamesIPNamesStereoDisemb4 OBJECT-TYPE
		SYNTAX		INTEGER { disable(0), enable(1) }
		MAX-ACCESS		read-write
		STATUS			current
		DESCRIPTION
				"TYPE: - Checkbox
				 PAGE: - Emb.Names
					Disemb 4  cmdID= 37403 "
		::= { iqdbe00CmdEntry 37403 }


	iqdbe00EmbNamesIPNamesStereoDisemb5 OBJECT-TYPE
		SYNTAX		INTEGER { disable(0), enable(1) }
		MAX-ACCESS		read-write
		STATUS			current
		DESCRIPTION
				"TYPE: - Checkbox
				 PAGE: - Emb.Names
					Disemb 5  cmdID= 37404 "
		::= { iqdbe00CmdEntry 37404 }


	iqdbe00EmbNamesIPNamesStereoDisemb6 OBJECT-TYPE
		SYNTAX		INTEGER { disable(0), enable(1) }
		MAX-ACCESS		read-write
		STATUS			current
		DESCRIPTION
				"TYPE: - Checkbox
				 PAGE: - Emb.Names
					Disemb 6  cmdID= 37405 "
		::= { iqdbe00CmdEntry 37405 }


	iqdbe00EmbNamesIPNamesStereoDisemb7 OBJECT-TYPE
		SYNTAX		INTEGER { disable(0), enable(1) }
		MAX-ACCESS		read-write
		STATUS			current
		DESCRIPTION
				"TYPE: - Checkbox
				 PAGE: - Emb.Names
					Disemb 7  cmdID= 37406 "
		::= { iqdbe00CmdEntry 37406 }


	iqdbe00EmbNamesIPNamesStereoDisemb8 OBJECT-TYPE
		SYNTAX		INTEGER { disable(0), enable(1) }
		MAX-ACCESS		read-write
		STATUS			current
		DESCRIPTION
				"TYPE: - Checkbox
				 PAGE: - Emb.Names
					Disemb 8  cmdID= 37407 "
		::= { iqdbe00CmdEntry 37407 }


	iqdbe00EmbNamesOPNamesStereoEmbed1 OBJECT-TYPE
		SYNTAX		INTEGER { disable(0), enable(1) }
		MAX-ACCESS		read-write
		STATUS			current
		DESCRIPTION
				"TYPE: - Checkbox
				 PAGE: - Emb.Names
					Embed 1  cmdID= 37410 "
		::= { iqdbe00CmdEntry 37410 }


	iqdbe00EmbNamesOPNamesStereoEmbed2 OBJECT-TYPE
		SYNTAX		INTEGER { disable(0), enable(1) }
		MAX-ACCESS		read-write
		STATUS			current
		DESCRIPTION
				"TYPE: - Checkbox
				 PAGE: - Emb.Names
					Embed 2  cmdID= 37411 "
		::= { iqdbe00CmdEntry 37411 }


	iqdbe00EmbNamesOPNamesStereoEmbed3 OBJECT-TYPE
		SYNTAX		INTEGER { disable(0), enable(1) }
		MAX-ACCESS		read-write
		STATUS			current
		DESCRIPTION
				"TYPE: - Checkbox
				 PAGE: - Emb.Names
					Embed 3  cmdID= 37412 "
		::= { iqdbe00CmdEntry 37412 }


	iqdbe00EmbNamesOPNamesStereoEmbed4 OBJECT-TYPE
		SYNTAX		INTEGER { disable(0), enable(1) }
		MAX-ACCESS		read-write
		STATUS			current
		DESCRIPTION
				"TYPE: - Checkbox
				 PAGE: - Emb.Names
					Embed 4  cmdID= 37413 "
		::= { iqdbe00CmdEntry 37413 }


	iqdbe00EmbNamesOPNamesStereoEmbed5 OBJECT-TYPE
		SYNTAX		INTEGER { disable(0), enable(1) }
		MAX-ACCESS		read-write
		STATUS			current
		DESCRIPTION
				"TYPE: - Checkbox
				 PAGE: - Emb.Names
					Embed 5  cmdID= 37414 "
		::= { iqdbe00CmdEntry 37414 }


	iqdbe00EmbNamesOPNamesStereoEmbed6 OBJECT-TYPE
		SYNTAX		INTEGER { disable(0), enable(1) }
		MAX-ACCESS		read-write
		STATUS			current
		DESCRIPTION
				"TYPE: - Checkbox
				 PAGE: - Emb.Names
					Embed 6  cmdID= 37415 "
		::= { iqdbe00CmdEntry 37415 }


	iqdbe00EmbNamesOPNamesStereoEmbed7 OBJECT-TYPE
		SYNTAX		INTEGER { disable(0), enable(1) }
		MAX-ACCESS		read-write
		STATUS			current
		DESCRIPTION
				"TYPE: - Checkbox
				 PAGE: - Emb.Names
					Embed 7  cmdID= 37416 "
		::= { iqdbe00CmdEntry 37416 }


	iqdbe00EmbNamesOPNamesStereoEmbed8 OBJECT-TYPE
		SYNTAX		INTEGER { disable(0), enable(1) }
		MAX-ACCESS		read-write
		STATUS			current
		DESCRIPTION
				"TYPE: - Checkbox
				 PAGE: - Emb.Names
					Embed 8  cmdID= 37417 "
		::= { iqdbe00CmdEntry 37417 }


	iqdbe00AudioMixNamesMix1 OBJECT-TYPE
		SYNTAX		RollCallString
		MAX-ACCESS		read-write
		STATUS			current
		DESCRIPTION
				"TYPE: - Editstring
					Mix 1  cmdID= 37810  "
		::= { iqdbe00CmdEntry 37810 }


	iqdbe00AudioMixNamesMix2 OBJECT-TYPE
		SYNTAX		RollCallString
		MAX-ACCESS		read-write
		STATUS			current
		DESCRIPTION
				"TYPE: - Editstring
					Mix 2  cmdID= 37811  "
		::= { iqdbe00CmdEntry 37811 }


	iqdbe00AudioMixNamesMix3 OBJECT-TYPE
		SYNTAX		RollCallString
		MAX-ACCESS		read-write
		STATUS			current
		DESCRIPTION
				"TYPE: - Editstring
					Mix 3  cmdID= 37812  "
		::= { iqdbe00CmdEntry 37812 }


	iqdbe00AudioMixNamesMix4 OBJECT-TYPE
		SYNTAX		RollCallString
		MAX-ACCESS		read-write
		STATUS			current
		DESCRIPTION
				"TYPE: - Editstring
					Mix 4  cmdID= 37813  "
		::= { iqdbe00CmdEntry 37813 }


	iqdbe00Mix1RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 1  cmdID= 37600
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37600 }


	iqdbe00Mix1RoutingInvert1 OBJECT-TYPE
		SYNTAX		INTEGER { disable(0), enable(1) }
		MAX-ACCESS		read-write
		STATUS			current
		DESCRIPTION
				"TYPE: - Checkbox
				 PAGE: - Mix 1
					Invert 1  cmdID= 37720 "
		::= { iqdbe00CmdEntry 37720 }


	iqdbe00Mix1RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 2  cmdID= 37601
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37601 }


	iqdbe00Mix1RoutingInvert2 OBJECT-TYPE
		SYNTAX		INTEGER { disable(0), enable(1) }
		MAX-ACCESS		read-write
		STATUS			current
		DESCRIPTION
				"TYPE: - Checkbox
				 PAGE: - Mix 1
					Invert 2  cmdID= 37721 "
		::= { iqdbe00CmdEntry 37721 }


	iqdbe00Mix1RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 3  cmdID= 37602
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37602 }


	iqdbe00Mix1RoutingInvert3 OBJECT-TYPE
		SYNTAX		INTEGER { disable(0), enable(1) }
		MAX-ACCESS		read-write
		STATUS			current
		DESCRIPTION
				"TYPE: - Checkbox
				 PAGE: - Mix 1
					Invert 3  cmdID= 37722 "
		::= { iqdbe00CmdEntry 37722 }


	iqdbe00Mix1RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 1
					Source 4  cmdID= 37603
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37603 }


	iqdbe00Mix1RoutingInvert4 OBJECT-TYPE
		SYNTAX		INTEGER { disable(0), enable(1) }
		MAX-ACCESS		read-write
		STATUS			current
		DESCRIPTION
				"TYPE: - Checkbox
				 PAGE: - Mix 1
					Invert 4  cmdID= 37723 "
		::= { iqdbe00CmdEntry 37723 }


	iqdbe00Mix1GainGain1 OBJECT-TYPE
		SYNTAX		INTEGER
		MAX-ACCESS		read-write
		STATUS			current
		DESCRIPTION
				"TYPE: - Number
				 PAGE: - Mix 1
					Gain 1  cmdID= 37640  min= -360  max= 120  step= 1  format= %0.1f dB  div_scale= 10
					Min = -36.0 dB  Max = 12.0 dB  Step = 0.1 dB "
		::= { iqdbe00CmdEntry 37640 }


	iqdbe00Mix1GainMute1 OBJECT-TYPE
		SYNTAX		INTEGER { disable(0), enable(1) }
		MAX-ACCESS		read-write
		STATUS			current
		DESCRIPTION
				"TYPE: - Checkbox
				 PAGE: - Mix 1
					Mute 1  cmdID= 37680 "
		::= { iqdbe00CmdEntry 37680 }


	iqdbe00Mix1GainGain2 OBJECT-TYPE
		SYNTAX		INTEGER
		MAX-ACCESS		read-write
		STATUS			current
		DESCRIPTION
				"TYPE: - Number
				 PAGE: - Mix 1
					Gain 2  cmdID= 37641  min= -360  max= 120  step= 1  format= %0.1f dB  div_scale= 10
					Min = -36.0 dB  Max = 12.0 dB  Step = 0.1 dB "
		::= { iqdbe00CmdEntry 37641 }


	iqdbe00Mix1GainMute2 OBJECT-TYPE
		SYNTAX		INTEGER { disable(0), enable(1) }
		MAX-ACCESS		read-write
		STATUS			current
		DESCRIPTION
				"TYPE: - Checkbox
				 PAGE: - Mix 1
					Mute 2  cmdID= 37681 "
		::= { iqdbe00CmdEntry 37681 }


	iqdbe00Mix1GainGain3 OBJECT-TYPE
		SYNTAX		INTEGER
		MAX-ACCESS		read-write
		STATUS			current
		DESCRIPTION
				"TYPE: - Number
				 PAGE: - Mix 1
					Gain 3  cmdID= 37642  min= -360  max= 120  step= 1  format= %0.1f dB  div_scale= 10
					Min = -36.0 dB  Max = 12.0 dB  Step = 0.1 dB "
		::= { iqdbe00CmdEntry 37642 }


	iqdbe00Mix1GainMute3 OBJECT-TYPE
		SYNTAX		INTEGER { disable(0), enable(1) }
		MAX-ACCESS		read-write
		STATUS			current
		DESCRIPTION
				"TYPE: - Checkbox
				 PAGE: - Mix 1
					Mute 3  cmdID= 37682 "
		::= { iqdbe00CmdEntry 37682 }


	iqdbe00Mix1GainGain4 OBJECT-TYPE
		SYNTAX		INTEGER
		MAX-ACCESS		read-write
		STATUS			current
		DESCRIPTION
				"TYPE: - Number
				 PAGE: - Mix 1
					Gain 4  cmdID= 37643  min= -360  max= 120  step= 1  format= %0.1f dB  div_scale= 10
					Min = -36.0 dB  Max = 12.0 dB  Step = 0.1 dB "
		::= { iqdbe00CmdEntry 37643 }


	iqdbe00Mix1GainMute4 OBJECT-TYPE
		SYNTAX		INTEGER { disable(0), enable(1) }
		MAX-ACCESS		read-write
		STATUS			current
		DESCRIPTION
				"TYPE: - Checkbox
				 PAGE: - Mix 1
					Mute 4  cmdID= 37683 "
		::= { iqdbe00CmdEntry 37683 }


	iqdbe00Mix1GainInp1Clip OBJECT-TYPE
		SYNTAX		RollCallString
		MAX-ACCESS		read-only
		STATUS			current
		DESCRIPTION
				"TYPE: - Display
				 PAGE: - Mix 1
					Inp1 Clip  cmdID= 37760  format=   "
		::= { iqdbe00CmdEntry 37760 }


	iqdbe00Mix1GainInp2Clip OBJECT-TYPE
		SYNTAX		RollCallString
		MAX-ACCESS		read-only
		STATUS			current
		DESCRIPTION
				"TYPE: - Display
				 PAGE: - Mix 1
					Inp2 Clip  cmdID= 37761  format=   "
		::= { iqdbe00CmdEntry 37761 }


	iqdbe00Mix1GainInp3Clip OBJECT-TYPE
		SYNTAX		RollCallString
		MAX-ACCESS		read-only
		STATUS			current
		DESCRIPTION
				"TYPE: - Display
				 PAGE: - Mix 1
					Inp3 Clip  cmdID= 37762  format=   "
		::= { iqdbe00CmdEntry 37762 }


	iqdbe00Mix1GainInp4Clip OBJECT-TYPE
		SYNTAX		RollCallString
		MAX-ACCESS		read-only
		STATUS			current
		DESCRIPTION
				"TYPE: - Display
				 PAGE: - Mix 1
					Inp4 Clip  cmdID= 37763  format=   "
		::= { iqdbe00CmdEntry 37763 }


	iqdbe00Mix1GainOPClip OBJECT-TYPE
		SYNTAX		RollCallString
		MAX-ACCESS		read-only
		STATUS			current
		DESCRIPTION
				"TYPE: - Display
				 PAGE: - Mix 1
					O/P Clip  cmdID= 37800  format=   "
		::= { iqdbe00CmdEntry 37800 }


	iqdbe00Mix2RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 1  cmdID= 37604
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37604 }


	iqdbe00Mix2RoutingInvert1 OBJECT-TYPE
		SYNTAX		INTEGER { disable(0), enable(1) }
		MAX-ACCESS		read-write
		STATUS			current
		DESCRIPTION
				"TYPE: - Checkbox
				 PAGE: - Mix 2
					Invert 1  cmdID= 37724 "
		::= { iqdbe00CmdEntry 37724 }


	iqdbe00Mix2RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 2  cmdID= 37605
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37605 }


	iqdbe00Mix2RoutingInvert2 OBJECT-TYPE
		SYNTAX		INTEGER { disable(0), enable(1) }
		MAX-ACCESS		read-write
		STATUS			current
		DESCRIPTION
				"TYPE: - Checkbox
				 PAGE: - Mix 2
					Invert 2  cmdID= 37725 "
		::= { iqdbe00CmdEntry 37725 }


	iqdbe00Mix2RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 3  cmdID= 37606
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37606 }


	iqdbe00Mix2RoutingInvert3 OBJECT-TYPE
		SYNTAX		INTEGER { disable(0), enable(1) }
		MAX-ACCESS		read-write
		STATUS			current
		DESCRIPTION
				"TYPE: - Checkbox
				 PAGE: - Mix 2
					Invert 3  cmdID= 37726 "
		::= { iqdbe00CmdEntry 37726 }


	iqdbe00Mix2RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 2
					Source 4  cmdID= 37607
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37607 }


	iqdbe00Mix2RoutingInvert4 OBJECT-TYPE
		SYNTAX		INTEGER { disable(0), enable(1) }
		MAX-ACCESS		read-write
		STATUS			current
		DESCRIPTION
				"TYPE: - Checkbox
				 PAGE: - Mix 2
					Invert 4  cmdID= 37727 "
		::= { iqdbe00CmdEntry 37727 }


	iqdbe00Mix2GainGain1 OBJECT-TYPE
		SYNTAX		INTEGER
		MAX-ACCESS		read-write
		STATUS			current
		DESCRIPTION
				"TYPE: - Number
				 PAGE: - Mix 2
					Gain 1  cmdID= 37644  min= -360  max= 120  step= 1  format= %0.1f dB  div_scale= 10
					Min = -36.0 dB  Max = 12.0 dB  Step = 0.1 dB "
		::= { iqdbe00CmdEntry 37644 }


	iqdbe00Mix2GainMute1 OBJECT-TYPE
		SYNTAX		INTEGER { disable(0), enable(1) }
		MAX-ACCESS		read-write
		STATUS			current
		DESCRIPTION
				"TYPE: - Checkbox
				 PAGE: - Mix 2
					Mute 1  cmdID= 37684 "
		::= { iqdbe00CmdEntry 37684 }


	iqdbe00Mix2GainGain2 OBJECT-TYPE
		SYNTAX		INTEGER
		MAX-ACCESS		read-write
		STATUS			current
		DESCRIPTION
				"TYPE: - Number
				 PAGE: - Mix 2
					Gain 2  cmdID= 37645  min= -360  max= 120  step= 1  format= %0.1f dB  div_scale= 10
					Min = -36.0 dB  Max = 12.0 dB  Step = 0.1 dB "
		::= { iqdbe00CmdEntry 37645 }


	iqdbe00Mix2GainMute2 OBJECT-TYPE
		SYNTAX		INTEGER { disable(0), enable(1) }
		MAX-ACCESS		read-write
		STATUS			current
		DESCRIPTION
				"TYPE: - Checkbox
				 PAGE: - Mix 2
					Mute 2  cmdID= 37685 "
		::= { iqdbe00CmdEntry 37685 }


	iqdbe00Mix2GainGain3 OBJECT-TYPE
		SYNTAX		INTEGER
		MAX-ACCESS		read-write
		STATUS			current
		DESCRIPTION
				"TYPE: - Number
				 PAGE: - Mix 2
					Gain 3  cmdID= 37646  min= -360  max= 120  step= 1  format= %0.1f dB  div_scale= 10
					Min = -36.0 dB  Max = 12.0 dB  Step = 0.1 dB "
		::= { iqdbe00CmdEntry 37646 }


	iqdbe00Mix2GainMute3 OBJECT-TYPE
		SYNTAX		INTEGER { disable(0), enable(1) }
		MAX-ACCESS		read-write
		STATUS			current
		DESCRIPTION
				"TYPE: - Checkbox
				 PAGE: - Mix 2
					Mute 3  cmdID= 37686 "
		::= { iqdbe00CmdEntry 37686 }


	iqdbe00Mix2GainGain4 OBJECT-TYPE
		SYNTAX		INTEGER
		MAX-ACCESS		read-write
		STATUS			current
		DESCRIPTION
				"TYPE: - Number
				 PAGE: - Mix 2
					Gain 4  cmdID= 37647  min= -360  max= 120  step= 1  format= %0.1f dB  div_scale= 10
					Min = -36.0 dB  Max = 12.0 dB  Step = 0.1 dB "
		::= { iqdbe00CmdEntry 37647 }


	iqdbe00Mix2GainMute4 OBJECT-TYPE
		SYNTAX		INTEGER { disable(0), enable(1) }
		MAX-ACCESS		read-write
		STATUS			current
		DESCRIPTION
				"TYPE: - Checkbox
				 PAGE: - Mix 2
					Mute 4  cmdID= 37687 "
		::= { iqdbe00CmdEntry 37687 }


	iqdbe00Mix2GainInp1Clip OBJECT-TYPE
		SYNTAX		RollCallString
		MAX-ACCESS		read-only
		STATUS			current
		DESCRIPTION
				"TYPE: - Display
				 PAGE: - Mix 2
					Inp1 Clip  cmdID= 37764  format=   "
		::= { iqdbe00CmdEntry 37764 }


	iqdbe00Mix2GainInp2Clip OBJECT-TYPE
		SYNTAX		RollCallString
		MAX-ACCESS		read-only
		STATUS			current
		DESCRIPTION
				"TYPE: - Display
				 PAGE: - Mix 2
					Inp2 Clip  cmdID= 37765  format=   "
		::= { iqdbe00CmdEntry 37765 }


	iqdbe00Mix2GainInp3Clip OBJECT-TYPE
		SYNTAX		RollCallString
		MAX-ACCESS		read-only
		STATUS			current
		DESCRIPTION
				"TYPE: - Display
				 PAGE: - Mix 2
					Inp3 Clip  cmdID= 37766  format=   "
		::= { iqdbe00CmdEntry 37766 }


	iqdbe00Mix2GainInp4Clip OBJECT-TYPE
		SYNTAX		RollCallString
		MAX-ACCESS		read-only
		STATUS			current
		DESCRIPTION
				"TYPE: - Display
				 PAGE: - Mix 2
					Inp4 Clip  cmdID= 37767  format=   "
		::= { iqdbe00CmdEntry 37767 }


	iqdbe00Mix2GainOPClip OBJECT-TYPE
		SYNTAX		RollCallString
		MAX-ACCESS		read-only
		STATUS			current
		DESCRIPTION
				"TYPE: - Display
				 PAGE: - Mix 2
					O/P Clip  cmdID= 37801  format=   "
		::= { iqdbe00CmdEntry 37801 }


	iqdbe00Mix3RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 1  cmdID= 37608
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37608 }


	iqdbe00Mix3RoutingInvert1 OBJECT-TYPE
		SYNTAX		INTEGER { disable(0), enable(1) }
		MAX-ACCESS		read-write
		STATUS			current
		DESCRIPTION
				"TYPE: - Checkbox
				 PAGE: - Mix 3
					Invert 1  cmdID= 37728 "
		::= { iqdbe00CmdEntry 37728 }


	iqdbe00Mix3RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 2  cmdID= 37609
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37609 }


	iqdbe00Mix3RoutingInvert2 OBJECT-TYPE
		SYNTAX		INTEGER { disable(0), enable(1) }
		MAX-ACCESS		read-write
		STATUS			current
		DESCRIPTION
				"TYPE: - Checkbox
				 PAGE: - Mix 3
					Invert 2  cmdID= 37729 "
		::= { iqdbe00CmdEntry 37729 }


	iqdbe00Mix3RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 3  cmdID= 37610
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37610 }


	iqdbe00Mix3RoutingInvert3 OBJECT-TYPE
		SYNTAX		INTEGER { disable(0), enable(1) }
		MAX-ACCESS		read-write
		STATUS			current
		DESCRIPTION
				"TYPE: - Checkbox
				 PAGE: - Mix 3
					Invert 3  cmdID= 37730 "
		::= { iqdbe00CmdEntry 37730 }


	iqdbe00Mix3RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 3
					Source 4  cmdID= 37611
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37611 }


	iqdbe00Mix3RoutingInvert4 OBJECT-TYPE
		SYNTAX		INTEGER { disable(0), enable(1) }
		MAX-ACCESS		read-write
		STATUS			current
		DESCRIPTION
				"TYPE: - Checkbox
				 PAGE: - Mix 3
					Invert 4  cmdID= 37731 "
		::= { iqdbe00CmdEntry 37731 }


	iqdbe00Mix3GainGain1 OBJECT-TYPE
		SYNTAX		INTEGER
		MAX-ACCESS		read-write
		STATUS			current
		DESCRIPTION
				"TYPE: - Number
				 PAGE: - Mix 3
					Gain 1  cmdID= 37648  min= -360  max= 120  step= 1  format= %0.1f dB  div_scale= 10
					Min = -36.0 dB  Max = 12.0 dB  Step = 0.1 dB "
		::= { iqdbe00CmdEntry 37648 }


	iqdbe00Mix3GainMute1 OBJECT-TYPE
		SYNTAX		INTEGER { disable(0), enable(1) }
		MAX-ACCESS		read-write
		STATUS			current
		DESCRIPTION
				"TYPE: - Checkbox
				 PAGE: - Mix 3
					Mute 1  cmdID= 37688 "
		::= { iqdbe00CmdEntry 37688 }


	iqdbe00Mix3GainGain2 OBJECT-TYPE
		SYNTAX		INTEGER
		MAX-ACCESS		read-write
		STATUS			current
		DESCRIPTION
				"TYPE: - Number
				 PAGE: - Mix 3
					Gain 2  cmdID= 37649  min= -360  max= 120  step= 1  format= %0.1f dB  div_scale= 10
					Min = -36.0 dB  Max = 12.0 dB  Step = 0.1 dB "
		::= { iqdbe00CmdEntry 37649 }


	iqdbe00Mix3GainMute2 OBJECT-TYPE
		SYNTAX		INTEGER { disable(0), enable(1) }
		MAX-ACCESS		read-write
		STATUS			current
		DESCRIPTION
				"TYPE: - Checkbox
				 PAGE: - Mix 3
					Mute 2  cmdID= 37689 "
		::= { iqdbe00CmdEntry 37689 }


	iqdbe00Mix3GainGain3 OBJECT-TYPE
		SYNTAX		INTEGER
		MAX-ACCESS		read-write
		STATUS			current
		DESCRIPTION
				"TYPE: - Number
				 PAGE: - Mix 3
					Gain 3  cmdID= 37650  min= -360  max= 120  step= 1  format= %0.1f dB  div_scale= 10
					Min = -36.0 dB  Max = 12.0 dB  Step = 0.1 dB "
		::= { iqdbe00CmdEntry 37650 }


	iqdbe00Mix3GainMute3 OBJECT-TYPE
		SYNTAX		INTEGER { disable(0), enable(1) }
		MAX-ACCESS		read-write
		STATUS			current
		DESCRIPTION
				"TYPE: - Checkbox
				 PAGE: - Mix 3
					Mute 3  cmdID= 37690 "
		::= { iqdbe00CmdEntry 37690 }


	iqdbe00Mix3GainGain4 OBJECT-TYPE
		SYNTAX		INTEGER
		MAX-ACCESS		read-write
		STATUS			current
		DESCRIPTION
				"TYPE: - Number
				 PAGE: - Mix 3
					Gain 4  cmdID= 37651  min= -360  max= 120  step= 1  format= %0.1f dB  div_scale= 10
					Min = -36.0 dB  Max = 12.0 dB  Step = 0.1 dB "
		::= { iqdbe00CmdEntry 37651 }


	iqdbe00Mix3GainMute4 OBJECT-TYPE
		SYNTAX		INTEGER { disable(0), enable(1) }
		MAX-ACCESS		read-write
		STATUS			current
		DESCRIPTION
				"TYPE: - Checkbox
				 PAGE: - Mix 3
					Mute 4  cmdID= 37691 "
		::= { iqdbe00CmdEntry 37691 }


	iqdbe00Mix3GainInp1Clip OBJECT-TYPE
		SYNTAX		RollCallString
		MAX-ACCESS		read-only
		STATUS			current
		DESCRIPTION
				"TYPE: - Display
				 PAGE: - Mix 3
					Inp1 Clip  cmdID= 37768  format=   "
		::= { iqdbe00CmdEntry 37768 }


	iqdbe00Mix3GainInp2Clip OBJECT-TYPE
		SYNTAX		RollCallString
		MAX-ACCESS		read-only
		STATUS			current
		DESCRIPTION
				"TYPE: - Display
				 PAGE: - Mix 3
					Inp2 Clip  cmdID= 37769  format=   "
		::= { iqdbe00CmdEntry 37769 }


	iqdbe00Mix3GainInp3Clip OBJECT-TYPE
		SYNTAX		RollCallString
		MAX-ACCESS		read-only
		STATUS			current
		DESCRIPTION
				"TYPE: - Display
				 PAGE: - Mix 3
					Inp3 Clip  cmdID= 37770  format=   "
		::= { iqdbe00CmdEntry 37770 }


	iqdbe00Mix3GainInp4Clip OBJECT-TYPE
		SYNTAX		RollCallString
		MAX-ACCESS		read-only
		STATUS			current
		DESCRIPTION
				"TYPE: - Display
				 PAGE: - Mix 3
					Inp4 Clip  cmdID= 37771  format=   "
		::= { iqdbe00CmdEntry 37771 }


	iqdbe00Mix3GainOPClip OBJECT-TYPE
		SYNTAX		RollCallString
		MAX-ACCESS		read-only
		STATUS			current
		DESCRIPTION
				"TYPE: - Display
				 PAGE: - Mix 3
					O/P Clip  cmdID= 37802  format=   "
		::= { iqdbe00CmdEntry 37802 }


	iqdbe00Mix4RoutingSource1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 1  cmdID= 37612
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37612 }


	iqdbe00Mix4RoutingInvert1 OBJECT-TYPE
		SYNTAX		INTEGER { disable(0), enable(1) }
		MAX-ACCESS		read-write
		STATUS			current
		DESCRIPTION
				"TYPE: - Checkbox
				 PAGE: - Mix 4
					Invert 1  cmdID= 37732 "
		::= { iqdbe00CmdEntry 37732 }


	iqdbe00Mix4RoutingSource2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 2  cmdID= 37613
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37613 }


	iqdbe00Mix4RoutingInvert2 OBJECT-TYPE
		SYNTAX		INTEGER { disable(0), enable(1) }
		MAX-ACCESS		read-write
		STATUS			current
		DESCRIPTION
				"TYPE: - Checkbox
				 PAGE: - Mix 4
					Invert 2  cmdID= 37733 "
		::= { iqdbe00CmdEntry 37733 }


	iqdbe00Mix4RoutingSource3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 3  cmdID= 37614
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37614 }


	iqdbe00Mix4RoutingInvert3 OBJECT-TYPE
		SYNTAX		INTEGER { disable(0), enable(1) }
		MAX-ACCESS		read-write
		STATUS			current
		DESCRIPTION
				"TYPE: - Checkbox
				 PAGE: - Mix 4
					Invert 3  cmdID= 37734 "
		::= { iqdbe00CmdEntry 37734 }


	iqdbe00Mix4RoutingSource4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Mix 4
					Source 4  cmdID= 37615
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 37615 }


	iqdbe00Mix4RoutingInvert4 OBJECT-TYPE
		SYNTAX		INTEGER { disable(0), enable(1) }
		MAX-ACCESS		read-write
		STATUS			current
		DESCRIPTION
				"TYPE: - Checkbox
				 PAGE: - Mix 4
					Invert 4  cmdID= 37735 "
		::= { iqdbe00CmdEntry 37735 }


	iqdbe00Mix4GainGain1 OBJECT-TYPE
		SYNTAX		INTEGER
		MAX-ACCESS		read-write
		STATUS			current
		DESCRIPTION
				"TYPE: - Number
				 PAGE: - Mix 4
					Gain 1  cmdID= 37652  min= -360  max= 120  step= 1  format= %0.1f dB  div_scale= 10
					Min = -36.0 dB  Max = 12.0 dB  Step = 0.1 dB "
		::= { iqdbe00CmdEntry 37652 }


	iqdbe00Mix4GainMute1 OBJECT-TYPE
		SYNTAX		INTEGER { disable(0), enable(1) }
		MAX-ACCESS		read-write
		STATUS			current
		DESCRIPTION
				"TYPE: - Checkbox
				 PAGE: - Mix 4
					Mute 1  cmdID= 37692 "
		::= { iqdbe00CmdEntry 37692 }


	iqdbe00Mix4GainGain2 OBJECT-TYPE
		SYNTAX		INTEGER
		MAX-ACCESS		read-write
		STATUS			current
		DESCRIPTION
				"TYPE: - Number
				 PAGE: - Mix 4
					Gain 2  cmdID= 37653  min= -360  max= 120  step= 1  format= %0.1f dB  div_scale= 10
					Min = -36.0 dB  Max = 12.0 dB  Step = 0.1 dB "
		::= { iqdbe00CmdEntry 37653 }


	iqdbe00Mix4GainMute2 OBJECT-TYPE
		SYNTAX		INTEGER { disable(0), enable(1) }
		MAX-ACCESS		read-write
		STATUS			current
		DESCRIPTION
				"TYPE: - Checkbox
				 PAGE: - Mix 4
					Mute 2  cmdID= 37693 "
		::= { iqdbe00CmdEntry 37693 }


	iqdbe00Mix4GainGain3 OBJECT-TYPE
		SYNTAX		INTEGER
		MAX-ACCESS		read-write
		STATUS			current
		DESCRIPTION
				"TYPE: - Number
				 PAGE: - Mix 4
					Gain 3  cmdID= 37654  min= -360  max= 120  step= 1  format= %0.1f dB  div_scale= 10
					Min = -36.0 dB  Max = 12.0 dB  Step = 0.1 dB "
		::= { iqdbe00CmdEntry 37654 }


	iqdbe00Mix4GainMute3 OBJECT-TYPE
		SYNTAX		INTEGER { disable(0), enable(1) }
		MAX-ACCESS		read-write
		STATUS			current
		DESCRIPTION
				"TYPE: - Checkbox
				 PAGE: - Mix 4
					Mute 3  cmdID= 37694 "
		::= { iqdbe00CmdEntry 37694 }


	iqdbe00Mix4GainGain4 OBJECT-TYPE
		SYNTAX		INTEGER
		MAX-ACCESS		read-write
		STATUS			current
		DESCRIPTION
				"TYPE: - Number
				 PAGE: - Mix 4
					Gain 4  cmdID= 37655  min= -360  max= 120  step= 1  format= %0.1f dB  div_scale= 10
					Min = -36.0 dB  Max = 12.0 dB  Step = 0.1 dB "
		::= { iqdbe00CmdEntry 37655 }


	iqdbe00Mix4GainMute4 OBJECT-TYPE
		SYNTAX		INTEGER { disable(0), enable(1) }
		MAX-ACCESS		read-write
		STATUS			current
		DESCRIPTION
				"TYPE: - Checkbox
				 PAGE: - Mix 4
					Mute 4  cmdID= 37695 "
		::= { iqdbe00CmdEntry 37695 }


	iqdbe00Mix4GainInp1Clip OBJECT-TYPE
		SYNTAX		RollCallString
		MAX-ACCESS		read-only
		STATUS			current
		DESCRIPTION
				"TYPE: - Display
				 PAGE: - Mix 4
					Inp1 Clip  cmdID= 37772  format=   "
		::= { iqdbe00CmdEntry 37772 }


	iqdbe00Mix4GainInp2Clip OBJECT-TYPE
		SYNTAX		RollCallString
		MAX-ACCESS		read-only
		STATUS			current
		DESCRIPTION
				"TYPE: - Display
				 PAGE: - Mix 4
					Inp2 Clip  cmdID= 37773  format=   "
		::= { iqdbe00CmdEntry 37773 }


	iqdbe00Mix4GainInp3Clip OBJECT-TYPE
		SYNTAX		RollCallString
		MAX-ACCESS		read-only
		STATUS			current
		DESCRIPTION
				"TYPE: - Display
				 PAGE: - Mix 4
					Inp3 Clip  cmdID= 37774  format=   "
		::= { iqdbe00CmdEntry 37774 }


	iqdbe00Mix4GainInp4Clip OBJECT-TYPE
		SYNTAX		RollCallString
		MAX-ACCESS		read-only
		STATUS			current
		DESCRIPTION
				"TYPE: - Display
				 PAGE: - Mix 4
					Inp4 Clip  cmdID= 37775  format=   "
		::= { iqdbe00CmdEntry 37775 }


	iqdbe00Mix4GainOPClip OBJECT-TYPE
		SYNTAX		RollCallString
		MAX-ACCESS		read-only
		STATUS			current
		DESCRIPTION
				"TYPE: - Display
				 PAGE: - Mix 4
					O/P Clip  cmdID= 37803  format=   "
		::= { iqdbe00CmdEntry 37803 }


	iqdbe00AESGainAESOut1AESOut1MuteL OBJECT-TYPE
		SYNTAX		INTEGER { disable(0), enable(1) }
		MAX-ACCESS		read-write
		STATUS			current
		DESCRIPTION
				"TYPE: - Checkbox
				 PAGE: - AES Ports- AES Gain
					AES Out 1 Mute L  cmdID= 38280 "
		::= { iqdbe00CmdEntry 38280 }


	iqdbe00AESGainAESOut1AESOut1MuteR OBJECT-TYPE
		SYNTAX		INTEGER { disable(0), enable(1) }
		MAX-ACCESS		read-write
		STATUS			current
		DESCRIPTION
				"TYPE: - Checkbox
				 PAGE: - AES Ports- AES Gain
					AES Out 1 Mute R  cmdID= 38281 "
		::= { iqdbe00CmdEntry 38281 }


	iqdbe00AESGainAESOut1AESOut1LGain OBJECT-TYPE
		SYNTAX		INTEGER
		MAX-ACCESS		read-write
		STATUS			current
		DESCRIPTION
				"TYPE: - Number
				 PAGE: - AES Ports- AES Gain
					AES Out 1 L Gain  cmdID= 38240  min= -661  max= 120  step= 1  format= %0.1f dB  div_scale= 10
					Min = -66.1 dB  Max = 12.0 dB  Step = 0.1 dB "
		::= { iqdbe00CmdEntry 38240 }


	iqdbe00AESGainAESOut1AESOut1RGain OBJECT-TYPE
		SYNTAX		INTEGER
		MAX-ACCESS		read-write
		STATUS			current
		DESCRIPTION
				"TYPE: - Number
				 PAGE: - AES Ports- AES Gain
					AES Out 1 R Gain  cmdID= 38241  min= -661  max= 120  step= 1  format= %0.1f dB  div_scale= 10
					Min = -66.1 dB  Max = 12.0 dB  Step = 0.1 dB "
		::= { iqdbe00CmdEntry 38241 }


	iqdbe00AESGainAESOut1Stereo OBJECT-TYPE
		SYNTAX		INTEGER { disable(0), enable(1) }
		MAX-ACCESS		read-write
		STATUS			current
		DESCRIPTION
				"TYPE: - Checkbox
				 PAGE: - AES Ports- AES Gain
					Stereo  cmdID= 38360 "
		::= { iqdbe00CmdEntry 38360 }


	iqdbe00AESGainAESOut1AESOut1InvertL OBJECT-TYPE
		SYNTAX		INTEGER { disable(0), enable(1) }
		MAX-ACCESS		read-write
		STATUS			current
		DESCRIPTION
				"TYPE: - Checkbox
				 PAGE: - AES Ports- AES Gain
					AES Out 1 Invert L  cmdID= 38320 "
		::= { iqdbe00CmdEntry 38320 }


	iqdbe00AESGainAESOut1AESOut1InvertR OBJECT-TYPE
		SYNTAX		INTEGER { disable(0), enable(1) }
		MAX-ACCESS		read-write
		STATUS			current
		DESCRIPTION
				"TYPE: - Checkbox
				 PAGE: - AES Ports- AES Gain
					AES Out 1 Invert R  cmdID= 38321 "
		::= { iqdbe00CmdEntry 38321 }


	iqdbe00AESGainAESOut1AESOut1LClip OBJECT-TYPE
		SYNTAX		RollCallString
		MAX-ACCESS		read-only
		STATUS			current
		DESCRIPTION
				"TYPE: - Display
				 PAGE: - AES Ports- AES Gain
					AES Out 1-L Clip  cmdID= 38520  format=   "
		::= { iqdbe00CmdEntry 38520 }


	iqdbe00AESGainAESOut1AESOut1RClip OBJECT-TYPE
		SYNTAX		RollCallString
		MAX-ACCESS		read-only
		STATUS			current
		DESCRIPTION
				"TYPE: - Display
				 PAGE: - AES Ports- AES Gain
					AES Out 1-R Clip  cmdID= 38521  format=   "
		::= { iqdbe00CmdEntry 38521 }


	iqdbe00AESGainAESOut2AESOut2MuteL OBJECT-TYPE
		SYNTAX		INTEGER { disable(0), enable(1) }
		MAX-ACCESS		read-write
		STATUS			current
		DESCRIPTION
				"TYPE: - Checkbox
				 PAGE: - AES Ports- AES Gain
					AES Out 2 Mute L  cmdID= 38282 "
		::= { iqdbe00CmdEntry 38282 }


	iqdbe00AESGainAESOut2AESOut2MuteR OBJECT-TYPE
		SYNTAX		INTEGER { disable(0), enable(1) }
		MAX-ACCESS		read-write
		STATUS			current
		DESCRIPTION
				"TYPE: - Checkbox
				 PAGE: - AES Ports- AES Gain
					AES Out 2 Mute R  cmdID= 38283 "
		::= { iqdbe00CmdEntry 38283 }


	iqdbe00AESGainAESOut2AESOut2LGain OBJECT-TYPE
		SYNTAX		INTEGER
		MAX-ACCESS		read-write
		STATUS			current
		DESCRIPTION
				"TYPE: - Number
				 PAGE: - AES Ports- AES Gain
					AES Out 2 L Gain  cmdID= 38242  min= -661  max= 120  step= 1  format= %0.1f dB  div_scale= 10
					Min = -66.1 dB  Max = 12.0 dB  Step = 0.1 dB "
		::= { iqdbe00CmdEntry 38242 }


	iqdbe00AESGainAESOut2AESOut2RGain OBJECT-TYPE
		SYNTAX		INTEGER
		MAX-ACCESS		read-write
		STATUS			current
		DESCRIPTION
				"TYPE: - Number
				 PAGE: - AES Ports- AES Gain
					AES Out 2 R Gain  cmdID= 38243  min= -661  max= 120  step= 1  format= %0.1f dB  div_scale= 10
					Min = -66.1 dB  Max = 12.0 dB  Step = 0.1 dB "
		::= { iqdbe00CmdEntry 38243 }


	iqdbe00AESGainAESOut2Stereo OBJECT-TYPE
		SYNTAX		INTEGER { disable(0), enable(1) }
		MAX-ACCESS		read-write
		STATUS			current
		DESCRIPTION
				"TYPE: - Checkbox
				 PAGE: - AES Ports- AES Gain
					Stereo  cmdID= 38361 "
		::= { iqdbe00CmdEntry 38361 }


	iqdbe00AESGainAESOut2AESOut2InvertL OBJECT-TYPE
		SYNTAX		INTEGER { disable(0), enable(1) }
		MAX-ACCESS		read-write
		STATUS			current
		DESCRIPTION
				"TYPE: - Checkbox
				 PAGE: - AES Ports- AES Gain
					AES Out 2 Invert L  cmdID= 38322 "
		::= { iqdbe00CmdEntry 38322 }


	iqdbe00AESGainAESOut2AESOut2InvertR OBJECT-TYPE
		SYNTAX		INTEGER { disable(0), enable(1) }
		MAX-ACCESS		read-write
		STATUS			current
		DESCRIPTION
				"TYPE: - Checkbox
				 PAGE: - AES Ports- AES Gain
					AES Out 2 Invert R  cmdID= 38323 "
		::= { iqdbe00CmdEntry 38323 }


	iqdbe00AESGainAESOut2AESOut2LClip OBJECT-TYPE
		SYNTAX		RollCallString
		MAX-ACCESS		read-only
		STATUS			current
		DESCRIPTION
				"TYPE: - Display
				 PAGE: - AES Ports- AES Gain
					AES Out 2-L Clip  cmdID= 38522  format=   "
		::= { iqdbe00CmdEntry 38522 }


	iqdbe00AESGainAESOut2AESOut2RClip OBJECT-TYPE
		SYNTAX		RollCallString
		MAX-ACCESS		read-only
		STATUS			current
		DESCRIPTION
				"TYPE: - Display
				 PAGE: - AES Ports- AES Gain
					AES Out 2-R Clip  cmdID= 38523  format=   "
		::= { iqdbe00CmdEntry 38523 }


	iqdbe00AESGainAESOut3AESOut3MuteL OBJECT-TYPE
		SYNTAX		INTEGER { disable(0), enable(1) }
		MAX-ACCESS		read-write
		STATUS			current
		DESCRIPTION
				"TYPE: - Checkbox
				 PAGE: - AES Ports- AES Gain
					AES Out 3 Mute L  cmdID= 38284 "
		::= { iqdbe00CmdEntry 38284 }


	iqdbe00AESGainAESOut3AESOut3MuteR OBJECT-TYPE
		SYNTAX		INTEGER { disable(0), enable(1) }
		MAX-ACCESS		read-write
		STATUS			current
		DESCRIPTION
				"TYPE: - Checkbox
				 PAGE: - AES Ports- AES Gain
					AES Out 3 Mute R  cmdID= 38285 "
		::= { iqdbe00CmdEntry 38285 }


	iqdbe00AESGainAESOut3AESOut3LGain OBJECT-TYPE
		SYNTAX		INTEGER
		MAX-ACCESS		read-write
		STATUS			current
		DESCRIPTION
				"TYPE: - Number
				 PAGE: - AES Ports- AES Gain
					AES Out 3 L Gain  cmdID= 38244  min= -661  max= 120  step= 1  format= %0.1f dB  div_scale= 10
					Min = -66.1 dB  Max = 12.0 dB  Step = 0.1 dB "
		::= { iqdbe00CmdEntry 38244 }


	iqdbe00AESGainAESOut3AESOut3RGain OBJECT-TYPE
		SYNTAX		INTEGER
		MAX-ACCESS		read-write
		STATUS			current
		DESCRIPTION
				"TYPE: - Number
				 PAGE: - AES Ports- AES Gain
					AES Out 3 R Gain  cmdID= 38245  min= -661  max= 120  step= 1  format= %0.1f dB  div_scale= 10
					Min = -66.1 dB  Max = 12.0 dB  Step = 0.1 dB "
		::= { iqdbe00CmdEntry 38245 }


	iqdbe00AESGainAESOut3Stereo OBJECT-TYPE
		SYNTAX		INTEGER { disable(0), enable(1) }
		MAX-ACCESS		read-write
		STATUS			current
		DESCRIPTION
				"TYPE: - Checkbox
				 PAGE: - AES Ports- AES Gain
					Stereo  cmdID= 38362 "
		::= { iqdbe00CmdEntry 38362 }


	iqdbe00AESGainAESOut3AESOut3InvertL OBJECT-TYPE
		SYNTAX		INTEGER { disable(0), enable(1) }
		MAX-ACCESS		read-write
		STATUS			current
		DESCRIPTION
				"TYPE: - Checkbox
				 PAGE: - AES Ports- AES Gain
					AES Out 3 Invert L  cmdID= 38324 "
		::= { iqdbe00CmdEntry 38324 }


	iqdbe00AESGainAESOut3AESOut3InvertR OBJECT-TYPE
		SYNTAX		INTEGER { disable(0), enable(1) }
		MAX-ACCESS		read-write
		STATUS			current
		DESCRIPTION
				"TYPE: - Checkbox
				 PAGE: - AES Ports- AES Gain
					AES Out 3 Invert R  cmdID= 38325 "
		::= { iqdbe00CmdEntry 38325 }


	iqdbe00AESGainAESOut3AESOut3LClip OBJECT-TYPE
		SYNTAX		RollCallString
		MAX-ACCESS		read-only
		STATUS			current
		DESCRIPTION
				"TYPE: - Display
				 PAGE: - AES Ports- AES Gain
					AES Out 3-L Clip  cmdID= 38524  format=   "
		::= { iqdbe00CmdEntry 38524 }


	iqdbe00AESGainAESOut3AESOut3RClip OBJECT-TYPE
		SYNTAX		RollCallString
		MAX-ACCESS		read-only
		STATUS			current
		DESCRIPTION
				"TYPE: - Display
				 PAGE: - AES Ports- AES Gain
					AES Out 3-R Clip  cmdID= 38525  format=   "
		::= { iqdbe00CmdEntry 38525 }


	iqdbe00AESGainAESOut4AESOut4MuteL OBJECT-TYPE
		SYNTAX		INTEGER { disable(0), enable(1) }
		MAX-ACCESS		read-write
		STATUS			current
		DESCRIPTION
				"TYPE: - Checkbox
				 PAGE: - AES Ports- AES Gain
					AES Out 4 Mute L  cmdID= 38286 "
		::= { iqdbe00CmdEntry 38286 }


	iqdbe00AESGainAESOut4AESOut4MuteR OBJECT-TYPE
		SYNTAX		INTEGER { disable(0), enable(1) }
		MAX-ACCESS		read-write
		STATUS			current
		DESCRIPTION
				"TYPE: - Checkbox
				 PAGE: - AES Ports- AES Gain
					AES Out 4 Mute R  cmdID= 38287 "
		::= { iqdbe00CmdEntry 38287 }


	iqdbe00AESGainAESOut4AESOut4LGain OBJECT-TYPE
		SYNTAX		INTEGER
		MAX-ACCESS		read-write
		STATUS			current
		DESCRIPTION
				"TYPE: - Number
				 PAGE: - AES Ports- AES Gain
					AES Out 4 L Gain  cmdID= 38246  min= -661  max= 120  step= 1  format= %0.1f dB  div_scale= 10
					Min = -66.1 dB  Max = 12.0 dB  Step = 0.1 dB "
		::= { iqdbe00CmdEntry 38246 }


	iqdbe00AESGainAESOut4AESOut4RGain OBJECT-TYPE
		SYNTAX		INTEGER
		MAX-ACCESS		read-write
		STATUS			current
		DESCRIPTION
				"TYPE: - Number
				 PAGE: - AES Ports- AES Gain
					AES Out 4 R Gain  cmdID= 38247  min= -661  max= 120  step= 1  format= %0.1f dB  div_scale= 10
					Min = -66.1 dB  Max = 12.0 dB  Step = 0.1 dB "
		::= { iqdbe00CmdEntry 38247 }


	iqdbe00AESGainAESOut4Stereo OBJECT-TYPE
		SYNTAX		INTEGER { disable(0), enable(1) }
		MAX-ACCESS		read-write
		STATUS			current
		DESCRIPTION
				"TYPE: - Checkbox
				 PAGE: - AES Ports- AES Gain
					Stereo  cmdID= 38363 "
		::= { iqdbe00CmdEntry 38363 }


	iqdbe00AESGainAESOut4AESOut4InvertL OBJECT-TYPE
		SYNTAX		INTEGER { disable(0), enable(1) }
		MAX-ACCESS		read-write
		STATUS			current
		DESCRIPTION
				"TYPE: - Checkbox
				 PAGE: - AES Ports- AES Gain
					AES Out 4 Invert L  cmdID= 38326 "
		::= { iqdbe00CmdEntry 38326 }


	iqdbe00AESGainAESOut4AESOut4InvertR OBJECT-TYPE
		SYNTAX		INTEGER { disable(0), enable(1) }
		MAX-ACCESS		read-write
		STATUS			current
		DESCRIPTION
				"TYPE: - Checkbox
				 PAGE: - AES Ports- AES Gain
					AES Out 4 Invert R  cmdID= 38327 "
		::= { iqdbe00CmdEntry 38327 }


	iqdbe00AESGainAESOut4AESOut4LClip OBJECT-TYPE
		SYNTAX		RollCallString
		MAX-ACCESS		read-only
		STATUS			current
		DESCRIPTION
				"TYPE: - Display
				 PAGE: - AES Ports- AES Gain
					AES Out 4-L Clip  cmdID= 38526  format=   "
		::= { iqdbe00CmdEntry 38526 }


	iqdbe00AESGainAESOut4AESOut4RClip OBJECT-TYPE
		SYNTAX		RollCallString
		MAX-ACCESS		read-only
		STATUS			current
		DESCRIPTION
				"TYPE: - Display
				 PAGE: - AES Ports- AES Gain
					AES Out 4-R Clip  cmdID= 38527  format=   "
		::= { iqdbe00CmdEntry 38527 }


	iqdbe00AESGainAESOut5AESOut5MuteL OBJECT-TYPE
		SYNTAX		INTEGER { disable(0), enable(1) }
		MAX-ACCESS		read-write
		STATUS			current
		DESCRIPTION
				"TYPE: - Checkbox
				 PAGE: - AES Ports- AES Gain
					AES Out 5 Mute L  cmdID= 38288 "
		::= { iqdbe00CmdEntry 38288 }


	iqdbe00AESGainAESOut5AESOut5MuteR OBJECT-TYPE
		SYNTAX		INTEGER { disable(0), enable(1) }
		MAX-ACCESS		read-write
		STATUS			current
		DESCRIPTION
				"TYPE: - Checkbox
				 PAGE: - AES Ports- AES Gain
					AES Out 5 Mute R  cmdID= 38289 "
		::= { iqdbe00CmdEntry 38289 }


	iqdbe00AESGainAESOut5AESOut5LGain OBJECT-TYPE
		SYNTAX		INTEGER
		MAX-ACCESS		read-write
		STATUS			current
		DESCRIPTION
				"TYPE: - Number
				 PAGE: - AES Ports- AES Gain
					AES Out 5 L Gain  cmdID= 38248  min= -661  max= 120  step= 1  format= %0.1f dB  div_scale= 10
					Min = -66.1 dB  Max = 12.0 dB  Step = 0.1 dB "
		::= { iqdbe00CmdEntry 38248 }


	iqdbe00AESGainAESOut5AESOut5RGain OBJECT-TYPE
		SYNTAX		INTEGER
		MAX-ACCESS		read-write
		STATUS			current
		DESCRIPTION
				"TYPE: - Number
				 PAGE: - AES Ports- AES Gain
					AES Out 5 R Gain  cmdID= 38249  min= -661  max= 120  step= 1  format= %0.1f dB  div_scale= 10
					Min = -66.1 dB  Max = 12.0 dB  Step = 0.1 dB "
		::= { iqdbe00CmdEntry 38249 }


	iqdbe00AESGainAESOut5Stereo OBJECT-TYPE
		SYNTAX		INTEGER { disable(0), enable(1) }
		MAX-ACCESS		read-write
		STATUS			current
		DESCRIPTION
				"TYPE: - Checkbox
				 PAGE: - AES Ports- AES Gain
					Stereo  cmdID= 38364 "
		::= { iqdbe00CmdEntry 38364 }


	iqdbe00AESGainAESOut5AESOut5InvertL OBJECT-TYPE
		SYNTAX		INTEGER { disable(0), enable(1) }
		MAX-ACCESS		read-write
		STATUS			current
		DESCRIPTION
				"TYPE: - Checkbox
				 PAGE: - AES Ports- AES Gain
					AES Out 5 Invert L  cmdID= 38328 "
		::= { iqdbe00CmdEntry 38328 }


	iqdbe00AESGainAESOut5AESOut5InvertR OBJECT-TYPE
		SYNTAX		INTEGER { disable(0), enable(1) }
		MAX-ACCESS		read-write
		STATUS			current
		DESCRIPTION
				"TYPE: - Checkbox
				 PAGE: - AES Ports- AES Gain
					AES Out 5 Invert R  cmdID= 38329 "
		::= { iqdbe00CmdEntry 38329 }


	iqdbe00AESGainAESOut5AESOut5LClip OBJECT-TYPE
		SYNTAX		RollCallString
		MAX-ACCESS		read-only
		STATUS			current
		DESCRIPTION
				"TYPE: - Display
				 PAGE: - AES Ports- AES Gain
					AES Out 5-L Clip  cmdID= 38528  format=   "
		::= { iqdbe00CmdEntry 38528 }


	iqdbe00AESGainAESOut5AESOut5RClip OBJECT-TYPE
		SYNTAX		RollCallString
		MAX-ACCESS		read-only
		STATUS			current
		DESCRIPTION
				"TYPE: - Display
				 PAGE: - AES Ports- AES Gain
					AES Out 5-R Clip  cmdID= 38529  format=   "
		::= { iqdbe00CmdEntry 38529 }


	iqdbe00AESGainAESOut6AESOut6MuteL OBJECT-TYPE
		SYNTAX		INTEGER { disable(0), enable(1) }
		MAX-ACCESS		read-write
		STATUS			current
		DESCRIPTION
				"TYPE: - Checkbox
				 PAGE: - AES Ports- AES Gain
					AES Out 6 Mute L  cmdID= 38290 "
		::= { iqdbe00CmdEntry 38290 }


	iqdbe00AESGainAESOut6AESOut6MuteR OBJECT-TYPE
		SYNTAX		INTEGER { disable(0), enable(1) }
		MAX-ACCESS		read-write
		STATUS			current
		DESCRIPTION
				"TYPE: - Checkbox
				 PAGE: - AES Ports- AES Gain
					AES Out 6 Mute R  cmdID= 38291 "
		::= { iqdbe00CmdEntry 38291 }


	iqdbe00AESGainAESOut6AESOut6LGain OBJECT-TYPE
		SYNTAX		INTEGER
		MAX-ACCESS		read-write
		STATUS			current
		DESCRIPTION
				"TYPE: - Number
				 PAGE: - AES Ports- AES Gain
					AES Out 6 L Gain  cmdID= 38250  min= -661  max= 120  step= 1  format= %0.1f dB  div_scale= 10
					Min = -66.1 dB  Max = 12.0 dB  Step = 0.1 dB "
		::= { iqdbe00CmdEntry 38250 }


	iqdbe00AESGainAESOut6AESOut6RGain OBJECT-TYPE
		SYNTAX		INTEGER
		MAX-ACCESS		read-write
		STATUS			current
		DESCRIPTION
				"TYPE: - Number
				 PAGE: - AES Ports- AES Gain
					AES Out 6 R Gain  cmdID= 38251  min= -661  max= 120  step= 1  format= %0.1f dB  div_scale= 10
					Min = -66.1 dB  Max = 12.0 dB  Step = 0.1 dB "
		::= { iqdbe00CmdEntry 38251 }


	iqdbe00AESGainAESOut6Stereo OBJECT-TYPE
		SYNTAX		INTEGER { disable(0), enable(1) }
		MAX-ACCESS		read-write
		STATUS			current
		DESCRIPTION
				"TYPE: - Checkbox
				 PAGE: - AES Ports- AES Gain
					Stereo  cmdID= 38365 "
		::= { iqdbe00CmdEntry 38365 }


	iqdbe00AESGainAESOut6AESOut6InvertL OBJECT-TYPE
		SYNTAX		INTEGER { disable(0), enable(1) }
		MAX-ACCESS		read-write
		STATUS			current
		DESCRIPTION
				"TYPE: - Checkbox
				 PAGE: - AES Ports- AES Gain
					AES Out 6 Invert L  cmdID= 38330 "
		::= { iqdbe00CmdEntry 38330 }


	iqdbe00AESGainAESOut6AESOut6InvertR OBJECT-TYPE
		SYNTAX		INTEGER { disable(0), enable(1) }
		MAX-ACCESS		read-write
		STATUS			current
		DESCRIPTION
				"TYPE: - Checkbox
				 PAGE: - AES Ports- AES Gain
					AES Out 6 Invert R  cmdID= 38331 "
		::= { iqdbe00CmdEntry 38331 }


	iqdbe00AESGainAESOut6AESOut6LClip OBJECT-TYPE
		SYNTAX		RollCallString
		MAX-ACCESS		read-only
		STATUS			current
		DESCRIPTION
				"TYPE: - Display
				 PAGE: - AES Ports- AES Gain
					AES Out 6-L Clip  cmdID= 38530  format=   "
		::= { iqdbe00CmdEntry 38530 }


	iqdbe00AESGainAESOut6AESOut6RClip OBJECT-TYPE
		SYNTAX		RollCallString
		MAX-ACCESS		read-only
		STATUS			current
		DESCRIPTION
				"TYPE: - Display
				 PAGE: - AES Ports- AES Gain
					AES Out 6-R Clip  cmdID= 38531  format=   "
		::= { iqdbe00CmdEntry 38531 }


	iqdbe00AESGainAESOut7AESOut7MuteL OBJECT-TYPE
		SYNTAX		INTEGER { disable(0), enable(1) }
		MAX-ACCESS		read-write
		STATUS			current
		DESCRIPTION
				"TYPE: - Checkbox
				 PAGE: - AES Ports- AES Gain
					AES Out 7 Mute L  cmdID= 38292 "
		::= { iqdbe00CmdEntry 38292 }


	iqdbe00AESGainAESOut7AESOut7MuteR OBJECT-TYPE
		SYNTAX		INTEGER { disable(0), enable(1) }
		MAX-ACCESS		read-write
		STATUS			current
		DESCRIPTION
				"TYPE: - Checkbox
				 PAGE: - AES Ports- AES Gain
					AES Out 7 Mute R  cmdID= 38293 "
		::= { iqdbe00CmdEntry 38293 }


	iqdbe00AESGainAESOut7AESOut7LGain OBJECT-TYPE
		SYNTAX		INTEGER
		MAX-ACCESS		read-write
		STATUS			current
		DESCRIPTION
				"TYPE: - Number
				 PAGE: - AES Ports- AES Gain
					AES Out 7 L Gain  cmdID= 38252  min= -661  max= 120  step= 1  format= %0.1f dB  div_scale= 10
					Min = -66.1 dB  Max = 12.0 dB  Step = 0.1 dB "
		::= { iqdbe00CmdEntry 38252 }


	iqdbe00AESGainAESOut7AESOut7RGain OBJECT-TYPE
		SYNTAX		INTEGER
		MAX-ACCESS		read-write
		STATUS			current
		DESCRIPTION
				"TYPE: - Number
				 PAGE: - AES Ports- AES Gain
					AES Out 7 R Gain  cmdID= 38253  min= -661  max= 120  step= 1  format= %0.1f dB  div_scale= 10
					Min = -66.1 dB  Max = 12.0 dB  Step = 0.1 dB "
		::= { iqdbe00CmdEntry 38253 }


	iqdbe00AESGainAESOut7Stereo OBJECT-TYPE
		SYNTAX		INTEGER { disable(0), enable(1) }
		MAX-ACCESS		read-write
		STATUS			current
		DESCRIPTION
				"TYPE: - Checkbox
				 PAGE: - AES Ports- AES Gain
					Stereo  cmdID= 38366 "
		::= { iqdbe00CmdEntry 38366 }


	iqdbe00AESGainAESOut7AESOut7InvertL OBJECT-TYPE
		SYNTAX		INTEGER { disable(0), enable(1) }
		MAX-ACCESS		read-write
		STATUS			current
		DESCRIPTION
				"TYPE: - Checkbox
				 PAGE: - AES Ports- AES Gain
					AES Out 7 Invert L  cmdID= 38332 "
		::= { iqdbe00CmdEntry 38332 }


	iqdbe00AESGainAESOut7AESOut7InvertR OBJECT-TYPE
		SYNTAX		INTEGER { disable(0), enable(1) }
		MAX-ACCESS		read-write
		STATUS			current
		DESCRIPTION
				"TYPE: - Checkbox
				 PAGE: - AES Ports- AES Gain
					AES Out 7 Invert R  cmdID= 38333 "
		::= { iqdbe00CmdEntry 38333 }


	iqdbe00AESGainAESOut7AESOut7LClip OBJECT-TYPE
		SYNTAX		RollCallString
		MAX-ACCESS		read-only
		STATUS			current
		DESCRIPTION
				"TYPE: - Display
				 PAGE: - AES Ports- AES Gain
					AES Out 7-L Clip  cmdID= 38532  format=   "
		::= { iqdbe00CmdEntry 38532 }


	iqdbe00AESGainAESOut7AESOut7RClip OBJECT-TYPE
		SYNTAX		RollCallString
		MAX-ACCESS		read-only
		STATUS			current
		DESCRIPTION
				"TYPE: - Display
				 PAGE: - AES Ports- AES Gain
					AES Out 7-R Clip  cmdID= 38533  format=   "
		::= { iqdbe00CmdEntry 38533 }


	iqdbe00AESGainAESOut8AESOut8MuteL OBJECT-TYPE
		SYNTAX		INTEGER { disable(0), enable(1) }
		MAX-ACCESS		read-write
		STATUS			current
		DESCRIPTION
				"TYPE: - Checkbox
				 PAGE: - AES Ports- AES Gain
					AES Out 8 Mute L  cmdID= 38294 "
		::= { iqdbe00CmdEntry 38294 }


	iqdbe00AESGainAESOut8AESOut8MuteR OBJECT-TYPE
		SYNTAX		INTEGER { disable(0), enable(1) }
		MAX-ACCESS		read-write
		STATUS			current
		DESCRIPTION
				"TYPE: - Checkbox
				 PAGE: - AES Ports- AES Gain
					AES Out 8 Mute R  cmdID= 38295 "
		::= { iqdbe00CmdEntry 38295 }


	iqdbe00AESGainAESOut8AESOut8LGain OBJECT-TYPE
		SYNTAX		INTEGER
		MAX-ACCESS		read-write
		STATUS			current
		DESCRIPTION
				"TYPE: - Number
				 PAGE: - AES Ports- AES Gain
					AES Out 8 L Gain  cmdID= 38254  min= -661  max= 120  step= 1  format= %0.1f dB  div_scale= 10
					Min = -66.1 dB  Max = 12.0 dB  Step = 0.1 dB "
		::= { iqdbe00CmdEntry 38254 }


	iqdbe00AESGainAESOut8AESOut8RGain OBJECT-TYPE
		SYNTAX		INTEGER
		MAX-ACCESS		read-write
		STATUS			current
		DESCRIPTION
				"TYPE: - Number
				 PAGE: - AES Ports- AES Gain
					AES Out 8 R Gain  cmdID= 38255  min= -661  max= 120  step= 1  format= %0.1f dB  div_scale= 10
					Min = -66.1 dB  Max = 12.0 dB  Step = 0.1 dB "
		::= { iqdbe00CmdEntry 38255 }


	iqdbe00AESGainAESOut8Stereo OBJECT-TYPE
		SYNTAX		INTEGER { disable(0), enable(1) }
		MAX-ACCESS		read-write
		STATUS			current
		DESCRIPTION
				"TYPE: - Checkbox
				 PAGE: - AES Ports- AES Gain
					Stereo  cmdID= 38367 "
		::= { iqdbe00CmdEntry 38367 }


	iqdbe00AESGainAESOut8AESOut8InvertL OBJECT-TYPE
		SYNTAX		INTEGER { disable(0), enable(1) }
		MAX-ACCESS		read-write
		STATUS			current
		DESCRIPTION
				"TYPE: - Checkbox
				 PAGE: - AES Ports- AES Gain
					AES Out 8 Invert L  cmdID= 38334 "
		::= { iqdbe00CmdEntry 38334 }


	iqdbe00AESGainAESOut8AESOut8InvertR OBJECT-TYPE
		SYNTAX		INTEGER { disable(0), enable(1) }
		MAX-ACCESS		read-write
		STATUS			current
		DESCRIPTION
				"TYPE: - Checkbox
				 PAGE: - AES Ports- AES Gain
					AES Out 8 Invert R  cmdID= 38335 "
		::= { iqdbe00CmdEntry 38335 }


	iqdbe00AESGainAESOut8AESOut8LClip OBJECT-TYPE
		SYNTAX		RollCallString
		MAX-ACCESS		read-only
		STATUS			current
		DESCRIPTION
				"TYPE: - Display
				 PAGE: - AES Ports- AES Gain
					AES Out 8-L Clip  cmdID= 38534  format=   "
		::= { iqdbe00CmdEntry 38534 }


	iqdbe00AESGainAESOut8AESOut8RClip OBJECT-TYPE
		SYNTAX		RollCallString
		MAX-ACCESS		read-only
		STATUS			current
		DESCRIPTION
				"TYPE: - Display
				 PAGE: - AES Ports- AES Gain
					AES Out 8-R Clip  cmdID= 38535  format=   "
		::= { iqdbe00CmdEntry 38535 }


	iqdbe00AESOutAESOut1Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 1
					Left  cmdID= 38200
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38200 }


	iqdbe00AESOutAESOut1Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 1
					Right  cmdID= 38201
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38201 }


	iqdbe00AESOutAESOut1LinkLRSelection OBJECT-TYPE
		SYNTAX		INTEGER { disable(0), enable(1) }
		MAX-ACCESS		read-write
		STATUS			current
		DESCRIPTION
				"TYPE: - Checkbox
				 PAGE: - AES Ports- AES Out 1
					Link L+R Selection  cmdID= 38380 "
		::= { iqdbe00CmdEntry 38380 }


	iqdbe00AESOutAESOut2Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 2
					Left  cmdID= 38202
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38202 }


	iqdbe00AESOutAESOut2Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 2
					Right  cmdID= 38203
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38203 }


	iqdbe00AESOutAESOut2LinkLRSelection OBJECT-TYPE
		SYNTAX		INTEGER { disable(0), enable(1) }
		MAX-ACCESS		read-write
		STATUS			current
		DESCRIPTION
				"TYPE: - Checkbox
				 PAGE: - AES Ports- AES Out 2
					Link L+R Selection  cmdID= 38381 "
		::= { iqdbe00CmdEntry 38381 }


	iqdbe00AESOutAESOut3Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 3
					Left  cmdID= 38204
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38204 }


	iqdbe00AESOutAESOut3Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 3
					Right  cmdID= 38205
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38205 }


	iqdbe00AESOutAESOut3LinkLRSelection OBJECT-TYPE
		SYNTAX		INTEGER { disable(0), enable(1) }
		MAX-ACCESS		read-write
		STATUS			current
		DESCRIPTION
				"TYPE: - Checkbox
				 PAGE: - AES Ports- AES Out 3
					Link L+R Selection  cmdID= 38382 "
		::= { iqdbe00CmdEntry 38382 }


	iqdbe00AESOutAESOut4Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 4
					Left  cmdID= 38206
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38206 }


	iqdbe00AESOutAESOut4Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 4
					Right  cmdID= 38207
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38207 }


	iqdbe00AESOutAESOut4LinkLRSelection OBJECT-TYPE
		SYNTAX		INTEGER { disable(0), enable(1) }
		MAX-ACCESS		read-write
		STATUS			current
		DESCRIPTION
				"TYPE: - Checkbox
				 PAGE: - AES Ports- AES Out 4
					Link L+R Selection  cmdID= 38383 "
		::= { iqdbe00CmdEntry 38383 }


	iqdbe00AESOutAESOut5Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 5
					Left  cmdID= 38208
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38208 }


	iqdbe00AESOutAESOut5Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 5
					Right  cmdID= 38209
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38209 }


	iqdbe00AESOutAESOut5LinkLRSelection OBJECT-TYPE
		SYNTAX		INTEGER { disable(0), enable(1) }
		MAX-ACCESS		read-write
		STATUS			current
		DESCRIPTION
				"TYPE: - Checkbox
				 PAGE: - AES Ports- AES Out 5
					Link L+R Selection  cmdID= 38384 "
		::= { iqdbe00CmdEntry 38384 }


	iqdbe00AESOutAESOut6Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 6
					Left  cmdID= 38210
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38210 }


	iqdbe00AESOutAESOut6Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 6
					Right  cmdID= 38211
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38211 }


	iqdbe00AESOutAESOut6LinkLRSelection OBJECT-TYPE
		SYNTAX		INTEGER { disable(0), enable(1) }
		MAX-ACCESS		read-write
		STATUS			current
		DESCRIPTION
				"TYPE: - Checkbox
				 PAGE: - AES Ports- AES Out 6
					Link L+R Selection  cmdID= 38385 "
		::= { iqdbe00CmdEntry 38385 }


	iqdbe00AESOutAESOut7Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 7
					Left  cmdID= 38212
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38212 }


	iqdbe00AESOutAESOut7Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 7
					Right  cmdID= 38213
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38213 }


	iqdbe00AESOutAESOut7LinkLRSelection OBJECT-TYPE
		SYNTAX		INTEGER { disable(0), enable(1) }
		MAX-ACCESS		read-write
		STATUS			current
		DESCRIPTION
				"TYPE: - Checkbox
				 PAGE: - AES Ports- AES Out 7
					Link L+R Selection  cmdID= 38386 "
		::= { iqdbe00CmdEntry 38386 }


	iqdbe00AESOutAESOut8Left OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 8
					Left  cmdID= 38214
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38214 }


	iqdbe00AESOutAESOut8Right OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- AES Out 8
					Right  cmdID= 38215
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38215 }


	iqdbe00AESOutAESOut8LinkLRSelection OBJECT-TYPE
		SYNTAX		INTEGER { disable(0), enable(1) }
		MAX-ACCESS		read-write
		STATUS			current
		DESCRIPTION
				"TYPE: - Checkbox
				 PAGE: - AES Ports- AES Out 8
					Link L+R Selection  cmdID= 38387 "
		::= { iqdbe00CmdEntry 38387 }


	iqdbe00AESOutMonitoropLeft OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- Monitor o/p
					Left  cmdID= 38641
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38641 }


	iqdbe00AESOutMonitoropRight OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_AES_Bus_8_L(41),
							val_AES_Bus_8_R(42),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - AES Ports- Monitor o/p
					Right  cmdID= 38642
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					AES Bus 8-L  value= 41
					AES Bus 8-R  value= 42
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38642 }


	iqdbe00AESOutMonitoropLinkLRSelection OBJECT-TYPE
		SYNTAX		INTEGER { disable(0), enable(1) }
		MAX-ACCESS		read-write
		STATUS			current
		DESCRIPTION
				"TYPE: - Checkbox
				 PAGE: - AES Ports- Monitor o/p
					Link L+R Selection  cmdID= 38640 "
		::= { iqdbe00CmdEntry 38640 }


	iqdbe00AESOutAESPortNamesAESPort1Stereo OBJECT-TYPE
		SYNTAX		INTEGER { disable(0), enable(1) }
		MAX-ACCESS		read-write
		STATUS			current
		DESCRIPTION
				"TYPE: - Checkbox
				 PAGE: - AES Ports- AES Port Names
					AES Port 1 Stereo  cmdID= 38448 "
		::= { iqdbe00CmdEntry 38448 }


	iqdbe00AESOutAESPortNamesAESPort1L OBJECT-TYPE
		SYNTAX		RollCallString
		MAX-ACCESS		read-write
		STATUS			current
		DESCRIPTION
				"TYPE: - Editstring
				 PAGE: - AES Ports- AES Port Names
					AES Port 1-L  cmdID= 38496  "
		::= { iqdbe00CmdEntry 38496 }


	iqdbe00AESOutAESPortNamesAESPort1R OBJECT-TYPE
		SYNTAX		RollCallString
		MAX-ACCESS		read-write
		STATUS			current
		DESCRIPTION
				"TYPE: - Editstring
				 PAGE: - AES Ports- AES Port Names
					AES Port 1-R  cmdID= 38497  "
		::= { iqdbe00CmdEntry 38497 }


	iqdbe00AESOutAESPortNamesAESPort2Stereo OBJECT-TYPE
		SYNTAX		INTEGER { disable(0), enable(1) }
		MAX-ACCESS		read-write
		STATUS			current
		DESCRIPTION
				"TYPE: - Checkbox
				 PAGE: - AES Ports- AES Port Names
					AES Port 2 Stereo  cmdID= 38449 "
		::= { iqdbe00CmdEntry 38449 }


	iqdbe00AESOutAESPortNamesAESPort2L OBJECT-TYPE
		SYNTAX		RollCallString
		MAX-ACCESS		read-write
		STATUS			current
		DESCRIPTION
				"TYPE: - Editstring
				 PAGE: - AES Ports- AES Port Names
					AES Port 2-L  cmdID= 38498  "
		::= { iqdbe00CmdEntry 38498 }


	iqdbe00AESOutAESPortNamesAESPort2R OBJECT-TYPE
		SYNTAX		RollCallString
		MAX-ACCESS		read-write
		STATUS			current
		DESCRIPTION
				"TYPE: - Editstring
				 PAGE: - AES Ports- AES Port Names
					AES Port 2-R  cmdID= 38499  "
		::= { iqdbe00CmdEntry 38499 }


	iqdbe00AESOutAESPortNamesAESPort3Stereo OBJECT-TYPE
		SYNTAX		INTEGER { disable(0), enable(1) }
		MAX-ACCESS		read-write
		STATUS			current
		DESCRIPTION
				"TYPE: - Checkbox
				 PAGE: - AES Ports- AES Port Names
					AES Port 3 Stereo  cmdID= 38450 "
		::= { iqdbe00CmdEntry 38450 }


	iqdbe00AESOutAESPortNamesAESPort3L OBJECT-TYPE
		SYNTAX		RollCallString
		MAX-ACCESS		read-write
		STATUS			current
		DESCRIPTION
				"TYPE: - Editstring
				 PAGE: - AES Ports- AES Port Names
					AES Port 3-L  cmdID= 38500  "
		::= { iqdbe00CmdEntry 38500 }


	iqdbe00AESOutAESPortNamesAESPort3R OBJECT-TYPE
		SYNTAX		RollCallString
		MAX-ACCESS		read-write
		STATUS			current
		DESCRIPTION
				"TYPE: - Editstring
				 PAGE: - AES Ports- AES Port Names
					AES Port 3-R  cmdID= 38501  "
		::= { iqdbe00CmdEntry 38501 }


	iqdbe00AESOutAESPortNamesAESPort4Stereo OBJECT-TYPE
		SYNTAX		INTEGER { disable(0), enable(1) }
		MAX-ACCESS		read-write
		STATUS			current
		DESCRIPTION
				"TYPE: - Checkbox
				 PAGE: - AES Ports- AES Port Names
					AES Port 4 Stereo  cmdID= 38451 "
		::= { iqdbe00CmdEntry 38451 }


	iqdbe00AESOutAESPortNamesAESPort4L OBJECT-TYPE
		SYNTAX		RollCallString
		MAX-ACCESS		read-write
		STATUS			current
		DESCRIPTION
				"TYPE: - Editstring
				 PAGE: - AES Ports- AES Port Names
					AES Port 4-L  cmdID= 38502  "
		::= { iqdbe00CmdEntry 38502 }


	iqdbe00AESOutAESPortNamesAESPort4R OBJECT-TYPE
		SYNTAX		RollCallString
		MAX-ACCESS		read-write
		STATUS			current
		DESCRIPTION
				"TYPE: - Editstring
				 PAGE: - AES Ports- AES Port Names
					AES Port 4-R  cmdID= 38503  "
		::= { iqdbe00CmdEntry 38503 }


	iqdbe00AESOutAESPortNamesAESPort5Stereo OBJECT-TYPE
		SYNTAX		INTEGER { disable(0), enable(1) }
		MAX-ACCESS		read-write
		STATUS			current
		DESCRIPTION
				"TYPE: - Checkbox
				 PAGE: - AES Ports- AES Port Names
					AES Port 5 Stereo  cmdID= 38452 "
		::= { iqdbe00CmdEntry 38452 }


	iqdbe00AESOutAESPortNamesAESPort5L OBJECT-TYPE
		SYNTAX		RollCallString
		MAX-ACCESS		read-write
		STATUS			current
		DESCRIPTION
				"TYPE: - Editstring
				 PAGE: - AES Ports- AES Port Names
					AES Port 5-L  cmdID= 38504  "
		::= { iqdbe00CmdEntry 38504 }


	iqdbe00AESOutAESPortNamesAESPort5R OBJECT-TYPE
		SYNTAX		RollCallString
		MAX-ACCESS		read-write
		STATUS			current
		DESCRIPTION
				"TYPE: - Editstring
				 PAGE: - AES Ports- AES Port Names
					AES Port 5-R  cmdID= 38505  "
		::= { iqdbe00CmdEntry 38505 }


	iqdbe00AESOutAESPortNamesAESPort6Stereo OBJECT-TYPE
		SYNTAX		INTEGER { disable(0), enable(1) }
		MAX-ACCESS		read-write
		STATUS			current
		DESCRIPTION
				"TYPE: - Checkbox
				 PAGE: - AES Ports- AES Port Names
					AES Port 6 Stereo  cmdID= 38453 "
		::= { iqdbe00CmdEntry 38453 }


	iqdbe00AESOutAESPortNamesAESPort6L OBJECT-TYPE
		SYNTAX		RollCallString
		MAX-ACCESS		read-write
		STATUS			current
		DESCRIPTION
				"TYPE: - Editstring
				 PAGE: - AES Ports- AES Port Names
					AES Port 6-L  cmdID= 38506  "
		::= { iqdbe00CmdEntry 38506 }


	iqdbe00AESOutAESPortNamesAESPort6R OBJECT-TYPE
		SYNTAX		RollCallString
		MAX-ACCESS		read-write
		STATUS			current
		DESCRIPTION
				"TYPE: - Editstring
				 PAGE: - AES Ports- AES Port Names
					AES Port 6-R  cmdID= 38507  "
		::= { iqdbe00CmdEntry 38507 }


	iqdbe00AESOutAESPortNamesAESPort7Stereo OBJECT-TYPE
		SYNTAX		INTEGER { disable(0), enable(1) }
		MAX-ACCESS		read-write
		STATUS			current
		DESCRIPTION
				"TYPE: - Checkbox
				 PAGE: - AES Ports- AES Port Names
					AES Port 7 Stereo  cmdID= 38454 "
		::= { iqdbe00CmdEntry 38454 }


	iqdbe00AESOutAESPortNamesAESPort7L OBJECT-TYPE
		SYNTAX		RollCallString
		MAX-ACCESS		read-write
		STATUS			current
		DESCRIPTION
				"TYPE: - Editstring
				 PAGE: - AES Ports- AES Port Names
					AES Port 7-L  cmdID= 38508  "
		::= { iqdbe00CmdEntry 38508 }


	iqdbe00AESOutAESPortNamesAESPort7R OBJECT-TYPE
		SYNTAX		RollCallString
		MAX-ACCESS		read-write
		STATUS			current
		DESCRIPTION
				"TYPE: - Editstring
				 PAGE: - AES Ports- AES Port Names
					AES Port 7-R  cmdID= 38509  "
		::= { iqdbe00CmdEntry 38509 }


	iqdbe00AESOutAESPortNamesAESPort8Stereo OBJECT-TYPE
		SYNTAX		INTEGER { disable(0), enable(1) }
		MAX-ACCESS		read-write
		STATUS			current
		DESCRIPTION
				"TYPE: - Checkbox
				 PAGE: - AES Ports- AES Port Names
					AES Port 8 Stereo  cmdID= 38455 "
		::= { iqdbe00CmdEntry 38455 }


	iqdbe00AESOutAESPortNamesAESPort8L OBJECT-TYPE
		SYNTAX		RollCallString
		MAX-ACCESS		read-write
		STATUS			current
		DESCRIPTION
				"TYPE: - Editstring
				 PAGE: - AES Ports- AES Port Names
					AES Port 8-L  cmdID= 38510  "
		::= { iqdbe00CmdEntry 38510 }


	iqdbe00AESOutAESPortNamesAESPort8R OBJECT-TYPE
		SYNTAX		RollCallString
		MAX-ACCESS		read-write
		STATUS			current
		DESCRIPTION
				"TYPE: - Editstring
				 PAGE: - AES Ports- AES Port Names
					AES Port 8-R  cmdID= 38511  "
		::= { iqdbe00CmdEntry 38511 }


	iqdbe00AESBusAESDataModeInput1 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 1  cmdID= 38400
					PCM  value= 0
					Data  value= 1
					Mixed  value= 2  "
		::= { iqdbe00CmdEntry 38400 }


	iqdbe00AESBusAESDataModeInput2 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 2  cmdID= 38401
					PCM  value= 0
					Data  value= 1
					Mixed  value= 2  "
		::= { iqdbe00CmdEntry 38401 }


	iqdbe00AESBusAESDataModeInput3 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 3  cmdID= 38402
					PCM  value= 0
					Data  value= 1
					Mixed  value= 2  "
		::= { iqdbe00CmdEntry 38402 }


	iqdbe00AESBusAESDataModeInput4 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 4  cmdID= 38403
					PCM  value= 0
					Data  value= 1
					Mixed  value= 2  "
		::= { iqdbe00CmdEntry 38403 }


	iqdbe00AESBusAESDataModeInput5 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 5  cmdID= 38404
					PCM  value= 0
					Data  value= 1
					Mixed  value= 2  "
		::= { iqdbe00CmdEntry 38404 }


	iqdbe00AESBusAESDataModeInput6 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 6  cmdID= 38405
					PCM  value= 0
					Data  value= 1
					Mixed  value= 2  "
		::= { iqdbe00CmdEntry 38405 }


	iqdbe00AESBusAESDataModeInput7 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 7  cmdID= 38406
					PCM  value= 0
					Data  value= 1
					Mixed  value= 2  "
		::= { iqdbe00CmdEntry 38406 }


	iqdbe00AESBusAESDataModeInput8 OBJECT-TYPE
		SYNTAX		INTEGER {
							val_PCM(0),
							val_Data(1),
							val_Mixed(2)
							}
		MAX-ACCESS		read-write
		STATUS			current
		DESCRIPTION
				"TYPE: - RadiobuttonList
				 PAGE: - AES Ports- AES Bus
					Input 8  cmdID= 38407
					PCM  value= 0
					Data  value= 1
					Mixed  value= 2  "
		::= { iqdbe00CmdEntry 38407 }


	iqdbe00AESBusAESBusNamesAESBus1Stereo OBJECT-TYPE
		SYNTAX		INTEGER { disable(0), enable(1) }
		MAX-ACCESS		read-write
		STATUS			current
		DESCRIPTION
				"TYPE: - Checkbox
				 PAGE: - AES Ports- AES Bus
					AES Bus 1 Stereo  cmdID= 38440 "
		::= { iqdbe00CmdEntry 38440 }


	iqdbe00AESBusAESBusNamesAESBus1 OBJECT-TYPE
		SYNTAX		RollCallString
		MAX-ACCESS		read-write
		STATUS			current
		DESCRIPTION
				"TYPE: - Editstring
				 PAGE: - AES Ports- AES Bus
					AES Bus 1  cmdID= 38480  "
		::= { iqdbe00CmdEntry 38480 }


	iqdbe00AESBusAESBusNamesAESBus1R OBJECT-TYPE
		SYNTAX		RollCallString
		MAX-ACCESS		read-write
		STATUS			current
		DESCRIPTION
				"TYPE: - Editstring
				 PAGE: - AES Ports- AES Bus
					AES Bus 1-R  cmdID= 38481  "
		::= { iqdbe00CmdEntry 38481 }


	iqdbe00AESBusAESBusNamesAESBus2Stereo OBJECT-TYPE
		SYNTAX		INTEGER { disable(0), enable(1) }
		MAX-ACCESS		read-write
		STATUS			current
		DESCRIPTION
				"TYPE: - Checkbox
				 PAGE: - AES Ports- AES Bus
					AES Bus 2 Stereo  cmdID= 38441 "
		::= { iqdbe00CmdEntry 38441 }


	iqdbe00AESBusAESBusNamesAESBus2 OBJECT-TYPE
		SYNTAX		RollCallString
		MAX-ACCESS		read-write
		STATUS			current
		DESCRIPTION
				"TYPE: - Editstring
				 PAGE: - AES Ports- AES Bus
					AES Bus 2  cmdID= 38482  "
		::= { iqdbe00CmdEntry 38482 }


	iqdbe00AESBusAESBusNamesAESBus2R OBJECT-TYPE
		SYNTAX		RollCallString
		MAX-ACCESS		read-write
		STATUS			current
		DESCRIPTION
				"TYPE: - Editstring
				 PAGE: - AES Ports- AES Bus
					AES Bus 2-R  cmdID= 38483  "
		::= { iqdbe00CmdEntry 38483 }


	iqdbe00AESBusAESBusNamesAESBus3Stereo OBJECT-TYPE
		SYNTAX		INTEGER { disable(0), enable(1) }
		MAX-ACCESS		read-write
		STATUS			current
		DESCRIPTION
				"TYPE: - Checkbox
				 PAGE: - AES Ports- AES Bus
					AES Bus 3 Stereo  cmdID= 38442 "
		::= { iqdbe00CmdEntry 38442 }


	iqdbe00AESBusAESBusNamesAESBus3 OBJECT-TYPE
		SYNTAX		RollCallString
		MAX-ACCESS		read-write
		STATUS			current
		DESCRIPTION
				"TYPE: - Editstring
				 PAGE: - AES Ports- AES Bus
					AES Bus 3  cmdID= 38484  "
		::= { iqdbe00CmdEntry 38484 }


	iqdbe00AESBusAESBusNamesAESBus3R OBJECT-TYPE
		SYNTAX		RollCallString
		MAX-ACCESS		read-write
		STATUS			current
		DESCRIPTION
				"TYPE: - Editstring
				 PAGE: - AES Ports- AES Bus
					AES Bus 3-R  cmdID= 38485  "
		::= { iqdbe00CmdEntry 38485 }


	iqdbe00AESBusAESBusNamesAESBus4Stereo OBJECT-TYPE
		SYNTAX		INTEGER { disable(0), enable(1) }
		MAX-ACCESS		read-write
		STATUS			current
		DESCRIPTION
				"TYPE: - Checkbox
				 PAGE: - AES Ports- AES Bus
					AES Bus 4 Stereo  cmdID= 38443 "
		::= { iqdbe00CmdEntry 38443 }


	iqdbe00AESBusAESBusNamesAESBus4 OBJECT-TYPE
		SYNTAX		RollCallString
		MAX-ACCESS		read-write
		STATUS			current
		DESCRIPTION
				"TYPE: - Editstring
				 PAGE: - AES Ports- AES Bus
					AES Bus 4  cmdID= 38486  "
		::= { iqdbe00CmdEntry 38486 }


	iqdbe00AESBusAESBusNamesAESBus4R OBJECT-TYPE
		SYNTAX		RollCallString
		MAX-ACCESS		read-write
		STATUS			current
		DESCRIPTION
				"TYPE: - Editstring
				 PAGE: - AES Ports- AES Bus
					AES Bus 4-R  cmdID= 38487  "
		::= { iqdbe00CmdEntry 38487 }


	iqdbe00AESBusAESBusNamesAESBus5Stereo OBJECT-TYPE
		SYNTAX		INTEGER { disable(0), enable(1) }
		MAX-ACCESS		read-write
		STATUS			current
		DESCRIPTION
				"TYPE: - Checkbox
				 PAGE: - AES Ports- AES Bus
					AES Bus 5 Stereo  cmdID= 38444 "
		::= { iqdbe00CmdEntry 38444 }


	iqdbe00AESBusAESBusNamesAESBus5 OBJECT-TYPE
		SYNTAX		RollCallString
		MAX-ACCESS		read-write
		STATUS			current
		DESCRIPTION
				"TYPE: - Editstring
				 PAGE: - AES Ports- AES Bus
					AES Bus 5  cmdID= 38488  "
		::= { iqdbe00CmdEntry 38488 }


	iqdbe00AESBusAESBusNamesAESBus5R OBJECT-TYPE
		SYNTAX		RollCallString
		MAX-ACCESS		read-write
		STATUS			current
		DESCRIPTION
				"TYPE: - Editstring
				 PAGE: - AES Ports- AES Bus
					AES Bus 5-R  cmdID= 38489  "
		::= { iqdbe00CmdEntry 38489 }


	iqdbe00AESBusAESBusNamesAESBus6Stereo OBJECT-TYPE
		SYNTAX		INTEGER { disable(0), enable(1) }
		MAX-ACCESS		read-write
		STATUS			current
		DESCRIPTION
				"TYPE: - Checkbox
				 PAGE: - AES Ports- AES Bus
					AES Bus 6 Stereo  cmdID= 38445 "
		::= { iqdbe00CmdEntry 38445 }


	iqdbe00AESBusAESBusNamesAESBus6 OBJECT-TYPE
		SYNTAX		RollCallString
		MAX-ACCESS		read-write
		STATUS			current
		DESCRIPTION
				"TYPE: - Editstring
				 PAGE: - AES Ports- AES Bus
					AES Bus 6  cmdID= 38490  "
		::= { iqdbe00CmdEntry 38490 }


	iqdbe00AESBusAESBusNamesAESBus6R OBJECT-TYPE
		SYNTAX		RollCallString
		MAX-ACCESS		read-write
		STATUS			current
		DESCRIPTION
				"TYPE: - Editstring
				 PAGE: - AES Ports- AES Bus
					AES Bus 6-R  cmdID= 38491  "
		::= { iqdbe00CmdEntry 38491 }


	iqdbe00AESBusAESBusNamesAESBus7Stereo OBJECT-TYPE
		SYNTAX		INTEGER { disable(0), enable(1) }
		MAX-ACCESS		read-write
		STATUS			current
		DESCRIPTION
				"TYPE: - Checkbox
				 PAGE: - AES Ports- AES Bus
					AES Bus 7 Stereo  cmdID= 38446 "
		::= { iqdbe00CmdEntry 38446 }


	iqdbe00AESBusAESBusNamesAESBus7 OBJECT-TYPE
		SYNTAX		RollCallString
		MAX-ACCESS		read-write
		STATUS			current
		DESCRIPTION
				"TYPE: - Editstring
				 PAGE: - AES Ports- AES Bus
					AES Bus 7  cmdID= 38492  "
		::= { iqdbe00CmdEntry 38492 }


	iqdbe00AESBusAESBusNamesAESBus7R OBJECT-TYPE
		SYNTAX		RollCallString
		MAX-ACCESS		read-write
		STATUS			current
		DESCRIPTION
				"TYPE: - Editstring
				 PAGE: - AES Ports- AES Bus
					AES Bus 7-R  cmdID= 38493  "
		::= { iqdbe00CmdEntry 38493 }


	iqdbe00AESBusAESBusNamesAESBus8Stereo OBJECT-TYPE
		SYNTAX		INTEGER { disable(0), enable(1) }
		MAX-ACCESS		read-write
		STATUS			current
		DESCRIPTION
				"TYPE: - Checkbox
				 PAGE: - AES Ports- AES Bus
					AES Bus 8 Stereo  cmdID= 38447 "
		::= { iqdbe00CmdEntry 38447 }


	iqdbe00AESBusAESBusNamesAESBus8 OBJECT-TYPE
		SYNTAX		RollCallString
		MAX-ACCESS		read-write
		STATUS			current
		DESCRIPTION
				"TYPE: - Editstring
				 PAGE: - AES Ports- AES Bus
					AES Bus 8  cmdID= 38494  "
		::= { iqdbe00CmdEntry 38494 }


	iqdbe00AESBusAESBusNamesAESBus8R OBJECT-TYPE
		SYNTAX		RollCallString
		MAX-ACCESS		read-write
		STATUS			current
		DESCRIPTION
				"TYPE: - Editstring
				 PAGE: - AES Ports- AES Bus
					AES Bus 8-R  cmdID= 38495  "
		::= { iqdbe00CmdEntry 38495 }


	iqdbe00AESBusAESBusRoutingSource1 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 1  cmdID= 38560
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38560 }


	iqdbe00AESBusAESBusRoutingSource2 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 2  cmdID= 38561
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38561 }


	iqdbe00AESBusAESBusRoutingSource3 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 3  cmdID= 38562
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38562 }


	iqdbe00AESBusAESBusRoutingSource4 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 4  cmdID= 38563
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38563 }


	iqdbe00AESBusAESBusRoutingSource5 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 5  cmdID= 38564
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38564 }


	iqdbe00AESBusAESBusRoutingSource6 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 6  cmdID= 38565
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38565 }


	iqdbe00AESBusAESBusRoutingSource7 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 7  cmdID= 38566
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38566 }


	iqdbe00AESBusAESBusRoutingSource8 OBJECT-TYPE
		SYNTAX		INTEGER {
							val_AES_Port_1(1),
							val_AES_Port_2(2),
							val_AES_Port_3(3),
							val_AES_Port_4(4),
							val_AES_Port_5(5),
							val_AES_Port_6(6),
							val_AES_Port_7(7),
							val_AES_Port_8(8)
							}
		MAX-ACCESS		read-write
		STATUS			current
		DESCRIPTION
				"TYPE: - RadiobuttonList
				 PAGE: - AES Ports- AES Bus
					Source 8  cmdID= 38567
					AES Port 1  value= 1
					AES Port 2  value= 2
					AES Port 3  value= 3
					AES Port 4  value= 4
					AES Port 5  value= 5
					AES Port 6  value= 6
					AES Port 7  value= 7
					AES Port 8  value= 8  "
		::= { iqdbe00CmdEntry 38567 }


	iqdbe00AESPortsAESDirectionAESPort1Dir OBJECT-TYPE
		SYNTAX		INTEGER {
							val_Input(0),
							val_Output(1)
							}
		MAX-ACCESS		read-write
		STATUS			current
		DESCRIPTION
				"TYPE: - RadiobuttonList
				 PAGE: - AES Ports
					AES Port 1 Dir  cmdID= 38420
					Input  value= 0
					Output  value= 1  "
		::= { iqdbe00CmdEntry 38420 }


	iqdbe00AESPortsAESDirectionAESPort2Dir OBJECT-TYPE
		SYNTAX		INTEGER {
							val_Input(0),
							val_Output(1)
							}
		MAX-ACCESS		read-write
		STATUS			current
		DESCRIPTION
				"TYPE: - RadiobuttonList
				 PAGE: - AES Ports
					AES Port 2 Dir  cmdID= 38421
					Input  value= 0
					Output  value= 1  "
		::= { iqdbe00CmdEntry 38421 }


	iqdbe00AESPortsAESDirectionAESPort3Dir OBJECT-TYPE
		SYNTAX		INTEGER {
							val_Input(0),
							val_Output(1)
							}
		MAX-ACCESS		read-write
		STATUS			current
		DESCRIPTION
				"TYPE: - RadiobuttonList
				 PAGE: - AES Ports
					AES Port 3 Dir  cmdID= 38422
					Input  value= 0
					Output  value= 1  "
		::= { iqdbe00CmdEntry 38422 }


	iqdbe00AESPortsAESDirectionAESPort4Dir OBJECT-TYPE
		SYNTAX		INTEGER {
							val_Input(0),
							val_Output(1)
							}
		MAX-ACCESS		read-write
		STATUS			current
		DESCRIPTION
				"TYPE: - RadiobuttonList
				 PAGE: - AES Ports
					AES Port 4 Dir  cmdID= 38423
					Input  value= 0
					Output  value= 1  "
		::= { iqdbe00CmdEntry 38423 }


	iqdbe00AESPortsAESDirectionAESPort5Dir OBJECT-TYPE
		SYNTAX		INTEGER {
							val_Input(0),
							val_Output(1)
							}
		MAX-ACCESS		read-write
		STATUS			current
		DESCRIPTION
				"TYPE: - RadiobuttonList
				 PAGE: - AES Ports
					AES Port 5 Dir  cmdID= 38424
					Input  value= 0
					Output  value= 1  "
		::= { iqdbe00CmdEntry 38424 }


	iqdbe00AESPortsAESDirectionAESPort6Dir OBJECT-TYPE
		SYNTAX		INTEGER {
							val_Input(0),
							val_Output(1)
							}
		MAX-ACCESS		read-write
		STATUS			current
		DESCRIPTION
				"TYPE: - RadiobuttonList
				 PAGE: - AES Ports
					AES Port 6 Dir  cmdID= 38425
					Input  value= 0
					Output  value= 1  "
		::= { iqdbe00CmdEntry 38425 }


	iqdbe00AESPortsAESDirectionAESPort7Dir OBJECT-TYPE
		SYNTAX		INTEGER {
							val_Input(0),
							val_Output(1)
							}
		MAX-ACCESS		read-write
		STATUS			current
		DESCRIPTION
				"TYPE: - RadiobuttonList
				 PAGE: - AES Ports
					AES Port 7 Dir  cmdID= 38426
					Input  value= 0
					Output  value= 1  "
		::= { iqdbe00CmdEntry 38426 }


	iqdbe00AESPortsAESDirectionAESPort8Dir OBJECT-TYPE
		SYNTAX		INTEGER {
							val_Input(0),
							val_Output(1)
							}
		MAX-ACCESS		read-write
		STATUS			current
		DESCRIPTION
				"TYPE: - RadiobuttonList
				 PAGE: - AES Ports
					AES Port 8 Dir  cmdID= 38427
					Input  value= 0
					Output  value= 1  "
		::= { iqdbe00CmdEntry 38427 }


	iqdbe00AudioDolbyETimingSelAudioPair OBJECT-TYPE
		SYNTAX		INTEGER
		MAX-ACCESS		read-write
		STATUS			current
		DESCRIPTION
				"TYPE: - Number
					Sel Audio Pair  cmdID= 38650  min= 1  max= 8  step= 1  format= %0.0f  div_scale= 1
					Min = 1  Max = 8  Step = 1 "
		::= { iqdbe00CmdEntry 38650 }


	iqdbe00AudioDolbyETimingRelativeTiming OBJECT-TYPE
		SYNTAX		RollCallString
		MAX-ACCESS		read-only
		STATUS			current
		DESCRIPTION
				"TYPE: - Display
					Relative Timing  cmdID= 38653  format=   "
		::= { iqdbe00CmdEntry 38653 }


	iqdbe00AudioDolbyETimingStatus OBJECT-TYPE
		SYNTAX		RollCallString
		MAX-ACCESS		read-only
		STATUS			current
		DESCRIPTION
				"TYPE: - Display
					Status  cmdID= 38652  format=   "
		::= { iqdbe00CmdEntry 38652 }


	iqdbe00AudioDolbyETimingError OBJECT-TYPE
		SYNTAX		RollCallString
		MAX-ACCESS		read-only
		STATUS			current
		DESCRIPTION
				"TYPE: - Display
					Error  cmdID= 38654  format=   "
		::= { iqdbe00CmdEntry 38654 }


	iqdbe00DolbyETimingDolbyELineStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
					Standard  cmdID= 38655
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe00CmdEntry 38655 }


	iqdbe00DolbyETimingDolbyELineAutoLineNo OBJECT-TYPE
		SYNTAX		INTEGER
		MAX-ACCESS		read-write
		STATUS			current
		DESCRIPTION
				"TYPE: - Number
					Auto Line No.  cmdID= 38656  min= 1  max= 10000  step= 1  format= %0.0f  div_scale= 1
					Min = 1  Max = 10000  Step = 1 "
		::= { iqdbe00CmdEntry 38656 }


	iqdbe00DolbyELineUserDolbyELinePair1 OBJECT-TYPE
		SYNTAX		INTEGER {
							val_User_Line(1),
							val_Standard_Line(0)
							}
		MAX-ACCESS		read-write
		STATUS			current
		DESCRIPTION
				"TYPE: - RadiobuttonList
					Pair 1  cmdID= 38670
					User Line  value= 1
					Standard Line  value= 0  "
		::= { iqdbe00CmdEntry 38670 }


	iqdbe00DolbyELineUserDolbyELinePair2 OBJECT-TYPE
		SYNTAX		INTEGER {
							val_User_Line(1),
							val_Standard_Line(0)
							}
		MAX-ACCESS		read-write
		STATUS			current
		DESCRIPTION
				"TYPE: - RadiobuttonList
					Pair 2  cmdID= 38671
					User Line  value= 1
					Standard Line  value= 0  "
		::= { iqdbe00CmdEntry 38671 }


	iqdbe00DolbyELineUserDolbyELinePair3 OBJECT-TYPE
		SYNTAX		INTEGER {
							val_User_Line(1),
							val_Standard_Line(0)
							}
		MAX-ACCESS		read-write
		STATUS			current
		DESCRIPTION
				"TYPE: - RadiobuttonList
					Pair 3  cmdID= 38672
					User Line  value= 1
					Standard Line  value= 0  "
		::= { iqdbe00CmdEntry 38672 }


	iqdbe00DolbyELineUserDolbyELinePair4 OBJECT-TYPE
		SYNTAX		INTEGER {
							val_User_Line(1),
							val_Standard_Line(0)
							}
		MAX-ACCESS		read-write
		STATUS			current
		DESCRIPTION
				"TYPE: - RadiobuttonList
					Pair 4  cmdID= 38673
					User Line  value= 1
					Standard Line  value= 0  "
		::= { iqdbe00CmdEntry 38673 }


	iqdbe00DolbyELineUserDolbyELinePair5 OBJECT-TYPE
		SYNTAX		INTEGER {
							val_User_Line(1),
							val_Standard_Line(0)
							}
		MAX-ACCESS		read-write
		STATUS			current
		DESCRIPTION
				"TYPE: - RadiobuttonList
					Pair 5  cmdID= 38674
					User Line  value= 1
					Standard Line  value= 0  "
		::= { iqdbe00CmdEntry 38674 }


	iqdbe00DolbyELineUserDolbyELinePair6 OBJECT-TYPE
		SYNTAX		INTEGER {
							val_User_Line(1),
							val_Standard_Line(0)
							}
		MAX-ACCESS		read-write
		STATUS			current
		DESCRIPTION
				"TYPE: - RadiobuttonList
					Pair 6  cmdID= 38675
					User Line  value= 1
					Standard Line  value= 0  "
		::= { iqdbe00CmdEntry 38675 }


	iqdbe00DolbyELineUserDolbyELinePair7 OBJECT-TYPE
		SYNTAX		INTEGER {
							val_User_Line(1),
							val_Standard_Line(0)
							}
		MAX-ACCESS		read-write
		STATUS			current
		DESCRIPTION
				"TYPE: - RadiobuttonList
					Pair 7  cmdID= 38676
					User Line  value= 1
					Standard Line  value= 0  "
		::= { iqdbe00CmdEntry 38676 }


	iqdbe00DolbyELineUserDolbyELinePair8 OBJECT-TYPE
		SYNTAX		INTEGER {
							val_User_Line(1),
							val_Standard_Line(0)
							}
		MAX-ACCESS		read-write
		STATUS			current
		DESCRIPTION
				"TYPE: - RadiobuttonList
					Pair 8  cmdID= 38677
					User Line  value= 1
					Standard Line  value= 0  "
		::= { iqdbe00CmdEntry 38677 }


	iqdbe00InputChanAssignInputAA1 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input A
					A1  cmdID= 38900
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38900 }


	iqdbe00InputChanAssignInputAA2 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input A
					A2  cmdID= 38901
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38901 }


	iqdbe00InputChanAssignInputALinkLR OBJECT-TYPE
		SYNTAX		INTEGER { disable(0), enable(1) }
		MAX-ACCESS		read-write
		STATUS			current
		DESCRIPTION
				"TYPE: - Checkbox
				 PAGE: - Dolby Encoder- Input A
					Link L+R  cmdID= 38910 "
		::= { iqdbe00CmdEntry 38910 }


	iqdbe00InputChanAssignInputBB3 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input B
					B3  cmdID= 38902
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38902 }


	iqdbe00InputChanAssignInputBB4 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input B
					B4  cmdID= 38903
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38903 }


	iqdbe00InputChanAssignInputBLinkLR OBJECT-TYPE
		SYNTAX		INTEGER { disable(0), enable(1) }
		MAX-ACCESS		read-write
		STATUS			current
		DESCRIPTION
				"TYPE: - Checkbox
				 PAGE: - Dolby Encoder- Input B
					Link L+R  cmdID= 38911 "
		::= { iqdbe00CmdEntry 38911 }


	iqdbe00InputChanAssignInputCC5 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input C
					C5  cmdID= 38904
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38904 }


	iqdbe00InputChanAssignInputCC6 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input C
					C6  cmdID= 38905
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38905 }


	iqdbe00InputChanAssignInputCLinkLR OBJECT-TYPE
		SYNTAX		INTEGER { disable(0), enable(1) }
		MAX-ACCESS		read-write
		STATUS			current
		DESCRIPTION
				"TYPE: - Checkbox
				 PAGE: - Dolby Encoder- Input C
					Link L+R  cmdID= 38912 "
		::= { iqdbe00CmdEntry 38912 }


	iqdbe00InputChanAssignInputDD7 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input D
					D7  cmdID= 38906
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38906 }


	iqdbe00InputChanAssignInputDD8 OBJECT-TYPE
		SYNTAX		INTEGER {
							val_Mute(-1),
							val_Disembed_1_L(1),
							val_Disembed_1_R(2),
							val_Disembed_2_L(3),
							val_Disembed_2_R(4),
							val_Disembed_3_L(5),
							val_Disembed_3_R(6),
							val_Disembed_4_L(7),
							val_Disembed_4_R(8),
							val_Disembed_5_L(9),
							val_Disembed_5_R(10),
							val_Disembed_6_L(11),
							val_Disembed_6_R(12),
							val_Disembed_7_L(13),
							val_Disembed_7_R(14),
							val_Disembed_8_L(15),
							val_Disembed_8_R(16),
							val_Mix_1(23),
							val_Mix_2(24),
							val_Mix_3(25),
							val_Mix_4(26),
							val_AES_Bus_1_L(27),
							val_AES_Bus_1_R(28),
							val_AES_Bus_2_L(29),
							val_AES_Bus_2_R(30),
							val_AES_Bus_3_L(31),
							val_AES_Bus_3_R(32),
							val_AES_Bus_4_L(33),
							val_AES_Bus_4_R(34),
							val_AES_Bus_5_L(35),
							val_AES_Bus_5_R(36),
							val_AES_Bus_6_L(37),
							val_AES_Bus_6_R(38),
							val_AES_Bus_7_L(39),
							val_AES_Bus_7_R(40),
							val_1kHz_20dBFS_Tone(17),
							val_2kHz_20dBFS_Tone(18),
							val_4kHz_20dBFS_Tone(19),
							val_1kHz_18dBFS_Tone(20),
							val_2kHz_18dBFS_Tone(21),
							val_4kHz_18dBFS_Tone(22)
							}
		MAX-ACCESS		read-write
		STATUS			current
		DESCRIPTION
				"TYPE: - RadiobuttonList
				 PAGE: - Dolby Encoder- Input D
					D8  cmdID= 38907
					Mute  value= -1
					Disembed 1-L  value= 1
					Disembed 1-R  value= 2
					Disembed 2-L  value= 3
					Disembed 2-R  value= 4
					Disembed 3-L  value= 5
					Disembed 3-R  value= 6
					Disembed 4-L  value= 7
					Disembed 4-R  value= 8
					Disembed 5-L  value= 9
					Disembed 5-R  value= 10
					Disembed 6-L  value= 11
					Disembed 6-R  value= 12
					Disembed 7-L  value= 13
					Disembed 7-R  value= 14
					Disembed 8-L  value= 15
					Disembed 8-R  value= 16
					Mix 1  value= 23
					Mix 2  value= 24
					Mix 3  value= 25
					Mix 4  value= 26
					AES Bus 1-L  value= 27
					AES Bus 1-R  value= 28
					AES Bus 2-L  value= 29
					AES Bus 2-R  value= 30
					AES Bus 3-L  value= 31
					AES Bus 3-R  value= 32
					AES Bus 4-L  value= 33
					AES Bus 4-R  value= 34
					AES Bus 5-L  value= 35
					AES Bus 5-R  value= 36
					AES Bus 6-L  value= 37
					AES Bus 6-R  value= 38
					AES Bus 7-L  value= 39
					AES Bus 7-R  value= 40
					1kHz -20dBFS Tone  value= 17
					2kHz -20dBFS Tone  value= 18
					4kHz -20dBFS Tone  value= 19
					1kHz -18dBFS Tone  value= 20
					2kHz -18dBFS Tone  value= 21
					4kHz -18dBFS Tone  value= 22  "
		::= { iqdbe00CmdEntry 38907 }


	iqdbe00InputChanAssignInputDLinkLR OBJECT-TYPE
		SYNTAX		INTEGER { disable(0), enable(1) }
		MAX-ACCESS		read-write
		STATUS			current
		DESCRIPTION
				"TYPE: - Checkbox
				 PAGE: - Dolby Encoder- Input D
					Link L+R  cmdID= 38913 "
		::= { iqdbe00CmdEntry 38913 }


	iqdbe00AudioDolbyEncoderBitDepth OBJECT-TYPE
		SYNTAX		INTEGER {
							val_20_bits(0),
							val_16_bits(1)
							}
		MAX-ACCESS		read-write
		STATUS			current
		DESCRIPTION
				"TYPE: - RadiobuttonList
				 PAGE: - Dolby Encoder
					Bit Depth  cmdID= 38922
					20 bits  value= 0
					16 bits  value= 1  "
		::= { iqdbe00CmdEntry 38922 }


	iqdbe00AudioDolbyEncoderMetadataSource OBJECT-TYPE
		SYNTAX		INTEGER {
							val_Internal(1),
							val_External(0)
							}
		MAX-ACCESS		read-write
		STATUS			current
		DESCRIPTION
				"TYPE: - RadiobuttonList
				 PAGE: - Dolby Encoder
					Metadata Source  cmdID= 38923
					Internal  value= 1
					External  value= 0  "
		::= { iqdbe00CmdEntry 38923 }


	iqdbe00AudioDolbyEncoderEncodingMode OBJECT-TYPE
		SYNTAX		INTEGER {
							val_Dolby_E_Encoding(0),
							val_Pass_through(1)
							}
		MAX-ACCESS		read-write
		STATUS			current
		DESCRIPTION
				"TYPE: - RadiobuttonList
				 PAGE: - Dolby Encoder
					Encoding Mode  cmdID= 38920
					Dolby E Encoding  value= 0
					Pass-through  value= 1  "
		::= { iqdbe00CmdEntry 38920 }


	iqdbe00AudioDolbyEncoderReversionMode OBJECT-TYPE
		SYNTAX		INTEGER {
							val_Last_Used_valid(0),
							val_Internal(1)
							}
		MAX-ACCESS		read-write
		STATUS			current
		DESCRIPTION
				"TYPE: - RadiobuttonList
				 PAGE: - Dolby Encoder
					Reversion Mode  cmdID= 38924
					Last Used (valid)  value= 0
					Internal  value= 1  "
		::= { iqdbe00CmdEntry 38924 }


	iqdbe00DolbyEncoderInternalMetadataProgramConfig OBJECT-TYPE
		SYNTAX		INTEGER {
							val_5_1_2(0),
							val_5_1_2x1(1),
							val_4_4(2),
							val_4_2x2(3),
							val_4_2_2x1(4),
							val_4_4x1(5),
							val_4x2(6),
							val_3x2_2x1(7),
							val_2x2_4x1(8),
							val_2_6x1(9),
							val_8x1(10),
							val_5_1(11),
							val_4_2(12),
							val_4_2x1(13),
							val_3x2(14),
							val_2x2_2x1(15),
							val_2_4x1(16),
							val_6x1(17),
							val_4(18),
							val_2_2(19),
							val_2_2x1(20),
							val_4x1(21),
							val_7_1(22),
							val_7_1_Screen(23),
							val_User_Preset_1(24),
							val_User_Preset_2(25),
							val_User_Preset_3(26),
							val_User_Preset_4(27),
							val_User_Preset_5(28),
							val_User_Preset_6(29),
							val_User_Preset_7(30),
							val_User_Preset_8(31)
							}
		MAX-ACCESS		read-write
		STATUS			current
		DESCRIPTION
				"TYPE: - RadiobuttonList
				 PAGE: - Dolby Encoder- Internal Metadata
					Program Config  cmdID= 38921
					5.1+2  value= 0
					5.1+2x1  value= 1
					4+4  value= 2
					4+2x2  value= 3
					4+2+2x1  value= 4
					4+4x1  value= 5
					4x2  value= 6
					3x2+2x1  value= 7
					2x2+4x1  value= 8
					2+6x1  value= 9
					8x1  value= 10
					5.1  value= 11
					4+2  value= 12
					4+2x1  value= 13
					3x2  value= 14
					2x2+2x1  value= 15
					2+4x1  value= 16
					6x1  value= 17
					4  value= 18
					2+2  value= 19
					2+2x1  value= 20
					4x1  value= 21
					7.1  value= 22
					7.1 Screen  value= 23
					User Preset 1  value= 24
					User Preset 2  value= 25
					User Preset 3  value= 26
					User Preset 4  value= 27
					User Preset 5  value= 28
					User Preset 6  value= 29
					User Preset 7  value= 30
					User Preset 8  value= 31  "
		::= { iqdbe00CmdEntry 38921 }


	iqdbe00DolbyEncoderInternalMetadataProgramSel OBJECT-TYPE
		SYNTAX		INTEGER {
							val_Prog_1(0),
							val_Prog_2(1),
							val_Prog_3(2),
							val_Prog_4(3),
							val_Prog_5(4),
							val_Prog_6(5),
							val_Prog_7(6),
							val_Prog_8(7)
							}
		MAX-ACCESS		read-write
		STATUS			current
		DESCRIPTION
				"TYPE: - RadiobuttonList
				 PAGE: - Dolby Encoder- Internal Metadata
					Program Sel  cmdID= 38950
					Prog 1  value= 0
					Prog 2  value= 1
					Prog 3  value= 2
					Prog 4  value= 3
					Prog 5  value= 4
					Prog 6  value= 5
					Prog 7  value= 6
					Prog 8  value= 7  "
		::= { iqdbe00CmdEntry 38950 }


	iqdbe00DolbyEncoderInternalMetadataDialogueNorm OBJECT-TYPE
		SYNTAX		INTEGER
		MAX-ACCESS		read-write
		STATUS			current
		DESCRIPTION
				"TYPE: - Number
				 PAGE: - Dolby Encoder- Internal Metadata
					Dialogue Norm  cmdID= 38951  min= -31  max= -1  step= 1  format= %0.0f dB  div_scale= 1
					Min = -31 dB  Max = -1 dB  Step = 1 dB "
		::= { iqdbe00CmdEntry 38951 }


	iqdbe00DolbyEncoderInternalMetadataInputAssignAB OBJECT-TYPE
		SYNTAX		RollCallString
		MAX-ACCESS		read-only
		STATUS			current
		DESCRIPTION
				"TYPE: - Display
				 PAGE: - Dolby Encoder- Internal Metadata
					Input Assign A-B  cmdID= 38963  format=   "
		::= { iqdbe00CmdEntry 38963 }


	iqdbe00DolbyEncoderInternalMetadataInputAssignCD OBJECT-TYPE
		SYNTAX		RollCallString
		MAX-ACCESS		read-only
		STATUS			current
		DESCRIPTION
				"TYPE: - Display
				 PAGE: - Dolby Encoder- Internal Metadata
					Input Assign C-D  cmdID= 38964  format=   "
		::= { iqdbe00CmdEntry 38964 }


	iqdbe00DolbyEncoderInternalMetadataChannelMode OBJECT-TYPE
		SYNTAX		INTEGER {
							val_3_2_L_C_R_SL_SR(7),
							val_2_2_L_R_SL_SR(6),
							val_3_1_L_C_R_S(5),
							val_2_1_L_R_S(4),
							val_3_0_L_C_R(3),
							val_2_0_L_R(2),
							val_1_0_C(1)
							}
		MAX-ACCESS		read-write
		STATUS			current
		DESCRIPTION
				"TYPE: - RadiobuttonList
				 PAGE: - Dolby Encoder- Internal Metadata
					Channel Mode  cmdID= 38953
					3/2 (L C R SL SR)  value= 7
					2/2 (L R SL SR)  value= 6
					3/1 (L C R S)  value= 5
					2/1 (L R S)  value= 4
					3/0 (L C R)  value= 3
					2/0 (L R)  value= 2
					1/0 (C)  value= 1  "
		::= { iqdbe00CmdEntry 38953 }


	iqdbe00DolbyEncoderInternalMetadataLFEChannel OBJECT-TYPE
		SYNTAX		INTEGER { disable(0), enable(1) }
		MAX-ACCESS		read-write
		STATUS			current
		DESCRIPTION
				"TYPE: - Checkbox
				 PAGE: - Dolby Encoder- Internal Metadata
					LFE Channel  cmdID= 38955 "
		::= { iqdbe00CmdEntry 38955 }


	iqdbe00DolbyEncoderInternalMetadataBitstreamMode OBJECT-TYPE
		SYNTAX		INTEGER {
							val_Complete_Main(0),
							val_Music_and_Effects(1),
							val_Visually_Impaired(2),
							val_Hearing_Impaired(3),
							val_Dialogue(4),
							val_Commentary(5),
							val_Emergency(6),
							val(7)
							}
		MAX-ACCESS		read-write
		STATUS			current
		DESCRIPTION
				"TYPE: - RadiobuttonList
				 PAGE: - Dolby Encoder- Internal Metadata
					Bitstream Mode  cmdID= 38952
					Complete Main  value= 0
					Music and Effects  value= 1
					Visually Impaired  value= 2
					Hearing Impaired  value= 3
					Dialogue  value= 4
					Commentary  value= 5
					Emergency  value= 6
					--  value= 7  "
		::= { iqdbe00CmdEntry 38952 }


	iqdbe00DolbyEncoderInternalMetadataRFMode OBJECT-TYPE
		SYNTAX		INTEGER {
							val_None(0),
							val_Film_Standard(1),
							val_Film_Light(2),
							val_Music_Standard(3),
							val_Music_Light(4),
							val_Speech(5)
							}
		MAX-ACCESS		read-write
		STATUS			current
		DESCRIPTION
				"TYPE: - RadiobuttonList
				 PAGE: - Dolby Encoder- Internal Metadata
					RF Mode  cmdID= 38954
					None  value= 0
					Film Standard  value= 1
					Film Light  value= 2
					Music Standard  value= 3
					Music Light  value= 4
					Speech  value= 5  "
		::= { iqdbe00CmdEntry 38954 }


	iqdbe00DolbyEncoderInternalMetadataLineMode OBJECT-TYPE
		SYNTAX		INTEGER {
							val_None(0),
							val_Film_Standard(1),
							val_Film_Light(2),
							val_Music_Standard(3),
							val_Music_Light(4),
							val_Speech(5)
							}
		MAX-ACCESS		read-write
		STATUS			current
		DESCRIPTION
				"TYPE: - RadiobuttonList
				 PAGE: - Dolby Encoder- Internal Metadata
					Line Mode  cmdID= 38956
					None  value= 0
					Film Standard  value= 1
					Film Light  value= 2
					Music Standard  value= 3
					Music Light  value= 4
					Speech  value= 5  "
		::= { iqdbe00CmdEntry 38956 }


	iqdbe00InternalMetadataAudioProdInfoExists OBJECT-TYPE
		SYNTAX		INTEGER { disable(0), enable(1) }
		MAX-ACCESS		read-write
		STATUS			current
		DESCRIPTION
				"TYPE: - Checkbox
				 PAGE: - Dolby Encoder- Internal Metadata
					Exists  cmdID= 38957 "
		::= { iqdbe00CmdEntry 38957 }


	iqdbe00InternalMetadataAudioProdInfoMixLevel OBJECT-TYPE
		SYNTAX		INTEGER
		MAX-ACCESS		read-write
		STATUS			current
		DESCRIPTION
				"TYPE: - Number
				 PAGE: - Dolby Encoder- Internal Metadata
					Mix Level  cmdID= 38958  min= 80  max= 111  step= 1  format= %0.0f dB  div_scale= 1
					Min = 80 dB  Max = 111 dB  Step = 1 dB "
		::= { iqdbe00CmdEntry 38958 }


	iqdbe00InternalMetadataAudioProdInfoRoomType OBJECT-TYPE
		SYNTAX		INTEGER {
							val_Not_Indicated(0),
							val_Large_Room(1),
							val_Small_Room(2)
							}
		MAX-ACCESS		read-write
		STATUS			current
		DESCRIPTION
				"TYPE: - RadiobuttonList
				 PAGE: - Dolby Encoder- Internal Metadata
					Room Type  cmdID= 38959
					Not Indicated  value= 0
					Large Room  value= 1
					Small Room  value= 2  "
		::= { iqdbe00CmdEntry 38959 }


	iqdbe00DolbyEncoderInternalMetadataSurroundMode OBJECT-TYPE
		SYNTAX		INTEGER {
							val_Not_Indicated(0),
							val_Not_Dolby_Surround(1),
							val_Dolby_Surround(2)
							}
		MAX-ACCESS		read-write
		STATUS			current
		DESCRIPTION
				"TYPE: - RadiobuttonList
				 PAGE: - Dolby Encoder- Internal Metadata
					Surround Mode  cmdID= 38960
					Not Indicated  value= 0
					Not Dolby Surround  value= 1
					Dolby Surround  value= 2  "
		::= { iqdbe00CmdEntry 38960 }


	iqdbe00DolbyEncoderInternalMetadataCenterMixLevel OBJECT-TYPE
		SYNTAX		INTEGER {
							val_0_707_3dB(0),
							val_0_596_4_5dB(1),
							val_0_500_6dB(2)
							}
		MAX-ACCESS		read-write
		STATUS			current
		DESCRIPTION
				"TYPE: - RadiobuttonList
				 PAGE: - Dolby Encoder- Internal Metadata
					Center Mix Level  cmdID= 38961
					0.707(-3dB)  value= 0
					0.596(-4.5dB)  value= 1
					0.500(-6dB)  value= 2  "
		::= { iqdbe00CmdEntry 38961 }


	iqdbe00DolbyEncoderInternalMetadataSurroundMixLevel OBJECT-TYPE
		SYNTAX		INTEGER {
							val_0_707_3dB(0),
							val_0_596_4_5dB(1),
							val_0_000_Inf_dB(2)
							}
		MAX-ACCESS		read-write
		STATUS			current
		DESCRIPTION
				"TYPE: - RadiobuttonList
				 PAGE: - Dolby Encoder- Internal Metadata
					Surround Mix Level  cmdID= 38962
					0.707(-3dB)  value= 0
					0.596(-4.5dB)  value= 1
					0.000(-Inf dB)  value= 2  "
		::= { iqdbe00CmdEntry 38962 }


	iqdbe00InternalMetadataExtendedBSI1ExtBSI1Exists OBJECT-TYPE
		SYNTAX		INTEGER { disable(0), enable(1) }
		MAX-ACCESS		read-write
		STATUS			current
		DESCRIPTION
				"TYPE: - Checkbox
				 PAGE: - Dolby Encoder- Internal Metadata
					Ext BSI1 Exists  cmdID= 38965 "
		::= { iqdbe00CmdEntry 38965 }


	iqdbe00InternalMetadataExtendedBSI1StereoDownmixMode OBJECT-TYPE
		SYNTAX		INTEGER {
							val_Not_Indicated(0),
							val_LtRt_Prefered(1),
							val_LoRo_Prefered(2)
							}
		MAX-ACCESS		read-write
		STATUS			current
		DESCRIPTION
				"TYPE: - RadiobuttonList
				 PAGE: - Dolby Encoder- Internal Metadata
					Stereo Downmix Mode  cmdID= 38966
					Not Indicated  value= 0
					LtRt Prefered  value= 1
					LoRo Prefered  value= 2  "
		::= { iqdbe00CmdEntry 38966 }


	iqdbe00InternalMetadataExtendedBSI1LtRtCenterDownmix OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LtRt Center Downmix  cmdID= 38967
					+3.0 db  value= 0
					+1.5 dB  value= 1
					0.0 dB  value= 2
					-1.5 dB  value= 3
					-3.0 dB  value= 4
					-4.5 dB  value= 5
					-6.0 dB  value= 6
					-Inf dB  value= 7  "
		::= { iqdbe00CmdEntry 38967 }


	iqdbe00InternalMetadataExtendedBSI1LoRoCenterDownmix OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LoRo Center Downmix  cmdID= 38968
					+3.0 db  value= 0
					+1.5 dB  value= 1
					0.0 dB  value= 2
					-1.5 dB  value= 3
					-3.0 dB  value= 4
					-4.5 dB  value= 5
					-6.0 dB  value= 6
					-Inf dB  value= 7  "
		::= { iqdbe00CmdEntry 38968 }


	iqdbe00InternalMetadataExtendedBSI1LtRtSurroundDownm OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LtRt Surround Downm  cmdID= 38969
					+3.0 db  value= 0
					+1.5 dB  value= 1
					0.0 dB  value= 2
					-1.5 dB  value= 3
					-3.0 dB  value= 4
					-4.5 dB  value= 5
					-6.0 dB  value= 6
					-Inf dB  value= 7  "
		::= { iqdbe00CmdEntry 38969 }


	iqdbe00InternalMetadataExtendedBSI1LoRoSurroundDownm OBJECT-TYPE
		SYNTAX		INTEGER {
							val_3_0_db(0),
							val_1_5_dB(1),
							val_0_0_dB(2),
							val_1_5_dB(3),
							val_3_0_dB(4),
							val_4_5_dB(5),
							val_6_0_dB(6),
							val_Inf_dB(7)
							}
		MAX-ACCESS		read-write
		STATUS			current
		DESCRIPTION
				"TYPE: - RadiobuttonList
				 PAGE: - Dolby Encoder- Internal Metadata
					LoRo Surround Downm  cmdID= 38970
					+3.0 db  value= 0
					+1.5 dB  value= 1
					0.0 dB  value= 2
					-1.5 dB  value= 3
					-3.0 dB  value= 4
					-4.5 dB  value= 5
					-6.0 dB  value= 6
					-Inf dB  value= 7  "
		::= { iqdbe00CmdEntry 38970 }


	iqdbe00InternalMetadataExtendedBSI2ExtBSI2Exists OBJECT-TYPE
		SYNTAX		INTEGER { disable(0), enable(1) }
		MAX-ACCESS		read-write
		STATUS			current
		DESCRIPTION
				"TYPE: - Checkbox
				 PAGE: - Dolby Encoder- Internal Metadata
					Ext BSI2 Exists  cmdID= 38971 "
		::= { iqdbe00CmdEntry 38971 }


	iqdbe00InternalMetadataExtendedBSI2SurroundExMode OBJECT-TYPE
		SYNTAX		INTEGER {
							val_Not_Indicated(0),
							val_Not_Dolby_Surround(1),
							val_Dolby_Surround_Ex(2)
							}
		MAX-ACCESS		read-write
		STATUS			current
		DESCRIPTION
				"TYPE: - RadiobuttonList
				 PAGE: - Dolby Encoder- Internal Metadata
					Surround Ex Mode  cmdID= 38972
					Not Indicated  value= 0
					Not Dolby Surround   value= 1
					Dolby Surround Ex  value= 2  "
		::= { iqdbe00CmdEntry 38972 }


	iqdbe00InternalMetadataExtendedBSI2LowpassFilter OBJECT-TYPE
		SYNTAX		INTEGER { disable(0), enable(1) }
		MAX-ACCESS		read-write
		STATUS			current
		DESCRIPTION
				"TYPE: - Checkbox
				 PAGE: - Dolby Encoder- Internal Metadata
					Lowpass Filter  cmdID= 38973 "
		::= { iqdbe00CmdEntry 38973 }


	iqdbe00InternalMetadataExtendedBSI2LFEFilter OBJECT-TYPE
		SYNTAX		INTEGER { disable(0), enable(1) }
		MAX-ACCESS		read-write
		STATUS			current
		DESCRIPTION
				"TYPE: - Checkbox
				 PAGE: - Dolby Encoder- Internal Metadata
					LFE Filter  cmdID= 38974 "
		::= { iqdbe00CmdEntry 38974 }


	iqdbe00InternalMetadataExtendedBSI2SurrPhaseShiftFi OBJECT-TYPE
		SYNTAX		INTEGER { disable(0), enable(1) }
		MAX-ACCESS		read-write
		STATUS			current
		DESCRIPTION
				"TYPE: - Checkbox
				 PAGE: - Dolby Encoder- Internal Metadata
					Surr Phase Shift Fi  cmdID= 38975 "
		::= { iqdbe00CmdEntry 38975 }


	iqdbe00InternalMetadataExtendedBSI2Surr3dBAttenuator OBJECT-TYPE
		SYNTAX		INTEGER { disable(0), enable(1) }
		MAX-ACCESS		read-write
		STATUS			current
		DESCRIPTION
				"TYPE: - Checkbox
				 PAGE: - Dolby Encoder- Internal Metadata
					Surr 3dB Attenuator  cmdID= 38976 "
		::= { iqdbe00CmdEntry 38976 }


	iqdbe00DolbyEncoderInternalMetadataProgDescpt1 OBJECT-TYPE
		SYNTAX		RollCallString
		MAX-ACCESS		read-write
		STATUS			current
		DESCRIPTION
				"TYPE: - Editstring
				 PAGE: - Dolby Encoder- Internal Metadata
					Prog Desc pt1  cmdID= 38978  "
		::= { iqdbe00CmdEntry 38978 }


	iqdbe00DolbyEncoderInternalMetadataProgDescpt2 OBJECT-TYPE
		SYNTAX		RollCallString
		MAX-ACCESS		read-write
		STATUS			current
		DESCRIPTION
				"TYPE: - Editstring
				 PAGE: - Dolby Encoder- Internal Metadata
					Prog Desc pt2  cmdID= 38979  "
		::= { iqdbe00CmdEntry 38979 }


	iqdbe00DolbyEncoderInternalMetadataDolbyEncReset OBJECT-TYPE
		SYNTAX		INTEGER { noAction(0),val_Dolby_Enc_Reset(1) }
		MAX-ACCESS		read-write
		STATUS			current
		DESCRIPTION
				"TYPE: - Button
				 PAGE: - Dolby Encoder- Internal Metadata
					Dolby Enc Reset  cmdID= 39999  value= 1  "
		::= { iqdbe00CmdEntry 39999 }


	iqdbe00InternalMetadataProgPresetIntMD OBJECT-TYPE
		SYNTAX		INTEGER {
							val_This_Prog_Defaults(1),
							val_All_Prog_Defaults(2),
							val_Copy_Ext_Meta(3)
							}
		MAX-ACCESS		read-write
		STATUS			current
		DESCRIPTION
				"TYPE: - Button
				 PAGE: - Dolby Encoder- Internal Metadata
					This Prog Defaults  cmdID= 38980  value= 1
					All Prog Defaults  cmdID= 38980  value= 2
					Copy Ext Meta  cmdID= 38980  value= 3  "
		::= { iqdbe00CmdEntry 38980 }


	iqdbe00ProgPresetIntMDSaveUserPresetSelUserPreset OBJECT-TYPE
		SYNTAX		INTEGER {
							val_Preset_1(0),
							val_Preset_2(1),
							val_Preset_3(2),
							val_Preset_4(3),
							val_Preset_5(4),
							val_Preset_6(5),
							val_Preset_7(6),
							val_Preset_8(7)
							}
		MAX-ACCESS		read-write
		STATUS			current
		DESCRIPTION
				"TYPE: - RadiobuttonList
				 PAGE: - Dolby Encoder- Internal Metadata
					Sel User Preset  cmdID= 38981
					Preset 1  value= 0
					Preset 2  value= 1
					Preset 3  value= 2
					Preset 4  value= 3
					Preset 5  value= 4
					Preset 6  value= 5
					Preset 7  value= 6
					Preset 8  value= 7  "
		::= { iqdbe00CmdEntry 38981 }


	iqdbe00ProgPresetIntMDSaveUserPresetSavePreset OBJECT-TYPE
		SYNTAX		INTEGER { noAction(0),val_Save_Preset(1) }
		MAX-ACCESS		read-write
		STATUS			current
		DESCRIPTION
				"TYPE: - Button
				 PAGE: - Dolby Encoder- Internal Metadata
					Save Preset  cmdID= 38982  value= 1  "
		::= { iqdbe00CmdEntry 38982 }


	iqdbe00ProgPresetIntMDSaveUserPresetNamePreset OBJECT-TYPE
		SYNTAX		RollCallString
		MAX-ACCESS		read-write
		STATUS			current
		DESCRIPTION
				"TYPE: - Editstring
				 PAGE: - Dolby Encoder- Internal Metadata
					Name Preset  cmdID= 38983  "
		::= { iqdbe00CmdEntry 38983 }


	iqdbe00DolbyEncoderOutputMetadataProgramSel OBJECT-TYPE
		SYNTAX		INTEGER {
							val_Prog_1(0),
							val_Prog_2(1),
							val_Prog_3(2),
							val_Prog_4(3),
							val_Prog_5(4),
							val_Prog_6(5),
							val_Prog_7(6),
							val_Prog_8(7)
							}
		MAX-ACCESS		read-write
		STATUS			current
		DESCRIPTION
				"TYPE: - RadiobuttonList
				 PAGE: - Dolby Encoder- Output Metadata
					Program Sel  cmdID= 39000
					Prog 1  value= 0
					Prog 2  value= 1
					Prog 3  value= 2
					Prog 4  value= 3
					Prog 5  value= 4
					Prog 6  value= 5
					Prog 7  value= 6
					Prog 8  value= 7  "
		::= { iqdbe00CmdEntry 39000 }


	iqdbe00DolbyEncoderOutputMetadataProgramConfig OBJECT-TYPE
		SYNTAX		RollCallString
		MAX-ACCESS		read-only
		STATUS			current
		DESCRIPTION
				"TYPE: - Display
				 PAGE: - Dolby Encoder- Output Metadata
					Program Config  cmdID= 39001  format=   "
		::= { iqdbe00CmdEntry 39001 }


	iqdbe00DolbyEncoderOutputMetadataProgramNamept1 OBJECT-TYPE
		SYNTAX		RollCallString
		MAX-ACCESS		read-only
		STATUS			current
		DESCRIPTION
				"TYPE: - Display
				 PAGE: - Dolby Encoder- Output Metadata
					Program Name (pt1)  cmdID= 39026  format=   "
		::= { iqdbe00CmdEntry 39026 }


	iqdbe00DolbyEncoderOutputMetadataProgramNamept2 OBJECT-TYPE
		SYNTAX		RollCallString
		MAX-ACCESS		read-only
		STATUS			current
		DESCRIPTION
				"TYPE: - Display
				 PAGE: - Dolby Encoder- Output Metadata
					Program Name (pt2)  cmdID= 39027  format=   "
		::= { iqdbe00CmdEntry 39027 }


	iqdbe00DolbyEncoderOutputMetadataDialogueNorm OBJECT-TYPE
		SYNTAX		RollCallString
		MAX-ACCESS		read-only
		STATUS			current
		DESCRIPTION
				"TYPE: - Display
				 PAGE: - Dolby Encoder- Output Metadata
					Dialogue Norm  cmdID= 39028  format=   "
		::= { iqdbe00CmdEntry 39028 }


	iqdbe00DolbyEncoderOutputMetadataChannelMode OBJECT-TYPE
		SYNTAX		RollCallString
		MAX-ACCESS		read-only
		STATUS			current
		DESCRIPTION
				"TYPE: - Display
				 PAGE: - Dolby Encoder- Output Metadata
					Channel Mode  cmdID= 39002  format=   "
		::= { iqdbe00CmdEntry 39002 }


	iqdbe00DolbyEncoderOutputMetadataLFEChannel OBJECT-TYPE
		SYNTAX		RollCallString
		MAX-ACCESS		read-only
		STATUS			current
		DESCRIPTION
				"TYPE: - Display
				 PAGE: - Dolby Encoder- Output Metadata
					LFE Channel  cmdID= 39003  format=   "
		::= { iqdbe00CmdEntry 39003 }


	iqdbe00DolbyEncoderOutputMetadataBitstreamMode OBJECT-TYPE
		SYNTAX		RollCallString
		MAX-ACCESS		read-only
		STATUS			current
		DESCRIPTION
				"TYPE: - Display
				 PAGE: - Dolby Encoder- Output Metadata
					Bitstream Mode  cmdID= 39004  format=   "
		::= { iqdbe00CmdEntry 39004 }


	iqdbe00DolbyEncoderOutputMetadataRFMode OBJECT-TYPE
		SYNTAX		RollCallString
		MAX-ACCESS		read-only
		STATUS			current
		DESCRIPTION
				"TYPE: - Display
				 PAGE: - Dolby Encoder- Output Metadata
					RF Mode  cmdID= 39005  format=   "
		::= { iqdbe00CmdEntry 39005 }


	iqdbe00DolbyEncoderOutputMetadataLineMode OBJECT-TYPE
		SYNTAX		RollCallString
		MAX-ACCESS		read-only
		STATUS			current
		DESCRIPTION
				"TYPE: - Display
				 PAGE: - Dolby Encoder- Output Metadata
					Line Mode  cmdID= 39006  format=   "
		::= { iqdbe00CmdEntry 39006 }


	iqdbe00DolbyEncoderOutputMetadataCenterMixLevel OBJECT-TYPE
		SYNTAX		RollCallString
		MAX-ACCESS		read-only
		STATUS			current
		DESCRIPTION
				"TYPE: - Display
				 PAGE: - Dolby Encoder- Output Metadata
					Center Mix Level  cmdID= 39010  format=   "
		::= { iqdbe00CmdEntry 39010 }


	iqdbe00DolbyEncoderOutputMetadataSurroundMixLevel OBJECT-TYPE
		SYNTAX		RollCallString
		MAX-ACCESS		read-only
		STATUS			current
		DESCRIPTION
				"TYPE: - Display
				 PAGE: - Dolby Encoder- Output Metadata
					Surround Mix Level  cmdID= 39011  format=   "
		::= { iqdbe00CmdEntry 39011 }


	iqdbe00DolbyEncoderOutputMetadataSurrondMode OBJECT-TYPE
		SYNTAX		RollCallString
		MAX-ACCESS		read-only
		STATUS			current
		DESCRIPTION
				"TYPE: - Display
				 PAGE: - Dolby Encoder- Output Metadata
					Surrond Mode  cmdID= 39012  format=   "
		::= { iqdbe00CmdEntry 39012 }


	iqdbe00OutputMetadataAudioProdInfoExists OBJECT-TYPE
		SYNTAX		RollCallString
		MAX-ACCESS		read-only
		STATUS			current
		DESCRIPTION
				"TYPE: - Display
				 PAGE: - Dolby Encoder- Output Metadata
					Exists  cmdID= 39007  format=   "
		::= { iqdbe00CmdEntry 39007 }


	iqdbe00OutputMetadataAudioProdInfoMixLevel OBJECT-TYPE
		SYNTAX		RollCallString
		MAX-ACCESS		read-only
		STATUS			current
		DESCRIPTION
				"TYPE: - Display
				 PAGE: - Dolby Encoder- Output Metadata
					Mix Level  cmdID= 39008  format=   "
		::= { iqdbe00CmdEntry 39008 }


	iqdbe00OutputMetadataAudioProdInfoRoomType OBJECT-TYPE
		SYNTAX		RollCallString
		MAX-ACCESS		read-only
		STATUS			current
		DESCRIPTION
				"TYPE: - Display
				 PAGE: - Dolby Encoder- Output Metadata
					Room Type  cmdID= 39009  format=   "
		::= { iqdbe00CmdEntry 39009 }


	iqdbe00OutputMetadataExtendedBSI1Exists OBJECT-TYPE
		SYNTAX		RollCallString
		MAX-ACCESS		read-only
		STATUS			current
		DESCRIPTION
				"TYPE: - Display
				 PAGE: - Dolby Encoder- Output Metadata
					Exists  cmdID= 39013  format=   "
		::= { iqdbe00CmdEntry 39013 }


	iqdbe00OutputMetadataExtendedBSI1StereoDownmixMode OBJECT-TYPE
		SYNTAX		RollCallString
		MAX-ACCESS		read-only
		STATUS			current
		DESCRIPTION
				"TYPE: - Display
				 PAGE: - Dolby Encoder- Output Metadata
					Stereo Downmix Mode  cmdID= 39014  format=   "
		::= { iqdbe00CmdEntry 39014 }


	iqdbe00OutputMetadataExtendedBSI1LtRtCenMixLevel OBJECT-TYPE
		SYNTAX		RollCallString
		MAX-ACCESS		read-only
		STATUS			current
		DESCRIPTION
				"TYPE: - Display
				 PAGE: - Dolby Encoder- Output Metadata
					LtRt Cen Mix Level  cmdID= 39015  format=   "
		::= { iqdbe00CmdEntry 39015 }


	iqdbe00OutputMetadataExtendedBSI1LtRtSurMixLevel OBJECT-TYPE
		SYNTAX		RollCallString
		MAX-ACCESS		read-only
		STATUS			current
		DESCRIPTION
				"TYPE: - Display
				 PAGE: - Dolby Encoder- Output Metadata
					LtRt Sur Mix Level  cmdID= 39016  format=   "
		::= { iqdbe00CmdEntry 39016 }


	iqdbe00OutputMetadataExtendedBSI1LoRoCenMixLevel OBJECT-TYPE
		SYNTAX		RollCallString
		MAX-ACCESS		read-only
		STATUS			current
		DESCRIPTION
				"TYPE: - Display
				 PAGE: - Dolby Encoder- Output Metadata
					LoRo Cen Mix Level  cmdID= 39017  format=   "
		::= { iqdbe00CmdEntry 39017 }


	iqdbe00OutputMetadataExtendedBSI1LoRoSurMixLevel OBJECT-TYPE
		SYNTAX		RollCallString
		MAX-ACCESS		read-only
		STATUS			current
		DESCRIPTION
				"TYPE: - Display
				 PAGE: - Dolby Encoder- Output Metadata
					LoRo Sur Mix Level  cmdID= 39018  format=   "
		::= { iqdbe00CmdEntry 39018 }


	iqdbe00OutputMetadataExtendedBSI2Exists OBJECT-TYPE
		SYNTAX		RollCallString
		MAX-ACCESS		read-only
		STATUS			current
		DESCRIPTION
				"TYPE: - Display
				 PAGE: - Dolby Encoder- Output Metadata
					Exists  cmdID= 39019  format=   "
		::= { iqdbe00CmdEntry 39019 }


	iqdbe00OutputMetadataExtendedBSI2SurExMode OBJECT-TYPE
		SYNTAX		RollCallString
		MAX-ACCESS		read-only
		STATUS			current
		DESCRIPTION
				"TYPE: - Display
				 PAGE: - Dolby Encoder- Output Metadata
					Sur Ex Mode  cmdID= 39020  format=   "
		::= { iqdbe00CmdEntry 39020 }


	iqdbe00OutputMetadataExtendedBSI2LowpassFilter OBJECT-TYPE
		SYNTAX		RollCallString
		MAX-ACCESS		read-only
		STATUS			current
		DESCRIPTION
				"TYPE: - Display
				 PAGE: - Dolby Encoder- Output Metadata
					Lowpass Filter  cmdID= 39021  format=   "
		::= { iqdbe00CmdEntry 39021 }


	iqdbe00OutputMetadataExtendedBSI2LFEFilter OBJECT-TYPE
		SYNTAX		RollCallString
		MAX-ACCESS		read-only
		STATUS			current
		DESCRIPTION
				"TYPE: - Display
				 PAGE: - Dolby Encoder- Output Metadata
					LFE Filter  cmdID= 39022  format=   "
		::= { iqdbe00CmdEntry 39022 }


	iqdbe00OutputMetadataExtendedBSI2SurPhshiftFilter OBJECT-TYPE
		SYNTAX		RollCallString
		MAX-ACCESS		read-only
		STATUS			current
		DESCRIPTION
				"TYPE: - Display
				 PAGE: - Dolby Encoder- Output Metadata
					Sur Ph shift Filter  cmdID= 39023  format=   "
		::= { iqdbe00CmdEntry 39023 }


	iqdbe00OutputMetadataExtendedBSI2Sur3dBAttenuator OBJECT-TYPE
		SYNTAX		RollCallString
		MAX-ACCESS		read-only
		STATUS			current
		DESCRIPTION
				"TYPE: - Display
				 PAGE: - Dolby Encoder- Output Metadata
					Sur 3dB Attenuator  cmdID= 39024  format=   "
		::= { iqdbe00CmdEntry 39024 }


	iqdbe00AudioDolbyEncoderFirmwareVersion OBJECT-TYPE
		SYNTAX		RollCallString
		MAX-ACCESS		read-only
		STATUS			current
		DESCRIPTION
				"TYPE: - Display
				 PAGE: - Dolby Encoder
					Firmware Version  cmdID= 38700  format=   "
		::= { iqdbe00CmdEntry 38700 }


	iqdbe00AudioVidDelayInternalDelay OBJECT-TYPE
		SYNTAX		RollCallString
		MAX-ACCESS		read-only
		STATUS			current
		DESCRIPTION
				"TYPE: - Display
				 PAGE: - Vid. Delay
					Internal Delay  cmdID= 33025  format=   "
		::= { iqdbe00CmdEntry 33025 }


	iqdbe00AudioVidDelayDelayMode OBJECT-TYPE
		SYNTAX		INTEGER {
							val_Minimum_Audio(3),
							val_Frames(4),
							val_Manual_H_V(5),
							val_Manual_ms(6)
							}
		MAX-ACCESS		read-write
		STATUS			current
		DESCRIPTION
				"TYPE: - RadiobuttonList
				 PAGE: - Vid. Delay
					Delay Mode  cmdID= 33026
					Minimum Audio  value= 3
					Frames  value= 4
					Manual H/V  value= 5
					Manual ms  value= 6  "
		::= { iqdbe00CmdEntry 33026 }


	iqdbe00VidDelaySetDelayDelayFrames OBJECT-TYPE
		SYNTAX		INTEGER
		MAX-ACCESS		read-write
		STATUS			current
		DESCRIPTION
				"TYPE: - Number
				 PAGE: - Vid. Delay
					Delay Frames  cmdID= 33024  min= 0  max= 11  step= 1  format= %0.0f frames  div_scale= 1
					Min = 0 frames  Max = 11 frames  Step = 1 frames "
		::= { iqdbe00CmdEntry 33024 }


	iqdbe00VidDelaySetDelayVerticalTiming OBJECT-TYPE
		SYNTAX		INTEGER
		MAX-ACCESS		read-write
		STATUS			current
		DESCRIPTION
				"TYPE: - Number
				 PAGE: - Vid. Delay
					Vertical Timing  cmdID= 33022  min= -1500  max= 1500  step= 1  format= %0.0f lines  div_scale= 1
					Min = -1500 lines  Max = 1500 lines  Step = 1 lines "
		::= { iqdbe00CmdEntry 33022 }


	iqdbe00VidDelaySetDelayHorizontalTiming OBJECT-TYPE
		SYNTAX		INTEGER
		MAX-ACCESS		read-write
		STATUS			current
		DESCRIPTION
				"TYPE: - Number
				 PAGE: - Vid. Delay
					Horizontal Timing  cmdID= 33021  min= -3000  max= 3000  step= 1  format= %0.0f pixels  div_scale= 1
					Min = -3000 pixels  Max = 3000 pixels  Step = 1 pixels "
		::= { iqdbe00CmdEntry 33021 }


	iqdbe00VidDelaySetDelayDelayms OBJECT-TYPE
		SYNTAX		INTEGER
		MAX-ACCESS		read-write
		STATUS			current
		DESCRIPTION
				"TYPE: - Number
				 PAGE: - Vid. Delay
					Delay ms  cmdID= 33027  min= -48000  max= 48000  step= 5  format= %0.2f ms  div_scale= 100
					Min = -480.00 ms  Max = 480.00 ms  Step = 0.05 ms "
		::= { iqdbe00CmdEntry 33027 }


	iqdbe00UtilsPatternsPatternEnable OBJECT-TYPE
		SYNTAX		INTEGER { disable(0), enable(1) }
		MAX-ACCESS		read-write
		STATUS			current
		DESCRIPTION
				"TYPE: - Checkbox
				 PAGE: - Utils
					Pattern Enable  cmdID= 33038 "
		::= { iqdbe00CmdEntry 33038 }


	iqdbe00UtilsPatternsScrollPattern OBJECT-TYPE
		SYNTAX		INTEGER { disable(0), enable(1) }
		MAX-ACCESS		read-write
		STATUS			current
		DESCRIPTION
				"TYPE: - Checkbox
				 PAGE: - Utils
					Scroll Pattern  cmdID= 33040 "
		::= { iqdbe00CmdEntry 33040 }


	iqdbe00UtilsPatternsPatternType OBJECT-TYPE
		SYNTAX		INTEGER {
							val_100_Color_Bars(1),
							val_75_Color_Bars(2),
							val_SMPTE_Bars(3),
							val_Tartan_Bars(4),
							val_Pluge(5),
							val_Ramp(6),
							val_Sweep(7),
							val_Pulse_Bar(8),
							val_Burst(9),
							val_Black(10)
							}
		MAX-ACCESS		read-write
		STATUS			current
		DESCRIPTION
				"TYPE: - RadiobuttonList
				 PAGE: - Utils
					Pattern Type  cmdID= 33039
					100% Color Bars  value= 1
					75% Color Bars  value= 2
					SMPTE Bars  value= 3
					Tartan Bars  value= 4
					Pluge  value= 5
					Ramp  value= 6
					Sweep  value= 7
					Pulse & Bar  value= 8
					Burst  value= 9
					Black  value= 10  "
		::= { iqdbe00CmdEntry 33039 }


	iqdbe00AudioUtilsANCblankonMismat OBJECT-TYPE
		SYNTAX		INTEGER { disable(0), enable(1) }
		MAX-ACCESS		read-write
		STATUS			current
		DESCRIPTION
				"TYPE: - Checkbox
				 PAGE: - Utils
					ANC blank on Mismat  cmdID= 33036 "
		::= { iqdbe00CmdEntry 33036 }


	iqdbe00UtilsFreezeForceFreeze OBJECT-TYPE
		SYNTAX		INTEGER { disable(0), enable(1) }
		MAX-ACCESS		read-write
		STATUS			current
		DESCRIPTION
				"TYPE: - Checkbox
				 PAGE: - Utils
					Force Freeze  cmdID= 33032 "
		::= { iqdbe00CmdEntry 33032 }


	iqdbe00UtilsFreezeFreezeType OBJECT-TYPE
		SYNTAX		INTEGER {
							val_Frame(0),
							val_Field(1)
							}
		MAX-ACCESS		read-write
		STATUS			current
		DESCRIPTION
				"TYPE: - RadiobuttonList
				 PAGE: - Utils
					Freeze Type  cmdID= 33033
					Frame  value= 0
					Field  value= 1  "
		::= { iqdbe00CmdEntry 33033 }


	iqdbe00UtilsMonochrome OBJECT-TYPE
		SYNTAX		INTEGER { disable(0), enable(1) }
		MAX-ACCESS		read-write
		STATUS			current
		DESCRIPTION
				"TYPE: - Checkbox
				 PAGE: - Utils
					Monochrome  cmdID= 33034 "
		::= { iqdbe00CmdEntry 33034 }


	iqdbe00UtilsMonochromeMonochromeType OBJECT-TYPE
		SYNTAX		INTEGER {
							val_Y_only(0),
							val_C_only(1)
							}
		MAX-ACCESS		read-write
		STATUS			current
		DESCRIPTION
				"TYPE: - RadiobuttonList
				 PAGE: - Utils
					Monochrome Type  cmdID= 33035
					Y only  value= 0
					C only  value= 1  "
		::= { iqdbe00CmdEntry 33035 }


	iqdbe00UtilsVBIBlankingANCMode OBJECT-TYPE
		SYNTAX		INTEGER {
							val_Pass_Input_ANC(0),
							val_Blank_HANC(2),
							val_Blank_All_ANC(1)
							}
		MAX-ACCESS		read-write
		STATUS			current
		DESCRIPTION
				"TYPE: - RadiobuttonList
				 PAGE: - Utils
					ANC Mode  cmdID= 33037
					Pass Input ANC  value= 0
					Blank HANC  value= 2
					Blank All ANC  value= 1  "
		::= { iqdbe00CmdEntry 33037 }


	iqdbe00UtilsVBIBlankingStandard OBJECT-TYPE
		SYNTAX		INTEGER {
							val_1125_1080_30i(6),
							val_1125_1080_30p(9),
							val_1125_1080_30sf(34),
							val_1125_1080_29i(7),
							val_1125_1080_29p(10),
							val_1125_1080_29sf(35),
							val_1125_1080_25i(8),
							val_1125_1080_25p(11),
							val_1125_1080_25sf(36),
							val_1125_1080_24p(12),
							val_1125_1080_24sf(23),
							val_1125_1080_23p(13),
							val_1125_1080_23sf(24),
							val_1125_1035_30i(1),
							val_1125_1035_29i(2),
							val_750_720_60p(16),
							val_750_720_59p(17),
							val_750_720_50p(30),
							val_525_480_29i(19),
							val_625_576_25i(20)
							}
		MAX-ACCESS		read-write
		STATUS			current
		DESCRIPTION
				"TYPE: - RadiobuttonList
				 PAGE: - Utils
					Standard  cmdID= 37200
					1125(1080)/30i  value= 6
					1125(1080)/30p  value= 9
					1125(1080)/30sf  value= 34
					1125(1080)/29i  value= 7
					1125(1080)/29p  value= 10
					1125(1080)/29sf  value= 35
					1125(1080)/25i  value= 8
					1125(1080)/25p  value= 11
					1125(1080)/25sf  value= 36
					1125(1080)/24p  value= 12
					1125(1080)/24sf  value= 23
					1125(1080)/23p  value= 13
					1125(1080)/23sf  value= 24
					1125(1035)/30i  value= 1
					1125(1035)/29i  value= 2
					750(720)/60p  value= 16
					750(720)/59p  value= 17
					750(720)/50p  value= 30
					525(480)/29i  value= 19
					625(576)/25i  value= 20  "
		::= { iqdbe00CmdEntry 37200 }


	iqdbe00UtilsVBIBlankingBlankAll OBJECT-TYPE
		SYNTAX		INTEGER { noAction(0),val_Blank_All(1) }
		MAX-ACCESS		read-write
		STATUS			current
		DESCRIPTION
				"TYPE: - Button
				 PAGE: - Utils
					Blank All  cmdID= 37201  value= 1  "
		::= { iqdbe00CmdEntry 37201 }


	iqdbe00UtilsVBIBlankingPassAll OBJECT-TYPE
		SYNTAX		INTEGER { noAction(0),val_Pass_All(1) }
		MAX-ACCESS		read-write
		STATUS			current
		DESCRIPTION
				"TYPE: - Button
				 PAGE: - Utils
					Pass All  cmdID= 37202  value= 1  "
		::= { iqdbe00CmdEntry 37202 }


	iqdbe00UtilsVBIBlankingBlank1 OBJECT-TYPE
		SYNTAX		INTEGER { disable(0), enable(1) }
		MAX-ACCESS		read-write
		STATUS			current
		DESCRIPTION
				"TYPE: - Checkbox
				 PAGE: - Utils
					Blank 1  cmdID= 37210 "
		::= { iqdbe00CmdEntry 37210 }


	iqdbe00UtilsVBIBlankingBlank2 OBJECT-TYPE
		SYNTAX		INTEGER { disable(0), enable(1) }
		MAX-ACCESS		read-write
		STATUS			current
		DESCRIPTION
				"TYPE: - Checkbox
				 PAGE: - Utils
					Blank 2  cmdID= 37211 "
		::= { iqdbe00CmdEntry 37211 }


	iqdbe00UtilsVBIBlankingBlank3 OBJECT-TYPE
		SYNTAX		INTEGER { disable(0), enable(1) }
		MAX-ACCESS		read-write
		STATUS			current
		DESCRIPTION
				"TYPE: - Checkbox
				 PAGE: - Utils
					Blank 3  cmdID= 37212 "
		::= { iqdbe00CmdEntry 37212 }


	iqdbe00UtilsVBIBlankingBlank4 OBJECT-TYPE
		SYNTAX		INTEGER { disable(0), enable(1) }
		MAX-ACCESS		read-write
		STATUS			current
		DESCRIPTION
				"TYPE: - Checkbox
				 PAGE: - Utils
					Blank 4  cmdID= 37213 "
		::= { iqdbe00CmdEntry 37213 }


	iqdbe00UtilsVBIBlankingBlank5 OBJECT-TYPE
		SYNTAX		INTEGER { disable(0), enable(1) }
		MAX-ACCESS		read-write
		STATUS			current
		DESCRIPTION
				"TYPE: - Checkbox
				 PAGE: - Utils
					Blank 5  cmdID= 37214 "
		::= { iqdbe00CmdEntry 37214 }


	iqdbe00UtilsVBIBlankingBlank6 OBJECT-TYPE
		SYNTAX		INTEGER { disable(0), enable(1) }
		MAX-ACCESS		read-write
		STATUS			current
		DESCRIPTION
				"TYPE: - Checkbox
				 PAGE: - Utils
					Blank 6  cmdID= 37215 "
		::= { iqdbe00CmdEntry 37215 }


	iqdbe00UtilsVBIBlankingBlank7 OBJECT-TYPE
		SYNTAX		INTEGER { disable(0), enable(1) }
		MAX-ACCESS		read-write
		STATUS			current
		DESCRIPTION
				"TYPE: - Checkbox
				 PAGE: - Utils
					Blank 7  cmdID= 37216 "
		::= { iqdbe00CmdEntry 37216 }


	iqdbe00UtilsVBIBlankingBlank8 OBJECT-TYPE
		SYNTAX		INTEGER { disable(0), enable(1) }
		MAX-ACCESS		read-write
		STATUS			current
		DESCRIPTION
				"TYPE: - Checkbox
				 PAGE: - Utils
					Blank 8  cmdID= 37217 "
		::= { iqdbe00CmdEntry 37217 }


	iqdbe00UtilsVBIBlankingBlank9 OBJECT-TYPE
		SYNTAX		INTEGER { disable(0), enable(1) }
		MAX-ACCESS		read-write
		STATUS			current
		DESCRIPTION
				"TYPE: - Checkbox
				 PAGE: - Utils
					Blank 9  cmdID= 37218 "
		::= { iqdbe00CmdEntry 37218 }


	iqdbe00UtilsVBIBlankingBlank10 OBJECT-TYPE
		SYNTAX		INTEGER { disable(0), enable(1) }
		MAX-ACCESS		read-write
		STATUS			current
		DESCRIPTION
				"TYPE: - Checkbox
				 PAGE: - Utils
					Blank 10  cmdID= 37219 "
		::= { iqdbe00CmdEntry 37219 }


	iqdbe00UtilsVBIBlankingBlank11 OBJECT-TYPE
		SYNTAX		INTEGER { disable(0), enable(1) }
		MAX-ACCESS		read-write
		STATUS			current
		DESCRIPTION
				"TYPE: - Checkbox
				 PAGE: - Utils
					Blank 11  cmdID= 37220 "
		::= { iqdbe00CmdEntry 37220 }


	iqdbe00UtilsVBIBlankingBlank12 OBJECT-TYPE
		SYNTAX		INTEGER { disable(0), enable(1) }
		MAX-ACCESS		read-write
		STATUS			current
		DESCRIPTION
				"TYPE: - Checkbox
				 PAGE: - Utils
					Blank 12  cmdID= 37221 "
		::= { iqdbe00CmdEntry 37221 }


	iqdbe00UtilsVBIBlankingBlank13 OBJECT-TYPE
		SYNTAX		INTEGER { disable(0), enable(1) }
		MAX-ACCESS		read-write
		STATUS			current
		DESCRIPTION
				"TYPE: - Checkbox
				 PAGE: - Utils
					Blank 13  cmdID= 37222 "
		::= { iqdbe00CmdEntry 37222 }


	iqdbe00UtilsVBIBlankingBlank14 OBJECT-TYPE
		SYNTAX		INTEGER { disable(0), enable(1) }
		MAX-ACCESS		read-write
		STATUS			current
		DESCRIPTION
				"TYPE: - Checkbox
				 PAGE: - Utils
					Blank 14  cmdID= 37223 "
		::= { iqdbe00CmdEntry 37223 }


	iqdbe00UtilsVBIBlankingBlank15 OBJECT-TYPE
		SYNTAX		INTEGER { disable(0), enable(1) }
		MAX-ACCESS		read-write
		STATUS			current
		DESCRIPTION
				"TYPE: - Checkbox
				 PAGE: - Utils
					Blank 15  cmdID= 37224 "
		::= { iqdbe00CmdEntry 37224 }


	iqdbe00UtilsVBIBlankingBlank16 OBJECT-TYPE
		SYNTAX		INTEGER { disable(0), enable(1) }
		MAX-ACCESS		read-write
		STATUS			current
		DESCRIPTION
				"TYPE: - Checkbox
				 PAGE: - Utils
					Blank 16  cmdID= 37225 "
		::= { iqdbe00CmdEntry 37225 }


	iqdbe00UtilsVBIBlankingBlank17 OBJECT-TYPE
		SYNTAX		INTEGER { disable(0), enable(1) }
		MAX-ACCESS		read-write
		STATUS			current
		DESCRIPTION
				"TYPE: - Checkbox
				 PAGE: - Utils
					Blank 17  cmdID= 37226 "
		::= { iqdbe00CmdEntry 37226 }


	iqdbe00UtilsVBIBlankingBlank18 OBJECT-TYPE
		SYNTAX		INTEGER { disable(0), enable(1) }
		MAX-ACCESS		read-write
		STATUS			current
		DESCRIPTION
				"TYPE: - Checkbox
				 PAGE: - Utils
					Blank 18  cmdID= 37227 "
		::= { iqdbe00CmdEntry 37227 }


	iqdbe00UtilsVBIBlankingBlank19 OBJECT-TYPE
		SYNTAX		INTEGER { disable(0), enable(1) }
		MAX-ACCESS		read-write
		STATUS			current
		DESCRIPTION
				"TYPE: - Checkbox
				 PAGE: - Utils
					Blank 19  cmdID= 37228 "
		::= { iqdbe00CmdEntry 37228 }


	iqdbe00UtilsVBIBlankingBlank20 OBJECT-TYPE
		SYNTAX		INTEGER { disable(0), enable(1) }
		MAX-ACCESS		read-write
		STATUS			current
		DESCRIPTION
				"TYPE: - Checkbox
				 PAGE: - Utils
					Blank 20  cmdID= 37229 "
		::= { iqdbe00CmdEntry 37229 }


	iqdbe00UtilsVBIBlankingBlank21 OBJECT-TYPE
		SYNTAX		INTEGER { disable(0), enable(1) }
		MAX-ACCESS		read-write
		STATUS			current
		DESCRIPTION
				"TYPE: - Checkbox
				 PAGE: - Utils
					Blank 21  cmdID= 37230 "
		::= { iqdbe00CmdEntry 37230 }


	iqdbe00UtilsVBIBlankingBlank22 OBJECT-TYPE
		SYNTAX		INTEGER { disable(0), enable(1) }
		MAX-ACCESS		read-write
		STATUS			current
		DESCRIPTION
				"TYPE: - Checkbox
				 PAGE: - Utils
					Blank 22  cmdID= 37231 "
		::= { iqdbe00CmdEntry 37231 }


	iqdbe00UtilsVBIBlankingBlank23 OBJECT-TYPE
		SYNTAX		INTEGER { disable(0), enable(1) }
		MAX-ACCESS		read-write
		STATUS			current
		DESCRIPTION
				"TYPE: - Checkbox
				 PAGE: - Utils
					Blank 23  cmdID= 37232 "
		::= { iqdbe00CmdEntry 37232 }


	iqdbe00UtilsVBIBlankingBlank24 OBJECT-TYPE
		SYNTAX		INTEGER { disable(0), enable(1) }
		MAX-ACCESS		read-write
		STATUS			current
		DESCRIPTION
				"TYPE: - Checkbox
				 PAGE: - Utils
					Blank 24  cmdID= 37233 "
		::= { iqdbe00CmdEntry 37233 }


	iqdbe00UtilsVBIBlankingBlank25 OBJECT-TYPE
		SYNTAX		INTEGER { disable(0), enable(1) }
		MAX-ACCESS		read-write
		STATUS			current
		DESCRIPTION
				"TYPE: - Checkbox
				 PAGE: - Utils
					Blank 25  cmdID= 37234 "
		::= { iqdbe00CmdEntry 37234 }


	iqdbe00UtilsVBIBlankingBlank26 OBJECT-TYPE
		SYNTAX		INTEGER { disable(0), enable(1) }
		MAX-ACCESS		read-write
		STATUS			current
		DESCRIPTION
				"TYPE: - Checkbox
				 PAGE: - Utils
					Blank 26  cmdID= 37235 "
		::= { iqdbe00CmdEntry 37235 }


	iqdbe00UtilsVBIBlankingBlank27 OBJECT-TYPE
		SYNTAX		INTEGER { disable(0), enable(1) }
		MAX-ACCESS		read-write
		STATUS			current
		DESCRIPTION
				"TYPE: - Checkbox
				 PAGE: - Utils
					Blank 27  cmdID= 37236 "
		::= { iqdbe00CmdEntry 37236 }


	iqdbe00UtilsVBIBlankingBlank28 OBJECT-TYPE
		SYNTAX		INTEGER { disable(0), enable(1) }
		MAX-ACCESS		read-write
		STATUS			current
		DESCRIPTION
				"TYPE: - Checkbox
				 PAGE: - Utils
					Blank 28  cmdID= 37237 "
		::= { iqdbe00CmdEntry 37237 }


	iqdbe00UtilsVBIBlankingBlank29 OBJECT-TYPE
		SYNTAX		INTEGER { disable(0), enable(1) }
		MAX-ACCESS		read-write
		STATUS			current
		DESCRIPTION
				"TYPE: - Checkbox
				 PAGE: - Utils
					Blank 29  cmdID= 37238 "
		::= { iqdbe00CmdEntry 37238 }


	iqdbe00UtilsVBIBlankingBlank30 OBJECT-TYPE
		SYNTAX		INTEGER { disable(0), enable(1) }
		MAX-ACCESS		read-write
		STATUS			current
		DESCRIPTION
				"TYPE: - Checkbox
				 PAGE: - Utils
					Blank 30  cmdID= 37239 "
		::= { iqdbe00CmdEntry 37239 }


	iqdbe00UtilsVBIBlankingBlank31 OBJECT-TYPE
		SYNTAX		INTEGER { disable(0), enable(1) }
		MAX-ACCESS		read-write
		STATUS			current
		DESCRIPTION
				"TYPE: - Checkbox
				 PAGE: - Utils
					Blank 31  cmdID= 37240 "
		::= { iqdbe00CmdEntry 37240 }


	iqdbe00UtilsVBIBlankingBlank32 OBJECT-TYPE
		SYNTAX		INTEGER { disable(0), enable(1) }
		MAX-ACCESS		read-write
		STATUS			current
		DESCRIPTION
				"TYPE: - Checkbox
				 PAGE: - Utils
					Blank 32  cmdID= 37241 "
		::= { iqdbe00CmdEntry 37241 }


	iqdbe00UtilsVBIBlankingBlank33 OBJECT-TYPE
		SYNTAX		INTEGER { disable(0), enable(1) }
		MAX-ACCESS		read-write
		STATUS			current
		DESCRIPTION
				"TYPE: - Checkbox
				 PAGE: - Utils
					Blank 33  cmdID= 37242 "
		::= { iqdbe00CmdEntry 37242 }


	iqdbe00UtilsVBIBlankingBlank34 OBJECT-TYPE
		SYNTAX		INTEGER { disable(0), enable(1) }
		MAX-ACCESS		read-write
		STATUS			current
		DESCRIPTION
				"TYPE: - Checkbox
				 PAGE: - Utils
					Blank 34  cmdID= 37243 "
		::= { iqdbe00CmdEntry 37243 }


	iqdbe00RecallMemory OBJECT-TYPE
		SYNTAX		INTEGER {
							val_None_Selected(0),
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Recall Memory  cmdID= 37100
					None Selected  value= 0
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqdbe00CmdEntry 37100 }


	iqdbe00SelMemory OBJECT-TYPE
		SYNTAX		INTEGER {
							val_User_Memory_1(1),
							val_User_Memory_2(2),
							val_User_Memory_3(3),
							val_User_Memory_4(4),
							val_User_Memory_5(5),
							val_User_Memory_6(6),
							val_User_Memory_7(7),
							val_User_Memory_8(8),
							val_User_Memory_9(9),
							val_User_Memory_10(10),
							val_User_Memory_11(11),
							val_User_Memory_12(12),
							val_User_Memory_13(13),
							val_User_Memory_14(14),
							val_User_Memory_15(15),
							val_User_Memory_16(16)
							}
		MAX-ACCESS		read-write
		STATUS			current
		DESCRIPTION
				"TYPE: - RadiobuttonList
				 PAGE: - Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqdbe00CmdEntry 37101 }


	iqdbe00SaveMemory OBJECT-TYPE
		SYNTAX		INTEGER { noAction(0),val_Save_Memory(1) }
		MAX-ACCESS		read-write
		STATUS			current
		DESCRIPTION
				"TYPE: - Button
				 PAGE: - Memories
					Save Memory  cmdID= 37102  value= 1  "
		::= { iqdbe00CmdEntry 37102 }


	iqdbe00ClearMemory OBJECT-TYPE
		SYNTAX		INTEGER { noAction(0),val_Clear_Memory(1) }
		MAX-ACCESS		read-write
		STATUS			current
		DESCRIPTION
				"TYPE: - Button
				 PAGE: - Memories
					Clear Memory  cmdID= 37105  value= 1  "
		::= { iqdbe00CmdEntry 37105 }


	iqdbe00MemoryNameChangeName OBJECT-TYPE
		SYNTAX		RollCallString
		MAX-ACCESS		read-write
		STATUS			current
		DESCRIPTION
				"TYPE: - Editstring
				 PAGE: - Memories
					Change Name  cmdID= 37103  "
		::= { iqdbe00CmdEntry 37103 }


	iqdbe00MemoryNameLastUserMemory OBJECT-TYPE
		SYNTAX		RollCallString
		MAX-ACCESS		read-only
		STATUS			current
		DESCRIPTION
				"TYPE: - Display
				 PAGE: - Memories
					Last User Memory  cmdID= 37104  format=   "
		::= { iqdbe00CmdEntry 37104 }


	iqdbe00MemoryName1 OBJECT-TYPE
		SYNTAX		RollCallString
		MAX-ACCESS		read-only
		STATUS			current
		DESCRIPTION
				"TYPE: - Display
				 PAGE: - Memories
					Memory Name1  cmdID= 37106  format=   "
		::= { iqdbe00CmdEntry 37106 }


	iqdbe00MemoryName2 OBJECT-TYPE
		SYNTAX		RollCallString
		MAX-ACCESS		read-only
		STATUS			current
		DESCRIPTION
				"TYPE: - Display
				 PAGE: - Memories
					Memory Name2  cmdID= 37107  format=   "
		::= { iqdbe00CmdEntry 37107 }


	iqdbe00MemoryName3 OBJECT-TYPE
		SYNTAX		RollCallString
		MAX-ACCESS		read-only
		STATUS			current
		DESCRIPTION
				"TYPE: - Display
				 PAGE: - Memories
					Memory Name3  cmdID= 37108  format=   "
		::= { iqdbe00CmdEntry 37108 }


	iqdbe00MemoryName4 OBJECT-TYPE
		SYNTAX		RollCallString
		MAX-ACCESS		read-only
		STATUS			current
		DESCRIPTION
				"TYPE: - Display
				 PAGE: - Memories
					Memory Name4  cmdID= 37109  format=   "
		::= { iqdbe00CmdEntry 37109 }


	iqdbe00MemoryName5 OBJECT-TYPE
		SYNTAX		RollCallString
		MAX-ACCESS		read-only
		STATUS			current
		DESCRIPTION
				"TYPE: - Display
				 PAGE: - Memories
					Memory Name5  cmdID= 37110  format=   "
		::= { iqdbe00CmdEntry 37110 }


	iqdbe00MemoryName6 OBJECT-TYPE
		SYNTAX		RollCallString
		MAX-ACCESS		read-only
		STATUS			current
		DESCRIPTION
				"TYPE: - Display
				 PAGE: - Memories
					Memory Name6  cmdID= 37111  format=   "
		::= { iqdbe00CmdEntry 37111 }


	iqdbe00MemoryName7 OBJECT-TYPE
		SYNTAX		RollCallString
		MAX-ACCESS		read-only
		STATUS			current
		DESCRIPTION
				"TYPE: - Display
				 PAGE: - Memories
					Memory Name7  cmdID= 37112  format=   "
		::= { iqdbe00CmdEntry 37112 }


	iqdbe00MemoryName8 OBJECT-TYPE
		SYNTAX		RollCallString
		MAX-ACCESS		read-only
		STATUS			current
		DESCRIPTION
				"TYPE: - Display
				 PAGE: - Memories
					Memory Name8  cmdID= 37113  format=   "
		::= { iqdbe00CmdEntry 37113 }


	iqdbe00MemoryName9 OBJECT-TYPE
		SYNTAX		RollCallString
		MAX-ACCESS		read-only
		STATUS			current
		DESCRIPTION
				"TYPE: - Display
				 PAGE: - Memories
					Memory Name9  cmdID= 37114  format=   "
		::= { iqdbe00CmdEntry 37114 }


	iqdbe00MemoryName10 OBJECT-TYPE
		SYNTAX		RollCallString
		MAX-ACCESS		read-only
		STATUS			current
		DESCRIPTION
				"TYPE: - Display
				 PAGE: - Memories
					Memory Name10  cmdID= 37115  format=   "
		::= { iqdbe00CmdEntry 37115 }


	iqdbe00MemoryName11 OBJECT-TYPE
		SYNTAX		RollCallString
		MAX-ACCESS		read-only
		STATUS			current
		DESCRIPTION
				"TYPE: - Display
				 PAGE: - Memories
					Memory Name11  cmdID= 37116  format=   "
		::= { iqdbe00CmdEntry 37116 }


	iqdbe00MemoryName12 OBJECT-TYPE
		SYNTAX		RollCallString
		MAX-ACCESS		read-only
		STATUS			current
		DESCRIPTION
				"TYPE: - Display
				 PAGE: - Memories
					Memory Name12  cmdID= 37117  format=   "
		::= { iqdbe00CmdEntry 37117 }


	iqdbe00MemoryName13 OBJECT-TYPE
		SYNTAX		RollCallString
		MAX-ACCESS		read-only
		STATUS			current
		DESCRIPTION
				"TYPE: - Display
				 PAGE: - Memories
					Memory Name13  cmdID= 37118  format=   "
		::= { iqdbe00CmdEntry 37118 }


	iqdbe00MemoryName14 OBJECT-TYPE
		SYNTAX		RollCallString
		MAX-ACCESS		read-only
		STATUS			current
		DESCRIPTION
				"TYPE: - Display
				 PAGE: - Memories
					Memory Name14  cmdID= 37119  format=   "
		::= { iqdbe00CmdEntry 37119 }


	iqdbe00MemoryName15 OBJECT-TYPE
		SYNTAX		RollCallString
		MAX-ACCESS		read-only
		STATUS			current
		DESCRIPTION
				"TYPE: - Display
				 PAGE: - Memories
					Memory Name15  cmdID= 37120  format=   "
		::= { iqdbe00CmdEntry 37120 }


	iqdbe00MemoryName16 OBJECT-TYPE
		SYNTAX		RollCallString
		MAX-ACCESS		read-only
		STATUS			current
		DESCRIPTION
				"TYPE: - Display
				 PAGE: - Memories
					Memory Name16  cmdID= 37121  format=   "
		::= { iqdbe00CmdEntry 37121 }


	iqdbe00LoggingVideoLoggingLogInput1Type OBJECT-TYPE
		SYNTAX		INTEGER { disable(0), enable(1) }
		MAX-ACCESS		read-write
		STATUS			current
		DESCRIPTION
				"TYPE: - Checkbox
				 PAGE: - RollCall- Logging
					Log Input 1 Type  cmdID= 35017 "
		::= { iqdbe00CmdEntry 35017 }


	iqdbe00LoggingVideoLoggingInput1Type OBJECT-TYPE
		SYNTAX		RollCallString
		MAX-ACCESS		read-only
		STATUS			current
		DESCRIPTION
				"TYPE: - Display
				 PAGE: - RollCall- Logging
					Input 1 Type=  cmdID= 36017  format=   "
		::= { iqdbe00CmdEntry 36017 }


	iqdbe00LoggingVideoLoggingLogInput1Status OBJECT-TYPE
		SYNTAX		INTEGER { disable(0), enable(1) }
		MAX-ACCESS		read-write
		STATUS			current
		DESCRIPTION
				"TYPE: - Checkbox
				 PAGE: - RollCall- Logging
					Log Input 1 Status  cmdID= 35005 "
		::= { iqdbe00CmdEntry 35005 }


	iqdbe00LoggingVideoLoggingInput1Status OBJECT-TYPE
		SYNTAX		RollCallString
		MAX-ACCESS		read-only
		STATUS			current
		DESCRIPTION
				"TYPE: - Display
				 PAGE: - RollCall- Logging
					Input 1 Status=  cmdID= 36005  format=   "
		::= { iqdbe00CmdEntry 36005 }


	iqdbe00LoggingVideoLoggingLogInput1Std OBJECT-TYPE
		SYNTAX		INTEGER { disable(0), enable(1) }
		MAX-ACCESS		read-write
		STATUS			current
		DESCRIPTION
				"TYPE: - Checkbox
				 PAGE: - RollCall- Logging
					Log Input 1 Std.  cmdID= 35016 "
		::= { iqdbe00CmdEntry 35016 }


	iqdbe00LoggingVideoLoggingInput1Std OBJECT-TYPE
		SYNTAX		RollCallString
		MAX-ACCESS		read-only
		STATUS			current
		DESCRIPTION
				"TYPE: - Display
				 PAGE: - RollCall- Logging
					Input 1 Std.=  cmdID= 36016  format=   "
		::= { iqdbe00CmdEntry 36016 }


	iqdbe00LoggingVideoLoggingLogInput1Errors OBJECT-TYPE
		SYNTAX		INTEGER { disable(0), enable(1) }
		MAX-ACCESS		read-write
		STATUS			current
		DESCRIPTION
				"TYPE: - Checkbox
				 PAGE: - RollCall- Logging
					Log Input 1 Errors  cmdID= 35002 "
		::= { iqdbe00CmdEntry 35002 }


	iqdbe00LoggingVideoLoggingInput1Errors OBJECT-TYPE
		SYNTAX		RollCallString
		MAX-ACCESS		read-only
		STATUS			current
		DESCRIPTION
				"TYPE: - Display
				 PAGE: - RollCall- Logging
					Input 1 Errors=  cmdID= 36002  format=   "
		::= { iqdbe00CmdEntry 36002 }


	iqdbe00LoggingVideoLoggingLogInput1ErrSecs OBJECT-TYPE
		SYNTAX		INTEGER { disable(0), enable(1) }
		MAX-ACCESS		read-write
		STATUS			current
		DESCRIPTION
				"TYPE: - Checkbox
				 PAGE: - RollCall- Logging
					Log Input 1 ErrSecs  cmdID= 35003 "
		::= { iqdbe00CmdEntry 35003 }


	iqdbe00LoggingVideoLoggingInput1ErrSecs OBJECT-TYPE
		SYNTAX		RollCallString
		MAX-ACCESS		read-only
		STATUS			current
		DESCRIPTION
				"TYPE: - Display
				 PAGE: - RollCall- Logging
					Input 1 ErrSecs=  cmdID= 36003  format=   "
		::= { iqdbe00CmdEntry 36003 }


	iqdbe00LoggingVideoLoggingLogInput1ANCErr OBJECT-TYPE
		SYNTAX		INTEGER { disable(0), enable(1) }
		MAX-ACCESS		read-write
		STATUS			current
		DESCRIPTION
				"TYPE: - Checkbox
				 PAGE: - RollCall- Logging
					Log Input 1 ANC Err  cmdID= 35000 "
		::= { iqdbe00CmdEntry 35000 }


	iqdbe00LoggingVideoLoggingInput1ANCErrors OBJECT-TYPE
		SYNTAX		RollCallString
		MAX-ACCESS		read-only
		STATUS			current
		DESCRIPTION
				"TYPE: - Display
				 PAGE: - RollCall- Logging
					Input 1 ANC Errors=  cmdID= 36000  format=   "
		::= { iqdbe00CmdEntry 36000 }


	iqdbe00LoggingVideoLoggingLogInput1ANCErrSec OBJECT-TYPE
		SYNTAX		INTEGER { disable(0), enable(1) }
		MAX-ACCESS		read-write
		STATUS			current
		DESCRIPTION
				"TYPE: - Checkbox
				 PAGE: - RollCall- Logging
					Log Input 1 ANC Err  cmdID= 35001 "
		::= { iqdbe00CmdEntry 35001 }


	iqdbe00LoggingVideoLoggingInput1ANCErrSecs OBJECT-TYPE
		SYNTAX		RollCallString
		MAX-ACCESS		read-only
		STATUS			current
		DESCRIPTION
				"TYPE: - Display
				 PAGE: - RollCall- Logging
					Input 1 ANC ErrSecs  cmdID= 36001  format=   "
		::= { iqdbe00CmdEntry 36001 }


	iqdbe00LoggingVideoLoggingLogOutputState OBJECT-TYPE
		SYNTAX		INTEGER { disable(0), enable(1) }
		MAX-ACCESS		read-write
		STATUS			current
		DESCRIPTION
				"TYPE: - Checkbox
				 PAGE: - RollCall- Logging
					Log Output State  cmdID= 35941 "
		::= { iqdbe00CmdEntry 35941 }


	iqdbe00LoggingVideoLoggingOutputState OBJECT-TYPE
		SYNTAX		RollCallString
		MAX-ACCESS		read-only
		STATUS			current
		DESCRIPTION
				"TYPE: - Display
				 PAGE: - RollCall- Logging
					Output State=  cmdID= 36941  format=   "
		::= { iqdbe00CmdEntry 36941 }


	iqdbe00LoggingVideoLoggingLogOutputType OBJECT-TYPE
		SYNTAX		INTEGER { disable(0), enable(1) }
		MAX-ACCESS		read-write
		STATUS			current
		DESCRIPTION
				"TYPE: - Checkbox
				 PAGE: - RollCall- Logging
					Log Output Type  cmdID= 35942 "
		::= { iqdbe00CmdEntry 35942 }


	iqdbe00LoggingVideoLoggingOutputType OBJECT-TYPE
		SYNTAX		RollCallString
		MAX-ACCESS		read-only
		STATUS			current
		DESCRIPTION
				"TYPE: - Display
				 PAGE: - RollCall- Logging
					Output Type=  cmdID= 36942  format=   "
		::= { iqdbe00CmdEntry 36942 }


	iqdbe00LoggingVideoLoggingLogOutputStandard OBJECT-TYPE
		SYNTAX		INTEGER { disable(0), enable(1) }
		MAX-ACCESS		read-write
		STATUS			current
		DESCRIPTION
				"TYPE: - Checkbox
				 PAGE: - RollCall- Logging
					Log Output Standard  cmdID= 35940 "
		::= { iqdbe00CmdEntry 35940 }


	iqdbe00LoggingVideoLoggingOutputStandard OBJECT-TYPE
		SYNTAX		RollCallString
		MAX-ACCESS		read-only
		STATUS			current
		DESCRIPTION
				"TYPE: - Display
				 PAGE: - RollCall- Logging
					Output Standard=  cmdID= 36940  format=   "
		::= { iqdbe00CmdEntry 36940 }


	iqdbe00LoggingVideoLoggingLogoutputANCstat OBJECT-TYPE
		SYNTAX		INTEGER { disable(0), enable(1) }
		MAX-ACCESS		read-write
		STATUS			current
		DESCRIPTION
				"TYPE: - Checkbox
				 PAGE: - RollCall- Logging
					Log output ANC stat  cmdID= 35946 "
		::= { iqdbe00CmdEntry 35946 }


	iqdbe00LoggingVideoLoggingOutputANCstate OBJECT-TYPE
		SYNTAX		RollCallString
		MAX-ACCESS		read-only
		STATUS			current
		DESCRIPTION
				"TYPE: - Display
				 PAGE: - RollCall- Logging
					Output ANC state=  cmdID= 36946  format=   "
		::= { iqdbe00CmdEntry 36946 }


	iqdbe00LoggingEmbAudLoggingLogInp1Emb1stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 stat  cmdID= 35006 "
		::= { iqdbe00CmdEntry 35006 }


	iqdbe00LoggingEmbAudLoggingInp1Emb1state OBJECT-TYPE
		SYNTAX		RollCallString
		MAX-ACCESS		read-only
		STATUS			current
		DESCRIPTION
				"TYPE: - Display
				 PAGE: - RollCall- Logging- Emb.Aud Logging
					Inp1 Emb.1 state=  cmdID= 36006  format=   "
		::= { iqdbe00CmdEntry 36006 }


	iqdbe00LoggingEmbAudLoggingLogInp1Emb2stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 stat  cmdID= 35007 "
		::= { iqdbe00CmdEntry 35007 }


	iqdbe00LoggingEmbAudLoggingInp1Emb2state OBJECT-TYPE
		SYNTAX		RollCallString
		MAX-ACCESS		read-only
		STATUS			current
		DESCRIPTION
				"TYPE: - Display
				 PAGE: - RollCall- Logging- Emb.Aud Logging
					Inp1 Emb.2 state=  cmdID= 36007  format=   "
		::= { iqdbe00CmdEntry 36007 }


	iqdbe00LoggingEmbAudLoggingLogInp1Emb3stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 stat  cmdID= 35008 "
		::= { iqdbe00CmdEntry 35008 }


	iqdbe00LoggingEmbAudLoggingInp1Emb3state OBJECT-TYPE
		SYNTAX		RollCallString
		MAX-ACCESS		read-only
		STATUS			current
		DESCRIPTION
				"TYPE: - Display
				 PAGE: - RollCall- Logging- Emb.Aud Logging
					Inp1 Emb.3 state=  cmdID= 36008  format=   "
		::= { iqdbe00CmdEntry 36008 }


	iqdbe00LoggingEmbAudLoggingLogInp1Emb4stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 stat  cmdID= 35009 "
		::= { iqdbe00CmdEntry 35009 }


	iqdbe00LoggingEmbAudLoggingInp1Emb4state OBJECT-TYPE
		SYNTAX		RollCallString
		MAX-ACCESS		read-only
		STATUS			current
		DESCRIPTION
				"TYPE: - Display
				 PAGE: - RollCall- Logging- Emb.Aud Logging
					Inp1 Emb.4 state=  cmdID= 36009  format=   "
		::= { iqdbe00CmdEntry 36009 }


	iqdbe00LoggingEmbAudLoggingLogInp1Emb5stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 stat  cmdID= 35010 "
		::= { iqdbe00CmdEntry 35010 }


	iqdbe00LoggingEmbAudLoggingInp1Emb5state OBJECT-TYPE
		SYNTAX		RollCallString
		MAX-ACCESS		read-only
		STATUS			current
		DESCRIPTION
				"TYPE: - Display
				 PAGE: - RollCall- Logging- Emb.Aud Logging
					Inp1 Emb.5 state=  cmdID= 36010  format=   "
		::= { iqdbe00CmdEntry 36010 }


	iqdbe00LoggingEmbAudLoggingLogInp1Emb6stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 stat  cmdID= 35011 "
		::= { iqdbe00CmdEntry 35011 }


	iqdbe00LoggingEmbAudLoggingInp1Emb6state OBJECT-TYPE
		SYNTAX		RollCallString
		MAX-ACCESS		read-only
		STATUS			current
		DESCRIPTION
				"TYPE: - Display
				 PAGE: - RollCall- Logging- Emb.Aud Logging
					Inp1 Emb.6 state=  cmdID= 36011  format=   "
		::= { iqdbe00CmdEntry 36011 }


	iqdbe00LoggingEmbAudLoggingLogInp1Emb7stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 stat  cmdID= 35012 "
		::= { iqdbe00CmdEntry 35012 }


	iqdbe00LoggingEmbAudLoggingInp1Emb7state OBJECT-TYPE
		SYNTAX		RollCallString
		MAX-ACCESS		read-only
		STATUS			current
		DESCRIPTION
				"TYPE: - Display
				 PAGE: - RollCall- Logging- Emb.Aud Logging
					Inp1 Emb.7 state=  cmdID= 36012  format=   "
		::= { iqdbe00CmdEntry 36012 }


	iqdbe00LoggingEmbAudLoggingLogInp1Emb8stat OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 stat  cmdID= 35013 "
		::= { iqdbe00CmdEntry 35013 }


	iqdbe00LoggingEmbAudLoggingInp1Emb8state OBJECT-TYPE
		SYNTAX		RollCallString
		MAX-ACCESS		read-only
		STATUS			current
		DESCRIPTION
				"TYPE: - Display
				 PAGE: - RollCall- Logging- Emb.Aud Logging
					Inp1 Emb.8 state=  cmdID= 36013  format=   "
		::= { iqdbe00CmdEntry 36013 }


	iqdbe00LoggingEmbAudLoggingLogInp1Emb1type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.1 type  cmdID= 35018 "
		::= { iqdbe00CmdEntry 35018 }


	iqdbe00LoggingEmbAudLoggingInp1Emb1type OBJECT-TYPE
		SYNTAX		RollCallString
		MAX-ACCESS		read-only
		STATUS			current
		DESCRIPTION
				"TYPE: - Display
				 PAGE: - RollCall- Logging- Emb.Aud Logging
					Inp1 Emb.1 type=  cmdID= 36018  format=   "
		::= { iqdbe00CmdEntry 36018 }


	iqdbe00LoggingEmbAudLoggingLogInp1Emb2type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.2 type  cmdID= 35019 "
		::= { iqdbe00CmdEntry 35019 }


	iqdbe00LoggingEmbAudLoggingInp1Emb2type OBJECT-TYPE
		SYNTAX		RollCallString
		MAX-ACCESS		read-only
		STATUS			current
		DESCRIPTION
				"TYPE: - Display
				 PAGE: - RollCall- Logging- Emb.Aud Logging
					Inp1 Emb.2 type=  cmdID= 36019  format=   "
		::= { iqdbe00CmdEntry 36019 }


	iqdbe00LoggingEmbAudLoggingLogInp1Emb3type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.3 type  cmdID= 35020 "
		::= { iqdbe00CmdEntry 35020 }


	iqdbe00LoggingEmbAudLoggingInp1Emb3type OBJECT-TYPE
		SYNTAX		RollCallString
		MAX-ACCESS		read-only
		STATUS			current
		DESCRIPTION
				"TYPE: - Display
				 PAGE: - RollCall- Logging- Emb.Aud Logging
					Inp1 Emb.3 type=  cmdID= 36020  format=   "
		::= { iqdbe00CmdEntry 36020 }


	iqdbe00LoggingEmbAudLoggingLogInp1Emb4type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.4 type  cmdID= 35021 "
		::= { iqdbe00CmdEntry 35021 }


	iqdbe00LoggingEmbAudLoggingInp1Emb4type OBJECT-TYPE
		SYNTAX		RollCallString
		MAX-ACCESS		read-only
		STATUS			current
		DESCRIPTION
				"TYPE: - Display
				 PAGE: - RollCall- Logging- Emb.Aud Logging
					Inp1 Emb.4 type=  cmdID= 36021  format=   "
		::= { iqdbe00CmdEntry 36021 }


	iqdbe00LoggingEmbAudLoggingLogInp1Emb5type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.5 type  cmdID= 35022 "
		::= { iqdbe00CmdEntry 35022 }


	iqdbe00LoggingEmbAudLoggingInp1Emb5type OBJECT-TYPE
		SYNTAX		RollCallString
		MAX-ACCESS		read-only
		STATUS			current
		DESCRIPTION
				"TYPE: - Display
				 PAGE: - RollCall- Logging- Emb.Aud Logging
					Inp1 Emb.5 type=  cmdID= 36022  format=   "
		::= { iqdbe00CmdEntry 36022 }


	iqdbe00LoggingEmbAudLoggingLogInp1Emb6type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.6 type  cmdID= 35023 "
		::= { iqdbe00CmdEntry 35023 }


	iqdbe00LoggingEmbAudLoggingInp1Emb6type OBJECT-TYPE
		SYNTAX		RollCallString
		MAX-ACCESS		read-only
		STATUS			current
		DESCRIPTION
				"TYPE: - Display
				 PAGE: - RollCall- Logging- Emb.Aud Logging
					Inp1 Emb.6 type=  cmdID= 36023  format=   "
		::= { iqdbe00CmdEntry 36023 }


	iqdbe00LoggingEmbAudLoggingLogInp1Emb7type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.7 type  cmdID= 35024 "
		::= { iqdbe00CmdEntry 35024 }


	iqdbe00LoggingEmbAudLoggingInp1Emb7type OBJECT-TYPE
		SYNTAX		RollCallString
		MAX-ACCESS		read-only
		STATUS			current
		DESCRIPTION
				"TYPE: - Display
				 PAGE: - RollCall- Logging- Emb.Aud Logging
					Inp1 Emb.7 type=  cmdID= 36024  format=   "
		::= { iqdbe00CmdEntry 36024 }


	iqdbe00LoggingEmbAudLoggingLogInp1Emb8type OBJECT-TYPE
		SYNTAX		INTEGER { disable(0), enable(1) }
		MAX-ACCESS		read-write
		STATUS			current
		DESCRIPTION
				"TYPE: - Checkbox
				 PAGE: - RollCall- Logging- Emb.Aud Logging
					Log Inp1 Emb.8 type  cmdID= 35025 "
		::= { iqdbe00CmdEntry 35025 }


	iqdbe00LoggingEmbAudLoggingInp1Emb8type OBJECT-TYPE
		SYNTAX		RollCallString
		MAX-ACCESS		read-only
		STATUS			current
		DESCRIPTION
				"TYPE: - Display
				 PAGE: - RollCall- Logging- Emb.Aud Logging
					Inp1 Emb.8 type=  cmdID= 36025  format=   "
		::= { iqdbe00CmdEntry 36025 }


	iqdbe00LoggingOPAudLoggingLogOutEmb1state OBJECT-TYPE
		SYNTAX		INTEGER { disable(0), enable(1) }
		MAX-ACCESS		read-write
		STATUS			current
		DESCRIPTION
				"TYPE: - Checkbox
				 PAGE: - RollCall- Logging
					Log Out Emb.1 state  cmdID= 35920 "
		::= { iqdbe00CmdEntry 35920 }


	iqdbe00LoggingOPAudLoggingOutEmb1state OBJECT-TYPE
		SYNTAX		RollCallString
		MAX-ACCESS		read-only
		STATUS			current
		DESCRIPTION
				"TYPE: - Display
				 PAGE: - RollCall- Logging
					Out Emb.1 state=  cmdID= 36920  format=   "
		::= { iqdbe00CmdEntry 36920 }


	iqdbe00LoggingOPAudLoggingLogOutEmb2state OBJECT-TYPE
		SYNTAX		INTEGER { disable(0), enable(1) }
		MAX-ACCESS		read-write
		STATUS			current
		DESCRIPTION
				"TYPE: - Checkbox
				 PAGE: - RollCall- Logging
					Log Out Emb.2 state  cmdID= 35921 "
		::= { iqdbe00CmdEntry 35921 }


	iqdbe00LoggingOPAudLoggingOutEmb2state OBJECT-TYPE
		SYNTAX		RollCallString
		MAX-ACCESS		read-only
		STATUS			current
		DESCRIPTION
				"TYPE: - Display
				 PAGE: - RollCall- Logging
					Out Emb.2 state=  cmdID= 36921  format=   "
		::= { iqdbe00CmdEntry 36921 }


	iqdbe00LoggingOPAudLoggingLogOutEmb3state OBJECT-TYPE
		SYNTAX		INTEGER { disable(0), enable(1) }
		MAX-ACCESS		read-write
		STATUS			current
		DESCRIPTION
				"TYPE: - Checkbox
				 PAGE: - RollCall- Logging
					Log Out Emb.3 state  cmdID= 35922 "
		::= { iqdbe00CmdEntry 35922 }


	iqdbe00LoggingOPAudLoggingOutEmb3state OBJECT-TYPE
		SYNTAX		RollCallString
		MAX-ACCESS		read-only
		STATUS			current
		DESCRIPTION
				"TYPE: - Display
				 PAGE: - RollCall- Logging
					Out Emb.3 state=  cmdID= 36922  format=   "
		::= { iqdbe00CmdEntry 36922 }


	iqdbe00LoggingOPAudLoggingLogOutEmb4state OBJECT-TYPE
		SYNTAX		INTEGER { disable(0), enable(1) }
		MAX-ACCESS		read-write
		STATUS			current
		DESCRIPTION
				"TYPE: - Checkbox
				 PAGE: - RollCall- Logging
					Log Out Emb.4 state  cmdID= 35923 "
		::= { iqdbe00CmdEntry 35923 }


	iqdbe00LoggingOPAudLoggingOutEmb4state OBJECT-TYPE
		SYNTAX		RollCallString
		MAX-ACCESS		read-only
		STATUS			current
		DESCRIPTION
				"TYPE: - Display
				 PAGE: - RollCall- Logging
					Out Emb.4 state=  cmdID= 36923  format=   "
		::= { iqdbe00CmdEntry 36923 }


	iqdbe00LoggingOPAudLoggingLogOutEmb5state OBJECT-TYPE
		SYNTAX		INTEGER { disable(0), enable(1) }
		MAX-ACCESS		read-write
		STATUS			current
		DESCRIPTION
				"TYPE: - Checkbox
				 PAGE: - RollCall- Logging
					Log Out Emb.5 state  cmdID= 35924 "
		::= { iqdbe00CmdEntry 35924 }


	iqdbe00LoggingOPAudLoggingOutEmb5state OBJECT-TYPE
		SYNTAX		RollCallString
		MAX-ACCESS		read-only
		STATUS			current
		DESCRIPTION
				"TYPE: - Display
				 PAGE: - RollCall- Logging
					Out Emb.5 state=  cmdID= 36924  format=   "
		::= { iqdbe00CmdEntry 36924 }


	iqdbe00LoggingOPAudLoggingLogOutEmb6state OBJECT-TYPE
		SYNTAX		INTEGER { disable(0), enable(1) }
		MAX-ACCESS		read-write
		STATUS			current
		DESCRIPTION
				"TYPE: - Checkbox
				 PAGE: - RollCall- Logging
					Log Out Emb.6 state  cmdID= 35925 "
		::= { iqdbe00CmdEntry 35925 }


	iqdbe00LoggingOPAudLoggingOutEmb6state OBJECT-TYPE
		SYNTAX		RollCallString
		MAX-ACCESS		read-only
		STATUS			current
		DESCRIPTION
				"TYPE: - Display
				 PAGE: - RollCall- Logging
					Out Emb.6 state=  cmdID= 36925  format=   "
		::= { iqdbe00CmdEntry 36925 }


	iqdbe00LoggingOPAudLoggingLogOutEmb7state OBJECT-TYPE
		SYNTAX		INTEGER { disable(0), enable(1) }
		MAX-ACCESS		read-write
		STATUS			current
		DESCRIPTION
				"TYPE: - Checkbox
				 PAGE: - RollCall- Logging
					Log Out Emb.7 state  cmdID= 35926 "
		::= { iqdbe00CmdEntry 35926 }


	iqdbe00LoggingOPAudLoggingOutEmb7state OBJECT-TYPE
		SYNTAX		RollCallString
		MAX-ACCESS		read-only
		STATUS			current
		DESCRIPTION
				"TYPE: - Display
				 PAGE: - RollCall- Logging
					Out Emb.7 state=  cmdID= 36926  format=   "
		::= { iqdbe00CmdEntry 36926 }


	iqdbe00LoggingOPAudLoggingLogOutEmb8state OBJECT-TYPE
		SYNTAX		INTEGER { disable(0), enable(1) }
		MAX-ACCESS		read-write
		STATUS			current
		DESCRIPTION
				"TYPE: - Checkbox
				 PAGE: - RollCall- Logging
					Log Out Emb.8 state  cmdID= 35927 "
		::= { iqdbe00CmdEntry 35927 }


	iqdbe00LoggingOPAudLoggingOutEmb8state OBJECT-TYPE
		SYNTAX		RollCallString
		MAX-ACCESS		read-only
		STATUS			current
		DESCRIPTION
				"TYPE: - Display
				 PAGE: - RollCall- Logging
					Out Emb.8 state=  cmdID= 36927  format=   "
		::= { iqdbe00CmdEntry 36927 }


	iqdbe00LoggingOPAudLoggingLogOutEmb1type OBJECT-TYPE
		SYNTAX		INTEGER { disable(0), enable(1) }
		MAX-ACCESS		read-write
		STATUS			current
		DESCRIPTION
				"TYPE: - Checkbox
				 PAGE: - RollCall- Logging
					Log Out Emb.1 type  cmdID= 35930 "
		::= { iqdbe00CmdEntry 35930 }


	iqdbe00LoggingOPAudLoggingOutEmb1type OBJECT-TYPE
		SYNTAX		RollCallString
		MAX-ACCESS		read-only
		STATUS			current
		DESCRIPTION
				"TYPE: - Display
				 PAGE: - RollCall- Logging
					Out Emb.1 type=  cmdID= 36930  format=   "
		::= { iqdbe00CmdEntry 36930 }


	iqdbe00LoggingOPAudLoggingLogOutEmb2type OBJECT-TYPE
		SYNTAX		INTEGER { disable(0), enable(1) }
		MAX-ACCESS		read-write
		STATUS			current
		DESCRIPTION
				"TYPE: - Checkbox
				 PAGE: - RollCall- Logging
					Log Out Emb.2 type  cmdID= 35931 "
		::= { iqdbe00CmdEntry 35931 }


	iqdbe00LoggingOPAudLoggingOutEmb2type OBJECT-TYPE
		SYNTAX		RollCallString
		MAX-ACCESS		read-only
		STATUS			current
		DESCRIPTION
				"TYPE: - Display
				 PAGE: - RollCall- Logging
					Out Emb.2 type=  cmdID= 36931  format=   "
		::= { iqdbe00CmdEntry 36931 }


	iqdbe00LoggingOPAudLoggingLogOutEmb3type OBJECT-TYPE
		SYNTAX		INTEGER { disable(0), enable(1) }
		MAX-ACCESS		read-write
		STATUS			current
		DESCRIPTION
				"TYPE: - Checkbox
				 PAGE: - RollCall- Logging
					Log Out Emb.3 type  cmdID= 35932 "
		::= { iqdbe00CmdEntry 35932 }


	iqdbe00LoggingOPAudLoggingOutEmb3type OBJECT-TYPE
		SYNTAX		RollCallString
		MAX-ACCESS		read-only
		STATUS			current
		DESCRIPTION
				"TYPE: - Display
				 PAGE: - RollCall- Logging
					Out Emb.3 type=  cmdID= 36932  format=   "
		::= { iqdbe00CmdEntry 36932 }


	iqdbe00LoggingOPAudLoggingLogOutEmb4type OBJECT-TYPE
		SYNTAX		INTEGER { disable(0), enable(1) }
		MAX-ACCESS		read-write
		STATUS			current
		DESCRIPTION
				"TYPE: - Checkbox
				 PAGE: - RollCall- Logging
					Log Out Emb.4 type  cmdID= 35933 "
		::= { iqdbe00CmdEntry 35933 }


	iqdbe00LoggingOPAudLoggingOutEmb4type OBJECT-TYPE
		SYNTAX		RollCallString
		MAX-ACCESS		read-only
		STATUS			current
		DESCRIPTION
				"TYPE: - Display
				 PAGE: - RollCall- Logging
					Out Emb.4 type=  cmdID= 36933  format=   "
		::= { iqdbe00CmdEntry 36933 }


	iqdbe00LoggingOPAudLoggingLogOutEmb5type OBJECT-TYPE
		SYNTAX		INTEGER { disable(0), enable(1) }
		MAX-ACCESS		read-write
		STATUS			current
		DESCRIPTION
				"TYPE: - Checkbox
				 PAGE: - RollCall- Logging
					Log Out Emb.5 type  cmdID= 35934 "
		::= { iqdbe00CmdEntry 35934 }


	iqdbe00LoggingOPAudLoggingOutEmb5type OBJECT-TYPE
		SYNTAX		RollCallString
		MAX-ACCESS		read-only
		STATUS			current
		DESCRIPTION
				"TYPE: - Display
				 PAGE: - RollCall- Logging
					Out Emb.5 type=  cmdID= 36934  format=   "
		::= { iqdbe00CmdEntry 36934 }


	iqdbe00LoggingOPAudLoggingLogOutEmb6type OBJECT-TYPE
		SYNTAX		INTEGER { disable(0), enable(1) }
		MAX-ACCESS		read-write
		STATUS			current
		DESCRIPTION
				"TYPE: - Checkbox
				 PAGE: - RollCall- Logging
					Log Out Emb.6 type  cmdID= 35935 "
		::= { iqdbe00CmdEntry 35935 }


	iqdbe00LoggingOPAudLoggingOutEmb6type OBJECT-TYPE
		SYNTAX		RollCallString
		MAX-ACCESS		read-only
		STATUS			current
		DESCRIPTION
				"TYPE: - Display
				 PAGE: - RollCall- Logging
					Out Emb.6 type=  cmdID= 36935  format=   "
		::= { iqdbe00CmdEntry 36935 }


	iqdbe00LoggingOPAudLoggingLogOutEmb7type OBJECT-TYPE
		SYNTAX		INTEGER { disable(0), enable(1) }
		MAX-ACCESS		read-write
		STATUS			current
		DESCRIPTION
				"TYPE: - Checkbox
				 PAGE: - RollCall- Logging
					Log Out Emb.7 type  cmdID= 35936 "
		::= { iqdbe00CmdEntry 35936 }


	iqdbe00LoggingOPAudLoggingOutEmb7type OBJECT-TYPE
		SYNTAX		RollCallString
		MAX-ACCESS		read-only
		STATUS			current
		DESCRIPTION
				"TYPE: - Display
				 PAGE: - RollCall- Logging
					Out Emb.7 type=  cmdID= 36936  format=   "
		::= { iqdbe00CmdEntry 36936 }


	iqdbe00LoggingOPAudLoggingLogOutEmb8type OBJECT-TYPE
		SYNTAX		INTEGER { disable(0), enable(1) }
		MAX-ACCESS		read-write
		STATUS			current
		DESCRIPTION
				"TYPE: - Checkbox
				 PAGE: - RollCall- Logging
					Log Out Emb.8 type  cmdID= 35937 "
		::= { iqdbe00CmdEntry 35937 }


	iqdbe00LoggingOPAudLoggingOutEmb8type OBJECT-TYPE
		SYNTAX		RollCallString
		MAX-ACCESS		read-only
		STATUS			current
		DESCRIPTION
				"TYPE: - Display
				 PAGE: - RollCall- Logging
					Out Emb.8 type=  cmdID= 36937  format=   "
		::= { iqdbe00CmdEntry 36937 }


	iqdbe00LoggingOPAudLevelLoggiLogOutEmb1LLev OBJECT-TYPE
		SYNTAX		INTEGER { disable(0), enable(1) }
		MAX-ACCESS		read-write
		STATUS			current
		DESCRIPTION
				"TYPE: - Checkbox
				 PAGE: - RollCall- Logging
					Log Out Emb.1-L Lev  cmdID= 35900 "
		::= { iqdbe00CmdEntry 35900 }


	iqdbe00LoggingOPAudLevelLoggiOutEmb1LLevel OBJECT-TYPE
		SYNTAX		RollCallString
		MAX-ACCESS		read-only
		STATUS			current
		DESCRIPTION
				"TYPE: - Display
				 PAGE: - RollCall- Logging
					Out Emb.1-L Level=  cmdID= 36900  format=   "
		::= { iqdbe00CmdEntry 36900 }


	iqdbe00LoggingOPAudLevelLoggiLogOutEmb1RLev OBJECT-TYPE
		SYNTAX		INTEGER { disable(0), enable(1) }
		MAX-ACCESS		read-write
		STATUS			current
		DESCRIPTION
				"TYPE: - Checkbox
				 PAGE: - RollCall- Logging
					Log Out Emb.1-R Lev  cmdID= 35901 "
		::= { iqdbe00CmdEntry 35901 }


	iqdbe00LoggingOPAudLevelLoggiOutEmb1RLevel OBJECT-TYPE
		SYNTAX		RollCallString
		MAX-ACCESS		read-only
		STATUS			current
		DESCRIPTION
				"TYPE: - Display
				 PAGE: - RollCall- Logging
					Out Emb.1-R Level=  cmdID= 36901  format=   "
		::= { iqdbe00CmdEntry 36901 }


	iqdbe00LoggingOPAudLevelLoggiLogOutEmb2LLev OBJECT-TYPE
		SYNTAX		INTEGER { disable(0), enable(1) }
		MAX-ACCESS		read-write
		STATUS			current
		DESCRIPTION
				"TYPE: - Checkbox
				 PAGE: - RollCall- Logging
					Log Out Emb.2-L Lev  cmdID= 35902 "
		::= { iqdbe00CmdEntry 35902 }


	iqdbe00LoggingOPAudLevelLoggiOutEmb2LLevel OBJECT-TYPE
		SYNTAX		RollCallString
		MAX-ACCESS		read-only
		STATUS			current
		DESCRIPTION
				"TYPE: - Display
				 PAGE: - RollCall- Logging
					Out Emb.2-L Level=  cmdID= 36902  format=   "
		::= { iqdbe00CmdEntry 36902 }


	iqdbe00LoggingOPAudLevelLoggiLogOutEmb2RLev OBJECT-TYPE
		SYNTAX		INTEGER { disable(0), enable(1) }
		MAX-ACCESS		read-write
		STATUS			current
		DESCRIPTION
				"TYPE: - Checkbox
				 PAGE: - RollCall- Logging
					Log Out Emb.2-R Lev  cmdID= 35903 "
		::= { iqdbe00CmdEntry 35903 }


	iqdbe00LoggingOPAudLevelLoggiOutEmb2RLevel OBJECT-TYPE
		SYNTAX		RollCallString
		MAX-ACCESS		read-only
		STATUS			current
		DESCRIPTION
				"TYPE: - Display
				 PAGE: - RollCall- Logging
					Out Emb.2-R Level=  cmdID= 36903  format=   "
		::= { iqdbe00CmdEntry 36903 }


	iqdbe00LoggingOPAudLevelLoggiLogOutEmb3LLev OBJECT-TYPE
		SYNTAX		INTEGER { disable(0), enable(1) }
		MAX-ACCESS		read-write
		STATUS			current
		DESCRIPTION
				"TYPE: - Checkbox
				 PAGE: - RollCall- Logging
					Log Out Emb.3-L Lev  cmdID= 35904 "
		::= { iqdbe00CmdEntry 35904 }


	iqdbe00LoggingOPAudLevelLoggiOutEmb3LLevel OBJECT-TYPE
		SYNTAX		RollCallString
		MAX-ACCESS		read-only
		STATUS			current
		DESCRIPTION
				"TYPE: - Display
				 PAGE: - RollCall- Logging
					Out Emb.3-L Level=  cmdID= 36904  format=   "
		::= { iqdbe00CmdEntry 36904 }


	iqdbe00LoggingOPAudLevelLoggiLogOutEmb3RLev OBJECT-TYPE
		SYNTAX		INTEGER { disable(0), enable(1) }
		MAX-ACCESS		read-write
		STATUS			current
		DESCRIPTION
				"TYPE: - Checkbox
				 PAGE: - RollCall- Logging
					Log Out Emb.3-R Lev  cmdID= 35905 "
		::= { iqdbe00CmdEntry 35905 }


	iqdbe00LoggingOPAudLevelLoggiOutEmb3RLevel OBJECT-TYPE
		SYNTAX		RollCallString
		MAX-ACCESS		read-only
		STATUS			current
		DESCRIPTION
				"TYPE: - Display
				 PAGE: - RollCall- Logging
					Out Emb.3-R Level=  cmdID= 36905  format=   "
		::= { iqdbe00CmdEntry 36905 }


	iqdbe00LoggingOPAudLevelLoggiLogOutEmb4LLev OBJECT-TYPE
		SYNTAX		INTEGER { disable(0), enable(1) }
		MAX-ACCESS		read-write
		STATUS			current
		DESCRIPTION
				"TYPE: - Checkbox
				 PAGE: - RollCall- Logging
					Log Out Emb.4-L Lev  cmdID= 35906 "
		::= { iqdbe00CmdEntry 35906 }


	iqdbe00LoggingOPAudLevelLoggiOutEmb4LLevel OBJECT-TYPE
		SYNTAX		RollCallString
		MAX-ACCESS		read-only
		STATUS			current
		DESCRIPTION
				"TYPE: - Display
				 PAGE: - RollCall- Logging
					Out Emb.4-L Level=  cmdID= 36906  format=   "
		::= { iqdbe00CmdEntry 36906 }


	iqdbe00LoggingOPAudLevelLoggiLogOutEmb4RLev OBJECT-TYPE
		SYNTAX		INTEGER { disable(0), enable(1) }
		MAX-ACCESS		read-write
		STATUS			current
		DESCRIPTION
				"TYPE: - Checkbox
				 PAGE: - RollCall- Logging
					Log Out Emb.4-R Lev  cmdID= 35907 "
		::= { iqdbe00CmdEntry 35907 }


	iqdbe00LoggingOPAudLevelLoggiOutEmb4RLevel OBJECT-TYPE
		SYNTAX		RollCallString
		MAX-ACCESS		read-only
		STATUS			current
		DESCRIPTION
				"TYPE: - Display
				 PAGE: - RollCall- Logging
					Out Emb.4-R Level=  cmdID= 36907  format=   "
		::= { iqdbe00CmdEntry 36907 }


	iqdbe00LoggingOPAudLevelLoggiLogOutEmb5LLev OBJECT-TYPE
		SYNTAX		INTEGER { disable(0), enable(1) }
		MAX-ACCESS		read-write
		STATUS			current
		DESCRIPTION
				"TYPE: - Checkbox
				 PAGE: - RollCall- Logging
					Log Out Emb.5-L Lev  cmdID= 35908 "
		::= { iqdbe00CmdEntry 35908 }


	iqdbe00LoggingOPAudLevelLoggiOutEmb5LLevel OBJECT-TYPE
		SYNTAX		RollCallString
		MAX-ACCESS		read-only
		STATUS			current
		DESCRIPTION
				"TYPE: - Display
				 PAGE: - RollCall- Logging
					Out Emb.5-L Level=  cmdID= 36908  format=   "
		::= { iqdbe00CmdEntry 36908 }


	iqdbe00LoggingOPAudLevelLoggiLogOutEmb5RLev OBJECT-TYPE
		SYNTAX		INTEGER { disable(0), enable(1) }
		MAX-ACCESS		read-write
		STATUS			current
		DESCRIPTION
				"TYPE: - Checkbox
				 PAGE: - RollCall- Logging
					Log Out Emb.5-R Lev  cmdID= 35909 "
		::= { iqdbe00CmdEntry 35909 }


	iqdbe00LoggingOPAudLevelLoggiOutEmb5RLevel OBJECT-TYPE
		SYNTAX		RollCallString
		MAX-ACCESS		read-only
		STATUS			current
		DESCRIPTION
				"TYPE: - Display
				 PAGE: - RollCall- Logging
					Out Emb.5-R Level=  cmdID= 36909  format=   "
		::= { iqdbe00CmdEntry 36909 }


	iqdbe00LoggingOPAudLevelLoggiLogOutEmb6LLev OBJECT-TYPE
		SYNTAX		INTEGER { disable(0), enable(1) }
		MAX-ACCESS		read-write
		STATUS			current
		DESCRIPTION
				"TYPE: - Checkbox
				 PAGE: - RollCall- Logging
					Log Out Emb.6-L Lev  cmdID= 35910 "
		::= { iqdbe00CmdEntry 35910 }


	iqdbe00LoggingOPAudLevelLoggiOutEmb6LLevel OBJECT-TYPE
		SYNTAX		RollCallString
		MAX-ACCESS		read-only
		STATUS			current
		DESCRIPTION
				"TYPE: - Display
				 PAGE: - RollCall- Logging
					Out Emb.6-L Level=  cmdID= 36910  format=   "
		::= { iqdbe00CmdEntry 36910 }


	iqdbe00LoggingOPAudLevelLoggiLogOutEmb6RLev OBJECT-TYPE
		SYNTAX		INTEGER { disable(0), enable(1) }
		MAX-ACCESS		read-write
		STATUS			current
		DESCRIPTION
				"TYPE: - Checkbox
				 PAGE: - RollCall- Logging
					Log Out Emb.6-R Lev  cmdID= 35911 "
		::= { iqdbe00CmdEntry 35911 }


	iqdbe00LoggingOPAudLevelLoggiOutEmb6RLevel OBJECT-TYPE
		SYNTAX		RollCallString
		MAX-ACCESS		read-only
		STATUS			current
		DESCRIPTION
				"TYPE: - Display
				 PAGE: - RollCall- Logging
					Out Emb.6-R Level=  cmdID= 36911  format=   "
		::= { iqdbe00CmdEntry 36911 }


	iqdbe00LoggingOPAudLevelLoggiLogOutEmb7LLev OBJECT-TYPE
		SYNTAX		INTEGER { disable(0), enable(1) }
		MAX-ACCESS		read-write
		STATUS			current
		DESCRIPTION
				"TYPE: - Checkbox
				 PAGE: - RollCall- Logging
					Log Out Emb.7-L Lev  cmdID= 35912 "
		::= { iqdbe00CmdEntry 35912 }


	iqdbe00LoggingOPAudLevelLoggiOutEmb7LLevel OBJECT-TYPE
		SYNTAX		RollCallString
		MAX-ACCESS		read-only
		STATUS			current
		DESCRIPTION
				"TYPE: - Display
				 PAGE: - RollCall- Logging
					Out Emb.7-L Level=  cmdID= 36912  format=   "
		::= { iqdbe00CmdEntry 36912 }


	iqdbe00LoggingOPAudLevelLoggiLogOutEmb7RLev OBJECT-TYPE
		SYNTAX		INTEGER { disable(0), enable(1) }
		MAX-ACCESS		read-write
		STATUS			current
		DESCRIPTION
				"TYPE: - Checkbox
				 PAGE: - RollCall- Logging
					Log Out Emb.7-R Lev  cmdID= 35913 "
		::= { iqdbe00CmdEntry 35913 }


	iqdbe00LoggingOPAudLevelLoggiOutEmb7RLevel OBJECT-TYPE
		SYNTAX		RollCallString
		MAX-ACCESS		read-only
		STATUS			current
		DESCRIPTION
				"TYPE: - Display
				 PAGE: - RollCall- Logging
					Out Emb.7-R Level=  cmdID= 36913  format=   "
		::= { iqdbe00CmdEntry 36913 }


	iqdbe00LoggingOPAudLevelLoggiLogOutEmb8LLev OBJECT-TYPE
		SYNTAX		INTEGER { disable(0), enable(1) }
		MAX-ACCESS		read-write
		STATUS			current
		DESCRIPTION
				"TYPE: - Checkbox
				 PAGE: - RollCall- Logging
					Log Out Emb.8-L Lev  cmdID= 35914 "
		::= { iqdbe00CmdEntry 35914 }


	iqdbe00LoggingOPAudLevelLoggiOutEmb8LLevel OBJECT-TYPE
		SYNTAX		RollCallString
		MAX-ACCESS		read-only
		STATUS			current
		DESCRIPTION
				"TYPE: - Display
				 PAGE: - RollCall- Logging
					Out Emb.8-L Level=  cmdID= 36914  format=   "
		::= { iqdbe00CmdEntry 36914 }


	iqdbe00LoggingOPAudLevelLoggiLogOutEmb8RLev OBJECT-TYPE
		SYNTAX		INTEGER { disable(0), enable(1) }
		MAX-ACCESS		read-write
		STATUS			current
		DESCRIPTION
				"TYPE: - Checkbox
				 PAGE: - RollCall- Logging
					Log Out Emb.8-R Lev  cmdID= 35915 "
		::= { iqdbe00CmdEntry 35915 }


	iqdbe00LoggingOPAudLevelLoggiOutEmb8RLevel OBJECT-TYPE
		SYNTAX		RollCallString
		MAX-ACCESS		read-only
		STATUS			current
		DESCRIPTION
				"TYPE: - Display
				 PAGE: - RollCall- Logging
					Out Emb.8-R Level=  cmdID= 36915  format=   "
		::= { iqdbe00CmdEntry 36915 }


	iqdbe00LoggingOPDolbyELoggingLogEmbDolbyE1 OBJECT-TYPE
		SYNTAX		INTEGER { disable(0), enable(1) }
		MAX-ACCESS		read-write
		STATUS			current
		DESCRIPTION
				"TYPE: - Checkbox
				 PAGE: - RollCall- Logging
					Log Emb DolbyE 1  cmdID= 35950 "
		::= { iqdbe00CmdEntry 35950 }


	iqdbe00LoggingOPDolbyELoggingEmbDolbyE1 OBJECT-TYPE
		SYNTAX		RollCallString
		MAX-ACCESS		read-only
		STATUS			current
		DESCRIPTION
				"TYPE: - Display
				 PAGE: - RollCall- Logging
					Emb DolbyE 1=  cmdID= 36950  format=   "
		::= { iqdbe00CmdEntry 36950 }


	iqdbe00LoggingOPDolbyELoggingLogEmbDolbyE2 OBJECT-TYPE
		SYNTAX		INTEGER { disable(0), enable(1) }
		MAX-ACCESS		read-write
		STATUS			current
		DESCRIPTION
				"TYPE: - Checkbox
				 PAGE: - RollCall- Logging
					Log Emb DolbyE 2  cmdID= 35951 "
		::= { iqdbe00CmdEntry 35951 }


	iqdbe00LoggingOPDolbyELoggingEmbDolbyE2 OBJECT-TYPE
		SYNTAX		RollCallString
		MAX-ACCESS		read-only
		STATUS			current
		DESCRIPTION
				"TYPE: - Display
				 PAGE: - RollCall- Logging
					Emb DolbyE 2=  cmdID= 36951  format=   "
		::= { iqdbe00CmdEntry 36951 }


	iqdbe00LoggingOPDolbyELoggingLogEmbDolbyE3 OBJECT-TYPE
		SYNTAX		INTEGER { disable(0), enable(1) }
		MAX-ACCESS		read-write
		STATUS			current
		DESCRIPTION
				"TYPE: - Checkbox
				 PAGE: - RollCall- Logging
					Log Emb DolbyE 3  cmdID= 35952 "
		::= { iqdbe00CmdEntry 35952 }


	iqdbe00LoggingOPDolbyELoggingEmbDolbyE3 OBJECT-TYPE
		SYNTAX		RollCallString
		MAX-ACCESS		read-only
		STATUS			current
		DESCRIPTION
				"TYPE: - Display
				 PAGE: - RollCall- Logging
					Emb DolbyE 3=  cmdID= 36952  format=   "
		::= { iqdbe00CmdEntry 36952 }


	iqdbe00LoggingOPDolbyELoggingLogEmbDolbyE4 OBJECT-TYPE
		SYNTAX		INTEGER { disable(0), enable(1) }
		MAX-ACCESS		read-write
		STATUS			current
		DESCRIPTION
				"TYPE: - Checkbox
				 PAGE: - RollCall- Logging
					Log Emb DolbyE 4  cmdID= 35953 "
		::= { iqdbe00CmdEntry 35953 }


	iqdbe00LoggingOPDolbyELoggingEmbDolbyE4 OBJECT-TYPE
		SYNTAX		RollCallString
		MAX-ACCESS		read-only
		STATUS			current
		DESCRIPTION
				"TYPE: - Display
				 PAGE: - RollCall- Logging
					Emb DolbyE 4=  cmdID= 36953  format=   "
		::= { iqdbe00CmdEntry 36953 }


	iqdbe00LoggingOPDolbyELoggingLogEmbDolbyE5 OBJECT-TYPE
		SYNTAX		INTEGER { disable(0), enable(1) }
		MAX-ACCESS		read-write
		STATUS			current
		DESCRIPTION
				"TYPE: - Checkbox
				 PAGE: - RollCall- Logging
					Log Emb DolbyE 5  cmdID= 35954 "
		::= { iqdbe00CmdEntry 35954 }


	iqdbe00LoggingOPDolbyELoggingEmbDolbyE5 OBJECT-TYPE
		SYNTAX		RollCallString
		MAX-ACCESS		read-only
		STATUS			current
		DESCRIPTION
				"TYPE: - Display
				 PAGE: - RollCall- Logging
					Emb DolbyE 5=  cmdID= 36954  format=   "
		::= { iqdbe00CmdEntry 36954 }


	iqdbe00LoggingOPDolbyELoggingLogEmbDolbyE6 OBJECT-TYPE
		SYNTAX		INTEGER { disable(0), enable(1) }
		MAX-ACCESS		read-write
		STATUS			current
		DESCRIPTION
				"TYPE: - Checkbox
				 PAGE: - RollCall- Logging
					Log Emb DolbyE 6  cmdID= 35955 "
		::= { iqdbe00CmdEntry 35955 }


	iqdbe00LoggingOPDolbyELoggingEmbDolbyE6 OBJECT-TYPE
		SYNTAX		RollCallString
		MAX-ACCESS		read-only
		STATUS			current
		DESCRIPTION
				"TYPE: - Display
				 PAGE: - RollCall- Logging
					Emb DolbyE 6=  cmdID= 36955  format=   "
		::= { iqdbe00CmdEntry 36955 }


	iqdbe00LoggingOPDolbyELoggingLogEmbDolbyE7 OBJECT-TYPE
		SYNTAX		INTEGER { disable(0), enable(1) }
		MAX-ACCESS		read-write
		STATUS			current
		DESCRIPTION
				"TYPE: - Checkbox
				 PAGE: - RollCall- Logging
					Log Emb DolbyE 7  cmdID= 35956 "
		::= { iqdbe00CmdEntry 35956 }


	iqdbe00LoggingOPDolbyELoggingEmbDolbyE7 OBJECT-TYPE
		SYNTAX		RollCallString
		MAX-ACCESS		read-only
		STATUS			current
		DESCRIPTION
				"TYPE: - Display
				 PAGE: - RollCall- Logging
					Emb DolbyE 7=  cmdID= 36956  format=   "
		::= { iqdbe00CmdEntry 36956 }


	iqdbe00LoggingOPDolbyELoggingLogEmbDolbyE8 OBJECT-TYPE
		SYNTAX		INTEGER { disable(0), enable(1) }
		MAX-ACCESS		read-write
		STATUS			current
		DESCRIPTION
				"TYPE: - Checkbox
				 PAGE: - RollCall- Logging
					Log Emb DolbyE 8  cmdID= 35957 "
		::= { iqdbe00CmdEntry 35957 }


	iqdbe00LoggingOPDolbyELoggingEmbDolbyE8 OBJECT-TYPE
		SYNTAX		RollCallString
		MAX-ACCESS		read-only
		STATUS			current
		DESCRIPTION
				"TYPE: - Display
				 PAGE: - RollCall- Logging
					Emb DolbyE 8=  cmdID= 36957  format=   "
		::= { iqdbe00CmdEntry 36957 }


	iqdbe00LoggingAESInputLoggingLogAESInput1sta OBJECT-TYPE
		SYNTAX		INTEGER { disable(0), enable(1) }
		MAX-ACCESS		read-write
		STATUS			current
		DESCRIPTION
				"TYPE: - Checkbox
				 PAGE: - RollCall- Logging
					Log AES Input 1 sta  cmdID= 35600 "
		::= { iqdbe00CmdEntry 35600 }


	iqdbe00LoggingAESInputLoggingAESInput1state OBJECT-TYPE
		SYNTAX		RollCallString
		MAX-ACCESS		read-only
		STATUS			current
		DESCRIPTION
				"TYPE: - Display
				 PAGE: - RollCall- Logging
					AES Input 1 state=  cmdID= 36600  format=   "
		::= { iqdbe00CmdEntry 36600 }


	iqdbe00LoggingAESInputLoggingLogAESInput2sta OBJECT-TYPE
		SYNTAX		INTEGER { disable(0), enable(1) }
		MAX-ACCESS		read-write
		STATUS			current
		DESCRIPTION
				"TYPE: - Checkbox
				 PAGE: - RollCall- Logging
					Log AES Input 2 sta  cmdID= 35601 "
		::= { iqdbe00CmdEntry 35601 }


	iqdbe00LoggingAESInputLoggingAESInput2state OBJECT-TYPE
		SYNTAX		RollCallString
		MAX-ACCESS		read-only
		STATUS			current
		DESCRIPTION
				"TYPE: - Display
				 PAGE: - RollCall- Logging
					AES Input 2 state=  cmdID= 36601  format=   "
		::= { iqdbe00CmdEntry 36601 }


	iqdbe00LoggingAESInputLoggingLogAESInput3sta OBJECT-TYPE
		SYNTAX		INTEGER { disable(0), enable(1) }
		MAX-ACCESS		read-write
		STATUS			current
		DESCRIPTION
				"TYPE: - Checkbox
				 PAGE: - RollCall- Logging
					Log AES Input 3 sta  cmdID= 35602 "
		::= { iqdbe00CmdEntry 35602 }


	iqdbe00LoggingAESInputLoggingAESInput3state OBJECT-TYPE
		SYNTAX		RollCallString
		MAX-ACCESS		read-only
		STATUS			current
		DESCRIPTION
				"TYPE: - Display
				 PAGE: - RollCall- Logging
					AES Input 3 state=  cmdID= 36602  format=   "
		::= { iqdbe00CmdEntry 36602 }


	iqdbe00LoggingAESInputLoggingLogAESInput4sta OBJECT-TYPE
		SYNTAX		INTEGER { disable(0), enable(1) }
		MAX-ACCESS		read-write
		STATUS			current
		DESCRIPTION
				"TYPE: - Checkbox
				 PAGE: - RollCall- Logging
					Log AES Input 4 sta  cmdID= 35603 "
		::= { iqdbe00CmdEntry 35603 }


	iqdbe00LoggingAESInputLoggingAESInput4state OBJECT-TYPE
		SYNTAX		RollCallString
		MAX-ACCESS		read-only
		STATUS			current
		DESCRIPTION
				"TYPE: - Display
				 PAGE: - RollCall- Logging
					AES Input 4 state=  cmdID= 36603  format=   "
		::= { iqdbe00CmdEntry 36603 }


	iqdbe00LoggingAESInputLoggingLogAESInput5sta OBJECT-TYPE
		SYNTAX		INTEGER { disable(0), enable(1) }
		MAX-ACCESS		read-write
		STATUS			current
		DESCRIPTION
				"TYPE: - Checkbox
				 PAGE: - RollCall- Logging
					Log AES Input 5 sta  cmdID= 35604 "
		::= { iqdbe00CmdEntry 35604 }


	iqdbe00LoggingAESInputLoggingAESInput5state OBJECT-TYPE
		SYNTAX		RollCallString
		MAX-ACCESS		read-only
		STATUS			current
		DESCRIPTION
				"TYPE: - Display
				 PAGE: - RollCall- Logging
					AES Input 5 state=  cmdID= 36604  format=   "
		::= { iqdbe00CmdEntry 36604 }


	iqdbe00LoggingAESInputLoggingLogAESInput6sta OBJECT-TYPE
		SYNTAX		INTEGER { disable(0), enable(1) }
		MAX-ACCESS		read-write
		STATUS			current
		DESCRIPTION
				"TYPE: - Checkbox
				 PAGE: - RollCall- Logging
					Log AES Input 6 sta  cmdID= 35605 "
		::= { iqdbe00CmdEntry 35605 }


	iqdbe00LoggingAESInputLoggingAESInput6state OBJECT-TYPE
		SYNTAX		RollCallString
		MAX-ACCESS		read-only
		STATUS			current
		DESCRIPTION
				"TYPE: - Display
				 PAGE: - RollCall- Logging
					AES Input 6 state=  cmdID= 36605  format=   "
		::= { iqdbe00CmdEntry 36605 }


	iqdbe00LoggingAESInputLoggingLogAESInput7sta OBJECT-TYPE
		SYNTAX		INTEGER { disable(0), enable(1) }
		MAX-ACCESS		read-write
		STATUS			current
		DESCRIPTION
				"TYPE: - Checkbox
				 PAGE: - RollCall- Logging
					Log AES Input 7 sta  cmdID= 35606 "
		::= { iqdbe00CmdEntry 35606 }


	iqdbe00LoggingAESInputLoggingAESInput7state OBJECT-TYPE
		SYNTAX		RollCallString
		MAX-ACCESS		read-only
		STATUS			current
		DESCRIPTION
				"TYPE: - Display
				 PAGE: - RollCall- Logging
					AES Input 7 state=  cmdID= 36606  format=   "
		::= { iqdbe00CmdEntry 36606 }


	iqdbe00LoggingAESInputLoggingLogAESInput8sta OBJECT-TYPE
		SYNTAX		INTEGER { disable(0), enable(1) }
		MAX-ACCESS		read-write
		STATUS			current
		DESCRIPTION
				"TYPE: - Checkbox
				 PAGE: - RollCall- Logging
					Log AES Input 8 sta  cmdID= 35607 "
		::= { iqdbe00CmdEntry 35607 }


	iqdbe00LoggingAESInputLoggingAESInput8state OBJECT-TYPE
		SYNTAX		RollCallString
		MAX-ACCESS		read-only
		STATUS			current
		DESCRIPTION
				"TYPE: - Display
				 PAGE: - RollCall- Logging
					AES Input 8 state=  cmdID= 36607  format=   "
		::= { iqdbe00CmdEntry 36607 }


	iqdbe00LoggingAESInputLoggingLogAESInput1typ OBJECT-TYPE
		SYNTAX		INTEGER { disable(0), enable(1) }
		MAX-ACCESS		read-write
		STATUS			current
		DESCRIPTION
				"TYPE: - Checkbox
				 PAGE: - RollCall- Logging
					Log AES Input 1 typ  cmdID= 35640 "
		::= { iqdbe00CmdEntry 35640 }


	iqdbe00LoggingAESInputLoggingAESInput1type OBJECT-TYPE
		SYNTAX		RollCallString
		MAX-ACCESS		read-only
		STATUS			current
		DESCRIPTION
				"TYPE: - Display
				 PAGE: - RollCall- Logging
					AES Input 1 type=  cmdID= 36640  format=   "
		::= { iqdbe00CmdEntry 36640 }


	iqdbe00LoggingAESInputLoggingLogAESInput2typ OBJECT-TYPE
		SYNTAX		INTEGER { disable(0), enable(1) }
		MAX-ACCESS		read-write
		STATUS			current
		DESCRIPTION
				"TYPE: - Checkbox
				 PAGE: - RollCall- Logging
					Log AES Input 2 typ  cmdID= 35641 "
		::= { iqdbe00CmdEntry 35641 }


	iqdbe00LoggingAESInputLoggingAESInput2type OBJECT-TYPE
		SYNTAX		RollCallString
		MAX-ACCESS		read-only
		STATUS			current
		DESCRIPTION
				"TYPE: - Display
				 PAGE: - RollCall- Logging
					AES Input 2 type=  cmdID= 36641  format=   "
		::= { iqdbe00CmdEntry 36641 }


	iqdbe00LoggingAESInputLoggingLogAESInput3typ OBJECT-TYPE
		SYNTAX		INTEGER { disable(0), enable(1) }
		MAX-ACCESS		read-write
		STATUS			current
		DESCRIPTION
				"TYPE: - Checkbox
				 PAGE: - RollCall- Logging
					Log AES Input 3 typ  cmdID= 35642 "
		::= { iqdbe00CmdEntry 35642 }


	iqdbe00LoggingAESInputLoggingAESInput3type OBJECT-TYPE
		SYNTAX		RollCallString
		MAX-ACCESS		read-only
		STATUS			current
		DESCRIPTION
				"TYPE: - Display
				 PAGE: - RollCall- Logging
					AES Input 3 type=  cmdID= 36642  format=   "
		::= { iqdbe00CmdEntry 36642 }


	iqdbe00LoggingAESInputLoggingLogAESInput4typ OBJECT-TYPE
		SYNTAX		INTEGER { disable(0), enable(1) }
		MAX-ACCESS		read-write
		STATUS			current
		DESCRIPTION
				"TYPE: - Checkbox
				 PAGE: - RollCall- Logging
					Log AES Input 4 typ  cmdID= 35643 "
		::= { iqdbe00CmdEntry 35643 }


	iqdbe00LoggingAESInputLoggingAESInput4type OBJECT-TYPE
		SYNTAX		RollCallString
		MAX-ACCESS		read-only
		STATUS			current
		DESCRIPTION
				"TYPE: - Display
				 PAGE: - RollCall- Logging
					AES Input 4 type=  cmdID= 36643  format=   "
		::= { iqdbe00CmdEntry 36643 }


	iqdbe00LoggingAESInputLoggingLogAESInput5typ OBJECT-TYPE
		SYNTAX		INTEGER { disable(0), enable(1) }
		MAX-ACCESS		read-write
		STATUS			current
		DESCRIPTION
				"TYPE: - Checkbox
				 PAGE: - RollCall- Logging
					Log AES Input 5 typ  cmdID= 35644 "
		::= { iqdbe00CmdEntry 35644 }


	iqdbe00LoggingAESInputLoggingAESInput5type OBJECT-TYPE
		SYNTAX		RollCallString
		MAX-ACCESS		read-only
		STATUS			current
		DESCRIPTION
				"TYPE: - Display
				 PAGE: - RollCall- Logging
					AES Input 5 type=  cmdID= 36644  format=   "
		::= { iqdbe00CmdEntry 36644 }


	iqdbe00LoggingAESInputLoggingLogAESInput6typ OBJECT-TYPE
		SYNTAX		INTEGER { disable(0), enable(1) }
		MAX-ACCESS		read-write
		STATUS			current
		DESCRIPTION
				"TYPE: - Checkbox
				 PAGE: - RollCall- Logging
					Log AES Input 6 typ  cmdID= 35645 "
		::= { iqdbe00CmdEntry 35645 }


	iqdbe00LoggingAESInputLoggingAESInput6type OBJECT-TYPE
		SYNTAX		RollCallString
		MAX-ACCESS		read-only
		STATUS			current
		DESCRIPTION
				"TYPE: - Display
				 PAGE: - RollCall- Logging
					AES Input 6 type=  cmdID= 36645  format=   "
		::= { iqdbe00CmdEntry 36645 }


	iqdbe00LoggingAESInputLoggingLogAESInput7typ OBJECT-TYPE
		SYNTAX		INTEGER { disable(0), enable(1) }
		MAX-ACCESS		read-write
		STATUS			current
		DESCRIPTION
				"TYPE: - Checkbox
				 PAGE: - RollCall- Logging
					Log AES Input 7 typ  cmdID= 35646 "
		::= { iqdbe00CmdEntry 35646 }


	iqdbe00LoggingAESInputLoggingAESInput7type OBJECT-TYPE
		SYNTAX		RollCallString
		MAX-ACCESS		read-only
		STATUS			current
		DESCRIPTION
				"TYPE: - Display
				 PAGE: - RollCall- Logging
					AES Input 7 type=  cmdID= 36646  format=   "
		::= { iqdbe00CmdEntry 36646 }


	iqdbe00LoggingAESInputLoggingLogAESInput8typ OBJECT-TYPE
		SYNTAX		INTEGER { disable(0), enable(1) }
		MAX-ACCESS		read-write
		STATUS			current
		DESCRIPTION
				"TYPE: - Checkbox
				 PAGE: - RollCall- Logging
					Log AES Input 8 typ  cmdID= 35647 "
		::= { iqdbe00CmdEntry 35647 }


	iqdbe00LoggingAESInputLoggingAESInput8type OBJECT-TYPE
		SYNTAX		RollCallString
		MAX-ACCESS		read-only
		STATUS			current
		DESCRIPTION
				"TYPE: - Display
				 PAGE: - RollCall- Logging
					AES Input 8 type=  cmdID= 36647  format=   "
		::= { iqdbe00CmdEntry 36647 }


	iqdbe00LoggingAESOutputLoggingLogAESOutput1st OBJECT-TYPE
		SYNTAX		INTEGER { disable(0), enable(1) }
		MAX-ACCESS		read-write
		STATUS			current
		DESCRIPTION
				"TYPE: - Checkbox
				 PAGE: - RollCall- Logging
					Log AES Output 1 st  cmdID= 35620 "
		::= { iqdbe00CmdEntry 35620 }


	iqdbe00LoggingAESOutputLoggingAESOutput1state OBJECT-TYPE
		SYNTAX		RollCallString
		MAX-ACCESS		read-only
		STATUS			current
		DESCRIPTION
				"TYPE: - Display
				 PAGE: - RollCall- Logging
					AES Output 1 state=  cmdID= 36620  format=   "
		::= { iqdbe00CmdEntry 36620 }


	iqdbe00LoggingAESOutputLoggingLogAESOutput2st OBJECT-TYPE
		SYNTAX		INTEGER { disable(0), enable(1) }
		MAX-ACCESS		read-write
		STATUS			current
		DESCRIPTION
				"TYPE: - Checkbox
				 PAGE: - RollCall- Logging
					Log AES Output 2 st  cmdID= 35621 "
		::= { iqdbe00CmdEntry 35621 }


	iqdbe00LoggingAESOutputLoggingAESOutput2state OBJECT-TYPE
		SYNTAX		RollCallString
		MAX-ACCESS		read-only
		STATUS			current
		DESCRIPTION
				"TYPE: - Display
				 PAGE: - RollCall- Logging
					AES Output 2 state=  cmdID= 36621  format=   "
		::= { iqdbe00CmdEntry 36621 }


	iqdbe00LoggingAESOutputLoggingLogAESOutput3st OBJECT-TYPE
		SYNTAX		INTEGER { disable(0), enable(1) }
		MAX-ACCESS		read-write
		STATUS			current
		DESCRIPTION
				"TYPE: - Checkbox
				 PAGE: - RollCall- Logging
					Log AES Output 3 st  cmdID= 35622 "
		::= { iqdbe00CmdEntry 35622 }


	iqdbe00LoggingAESOutputLoggingAESOutput3state OBJECT-TYPE
		SYNTAX		RollCallString
		MAX-ACCESS		read-only
		STATUS			current
		DESCRIPTION
				"TYPE: - Display
				 PAGE: - RollCall- Logging
					AES Output 3 state=  cmdID= 36622  format=   "
		::= { iqdbe00CmdEntry 36622 }


	iqdbe00LoggingAESOutputLoggingLogAESOutput4st OBJECT-TYPE
		SYNTAX		INTEGER { disable(0), enable(1) }
		MAX-ACCESS		read-write
		STATUS			current
		DESCRIPTION
				"TYPE: - Checkbox
				 PAGE: - RollCall- Logging
					Log AES Output 4 st  cmdID= 35623 "
		::= { iqdbe00CmdEntry 35623 }


	iqdbe00LoggingAESOutputLoggingAESOutput4state OBJECT-TYPE
		SYNTAX		RollCallString
		MAX-ACCESS		read-only
		STATUS			current
		DESCRIPTION
				"TYPE: - Display
				 PAGE: - RollCall- Logging
					AES Output 4 state=  cmdID= 36623  format=   "
		::= { iqdbe00CmdEntry 36623 }


	iqdbe00LoggingAESOutputLoggingLogAESOutput5st OBJECT-TYPE
		SYNTAX		INTEGER { disable(0), enable(1) }
		MAX-ACCESS		read-write
		STATUS			current
		DESCRIPTION
				"TYPE: - Checkbox
				 PAGE: - RollCall- Logging
					Log AES Output 5 st  cmdID= 35624 "
		::= { iqdbe00CmdEntry 35624 }


	iqdbe00LoggingAESOutputLoggingAESOutput5state OBJECT-TYPE
		SYNTAX		RollCallString
		MAX-ACCESS		read-only
		STATUS			current
		DESCRIPTION
				"TYPE: - Display
				 PAGE: - RollCall- Logging
					AES Output 5 state=  cmdID= 36624  format=   "
		::= { iqdbe00CmdEntry 36624 }


	iqdbe00LoggingAESOutputLoggingLogAESOutput6st OBJECT-TYPE
		SYNTAX		INTEGER { disable(0), enable(1) }
		MAX-ACCESS		read-write
		STATUS			current
		DESCRIPTION
				"TYPE: - Checkbox
				 PAGE: - RollCall- Logging
					Log AES Output 6 st  cmdID= 35625 "
		::= { iqdbe00CmdEntry 35625 }


	iqdbe00LoggingAESOutputLoggingAESOutput6state OBJECT-TYPE
		SYNTAX		RollCallString
		MAX-ACCESS		read-only
		STATUS			current
		DESCRIPTION
				"TYPE: - Display
				 PAGE: - RollCall- Logging
					AES Output 6 state=  cmdID= 36625  format=   "
		::= { iqdbe00CmdEntry 36625 }


	iqdbe00LoggingAESOutputLoggingLogAESOutput7st OBJECT-TYPE
		SYNTAX		INTEGER { disable(0), enable(1) }
		MAX-ACCESS		read-write
		STATUS			current
		DESCRIPTION
				"TYPE: - Checkbox
				 PAGE: - RollCall- Logging
					Log AES Output 7 st  cmdID= 35626 "
		::= { iqdbe00CmdEntry 35626 }


	iqdbe00LoggingAESOutputLoggingAESOutput7state OBJECT-TYPE
		SYNTAX		RollCallString
		MAX-ACCESS		read-only
		STATUS			current
		DESCRIPTION
				"TYPE: - Display
				 PAGE: - RollCall- Logging
					AES Output 7 state=  cmdID= 36626  format=   "
		::= { iqdbe00CmdEntry 36626 }


	iqdbe00LoggingAESOutputLoggingLogAESOutput8st OBJECT-TYPE
		SYNTAX		INTEGER { disable(0), enable(1) }
		MAX-ACCESS		read-write
		STATUS			current
		DESCRIPTION
				"TYPE: - Checkbox
				 PAGE: - RollCall- Logging
					Log AES Output 8 st  cmdID= 35627 "
		::= { iqdbe00CmdEntry 35627 }


	iqdbe00LoggingAESOutputLoggingAESOutput8state OBJECT-TYPE
		SYNTAX		RollCallString
		MAX-ACCESS		read-only
		STATUS			current
		DESCRIPTION
				"TYPE: - Display
				 PAGE: - RollCall- Logging
					AES Output 8 state=  cmdID= 36627  format=   "
		::= { iqdbe00CmdEntry 36627 }


	iqdbe00LoggingAESOutputLoggingLogAESOutput1ty OBJECT-TYPE
		SYNTAX		INTEGER { disable(0), enable(1) }
		MAX-ACCESS		read-write
		STATUS			current
		DESCRIPTION
				"TYPE: - Checkbox
				 PAGE: - RollCall- Logging
					Log AES Output 1 ty  cmdID= 35660 "
		::= { iqdbe00CmdEntry 35660 }


	iqdbe00LoggingAESOutputLoggingAESOutput1type OBJECT-TYPE
		SYNTAX		RollCallString
		MAX-ACCESS		read-only
		STATUS			current
		DESCRIPTION
				"TYPE: - Display
				 PAGE: - RollCall- Logging
					AES Output 1 type=  cmdID= 36660  format=   "
		::= { iqdbe00CmdEntry 36660 }


	iqdbe00LoggingAESOutputLoggingLogAESOutput2ty OBJECT-TYPE
		SYNTAX		INTEGER { disable(0), enable(1) }
		MAX-ACCESS		read-write
		STATUS			current
		DESCRIPTION
				"TYPE: - Checkbox
				 PAGE: - RollCall- Logging
					Log AES Output 2 ty  cmdID= 35661 "
		::= { iqdbe00CmdEntry 35661 }


	iqdbe00LoggingAESOutputLoggingAESOutput2type OBJECT-TYPE
		SYNTAX		RollCallString
		MAX-ACCESS		read-only
		STATUS			current
		DESCRIPTION
				"TYPE: - Display
				 PAGE: - RollCall- Logging
					AES Output 2 type=  cmdID= 36661  format=   "
		::= { iqdbe00CmdEntry 36661 }


	iqdbe00LoggingAESOutputLoggingLogAESOutput3ty OBJECT-TYPE
		SYNTAX		INTEGER { disable(0), enable(1) }
		MAX-ACCESS		read-write
		STATUS			current
		DESCRIPTION
				"TYPE: - Checkbox
				 PAGE: - RollCall- Logging
					Log AES Output 3 ty  cmdID= 35662 "
		::= { iqdbe00CmdEntry 35662 }


	iqdbe00LoggingAESOutputLoggingAESOutput3type OBJECT-TYPE
		SYNTAX		RollCallString
		MAX-ACCESS		read-only
		STATUS			current
		DESCRIPTION
				"TYPE: - Display
				 PAGE: - RollCall- Logging
					AES Output 3 type=  cmdID= 36662  format=   "
		::= { iqdbe00CmdEntry 36662 }


	iqdbe00LoggingAESOutputLoggingLogAESOutput4ty OBJECT-TYPE
		SYNTAX		INTEGER { disable(0), enable(1) }
		MAX-ACCESS		read-write
		STATUS			current
		DESCRIPTION
				"TYPE: - Checkbox
				 PAGE: - RollCall- Logging
					Log AES Output 4 ty  cmdID= 35663 "
		::= { iqdbe00CmdEntry 35663 }


	iqdbe00LoggingAESOutputLoggingAESOutput4type OBJECT-TYPE
		SYNTAX		RollCallString
		MAX-ACCESS		read-only
		STATUS			current
		DESCRIPTION
				"TYPE: - Display
				 PAGE: - RollCall- Logging
					AES Output 4 type=  cmdID= 36663  format=   "
		::= { iqdbe00CmdEntry 36663 }


	iqdbe00LoggingAESOutputLoggingLogAESOutput5ty OBJECT-TYPE
		SYNTAX		INTEGER { disable(0), enable(1) }
		MAX-ACCESS		read-write
		STATUS			current
		DESCRIPTION
				"TYPE: - Checkbox
				 PAGE: - RollCall- Logging
					Log AES Output 5 ty  cmdID= 35664 "
		::= { iqdbe00CmdEntry 35664 }


	iqdbe00LoggingAESOutputLoggingAESOutput5type OBJECT-TYPE
		SYNTAX		RollCallString
		MAX-ACCESS		read-only
		STATUS			current
		DESCRIPTION
				"TYPE: - Display
				 PAGE: - RollCall- Logging
					AES Output 5 type=  cmdID= 36664  format=   "
		::= { iqdbe00CmdEntry 36664 }


	iqdbe00LoggingAESOutputLoggingLogAESOutput6ty OBJECT-TYPE
		SYNTAX		INTEGER { disable(0), enable(1) }
		MAX-ACCESS		read-write
		STATUS			current
		DESCRIPTION
				"TYPE: - Checkbox
				 PAGE: - RollCall- Logging
					Log AES Output 6 ty  cmdID= 35665 "
		::= { iqdbe00CmdEntry 35665 }


	iqdbe00LoggingAESOutputLoggingAESOutput6type OBJECT-TYPE
		SYNTAX		RollCallString
		MAX-ACCESS		read-only
		STATUS			current
		DESCRIPTION
				"TYPE: - Display
				 PAGE: - RollCall- Logging
					AES Output 6 type=  cmdID= 36665  format=   "
		::= { iqdbe00CmdEntry 36665 }


	iqdbe00LoggingAESOutputLoggingLogAESOutput7ty OBJECT-TYPE
		SYNTAX		INTEGER { disable(0), enable(1) }
		MAX-ACCESS		read-write
		STATUS			current
		DESCRIPTION
				"TYPE: - Checkbox
				 PAGE: - RollCall- Logging
					Log AES Output 7 ty  cmdID= 35666 "
		::= { iqdbe00CmdEntry 35666 }


	iqdbe00LoggingAESOutputLoggingAESOutput7type OBJECT-TYPE
		SYNTAX		RollCallString
		MAX-ACCESS		read-only
		STATUS			current
		DESCRIPTION
				"TYPE: - Display
				 PAGE: - RollCall- Logging
					AES Output 7 type=  cmdID= 36666  format=   "
		::= { iqdbe00CmdEntry 36666 }


	iqdbe00LoggingAESOutputLoggingLogAESOutput8ty OBJECT-TYPE
		SYNTAX		INTEGER { disable(0), enable(1) }
		MAX-ACCESS		read-write
		STATUS			current
		DESCRIPTION
				"TYPE: - Checkbox
				 PAGE: - RollCall- Logging
					Log AES Output 8 ty  cmdID= 35667 "
		::= { iqdbe00CmdEntry 35667 }


	iqdbe00LoggingAESOutputLoggingAESOutput8type OBJECT-TYPE
		SYNTAX		RollCallString
		MAX-ACCESS		read-only
		STATUS			current
		DESCRIPTION
				"TYPE: - Display
				 PAGE: - RollCall- Logging
					AES Output 8 type=  cmdID= 36667  format=   "
		::= { iqdbe00CmdEntry 36667 }


	iqdbe00LoggingDolbyEncoderLogProgConfig OBJECT-TYPE
		SYNTAX		INTEGER { disable(0), enable(1) }
		MAX-ACCESS		read-write
		STATUS			current
		DESCRIPTION
				"TYPE: - Checkbox
				 PAGE: - RollCall- Logging- Dolby Encoder
					Log Prog Config  cmdID= 35800 "
		::= { iqdbe00CmdEntry 35800 }


	iqdbe00LoggingDolbyEncoderProgramConfig OBJECT-TYPE
		SYNTAX		RollCallString
		MAX-ACCESS		read-only
		STATUS			current
		DESCRIPTION
				"TYPE: - Display
				 PAGE: - RollCall- Logging- Dolby Encoder
					Program Config=  cmdID= 36800  format=   "
		::= { iqdbe00CmdEntry 36800 }


	iqdbe00LoggingDolbyEncoderLogSource OBJECT-TYPE
		SYNTAX		INTEGER { disable(0), enable(1) }
		MAX-ACCESS		read-write
		STATUS			current
		DESCRIPTION
				"TYPE: - Checkbox
				 PAGE: - RollCall- Logging- Dolby Encoder
					Log Source  cmdID= 35801 "
		::= { iqdbe00CmdEntry 35801 }


	iqdbe00LoggingDolbyEncoderSource OBJECT-TYPE
		SYNTAX		RollCallString
		MAX-ACCESS		read-only
		STATUS			current
		DESCRIPTION
				"TYPE: - Display
				 PAGE: - RollCall- Logging- Dolby Encoder
					Source=  cmdID= 36801  format=   "
		::= { iqdbe00CmdEntry 36801 }


	iqdbe00LoggingDolbyEncoderLogStatus OBJECT-TYPE
		SYNTAX		INTEGER { disable(0), enable(1) }
		MAX-ACCESS		read-write
		STATUS			current
		DESCRIPTION
				"TYPE: - Checkbox
				 PAGE: - RollCall- Logging- Dolby Encoder
					Log Status  cmdID= 35802 "
		::= { iqdbe00CmdEntry 35802 }


	iqdbe00LoggingDolbyEncoderStatus OBJECT-TYPE
		SYNTAX		RollCallString
		MAX-ACCESS		read-only
		STATUS			current
		DESCRIPTION
				"TYPE: - Display
				 PAGE: - RollCall- Logging- Dolby Encoder
					Status=  cmdID= 36802  format=   "
		::= { iqdbe00CmdEntry 36802 }


	iqdbe00LoggingDolbyEncoderLogAC3 OBJECT-TYPE
		SYNTAX		INTEGER { disable(0), enable(1) }
		MAX-ACCESS		read-write
		STATUS			current
		DESCRIPTION
				"TYPE: - Checkbox
				 PAGE: - RollCall- Logging- Dolby Encoder
					Log AC_3  cmdID= 35803 "
		::= { iqdbe00CmdEntry 35803 }


	iqdbe00LoggingDolbyEncoderAC3 OBJECT-TYPE
		SYNTAX		RollCallString
		MAX-ACCESS		read-only
		STATUS			current
		DESCRIPTION
				"TYPE: - Display
				 PAGE: - RollCall- Logging- Dolby Encoder
					AC_3=  cmdID= 36803  format=   "
		::= { iqdbe00CmdEntry 36803 }


	iqdbe00LoggingDolbyEncoderLogExBSI OBJECT-TYPE
		SYNTAX		INTEGER { disable(0), enable(1) }
		MAX-ACCESS		read-write
		STATUS			current
		DESCRIPTION
				"TYPE: - Checkbox
				 PAGE: - RollCall- Logging- Dolby Encoder
					Log Ex BSI  cmdID= 35804 "
		::= { iqdbe00CmdEntry 35804 }


	iqdbe00LoggingDolbyEncoderExBSI OBJECT-TYPE
		SYNTAX		RollCallString
		MAX-ACCESS		read-only
		STATUS			current
		DESCRIPTION
				"TYPE: - Display
				 PAGE: - RollCall- Logging- Dolby Encoder
					Ex BSI=  cmdID= 36804  format=   "
		::= { iqdbe00CmdEntry 36804 }


	iqdbe00LoggingDolbyEncoderLogVFS OBJECT-TYPE
		SYNTAX		INTEGER { disable(0), enable(1) }
		MAX-ACCESS		read-write
		STATUS			current
		DESCRIPTION
				"TYPE: - Checkbox
				 PAGE: - RollCall- Logging- Dolby Encoder
					Log VFS  cmdID= 35805 "
		::= { iqdbe00CmdEntry 35805 }


	iqdbe00LoggingDolbyEncoderVFS OBJECT-TYPE
		SYNTAX		RollCallString
		MAX-ACCESS		read-only
		STATUS			current
		DESCRIPTION
				"TYPE: - Display
				 PAGE: - RollCall- Logging- Dolby Encoder
					VFS=  cmdID= 36805  format=   "
		::= { iqdbe00CmdEntry 36805 }


	iqdbe00LoggingDolbyEncoderLogFramerate OBJECT-TYPE
		SYNTAX		INTEGER { disable(0), enable(1) }
		MAX-ACCESS		read-write
		STATUS			current
		DESCRIPTION
				"TYPE: - Checkbox
				 PAGE: - RollCall- Logging- Dolby Encoder
					Log Framerate  cmdID= 35806 "
		::= { iqdbe00CmdEntry 35806 }


	iqdbe00LoggingDolbyEncoderFramerate OBJECT-TYPE
		SYNTAX		RollCallString
		MAX-ACCESS		read-only
		STATUS			current
		DESCRIPTION
				"TYPE: - Display
				 PAGE: - RollCall- Logging- Dolby Encoder
					Framerate=  cmdID= 36806  format=   "
		::= { iqdbe00CmdEntry 36806 }


	iqdbe00LoggingDolbyEncoderLogProg1DescTxt OBJECT-TYPE
		SYNTAX		INTEGER { disable(0), enable(1) }
		MAX-ACCESS		read-write
		STATUS			current
		DESCRIPTION
				"TYPE: - Checkbox
				 PAGE: - RollCall- Logging- Dolby Encoder
					Log Prog 1 Desc Txt  cmdID= 35821 "
		::= { iqdbe00CmdEntry 35821 }


	iqdbe00LoggingDolbyEncoderProg1DescTxt OBJECT-TYPE
		SYNTAX		RollCallString
		MAX-ACCESS		read-only
		STATUS			current
		DESCRIPTION
				"TYPE: - Display
				 PAGE: - RollCall- Logging- Dolby Encoder
					Log Prog 1 Desc Txt  cmdID= 36821  format=   "
		::= { iqdbe00CmdEntry 36821 }


	iqdbe00LoggingDolbyEncoderProg1DescTxtpt2 OBJECT-TYPE
		SYNTAX		RollCallString
		MAX-ACCESS		read-only
		STATUS			current
		DESCRIPTION
				"TYPE: - Display
				 PAGE: - RollCall- Logging- Dolby Encoder
					Prog 1 Desc Txt pt2  cmdID= 39029  format=   "
		::= { iqdbe00CmdEntry 39029 }


	iqdbe00LoggingDolbyEncoderLogProg2DescTxt OBJECT-TYPE
		SYNTAX		INTEGER { disable(0), enable(1) }
		MAX-ACCESS		read-write
		STATUS			current
		DESCRIPTION
				"TYPE: - Checkbox
				 PAGE: - RollCall- Logging- Dolby Encoder
					Log Prog 2 Desc Txt  cmdID= 35822 "
		::= { iqdbe00CmdEntry 35822 }


	iqdbe00LoggingDolbyEncoderProg2DescTxt OBJECT-TYPE
		SYNTAX		RollCallString
		MAX-ACCESS		read-only
		STATUS			current
		DESCRIPTION
				"TYPE: - Display
				 PAGE: - RollCall- Logging- Dolby Encoder
					Log Prog 2 Desc Txt  cmdID= 36822  format=   "
		::= { iqdbe00CmdEntry 36822 }


	iqdbe00LoggingDolbyEncoderProg2DescTxtpt2 OBJECT-TYPE
		SYNTAX		RollCallString
		MAX-ACCESS		read-only
		STATUS			current
		DESCRIPTION
				"TYPE: - Display
				 PAGE: - RollCall- Logging- Dolby Encoder
					Prog 2 Desc Txt pt2  cmdID= 39030  format=   "
		::= { iqdbe00CmdEntry 39030 }


	iqdbe00LoggingDolbyEncoderLogProg3DescTxt OBJECT-TYPE
		SYNTAX		INTEGER { disable(0), enable(1) }
		MAX-ACCESS		read-write
		STATUS			current
		DESCRIPTION
				"TYPE: - Checkbox
				 PAGE: - RollCall- Logging- Dolby Encoder
					Log Prog 3 Desc Txt  cmdID= 35823 "
		::= { iqdbe00CmdEntry 35823 }


	iqdbe00LoggingDolbyEncoderProg3DescTxt OBJECT-TYPE
		SYNTAX		RollCallString
		MAX-ACCESS		read-only
		STATUS			current
		DESCRIPTION
				"TYPE: - Display
				 PAGE: - RollCall- Logging- Dolby Encoder
					Log Prog 3 Desc Txt  cmdID= 36823  format=   "
		::= { iqdbe00CmdEntry 36823 }


	iqdbe00LoggingDolbyEncoderProg3DescTxtpt2 OBJECT-TYPE
		SYNTAX		RollCallString
		MAX-ACCESS		read-only
		STATUS			current
		DESCRIPTION
				"TYPE: - Display
				 PAGE: - RollCall- Logging- Dolby Encoder
					Prog 3 Desc Txt pt2  cmdID= 39031  format=   "
		::= { iqdbe00CmdEntry 39031 }


	iqdbe00LoggingDolbyEncoderLogProg4DescTxt OBJECT-TYPE
		SYNTAX		INTEGER { disable(0), enable(1) }
		MAX-ACCESS		read-write
		STATUS			current
		DESCRIPTION
				"TYPE: - Checkbox
				 PAGE: - RollCall- Logging- Dolby Encoder
					Log Prog 4 Desc Txt  cmdID= 35824 "
		::= { iqdbe00CmdEntry 35824 }


	iqdbe00LoggingDolbyEncoderProg4DescTxt OBJECT-TYPE
		SYNTAX		RollCallString
		MAX-ACCESS		read-only
		STATUS			current
		DESCRIPTION
				"TYPE: - Display
				 PAGE: - RollCall- Logging- Dolby Encoder
					Log Prog 4 Desc Txt  cmdID= 36824  format=   "
		::= { iqdbe00CmdEntry 36824 }


	iqdbe00LoggingDolbyEncoderProg4DescTxtpt2 OBJECT-TYPE
		SYNTAX		RollCallString
		MAX-ACCESS		read-only
		STATUS			current
		DESCRIPTION
				"TYPE: - Display
				 PAGE: - RollCall- Logging- Dolby Encoder
					Prog 4 Desc Txt pt2  cmdID= 39032  format=   "
		::= { iqdbe00CmdEntry 39032 }


	iqdbe00LoggingDolbyEncoderLogProg5DescTxt OBJECT-TYPE
		SYNTAX		INTEGER { disable(0), enable(1) }
		MAX-ACCESS		read-write
		STATUS			current
		DESCRIPTION
				"TYPE: - Checkbox
				 PAGE: - RollCall- Logging- Dolby Encoder
					Log Prog 5 Desc Txt  cmdID= 35825 "
		::= { iqdbe00CmdEntry 35825 }


	iqdbe00LoggingDolbyEncoderProg5DescTxt OBJECT-TYPE
		SYNTAX		RollCallString
		MAX-ACCESS		read-only
		STATUS			current
		DESCRIPTION
				"TYPE: - Display
				 PAGE: - RollCall- Logging- Dolby Encoder
					Log Prog 5 Desc Txt  cmdID= 36825  format=   "
		::= { iqdbe00CmdEntry 36825 }


	iqdbe00LoggingDolbyEncoderProg5DescTxtpt2 OBJECT-TYPE
		SYNTAX		RollCallString
		MAX-ACCESS		read-only
		STATUS			current
		DESCRIPTION
				"TYPE: - Display
				 PAGE: - RollCall- Logging- Dolby Encoder
					Prog 5 Desc Txt pt2  cmdID= 39033  format=   "
		::= { iqdbe00CmdEntry 39033 }


	iqdbe00LoggingDolbyEncoderLogProg6DescTxt OBJECT-TYPE
		SYNTAX		INTEGER { disable(0), enable(1) }
		MAX-ACCESS		read-write
		STATUS			current
		DESCRIPTION
				"TYPE: - Checkbox
				 PAGE: - RollCall- Logging- Dolby Encoder
					Log Prog 6 Desc Txt  cmdID= 35826 "
		::= { iqdbe00CmdEntry 35826 }


	iqdbe00LoggingDolbyEncoderProg6DescTxt OBJECT-TYPE
		SYNTAX		RollCallString
		MAX-ACCESS		read-only
		STATUS			current
		DESCRIPTION
				"TYPE: - Display
				 PAGE: - RollCall- Logging- Dolby Encoder
					Log Prog 6 Desc Txt  cmdID= 36826  format=   "
		::= { iqdbe00CmdEntry 36826 }


	iqdbe00LoggingDolbyEncoderProg6DescTxtpt2 OBJECT-TYPE
		SYNTAX		RollCallString
		MAX-ACCESS		read-only
		STATUS			current
		DESCRIPTION
				"TYPE: - Display
				 PAGE: - RollCall- Logging- Dolby Encoder
					Prog 6 Desc Txt pt2  cmdID= 39034  format=   "
		::= { iqdbe00CmdEntry 39034 }


	iqdbe00LoggingDolbyEncoderLogProg7DescTxt OBJECT-TYPE
		SYNTAX		INTEGER { disable(0), enable(1) }
		MAX-ACCESS		read-write
		STATUS			current
		DESCRIPTION
				"TYPE: - Checkbox
				 PAGE: - RollCall- Logging- Dolby Encoder
					Log Prog 7 Desc Txt  cmdID= 35827 "
		::= { iqdbe00CmdEntry 35827 }


	iqdbe00LoggingDolbyEncoderProg7DescTxt OBJECT-TYPE
		SYNTAX		RollCallString
		MAX-ACCESS		read-only
		STATUS			current
		DESCRIPTION
				"TYPE: - Display
				 PAGE: - RollCall- Logging- Dolby Encoder
					Log Prog 7 Desc Txt  cmdID= 36827  format=   "
		::= { iqdbe00CmdEntry 36827 }


	iqdbe00LoggingDolbyEncoderProg7DescTxtpt2 OBJECT-TYPE
		SYNTAX		RollCallString
		MAX-ACCESS		read-only
		STATUS			current
		DESCRIPTION
				"TYPE: - Display
				 PAGE: - RollCall- Logging- Dolby Encoder
					Prog 7 Desc Txt pt2  cmdID= 39035  format=   "
		::= { iqdbe00CmdEntry 39035 }


	iqdbe00LoggingDolbyEncoderLogProg8DescTxt OBJECT-TYPE
		SYNTAX		INTEGER { disable(0), enable(1) }
		MAX-ACCESS		read-write
		STATUS			current
		DESCRIPTION
				"TYPE: - Checkbox
				 PAGE: - RollCall- Logging- Dolby Encoder
					Log Prog 8 Desc Txt  cmdID= 35828 "
		::= { iqdbe00CmdEntry 35828 }


	iqdbe00LoggingDolbyEncoderProg8DescTxt OBJECT-TYPE
		SYNTAX		RollCallString
		MAX-ACCESS		read-only
		STATUS			current
		DESCRIPTION
				"TYPE: - Display
				 PAGE: - RollCall- Logging- Dolby Encoder
					Log Prog 8 Desc Txt  cmdID= 36828  format=   "
		::= { iqdbe00CmdEntry 36828 }


	iqdbe00LoggingDolbyEncoderProg8DescTxtpt2 OBJECT-TYPE
		SYNTAX		RollCallString
		MAX-ACCESS		read-only
		STATUS			current
		DESCRIPTION
				"TYPE: - Display
				 PAGE: - RollCall- Logging- Dolby Encoder
					Prog 8 Desc Txt pt2  cmdID= 39036  format=   "
		::= { iqdbe00CmdEntry 39036 }


	iqdbe00LoggingMiscLoggingLogSerialNo OBJECT-TYPE
		SYNTAX		INTEGER { disable(0), enable(1) }
		MAX-ACCESS		read-write
		STATUS			current
		DESCRIPTION
				"TYPE: - Checkbox
				 PAGE: - RollCall- Logging
					Log Serial No.  cmdID= 35015 "
		::= { iqdbe00CmdEntry 35015 }


	iqdbe00LoggingMiscLoggingSerialNo OBJECT-TYPE
		SYNTAX		RollCallString
		MAX-ACCESS		read-only
		STATUS			current
		DESCRIPTION
				"TYPE: - Display
				 PAGE: - RollCall- Logging
					Serial No.=  cmdID= 36015  format=   "
		::= { iqdbe00CmdEntry 36015 }


	iqdbe00LoggingMiscLoggingLogOSVersion OBJECT-TYPE
		SYNTAX		INTEGER { disable(0), enable(1) }
		MAX-ACCESS		read-write
		STATUS			current
		DESCRIPTION
				"TYPE: - Checkbox
				 PAGE: - RollCall- Logging
					Log OS Version  cmdID= 35993 "
		::= { iqdbe00CmdEntry 35993 }


	iqdbe00LoggingMiscLoggingOSVersion OBJECT-TYPE
		SYNTAX		RollCallString
		MAX-ACCESS		read-only
		STATUS			current
		DESCRIPTION
				"TYPE: - Display
				 PAGE: - RollCall- Logging
					OS Version=  cmdID= 36993  format=   "
		::= { iqdbe00CmdEntry 36993 }


	iqdbe00LoggingMiscLoggingLogBuildNo OBJECT-TYPE
		SYNTAX		INTEGER { disable(0), enable(1) }
		MAX-ACCESS		read-write
		STATUS			current
		DESCRIPTION
				"TYPE: - Checkbox
				 PAGE: - RollCall- Logging
					Log Build No.  cmdID= 35990 "
		::= { iqdbe00CmdEntry 35990 }


	iqdbe00LoggingMiscLoggingBuildNo OBJECT-TYPE
		SYNTAX		RollCallString
		MAX-ACCESS		read-only
		STATUS			current
		DESCRIPTION
				"TYPE: - Display
				 PAGE: - RollCall- Logging
					Build No.=  cmdID= 36990  format=   "
		::= { iqdbe00CmdEntry 36990 }


	iqdbe00LoggingMiscLoggingLogHardwareVer OBJECT-TYPE
		SYNTAX		INTEGER { disable(0), enable(1) }
		MAX-ACCESS		read-write
		STATUS			current
		DESCRIPTION
				"TYPE: - Checkbox
				 PAGE: - RollCall- Logging
					Log Hardware Ver.  cmdID= 35992 "
		::= { iqdbe00CmdEntry 35992 }


	iqdbe00LoggingMiscLoggingHardwareVer OBJECT-TYPE
		SYNTAX		RollCallString
		MAX-ACCESS		read-only
		STATUS			current
		DESCRIPTION
				"TYPE: - Display
				 PAGE: - RollCall- Logging
					Hardware Ver.=  cmdID= 36992  format=   "
		::= { iqdbe00CmdEntry 36992 }


	iqdbe00LoggingMiscLoggingLogFirmwareVer OBJECT-TYPE
		SYNTAX		INTEGER { disable(0), enable(1) }
		MAX-ACCESS		read-write
		STATUS			current
		DESCRIPTION
				"TYPE: - Checkbox
				 PAGE: - RollCall- Logging
					Log Firmware Ver.  cmdID= 35991 "
		::= { iqdbe00CmdEntry 35991 }


	iqdbe00LoggingMiscLoggingFirmwareVer OBJECT-TYPE
		SYNTAX		RollCallString
		MAX-ACCESS		read-only
		STATUS			current
		DESCRIPTION
				"TYPE: - Display
				 PAGE: - RollCall- Logging
					Firmware Ver.=  cmdID= 36991  format=   "
		::= { iqdbe00CmdEntry 36991 }


	iqdbe00LoggingMiscLoggingLogUpTime OBJECT-TYPE
		SYNTAX		INTEGER { disable(0), enable(1) }
		MAX-ACCESS		read-write
		STATUS			current
		DESCRIPTION
				"TYPE: - Checkbox
				 PAGE: - RollCall- Logging
					Log Up Time  cmdID= 35994 "
		::= { iqdbe00CmdEntry 35994 }


	iqdbe00LoggingMiscLoggingUpTime OBJECT-TYPE
		SYNTAX		RollCallString
		MAX-ACCESS		read-only
		STATUS			current
		DESCRIPTION
				"TYPE: - Display
				 PAGE: - RollCall- Logging
					Up Time=  cmdID= 36994  format=   "
		::= { iqdbe00CmdEntry 36994 }


	iqdbe00RollCallRollTrackDisableAll OBJECT-TYPE
		SYNTAX		INTEGER { disable(0), enable(1) }
		MAX-ACCESS		read-write
		STATUS			current
		DESCRIPTION
				"TYPE: - Checkbox
				 PAGE: - RollCall
					Disable All  cmdID= 36104 "
		::= { iqdbe00CmdEntry 36104 }


	iqdbe00RollCallRollTrackIndex OBJECT-TYPE
		SYNTAX		INTEGER
		MAX-ACCESS		read-write
		STATUS			current
		DESCRIPTION
				"TYPE: - BarGraph
				 PAGE: - RollCall
					Index  cmdID= 36100  min= 1  max= 16   step= 1  format= %0.0f  div_scale= 1
					Min = 1  Max = 16  Step = 1 "
		::= { iqdbe00CmdEntry 36100 }


	iqdbe00RollCallRollTrackSource OBJECT-TYPE
		SYNTAX		INTEGER {
							val_Unused(-1),
							val_Video_Delay(0),
							val_Input_Present(1),
							val_Input_Loss(2),
							val_O_p_Freeze(3),
							val_O_p_UnFreeze(4),
							val_Output_1080(53),
							val_Output_720(54),
							val_Output_576_625(55),
							val_Output_480_525(56),
							val_Disembed_1_Data(5),
							val_Disembed_1_Pcm(6),
							val_Disembed_1_Lost(7),
							val_Disembed_2_Data(8),
							val_Disembed_2_Pcm(9),
							val_Disembed_2_Lost(10),
							val_Disembed_3_Data(11),
							val_Disembed_3_Pcm(12),
							val_Disembed_3_Lost(13),
							val_Disembed_4_Data(14),
							val_Disembed_4_Pcm(15),
							val_Disembed_4_Lost(16),
							val_Disembed_5_Data(17),
							val_Disembed_5_Pcm(18),
							val_Disembed_5_Lost(19),
							val_Disembed_6_Data(20),
							val_Disembed_6_Pcm(21),
							val_Disembed_6_Lost(22),
							val_Disembed_7_Data(23),
							val_Disembed_7_Pcm(24),
							val_Disembed_7_Lost(25),
							val_Disembed_8_Data(26),
							val_Disembed_8_Pcm(27),
							val_Disembed_8_Lost(28),
							val_AES_1_Data(29),
							val_AES_1_Pcm(30),
							val_AES_1_Lost(31),
							val_AES_2_Data(32),
							val_AES_2_Pcm(33),
							val_AES_2_Lost(34),
							val_AES_3_Data(35),
							val_AES_3_Pcm(36),
							val_AES_3_Lost(37),
							val_AES_4_Data(38),
							val_AES_4_Pcm(39),
							val_AES_4_Lost(40),
							val_AES_5_Data(41),
							val_AES_5_Pcm(42),
							val_AES_5_Lost(43),
							val_AES_6_Data(44),
							val_AES_6_Pcm(45),
							val_AES_6_Lost(46),
							val_AES_7_Data(47),
							val_AES_7_Pcm(48),
							val_AES_7_Lost(49)
							}
		MAX-ACCESS		read-write
		STATUS			current
		DESCRIPTION
				"TYPE: - RadiobuttonList
				 PAGE: - RollCall
					Source  cmdID= 36101
					Unused  value= -1
					Video Delay  value= 0
					Input Present  value= 1
					Input Loss  value= 2
					O/p Freeze  value= 3
					O/p UnFreeze  value= 4
					Output:1080  value= 53
					Output:720  value= 54
					Output:576(625)  value= 55
					Output:480(525)  value= 56
					Disembed 1 Data  value= 5
					Disembed 1 Pcm  value= 6
					Disembed 1 Lost  value= 7
					Disembed 2 Data  value= 8
					Disembed 2 Pcm  value= 9
					Disembed 2 Lost  value= 10
					Disembed 3 Data  value= 11
					Disembed 3 Pcm  value= 12
					Disembed 3 Lost  value= 13
					Disembed 4 Data  value= 14
					Disembed 4 Pcm  value= 15
					Disembed 4 Lost  value= 16
					Disembed 5 Data  value= 17
					Disembed 5 Pcm  value= 18
					Disembed 5 Lost  value= 19
					Disembed 6 Data  value= 20
					Disembed 6 Pcm  value= 21
					Disembed 6 Lost  value= 22
					Disembed 7 Data  value= 23
					Disembed 7 Pcm  value= 24
					Disembed 7 Lost  value= 25
					Disembed 8 Data  value= 26
					Disembed 8 Pcm  value= 27
					Disembed 8 Lost  value= 28
					AES 1 Data  value= 29
					AES 1 Pcm  value= 30
					AES 1 Lost  value= 31
					AES 2 Data  value= 32
					AES 2 Pcm  value= 33
					AES 2 Lost  value= 34
					AES 3 Data  value= 35
					AES 3 Pcm  value= 36
					AES 3 Lost  value= 37
					AES 4 Data  value= 38
					AES 4 Pcm  value= 39
					AES 4 Lost  value= 40
					AES 5 Data  value= 41
					AES 5 Pcm  value= 42
					AES 5 Lost  value= 43
					AES 6 Data  value= 44
					AES 6 Pcm  value= 45
					AES 6 Lost  value= 46
					AES 7 Data  value= 47
					AES 7 Pcm  value= 48
					AES 7 Lost  value= 49  "
		::= { iqdbe00CmdEntry 36101 }


	iqdbe00RollCallRollTrackAddress OBJECT-TYPE
		SYNTAX		RollCallString
		MAX-ACCESS		read-write
		STATUS			current
		DESCRIPTION
				"TYPE: - Editstring
				 PAGE: - RollCall
					Address  cmdID= 36102  "
		::= { iqdbe00CmdEntry 36102 }


	iqdbe00RollCallRollTrackCommand OBJECT-TYPE
		SYNTAX		RollCallString
		MAX-ACCESS		read-write
		STATUS			current
		DESCRIPTION
				"TYPE: - Editstring
				 PAGE: - RollCall
					Command  cmdID= 36103  "
		::= { iqdbe00CmdEntry 36103 }


	iqdbe00RollCallRollTrackStatus OBJECT-TYPE
		SYNTAX		RollCallString
		MAX-ACCESS		read-only
		STATUS			current
		DESCRIPTION
				"TYPE: - Display
				 PAGE: - RollCall
					Status  cmdID= 36105  format=   "
		::= { iqdbe00CmdEntry 36105 }


	iqdbe00RollCallRollTrackSending OBJECT-TYPE
		SYNTAX		RollCallString
		MAX-ACCESS		read-only
		STATUS			current
		DESCRIPTION
				"TYPE: - Display
				 PAGE: - RollCall
					Sending  cmdID= 36106  format=   "
		::= { iqdbe00CmdEntry 36106 }


	iqdbe00AudioSetupUnitStatusDisplay OBJECT-TYPE
		SYNTAX		INTEGER {
							val_Video_Status(0),
							val_Audio_Status(1),
							val_Dolby_Enc_Status(2),
							val_Dolby_Enc_Metadata(3)
							}
		MAX-ACCESS		read-write
		STATUS			current
		DESCRIPTION
				"TYPE: - RadiobuttonList
					Unit Status Display  cmdID= 32773
					Video Status  value= 0
					Audio Status  value= 1
					Dolby Enc Status  value= 2
					Dolby Enc Metadata  value= 3  "
		::= { iqdbe00CmdEntry 32773 }


	iqdbe00AudioSetupProduct OBJECT-TYPE
		SYNTAX		RollCallString
		MAX-ACCESS		read-only
		STATUS			current
		DESCRIPTION
				"TYPE: - Display
					Product  cmdID= 32771  format=   "
		::= { iqdbe00CmdEntry 32771 }


	iqdbe00AudioSetupRelease OBJECT-TYPE
		SYNTAX		RollCallString
		MAX-ACCESS		read-only
		STATUS			current
		DESCRIPTION
				"TYPE: - Display
					Release  cmdID= 2  format=   "
		::= { iqdbe00CmdEntry 2 }


	iqdbe00AudioSetupBuild OBJECT-TYPE
		SYNTAX		RollCallString
		MAX-ACCESS		read-only
		STATUS			current
		DESCRIPTION
				"TYPE: - Display
					Build  cmdID= 5  format=   "
		::= { iqdbe00CmdEntry 5 }


	iqdbe00AudioSetupKOS OBJECT-TYPE
		SYNTAX		RollCallString
		MAX-ACCESS		read-only
		STATUS			current
		DESCRIPTION
				"TYPE: - Display
					KOS  cmdID= 32772  format=   "
		::= { iqdbe00CmdEntry 32772 }


	iqdbe00AudioSetupSerialNo OBJECT-TYPE
		SYNTAX		RollCallString
		MAX-ACCESS		read-only
		STATUS			current
		DESCRIPTION
				"TYPE: - Display
					Serial No.  cmdID= 1  format=   "
		::= { iqdbe00CmdEntry 1 }


	iqdbe00AudioSetupFirmware OBJECT-TYPE
		SYNTAX		RollCallString
		MAX-ACCESS		read-only
		STATUS			current
		DESCRIPTION
				"TYPE: - Display
					Firmware  cmdID= 32769  format=   "
		::= { iqdbe00CmdEntry 32769 }


	iqdbe00AudioSetupPCB OBJECT-TYPE
		SYNTAX		RollCallString
		MAX-ACCESS		read-only
		STATUS			current
		DESCRIPTION
				"TYPE: - Display
					PCB  cmdID= 32770  format=   "
		::= { iqdbe00CmdEntry 32770 }


	iqdbe00AudioSetupFactoryDefault OBJECT-TYPE
		SYNTAX		INTEGER { noAction(0),val_Factory_Default(1) }
		MAX-ACCESS		read-write
		STATUS			current
		DESCRIPTION
				"TYPE: - Button
					Factory Default  cmdID= 37002  value= 1  "
		::= { iqdbe00CmdEntry 37002 }


	iqdbe00AudioSetupRestart OBJECT-TYPE
		SYNTAX		INTEGER { noAction(0),val_Restart(1) }
		MAX-ACCESS		read-write
		STATUS			current
		DESCRIPTION
				"TYPE: - Button
					Restart  cmdID= 4  value= 1  "
		::= { iqdbe00CmdEntry 4 }


	iqdbe00AudioSetupDefaultSettings OBJECT-TYPE
		SYNTAX		INTEGER { noAction(0),val_Default_Settings(1) }
		MAX-ACCESS		read-write
		STATUS			current
		DESCRIPTION
				"TYPE: - Button
					Default Settings  cmdID= 37001  value= 1  "
		::= { iqdbe00CmdEntry 37001 }


	iqdbe00AudioSetupSerialNumber OBJECT-TYPE
		SYNTAX		RollCallString
		MAX-ACCESS		read-write
		STATUS			current
		DESCRIPTION
				"TYPE: - Editstring
					Serial Number  cmdID= 32774  "
		::= { iqdbe00CmdEntry 32774 }


	iqdbe00AudioSetupBoardID OBJECT-TYPE
		SYNTAX		INTEGER {
							val_IQDBE00(562),
							val_IQDBE01(563)
							}
		MAX-ACCESS		read-write
		STATUS			current
		DESCRIPTION
				"TYPE: - RadiobuttonList
					BoardID  cmdID= 32776
					IQDBE00  value= 562
					IQDBE01  value= 563  "
		::= { iqdbe00CmdEntry 32776 }


	iqdbe00AudioSetupSaveID OBJECT-TYPE
		SYNTAX		INTEGER { noAction(0),val_Save_ID(1) }
		MAX-ACCESS		read-write
		STATUS			current
		DESCRIPTION
				"TYPE: - Button
					Save ID  cmdID= 32775  value= 1  "
		::= { iqdbe00CmdEntry 32775 }


	iqdbe00AudioEngineerEngineerPassword OBJECT-TYPE
		SYNTAX		RollCallString
		MAX-ACCESS		read-write
		STATUS			current
		DESCRIPTION
				"TYPE: - Editstring
				 PAGE: - Engineer
					Engineer Password  cmdID= 34011  "
		::= { iqdbe00CmdEntry 34011 }


	iqdbe00AudioEngineerShowEngineer OBJECT-TYPE
		SYNTAX		INTEGER { disable(0), enable(1) }
		MAX-ACCESS		read-write
		STATUS			current
		DESCRIPTION
				"TYPE: - Checkbox
				 PAGE: - Engineer
					Show Engineer  cmdID= 34012 "
		::= { iqdbe00CmdEntry 34012 }


	iqdbe00EngineerPageOptions1 OBJECT-TYPE
		SYNTAX		INTEGER { disable(0), enable(1) }
		MAX-ACCESS		read-write
		STATUS			current
		DESCRIPTION
				"TYPE: - Checkbox
				 PAGE: - Engineer
					$S1  cmdID= 34014 "
		::= { iqdbe00CmdEntry 34014 }


	iqdbe00EngineerPageOptions2 OBJECT-TYPE
		SYNTAX		INTEGER { disable(0), enable(1) }
		MAX-ACCESS		read-write
		STATUS			current
		DESCRIPTION
				"TYPE: - Checkbox
				 PAGE: - Engineer
					$S1  cmdID= 34015 "
		::= { iqdbe00CmdEntry 34015 }


	iqdbe00EngineerPageOptions3 OBJECT-TYPE
		SYNTAX		INTEGER { disable(0), enable(1) }
		MAX-ACCESS		read-write
		STATUS			current
		DESCRIPTION
				"TYPE: - Checkbox
				 PAGE: - Engineer
					$S1  cmdID= 34016 "
		::= { iqdbe00CmdEntry 34016 }


	iqdbe00EngineerEngineerPageUndoChanges OBJECT-TYPE
		SYNTAX		INTEGER { noAction(0),val_Undo_Changes(1) }
		MAX-ACCESS		read-write
		STATUS			current
		DESCRIPTION
				"TYPE: - Button
				 PAGE: - Engineer
					Undo Changes  cmdID= 34013  value= 1  "
		::= { iqdbe00CmdEntry 34013 }


	iqdbe00EngineerEngineerPageLineNumber OBJECT-TYPE
		SYNTAX		RollCallString
		MAX-ACCESS		read-only
		STATUS			current
		DESCRIPTION
				"TYPE: - Display
				 PAGE: - Engineer
					Line Number  cmdID= 38651  format=   "
		::= { iqdbe00CmdEntry 38651 }


	iqdbe00EngineerEngineerPageSampleNumber OBJECT-TYPE
		SYNTAX		RollCallString
		MAX-ACCESS		read-only
		STATUS			current
		DESCRIPTION
				"TYPE: - Display
				 PAGE: - Engineer
					Sample Number  cmdID= 38657  format=   "
		::= { iqdbe00CmdEntry 38657 }


	iqdbe00EngineerEngineerPageDolbyModuleUpdate OBJECT-TYPE
		SYNTAX		INTEGER {
							val_Disabled_Update(0),
							val_Enable_Ext_Ser_Upd(1),
							val_Start_Internal_Upd(2)
							}
		MAX-ACCESS		read-write
		STATUS			current
		DESCRIPTION
				"TYPE: - RadiobuttonList
				 PAGE: - Engineer
					Dolby Module Update  cmdID= 39998
					Disabled Update  value= 0
					Enable Ext Ser Upd  value= 1
					Start Internal Upd  value= 2  "
		::= { iqdbe00CmdEntry 39998 }


	iqdbe00EngineerPaAutoalignEmbeddedInputs OBJECT-TYPE
		SYNTAX		INTEGER { disable(0), enable(1) }
		MAX-ACCESS		read-write
		STATUS			current
		DESCRIPTION
				"TYPE: - Checkbox
				 PAGE: - Engineer
					Embedded Inputs  cmdID= 34060 "
		::= { iqdbe00CmdEntry 34060 }


	iqdbe00EngineerPaAutoalignAESInputs OBJECT-TYPE
		SYNTAX		INTEGER { disable(0), enable(1) }
		MAX-ACCESS		read-write
		STATUS			current
		DESCRIPTION
				"TYPE: - Checkbox
				 PAGE: - Engineer
					AES Inputs  cmdID= 34061 "
		::= { iqdbe00CmdEntry 34061 }


	iqdbe00MenuAudioShowEngineer2 OBJECT-TYPE
		SYNTAX		INTEGER { disable(0), enable(1) }
		MAX-ACCESS		read-write
		STATUS			current
		DESCRIPTION
				"TYPE: - Checkbox
					Show Engineer2  cmdID= 34050 "
		::= { iqdbe00CmdEntry 34050 }


	iqdbe00MenuAudioUseEmbDelayFbac OBJECT-TYPE
		SYNTAX		INTEGER { disable(0), enable(1) }
		MAX-ACCESS		read-write
		STATUS			current
		DESCRIPTION
				"TYPE: - Checkbox
					Use Emb Delay F/bac  cmdID= 34049 "
		::= { iqdbe00CmdEntry 34049 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S35034500
--				:
-- Comments		: Serial Number or module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:34:00
--				:
-- Comments		: Uptime in formated date-time string
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number or current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 2001420336
--				:
-- Comments		: String of current Software build number
--
---------------------------------------------------------------------------------------------------
-- Header		: INFORMATION1
--
-- MIB ref		: swCardEventLogSlotXX       .12.73.78.70.79.82.77.65.84.73.79.78.49
-- absolute OID	: 1.3.6.1.4.1.7995.2.6.1.1.XX.12.73.78.70.79.82.77.65.84.73.79.78.49
-- Vary			: YES
--
-- Value(s)		: E Encode Text A
--				:
-- Comments		: User configurable text string
--
---------------------------------------------------------------------------------------------------
-- Header		: INFORMATION2
--
-- MIB ref		: swCardEventLogSlotXX       .12.73.78.70.79.82.77.65.84.73.79.78.50
-- absolute OID	: 1.3.6.1.4.1.7995.2.6.1.1.XX.12.73.78.70.79.82.77.65.84.73.79.78.50
-- Vary			: YES
--
-- Value(s)		: E Encode Text B
--				:
-- Comments		: User configurable text string
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: HD / SD SDI
--				:
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2010-04-22T09:50:22Z
--				:
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: OK
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2010-04-22T08:51:21Z
--				:
-- Comments		: Time String of last control modification
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: HD / SD SDI
--				:
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: BLACK
--				: PATTERN
--				: MONO
--				: FROZEN
--				: OK
--				: FAIL
-- Comments		:
--
---------------------------------------------------------------------------------------------------
-- Header		: AES_INPUT_1_TYPE
--
-- MIB ref		: swCardEventLogSlotXX       .16.65.69.83.95.73.78.80.85.84.95.49.95.84.89.80.69
-- absolute OID	: 1.3.6.1.4.1.7995.2.6.1.1.XX.16.65.69.83.95.73.78.80.85.84.95.49.95.84.89.80.69
-- Vary			: YES
--
-- Value(s)		: Unknown
--				: NONPCM
--              : PCM
--              : WARN: No Input
-- Comments		:
--
---------------------------------------------------------------------------------------------------
-- Header		: AES_INPUT_2_TYPE
--
-- MIB ref		: swCardEventLogSlotXX       .16.65.69.83.95.73.78.80.85.84.95.50.95.84.89.80.69
-- absolute OID	: 1.3.6.1.4.1.7995.2.6.1.1.XX.16.65.69.83.95.73.78.80.85.84.95.50.95.84.89.80.69
-- Vary			: YES
--
-- Value(s)		: Unknown
--				: NONPCM
--              : PCM
--              : WARN: No Input
-- Comments		:
--
---------------------------------------------------------------------------------------------------
-- Header		: AES_INPUT_3_TYPE
--
-- MIB ref		: swCardEventLogSlotXX       .16.65.69.83.95.73.78.80.85.84.95.51.95.84.89.80.69
-- absolute OID	: 1.3.6.1.4.1.7995.2.6.1.1.XX.16.65.69.83.95.73.78.80.85.84.95.51.95.84.89.80.69
-- Vary			: YES
--
-- Value(s)		: Unknown
--				: NONPCM
--              : PCM
--              : WARN: No Input
-- Comments		:
--
---------------------------------------------------------------------------------------------------
-- Header		: AES_INPUT_4_TYPE
--
-- MIB ref		: swCardEventLogSlotXX       .16.65.69.83.95.73.78.80.85.84.95.52.95.84.89.80.69
-- absolute OID	: 1.3.6.1.4.1.7995.2.6.1.1.XX.16.65.69.83.95.73.78.80.85.84.95.52.95.84.89.80.69
-- Vary			: YES
--
-- Value(s)		: Unknown
--				: NONPCM
--              : PCM
--              : WARN: No Input
-- Comments		:
--
---------------------------------------------------------------------------------------------------
-- Header		: AES_INPUT_5_TYPE
--
-- MIB ref		: swCardEventLogSlotXX       .16.65.69.83.95.73.78.80.85.84.95.53.95.84.89.80.69
-- absolute OID	: 1.3.6.1.4.1.7995.2.6.1.1.XX.16.65.69.83.95.73.78.80.85.84.95.53.95.84.89.80.69
-- Vary			: YES
--
-- Value(s)		: Unknown
--				: NONPCM
--              : PCM
--              : WARN: No Input
-- Comments		:
--
---------------------------------------------------------------------------------------------------
-- Header		: AES_INPUT_6_TYPE
--
-- MIB ref		: swCardEventLogSlotXX       .16.65.69.83.95.73.78.80.85.84.95.54.95.84.89.80.69
-- absolute OID	: 1.3.6.1.4.1.7995.2.6.1.1.XX.16.65.69.83.95.73.78.80.85.84.95.54.95.84.89.80.69
-- Vary			: YES
--
-- Value(s)		: Unknown
--				: NONPCM
--              : PCM
--              : WARN: No Input
-- Comments		:
--
---------------------------------------------------------------------------------------------------
-- Header		: AES_INPUT_7_TYPE
--
-- MIB ref		: swCardEventLogSlotXX       .16.65.69.83.95.73.78.80.85.84.95.55.95.84.89.80.69
-- absolute OID	: 1.3.6.1.4.1.7995.2.6.1.1.XX.16.65.69.83.95.73.78.80.85.84.95.55.95.84.89.80.69
-- Vary			: YES
--
-- Value(s)		: Unknown
--				: NONPCM
--              : PCM
--              : WARN: No Input
-- Comments		:
--
---------------------------------------------------------------------------------------------------
-- Header		: AES_INPUT_8_TYPE
--
-- MIB ref		: swCardEventLogSlotXX       .16.65.69.83.95.73.78.80.85.84.95.56.95.84.89.80.69
-- absolute OID	: 1.3.6.1.4.1.7995.2.6.1.1.XX.16.65.69.83.95.73.78.80.85.84.95.56.95.84.89.80.69
-- Vary			: YES
--
-- Value(s)		: Unknown
--				: NONPCM
--              : PCM
--              : WARN: No Input
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 2.158
--				:
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RDAUD1B.004
--				:
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
-- Vary			: YES
--
-- Value(s)		: OK
--				: NONE
--              : WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_INPUT_1_STATE
--
-- MIB ref		: swCardEventLogSlotXX       .17.65.69.83.95.73.78.80.85.84.95.49.95.83.84.65.84.69
-- absolute OID	: 1.3.6.1.4.1.7995.2.6.1.1.XX.17.65.69.83.95.73.78.80.85.84.95.49.95.83.84.65.84.69
-- Vary			: YES
--
-- Value(s)		: LOST
--				: FAIL:Lost
--              : OK
--              : Unknown
-- Comments		:
--
---------------------------------------------------------------------------------------------------
-- Header		: AES_INPUT_2_STATE
--
-- MIB ref		: swCardEventLogSlotXX       .17.65.69.83.95.73.78.80.85.84.95.50.95.83.84.65.84.69
-- absolute OID	: 1.3.6.1.4.1.7995.2.6.1.1.XX.17.65.69.83.95.73.78.80.85.84.95.50.95.83.84.65.84.69
-- Vary			: YES
--
-- Value(s)		: LOST
--				: FAIL:Lost
--              : OK
--              : Unknown
-- Comments		:
--
---------------------------------------------------------------------------------------------------
-- Header		: AES_INPUT_3_STATE
--
-- MIB ref		: swCardEventLogSlotXX       .17.65.69.83.95.73.78.80.85.84.95.51.95.83.84.65.84.69
-- absolute OID	: 1.3.6.1.4.1.7995.2.6.1.1.XX.17.65.69.83.95.73.78.80.85.84.95.51.95.83.84.65.84.69
-- Vary			: YES
--
-- Value(s)		: LOST
--				: FAIL:Lost
--              : OK
--              : Unknown
-- Comments		:
--
---------------------------------------------------------------------------------------------------
-- Header		: AES_INPUT_4_STATE
--
-- MIB ref		: swCardEventLogSlotXX       .17.65.69.83.95.73.78.80.85.84.95.52.95.83.84.65.84.69
-- absolute OID	: 1.3.6.1.4.1.7995.2.6.1.1.XX.17.65.69.83.95.73.78.80.85.84.95.52.95.83.84.65.84.69
-- Vary			: YES
--
-- Value(s)		: LOST
--				: FAIL:Lost
--              : OK
--              : Unknown
-- Comments		:
--
---------------------------------------------------------------------------------------------------
-- Header		: AES_INPUT_5_STATE
--
-- MIB ref		: swCardEventLogSlotXX       .17.65.69.83.95.73.78.80.85.84.95.53.95.83.84.65.84.69
-- absolute OID	: 1.3.6.1.4.1.7995.2.6.1.1.XX.17.65.69.83.95.73.78.80.85.84.95.53.95.83.84.65.84.69
-- Vary			: YES
--
-- Value(s)		: LOST
--				: FAIL:Lost
--              : OK
--              : Unknown
-- Comments		:
--
---------------------------------------------------------------------------------------------------
-- Header		: AES_INPUT_6_STATE
--
-- MIB ref		: swCardEventLogSlotXX       .17.65.69.83.95.73.78.80.85.84.95.54.95.83.84.65.84.69
-- absolute OID	: 1.3.6.1.4.1.7995.2.6.1.1.XX.17.65.69.83.95.73.78.80.85.84.95.54.95.83.84.65.84.69
-- Vary			: YES
--
-- Value(s)		: LOST
--				: FAIL:Lost
--              : OK
--              : Unknown
-- Comments		:
--
---------------------------------------------------------------------------------------------------
-- Header		: AES_INPUT_7_STATE
--
-- MIB ref		: swCardEventLogSlotXX       .17.65.69.83.95.73.78.80.85.84.95.55.95.83.84.65.84.69
-- absolute OID	: 1.3.6.1.4.1.7995.2.6.1.1.XX.17.65.69.83.95.73.78.80.85.84.95.55.95.83.84.65.84.69
-- Vary			: YES
--
-- Value(s)		: LOST
--				: FAIL:Lost
--              : OK
--              : Unknown
-- Comments		:
--
---------------------------------------------------------------------------------------------------
-- Header		: AES_INPUT_8_STATE
--
-- MIB ref		: swCardEventLogSlotXX       .17.65.69.83.95.73.78.80.85.84.95.56.95.83.84.65.84.69
-- absolute OID	: 1.3.6.1.4.1.7995.2.6.1.1.XX.17.65.69.83.95.73.78.80.85.84.95.56.95.83.84.65.84.69
-- Vary			: YES
--
-- Value(s)		: LOST
--				: FAIL:Lost
--              : OK
--              : Unknown
-- Comments		:
--
---------------------------------------------------------------------------------------------------
-- Header		: AES_OUTPUT_1_TYPE
--
-- MIB ref		: swCardEventLogSlotXX       .17.65.69.83.95.79.85.84.80.85.84.95.49.95.84.89.80.69
-- absolute OID	: 1.3.6.1.4.1.7995.2.6.1.1.XX.17.65.69.83.95.79.85.84.80.85.84.95.49.95.84.89.80.69
-- Vary			: YES
--
-- Value(s)		: Unknown
--				: PCM
--              : NONPCM
--              : WARN: No Input
-- Comments		:
--
---------------------------------------------------------------------------------------------------
-- Header		: AES_OUTPUT_2_TYPE
--
-- MIB ref		: swCardEventLogSlotXX       .17.65.69.83.95.79.85.84.80.85.84.95.50.95.84.89.80.69
-- absolute OID	: 1.3.6.1.4.1.7995.2.6.1.1.XX.17.65.69.83.95.79.85.84.80.85.84.95.50.95.84.89.80.69
-- Vary			: YES
--
-- Value(s)		: Unknown
--				: PCM
--              : NONPCM
--              : WARN: No Input
-- Comments		:
--
---------------------------------------------------------------------------------------------------
-- Header		: AES_OUTPUT_3_TYPE
--
-- MIB ref		: swCardEventLogSlotXX       .17.65.69.83.95.79.85.84.80.85.84.95.51.95.84.89.80.69
-- absolute OID	: 1.3.6.1.4.1.7995.2.6.1.1.XX.17.65.69.83.95.79.85.84.80.85.84.95.51.95.84.89.80.69
-- Vary			: YES
--
-- Value(s)		: Unknown
--				: PCM
--              : NONPCM
--              : WARN: No Input
-- Comments		:
--
---------------------------------------------------------------------------------------------------
-- Header		: AES_OUTPUT_4_TYPE
--
-- MIB ref		: swCardEventLogSlotXX       .17.65.69.83.95.79.85.84.80.85.84.95.52.95.84.89.80.69
-- absolute OID	: 1.3.6.1.4.1.7995.2.6.1.1.XX.17.65.69.83.95.79.85.84.80.85.84.95.52.95.84.89.80.69
-- Vary			: YES
--
-- Value(s)		: Unknown
--				: PCM
--              : NONPCM
--              : WARN: No Input
-- Comments		:
--
---------------------------------------------------------------------------------------------------
-- Header		: AES_OUTPUT_5_TYPE
--
-- MIB ref		: swCardEventLogSlotXX       .17.65.69.83.95.79.85.84.80.85.84.95.53.95.84.89.80.69
-- absolute OID	: 1.3.6.1.4.1.7995.2.6.1.1.XX.17.65.69.83.95.79.85.84.80.85.84.95.53.95.84.89.80.69
-- Vary			: YES
--
-- Value(s)		: Unknown
--				: PCM
--              : NONPCM
--              : WARN: No Input
-- Comments		:
--
---------------------------------------------------------------------------------------------------
-- Header		: AES_OUTPUT_6_TYPE
--
-- MIB ref		: swCardEventLogSlotXX       .17.65.69.83.95.79.85.84.80.85.84.95.54.95.84.89.80.69
-- absolute OID	: 1.3.6.1.4.1.7995.2.6.1.1.XX.17.65.69.83.95.79.85.84.80.85.84.95.54.95.84.89.80.69
-- Vary			: YES
--
-- Value(s)		: Unknown
--				: PCM
--              : NONPCM
--              : WARN: No Input
-- Comments		:
--
---------------------------------------------------------------------------------------------------
-- Header		: AES_OUTPUT_7_TYPE
--
-- MIB ref		: swCardEventLogSlotXX       .17.65.69.83.95.79.85.84.80.85.84.95.55.95.84.89.80.69
-- absolute OID	: 1.3.6.1.4.1.7995.2.6.1.1.XX.17.65.69.83.95.79.85.84.80.85.84.95.55.95.84.89.80.69
-- Vary			: YES
--
-- Value(s)		: Unknown
--				: PCM
--              : NONPCM
--              : WARN: No Input
-- Comments		:
--
---------------------------------------------------------------------------------------------------
-- Header		: AES_OUTPUT_8_TYPE
--
-- MIB ref		: swCardEventLogSlotXX       .17.65.69.83.95.79.85.84.80.85.84.95.56.95.84.89.80.69
-- absolute OID	: 1.3.6.1.4.1.7995.2.6.1.1.XX.17.65.69.83.95.79.85.84.80.85.84.95.56.95.84.89.80.69
-- Vary			: YES
--
-- Value(s)		: Unknown
--				: PCM
--              : NONPCM
--              : WARN: No Input
-- Comments		:
--
---------------------------------------------------------------------------------------------------
-- Header		: DOLBY_ENCODER_VFS
--
-- MIB ref		: swCardEventLogSlotXX       .17.68.79.76.66.89.95.69.78.67.79.68.69.82.95.86.70.83
-- absolute OID	: 1.3.6.1.4.1.7995.2.6.1.1.XX.17.68.79.76.66.89.95.69.78.67.79.68.69.82.95.86.70.83
-- Vary			: YES
--
-- Value(s)     :OK
--              :WARN:Error
--              :WARN:Invalid
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: Unknown
--              : 1035/30i
--              : 1035/29i
--              : 1080/60p
--              : 1080/59p
--              : 1080/50p
--              : 1080/30i
--              : 1080/29i
--              : 1080/25i
--              : 1080/30p
--              : 1080/29p
--              : 1080/25p
--              : 1080/24p
--              : 1080/23p
--              : 1080/50p
--              : 1080/25i
--              : 720/60p
--              : 720/59p
--              : 525/59p
--              : 525/29i
--              : 625/25i
--              : 525/29i
--              : 625/25i
--              : 1080/24sF
--              : 1080/23sF
--              : 480/60p
--              : 480/59p
--              : 625/24sF
--              : 625/23sF
--              : 1152/25i
--              : 720/50p
--              : 576/50p
--              : 480/60p
--              : 480/59p
--              : 1080/30sF
--              : 1080/29sF
--              : 1080/25sF
--              : 720/30p
--              : 720/29p
--              : 720/25p
--              : 720/24p
--              : 720/23p
--              : Invalid
-- Comments		:
--
---------------------------------------------------------------------------------------------------
-- Header		: AES_OUTPUT_1_STATE
--
-- MIB ref		: swCardEventLogSlotXX       .18.65.69.83.95.79.85.84.80.85.84.95.49.95.83.84.65.84.69
-- absolute OID	: 1.3.6.1.4.1.7995.2.6.1.1.XX.18.65.69.83.95.79.85.84.80.85.84.95.49.95.83.84.65.84.69
-- Vary			: YES
--
-- Value(s)		: WARN:Off
-- Value(s)		: LOST
--				: FAIL:Lost
--              : OK
--              : Unknown
-- Comments		:
--
---------------------------------------------------------------------------------------------------
-- Header		: AES_OUTPUT_2_STATE
--
-- MIB ref		: swCardEventLogSlotXX       .18.65.69.83.95.79.85.84.80.85.84.95.50.95.83.84.65.84.69
-- absolute OID	: 1.3.6.1.4.1.7995.2.6.1.1.XX.18.65.69.83.95.79.85.84.80.85.84.95.50.95.83.84.65.84.69
-- Vary			: YES
--
-- Value(s)		: WARN:Off
-- Value(s)		: LOST
--				: FAIL:Lost
--              : OK
--              : Unknown
-- Comments		:
--
---------------------------------------------------------------------------------------------------
-- Header		: AES_OUTPUT_3_STATE
--
-- MIB ref		: swCardEventLogSlotXX       .18.65.69.83.95.79.85.84.80.85.84.95.51.95.83.84.65.84.69
-- absolute OID	: 1.3.6.1.4.1.7995.2.6.1.1.XX.18.65.69.83.95.79.85.84.80.85.84.95.51.95.83.84.65.84.69
-- Vary			: YES
--
-- Value(s)		: WARN:Off
-- Value(s)		: LOST
--				: FAIL:Lost
--              : OK
--              : Unknown
-- Comments		:
--
---------------------------------------------------------------------------------------------------
-- Header		: AES_OUTPUT_4_STATE
--
-- MIB ref		: swCardEventLogSlotXX       .18.65.69.83.95.79.85.84.80.85.84.95.52.95.83.84.65.84.69
-- absolute OID	: 1.3.6.1.4.1.7995.2.6.1.1.XX.18.65.69.83.95.79.85.84.80.85.84.95.52.95.83.84.65.84.69
-- Vary			: YES
--
-- Value(s)		: WARN:Off
-- Value(s)		: LOST
--				: FAIL:Lost
--              : OK
--              : Unknown
-- Comments		:
--
---------------------------------------------------------------------------------------------------
-- Header		: AES_OUTPUT_5_STATE
--
-- MIB ref		: swCardEventLogSlotXX       .18.65.69.83.95.79.85.84.80.85.84.95.53.95.83.84.65.84.69
-- absolute OID	: 1.3.6.1.4.1.7995.2.6.1.1.XX.18.65.69.83.95.79.85.84.80.85.84.95.53.95.83.84.65.84.69
-- Vary			: YES
--
-- Value(s)		: WARN:Off
-- Value(s)		: LOST
--				: FAIL:Lost
--              : OK
--              : Unknown
-- Comments		:
--
---------------------------------------------------------------------------------------------------
-- Header		: AES_OUTPUT_6_STATE
--
-- MIB ref		: swCardEventLogSlotXX       .18.65.69.83.95.79.85.84.80.85.84.95.54.95.83.84.65.84.69
-- absolute OID	: 1.3.6.1.4.1.7995.2.6.1.1.XX.18.65.69.83.95.79.85.84.80.85.84.95.54.95.83.84.65.84.69
-- Vary			: YES
--
-- Value(s)		: WARN:Off
-- Value(s)		: LOST
--				: FAIL:Lost
--              : OK
--              : Unknown
-- Comments		:
--
---------------------------------------------------------------------------------------------------
-- Header		: AES_OUTPUT_7_STATE
--
-- MIB ref		: swCardEventLogSlotXX       .18.65.69.83.95.79.85.84.80.85.84.95.55.95.83.84.65.84.69
-- absolute OID	: 1.3.6.1.4.1.7995.2.6.1.1.XX.18.65.69.83.95.79.85.84.80.85.84.95.55.95.83.84.65.84.69
-- Vary			: YES
--
-- Value(s)		: WARN:Off
-- Value(s)		: LOST
--				: FAIL:Lost
--              : OK
--              : Unknown
-- Comments		:
--
---------------------------------------------------------------------------------------------------
-- Header		: AES_OUTPUT_8_STATE
--
-- MIB ref		: swCardEventLogSlotXX       .18.65.69.83.95.79.85.84.80.85.84.95.56.95.83.84.65.84.69
-- absolute OID	: 1.3.6.1.4.1.7995.2.6.1.1.XX.18.65.69.83.95.79.85.84.80.85.84.95.56.95.83.84.65.84.69
-- Vary			: YES
--
-- Value(s)		: Warn:Off
-- Value(s)		: LOST
--				: FAIL:Lost
--              : OK
--              : Unknown
-- Comments		:
--
---------------------------------------------------------------------------------------------------
-- Header		: DOLBY_ENCODER_AC_3
--
-- MIB ref		: swCardEventLogSlotXX       .18.68.79.76.66.89.95.69.78.67.79.68.69.82.95.65.67.95.51
-- absolute OID	: 1.3.6.1.4.1.7995.2.6.1.1.XX.18.68.79.76.66.89.95.69.78.67.79.68.69.82.95.65.67.95.51
-- Vary			: YES
--
-- Value(s)     :No
--              :Yes
--              :-
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
-- Vary			: YES
--
-- Value(s)		: 0
--				:
-- Comments		: Number of error seconds
--
---------------------------------------------------------------------------------------------------
-- Header		: OUTPUT_1_ANC_STATE
--
-- MIB ref		: swCardEventLogSlotXX       .18.79.85.84.80.85.84.95.49.95.65.78.67.95.83.84.65.84.69
-- absolute OID	: 1.3.6.1.4.1.7995.2.6.1.1.XX.18.79.85.84.80.85.84.95.49.95.65.78.67.95.83.84.65.84.69
-- Vary			: YES
--
-- Value(s)		: OK
--				: ANC FULL
-- Comments		:
--
---------------------------------------------------------------------------------------------------
-- Header		: DOLBY_ENCODER_EX_BSI
--
-- MIB ref		: swCardEventLogSlotXX       .20.68.79.76.66.89.95.69.78.67.79.68.69.82.95.69.88.95.66.83.73
-- absolute OID	: 1.3.6.1.4.1.7995.2.6.1.1.XX.20.68.79.76.66.89.95.69.78.67.79.68.69.82.95.69.88.95.66.83.73
-- Vary			: YES
--
-- Value(s)     : No
--              : Yes
--              : -
-- Comments		:
--
---------------------------------------------------------------------------------------------------
-- Header		: DOLBY_ENCODER_SOURCE
--
-- MIB ref		: swCardEventLogSlotXX       .20.68.79.76.66.89.95.69.78.67.79.68.69.82.95.83.79.85.82.67.69
-- absolute OID	: 1.3.6.1.4.1.7995.2.6.1.1.XX.20.68.79.76.66.89.95.69.78.67.79.68.69.82.95.83.79.85.82.67.69
-- Vary			: YES
--
-- Value(s)     : Internal
--              : External
--              : Last Valid
--              : Internal:Rev
--              : External:Rev
--              : Last Valid:Rev
--              : -
-- Comments		:
--
---------------------------------------------------------------------------------------------------
-- Header		: DOLBY_ENCODER_STATUS
--
-- MIB ref		: swCardEventLogSlotXX       .20.68.79.76.66.89.95.69.78.67.79.68.69.82.95.83.84.65.84.85.83
-- absolute OID	: 1.3.6.1.4.1.7995.2.6.1.1.XX.20.68.79.76.66.89.95.69.78.67.79.68.69.82.95.83.84.65.84.85.83
-- Vary			: YES
--
-- Value(s)     : Encoder Active
--              : Encoder Stopped
--              : Pass Mode
--              : -
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
-- Vary			: YES
--
-- Value(s)		: OK
--				: NONE
--              : WARN
--				:
-- Comments		:
--
---------------------------------------------------------------------------------------------------
-- Header		: DOLBY_ENCODER_FRAMERATE
--
-- MIB ref		: swCardEventLogSlotXX       .23.68.79.76.66.89.95.69.78.67.79.68.69.82.95.70.82.65.77.69.82.65.84.69
-- absolute OID	: 1.3.6.1.4.1.7995.2.6.1.1.XX.23.68.79.76.66.89.95.69.78.67.79.68.69.82.95.70.82.65.77.69.82.65.84.69
-- Vary			: YES
--
-- Value(s)     : Not Ind
--              : 23.98fps
--              : 24fps
--              : 25fps
--              : 29.97fps
--              : 30fps
--              : 50fps
--              : 50.94fps
--              : 60fps
--              : ??
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
-- Vary			: YES
--
-- Value(s)		: 0
--				:
-- Comments		: Number of error seconds
--
---------------------------------------------------------------------------------------------------
-- Header		: DOLBY_ENCODER_PROG_CONFIG
--
-- MIB ref		: swCardEventLogSlotXX       .25.68.79.76.66.89.95.69.78.67.79.68.69.82.95.80.82.79.71.95.67.79.78.70.73.71
-- absolute OID	: 1.3.6.1.4.1.7995.2.6.1.1.XX.25.68.79.76.66.89.95.69.78.67.79.68.69.82.95.80.82.79.71.95.67.79.78.70.73.71
-- Vary			: YES
--
-- Value(s)     : 5.1+2"
--              : 5.1+2x1"
--              : 4+4"
--              : 4+2x2"
--              : 4+2+2x1"
--              : 4+4x1"
--              : 4x2"
--              : 3x2+2x1"
--              : 2x2+4x1"
--              : 2+6x1"
--              : 8x1"
--              : 5.1"
--              : 4+2"
--              : 4+2x1"
--              : 3x2"
--              : 2x2+2x1"
--              : 2+4x1"
--              : 6x1"
--              : 4"
--              : 2+2"
--              : 2+2x1"
--              : 4x1"
--              : 7.1"
--              : 7.1 Scrn"
-- Comments		:
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: DOLBY_ENCODER_PROG_1_DESC_TEXT
--
-- MIB ref		: swCardEventLogSlotXX       .30.68.79.76.66.89.95.69.78.67.79.68.69.82.95.80.82.79.71.95.49.95.68.69.83.67.95.84.69.88.84
-- absolute OID	: 1.3.6.1.4.1.7995.2.6.1.1.XX.30.68.79.76.66.89.95.69.78.67.79.68.69.82.95.80.82.79.71.95.49.95.68.69.83.67.95.84.69.88.84
-- Vary			: YES
--
-- Value(s)		: Prog 1
--              : <32Character Program Description>
--
---------------------------------------------------------------------------------------------------
-- Header		: DOLBY_ENCODER_PROG_2_DESC_TEXT
--
-- MIB ref		: swCardEventLogSlotXX       .30.68.79.76.66.89.95.69.78.67.79.68.69.82.95.80.82.79.71.95.50.95.68.69.83.67.95.84.69.88.84
-- absolute OID	: 1.3.6.1.4.1.7995.2.6.1.1.XX.30.68.79.76.66.89.95.69.78.67.79.68.69.82.95.80.82.79.71.95.50.95.68.69.83.67.95.84.69.88.84
-- Vary			: YES
--
-- Value(s)		: Prog 2
--              : <32Character Program Description>
--
---------------------------------------------------------------------------------------------------
-- Header		: DOLBY_ENCODER_PROG_3_DESC_TEXT
--
-- MIB ref		: swCardEventLogSlotXX       .30.68.79.76.66.89.95.69.78.67.79.68.69.82.95.80.82.79.71.95.51.95.68.69.83.67.95.84.69.88.84
-- absolute OID	: 1.3.6.1.4.1.7995.2.6.1.1.XX.30.68.79.76.66.89.95.69.78.67.79.68.69.82.95.80.82.79.71.95.51.95.68.69.83.67.95.84.69.88.84
-- Vary			: YES
--
-- Value(s)		:
--              : <32Character Program Description>
--
---------------------------------------------------------------------------------------------------
-- Header		: DOLBY_ENCODER_PROG_4_DESC_TEXT
--
-- MIB ref		: swCardEventLogSlotXX       .30.68.79.76.66.89.95.69.78.67.79.68.69.82.95.80.82.79.71.95.52.95.68.69.83.67.95.84.69.88.84
-- absolute OID	: 1.3.6.1.4.1.7995.2.6.1.1.XX.30.68.79.76.66.89.95.69.78.67.79.68.69.82.95.80.82.79.71.95.52.95.68.69.83.67.95.84.69.88.84
-- Vary			: YES
--
-- Value(s)		:
--              : <32Character Program Description>
--
---------------------------------------------------------------------------------------------------
-- Header		: DOLBY_ENCODER_PROG_5_DESC_TEXT
--
-- MIB ref		: swCardEventLogSlotXX       .30.68.79.76.66.89.95.69.78.67.79.68.69.82.95.80.82.79.71.95.53.95.68.69.83.67.95.84.69.88.84
-- absolute OID	: 1.3.6.1.4.1.7995.2.6.1.1.XX.30.68.79.76.66.89.95.69.78.67.79.68.69.82.95.80.82.79.71.95.53.95.68.69.83.67.95.84.69.88.84
-- Vary			: YES
--
-- Value(s)		:
--              : <32Character Program Description>
--
---------------------------------------------------------------------------------------------------
-- Header		: DOLBY_ENCODER_PROG_6_DESC_TEXT
--
-- MIB ref		: swCardEventLogSlotXX       .30.68.79.76.66.89.95.69.78.67.79.68.69.82.95.80.82.79.71.95.54.95.68.69.83.67.95.84.69.88.84
-- absolute OID	: 1.3.6.1.4.1.7995.2.6.1.1.XX.30.68.79.76.66.89.95.69.78.67.79.68.69.82.95.80.82.79.71.95.54.95.68.69.83.67.95.84.69.88.84
-- Vary			: YES
--
-- Value(s)		:
--              : <32Character Program Description>
--
---------------------------------------------------------------------------------------------------
-- Header		: DOLBY_ENCODER_PROG_7_DESC_TEXT
--
-- MIB ref		: swCardEventLogSlotXX       .30.68.79.76.66.89.95.69.78.67.79.68.69.82.95.80.82.79.71.95.55.95.68.69.83.67.95.84.69.88.84
-- absolute OID	: 1.3.6.1.4.1.7995.2.6.1.1.XX.30.68.79.76.66.89.95.69.78.67.79.68.69.82.95.80.82.79.71.95.55.95.68.69.83.67.95.84.69.88.84
-- Vary			: YES
--
-- Value(s)		:
--              : <32Character Program Description>
--
---------------------------------------------------------------------------------------------------
-- Header		: DOLBY_ENCODER_PROG_8_DESC_TEXT
--
-- MIB ref		: swCardEventLogSlotXX       .30.68.79.76.66.89.95.69.78.67.79.68.69.82.95.80.82.79.71.95.56.95.68.69.83.67.95.84.69.88.84
-- absolute OID	: 1.3.6.1.4.1.7995.2.6.1.1.XX.30.68.79.76.66.89.95.69.78.67.79.68.69.82.95.80.82.79.71.95.56.95.68.69.83.67.95.84.69.88.84
-- Vary			: YES
--
-- Value(s)		:
--              : <32Character Program Description>
--
---------------------------------------------------------------------------------------------------
-- Header		: DOLBY_ENCODER_PROG_9_DESC_TEXT
--
-- MIB ref		: swCardEventLogSlotXX       .30.68.79.76.66.89.95.69.78.67.79.68.69.82.95.80.82.79.71.95.57.95.68.69.83.67.95.84.69.88.84
-- absolute OID	: 1.3.6.1.4.1.7995.2.6.1.1.XX.30.68.79.76.66.89.95.69.78.67.79.68.69.82.95.80.82.79.71.95.57.95.68.69.83.67.95.84.69.88.84
-- Vary			: YES
--
-- Value(s)		:
--              : <32Character Program Description>
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
-- Vary			: YES
--
-- Value(s)		: LOST
--				: FAIL:Lost
--              : OK
--              : Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
-- Vary			: YES
--
-- Value(s)		: LOST
--				: FAIL:Lost
--              : OK
--              : Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
-- Vary			: YES
--
-- Value(s)		: LOST
--				: FAIL:Lost
--              : OK
--              : Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
-- Vary			: YES
--
-- Value(s)		: LOST
--				: FAIL:Lost
--              : OK
--              : Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
-- Vary			: YES
--
-- Value(s)		: LOST
--				: FAIL:Lost
--              : OK
--              : Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
-- Vary			: YES
--
-- Value(s)		: LOST
--				: FAIL:Lost
--              : OK
--              : Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
-- Vary			: YES
--
-- Value(s)		: LOST
--				: FAIL:Lost
--              : OK
--              : Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
-- Vary			: YES
--
-- Value(s)		: LOST
--				: FAIL:Lost
--              : OK
--              : Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: WARN: No Input
--				: PCM
--              : NONPCM
--              : Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: WARN: No Input
--				: PCM
--              : NONPCM
--              : Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: WARN: No Input
--				: PCM
--              : NONPCM
--              : Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: WARN: No Input
--				: PCM
--              : NONPCM
--              : Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: WARN: No Input
--				: PCM
--              : NONPCM
--              : Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: WARN: No Input
--				: PCM
--              : NONPCM
--              : Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: WARN: No Input
--				: PCM
--              : NONPCM
--              : Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: WARN: No Input
--				: PCM
--              : NONPCM
--              : Unknown
-- Comments		:
--
---------------------------------------------------------------------------------------------------
-- Header		: DOLBY_ENCODER_PROG_10_DESC_TEXT
--
-- MIB ref		: swCardEventLogSlotXX       .31.68.79.76.66.89.95.69.78.67.79.68.69.82.95.80.82.79.71.95.49.48.95.68.69.83.67.95.84.69.88.84
-- absolute OID	: 1.3.6.1.4.1.7995.2.6.1.1.XX.31.68.79.76.66.89.95.69.78.67.79.68.69.82.95.80.82.79.71.95.49.48.95.68.69.83.67.95.84.69.88.84
-- Vary			: YES
--
-- Value(s)		:
--              : <32Character Program Description>
--
---------------------------------------------------------------------------------------------------
-- Header		: DOLBY_ENCODER_PROG_11_DESC_TEXT
--
-- MIB ref		: swCardEventLogSlotXX       .31.68.79.76.66.89.95.69.78.67.79.68.69.82.95.80.82.79.71.95.49.49.95.68.69.83.67.95.84.69.88.84
-- absolute OID	: 1.3.6.1.4.1.7995.2.6.1.1.XX.31.68.79.76.66.89.95.69.78.67.79.68.69.82.95.80.82.79.71.95.49.49.95.68.69.83.67.95.84.69.88.84
-- Vary			: YES
--
-- Value(s)		:
--              : <32Character Program Description>
--
---------------------------------------------------------------------------------------------------
-- Header		: DOLBY_ENCODER_PROG_12_DESC_TEXT
--
-- MIB ref		: swCardEventLogSlotXX       .31.68.79.76.66.89.95.69.78.67.79.68.69.82.95.80.82.79.71.95.49.50.95.68.69.83.67.95.84.69.88.84
-- absolute OID	: 1.3.6.1.4.1.7995.2.6.1.1.XX.31.68.79.76.66.89.95.69.78.67.79.68.69.82.95.80.82.79.71.95.49.50.95.68.69.83.67.95.84.69.88.84
-- Vary			: YES
--
-- Value(s)		:
--              : <32Character Program Description>
--
---------------------------------------------------------------------------------------------------
-- Header		: DOLBY_ENCODER_PROG_13_DESC_TEXT
--
-- MIB ref		: swCardEventLogSlotXX       .31.68.79.76.66.89.95.69.78.67.79.68.69.82.95.80.82.79.71.95.49.51.95.68.69.83.67.95.84.69.88.84
-- absolute OID	: 1.3.6.1.4.1.7995.2.6.1.1.XX.31.68.79.76.66.89.95.69.78.67.79.68.69.82.95.80.82.79.71.95.49.51.95.68.69.83.67.95.84.69.88.84
-- Vary			: YES
--
-- Value(s)		:
--              : <32Character Program Description>
--
---------------------------------------------------------------------------------------------------
-- Header		: DOLBY_ENCODER_PROG_14_DESC_TEXT
--
-- MIB ref		: swCardEventLogSlotXX       .31.68.79.76.66.89.95.69.78.67.79.68.69.82.95.80.82.79.71.95.49.52.95.68.69.83.67.95.84.69.88.84
-- absolute OID	: 1.3.6.1.4.1.7995.2.6.1.1.XX.31.68.79.76.66.89.95.69.78.67.79.68.69.82.95.80.82.79.71.95.49.52.95.68.69.83.67.95.84.69.88.84
-- Vary			: YES
--
-- Value(s)		:
--              : <32Character Program Description>
--
---------------------------------------------------------------------------------------------------
-- Header		: DOLBY_ENCODER_PROG_15_DESC_TEXT
--
-- MIB ref		: swCardEventLogSlotXX       .31.68.79.76.66.89.95.69.78.67.79.68.69.82.95.80.82.79.71.95.49.53.95.68.69.83.67.95.84.69.88.84
-- absolute OID	: 1.3.6.1.4.1.7995.2.6.1.1.XX.31.68.79.76.66.89.95.69.78.67.79.68.69.82.95.80.82.79.71.95.49.53.95.68.69.83.67.95.84.69.88.84
-- Vary			: YES
--
-- Value(s)		:
--              : <32Character Program Description>
--
---------------------------------------------------------------------------------------------------
-- Header		: DOLBY_ENCODER_PROG_16_DESC_TEXT
--
-- MIB ref		: swCardEventLogSlotXX       .31.68.79.76.66.89.95.69.78.67.79.68.69.82.95.80.82.79.71.95.49.54.95.68.69.83.67.95.84.69.88.84
-- absolute OID	: 1.3.6.1.4.1.7995.2.6.1.1.XX.31.68.79.76.66.89.95.69.78.67.79.68.69.82.95.80.82.79.71.95.49.54.95.68.69.83.67.95.84.69.88.84
-- Vary			: YES
--
-- Value(s)		:
--              : <32Character Program Description>
--
---------------------------------------------------------------------------------------------------
-- Header		: DOLBY_ENCODER_PROG_17_DESC_TEXT
--
-- MIB ref		: swCardEventLogSlotXX       .31.68.79.76.66.89.95.69.78.67.79.68.69.82.95.80.82.79.71.95.49.55.95.68.69.83.67.95.84.69.88.84
-- absolute OID	: 1.3.6.1.4.1.7995.2.6.1.1.XX.31.68.79.76.66.89.95.69.78.67.79.68.69.82.95.80.82.79.71.95.49.55.95.68.69.83.67.95.84.69.88.84
-- Vary			: YES
--
-- Value(s)		:
--              : <32Character Program Description>
--
---------------------------------------------------------------------------------------------------
-- Header		: DOLBY_ENCODER_PROG_18_DESC_TEXT
--
-- MIB ref		: swCardEventLogSlotXX       .31.68.79.76.66.89.95.69.78.67.79.68.69.82.95.80.82.79.71.95.49.56.95.68.69.83.67.95.84.69.88.84
-- absolute OID	: 1.3.6.1.4.1.7995.2.6.1.1.XX.31.68.79.76.66.89.95.69.78.67.79.68.69.82.95.80.82.79.71.95.49.56.95.68.69.83.67.95.84.69.88.84
-- Vary			: YES
--
-- Value(s)		:
--              : <32Character Program Description>
--
---------------------------------------------------------------------------------------------------
-- Header		: DOLBY_ENCODER_PROG_19_DESC_TEXT
--
-- MIB ref		: swCardEventLogSlotXX       .31.68.79.76.66.89.95.69.78.67.79.68.69.82.95.80.82.79.71.95.49.57.95.68.69.83.67.95.84.69.88.84
-- absolute OID	: 1.3.6.1.4.1.7995.2.6.1.1.XX.31.68.79.76.66.89.95.69.78.67.79.68.69.82.95.80.82.79.71.95.49.57.95.68.69.83.67.95.84.69.88.84
-- Vary			: YES
--
-- Value(s)		:
--              : <32Character Program Description>
--
---------------------------------------------------------------------------------------------------
-- Header		: DOLBY_ENCODER_PROG_20_DESC_TEXT
--
-- MIB ref		: swCardEventLogSlotXX       .31.68.79.76.66.89.95.69.78.67.79.68.69.82.95.80.82.79.71.95.50.48.95.68.69.83.67.95.84.69.88.84
-- absolute OID	: 1.3.6.1.4.1.7995.2.6.1.1.XX.31.68.79.76.66.89.95.69.78.67.79.68.69.82.95.80.82.79.71.95.50.48.95.68.69.83.67.95.84.69.88.84
-- Vary			: YES
--
-- Value(s)		:
--              : <32Character Program Description>
--
---------------------------------------------------------------------------------------------------
-- Header		: DOLBY_ENCODER_PROG_21_DESC_TEXT
--
-- MIB ref		: swCardEventLogSlotXX       .31.68.79.76.66.89.95.69.78.67.79.68.69.82.95.80.82.79.71.95.50.49.95.68.69.83.67.95.84.69.88.84
-- absolute OID	: 1.3.6.1.4.1.7995.2.6.1.1.XX.31.68.79.76.66.89.95.69.78.67.79.68.69.82.95.80.82.79.71.95.50.49.95.68.69.83.67.95.84.69.88.84
-- Vary			: YES
--
-- Value(s)		:
--              : <32Character Program Description>
--
---------------------------------------------------------------------------------------------------
-- Header		: DOLBY_ENCODER_PROG_22_DESC_TEXT
--
-- MIB ref		: swCardEventLogSlotXX       .31.68.79.76.66.89.95.69.78.67.79.68.69.82.95.80.82.79.71.95.50.50.95.68.69.83.67.95.84.69.88.84
-- absolute OID	: 1.3.6.1.4.1.7995.2.6.1.1.XX.31.68.79.76.66.89.95.69.78.67.79.68.69.82.95.80.82.79.71.95.50.50.95.68.69.83.67.95.84.69.88.84
-- Vary			: YES
--
-- Value(s)		:
--              : <32Character Program Description>
--
---------------------------------------------------------------------------------------------------
-- Header		: DOLBY_ENCODER_PROG_23_DESC_TEXT
--
-- MIB ref		: swCardEventLogSlotXX       .31.68.79.76.66.89.95.69.78.67.79.68.69.82.95.80.82.79.71.95.50.51.95.68.69.83.67.95.84.69.88.84
-- absolute OID	: 1.3.6.1.4.1.7995.2.6.1.1.XX.31.68.79.76.66.89.95.69.78.67.79.68.69.82.95.80.82.79.71.95.50.51.95.68.69.83.67.95.84.69.88.84
-- Vary			: YES
--
-- Value(s)		:
--              : <32Character Program Description>
--
---------------------------------------------------------------------------------------------------
-- Header		: DOLBY_ENCODER_PROG_24_DESC_TEXT
--
-- MIB ref		: swCardEventLogSlotXX       .31.68.79.76.66.89.95.69.78.67.79.68.69.82.95.80.82.79.71.95.50.52.95.68.69.83.67.95.84.69.88.84
-- absolute OID	: 1.3.6.1.4.1.7995.2.6.1.1.XX.31.68.79.76.66.89.95.69.78.67.79.68.69.82.95.80.82.79.71.95.50.52.95.68.69.83.67.95.84.69.88.84
-- Vary			: YES
--
-- Value(s)		:
--              : <32Character Program Description>
--
---------------------------------------------------------------------------------------------------
-- Header		: DOLBY_ENCODER_PROG_25_DESC_TEXT
--
-- MIB ref		: swCardEventLogSlotXX       .31.68.79.76.66.89.95.69.78.67.79.68.69.82.95.80.82.79.71.95.50.53.95.68.69.83.67.95.84.69.88.84
-- absolute OID	: 1.3.6.1.4.1.7995.2.6.1.1.XX.31.68.79.76.66.89.95.69.78.67.79.68.69.82.95.80.82.79.71.95.50.53.95.68.69.83.67.95.84.69.88.84
-- Vary			: YES
--
-- Value(s)		:
--              : <32Character Program Description>
--
---------------------------------------------------------------------------------------------------
-- Header		: DOLBY_ENCODER_PROG_26_DESC_TEXT
--
-- MIB ref		: swCardEventLogSlotXX       .31.68.79.76.66.89.95.69.78.67.79.68.69.82.95.80.82.79.71.95.50.54.95.68.69.83.67.95.84.69.88.84
-- absolute OID	: 1.3.6.1.4.1.7995.2.6.1.1.XX.31.68.79.76.66.89.95.69.78.67.79.68.69.82.95.80.82.79.71.95.50.54.95.68.69.83.67.95.84.69.88.84
-- Vary			: YES
--
-- Value(s)		:
--              : <32Character Program Description>
--
---------------------------------------------------------------------------------------------------
-- Header		: DOLBY_ENCODER_PROG_27_DESC_TEXT
--
-- MIB ref		: swCardEventLogSlotXX       .31.68.79.76.66.89.95.69.78.67.79.68.69.82.95.80.82.79.71.95.50.55.95.68.69.83.67.95.84.69.88.84
-- absolute OID	: 1.3.6.1.4.1.7995.2.6.1.1.XX.31.68.79.76.66.89.95.69.78.67.79.68.69.82.95.80.82.79.71.95.50.55.95.68.69.83.67.95.84.69.88.84
-- Vary			: YES
--
-- Value(s)		:
--              : <32Character Program Description>
--
---------------------------------------------------------------------------------------------------
-- Header		: DOLBY_ENCODER_PROG_28_DESC_TEXT
--
-- MIB ref		: swCardEventLogSlotXX       .31.68.79.76.66.89.95.69.78.67.79.68.69.82.95.80.82.79.71.95.50.56.95.68.69.83.67.95.84.69.88.84
-- absolute OID	: 1.3.6.1.4.1.7995.2.6.1.1.XX.31.68.79.76.66.89.95.69.78.67.79.68.69.82.95.80.82.79.71.95.50.56.95.68.69.83.67.95.84.69.88.84
-- Vary			: YES
--
-- Value(s)		:
--              : <32Character Program Description>
--
---------------------------------------------------------------------------------------------------
-- Header		: DOLBY_ENCODER_PROG_29_DESC_TEXT
--
-- MIB ref		: swCardEventLogSlotXX       .31.68.79.76.66.89.95.69.78.67.79.68.69.82.95.80.82.79.71.95.50.57.95.68.69.83.67.95.84.69.88.84
-- absolute OID	: 1.3.6.1.4.1.7995.2.6.1.1.XX.31.68.79.76.66.89.95.69.78.67.79.68.69.82.95.80.82.79.71.95.50.57.95.68.69.83.67.95.84.69.88.84
-- Vary			: YES
--
-- Value(s)		:
--              : <32Character Program Description>
--
---------------------------------------------------------------------------------------------------
-- Header		: DOLBY_ENCODER_PROG_30_DESC_TEXT
--
-- MIB ref		: swCardEventLogSlotXX       .31.68.79.76.66.89.95.69.78.67.79.68.69.82.95.80.82.79.71.95.51.48.95.68.69.83.67.95.84.69.88.84
-- absolute OID	: 1.3.6.1.4.1.7995.2.6.1.1.XX.31.68.79.76.66.89.95.69.78.67.79.68.69.82.95.80.82.79.71.95.51.48.95.68.69.83.67.95.84.69.88.84
-- Vary			: YES
--
-- Value(s)		:
--              : <32Character Program Description>
--
---------------------------------------------------------------------------------------------------
-- Header		: DOLBY_ENCODER_PROG_31_DESC_TEXT
--
-- MIB ref		: swCardEventLogSlotXX       .31.68.79.76.66.89.95.69.78.67.79.68.69.82.95.80.82.79.71.95.51.49.95.68.69.83.67.95.84.69.88.84
-- absolute OID	: 1.3.6.1.4.1.7995.2.6.1.1.XX.31.68.79.76.66.89.95.69.78.67.79.68.69.82.95.80.82.79.71.95.51.49.95.68.69.83.67.95.84.69.88.84
-- Vary			: YES
--
-- Value(s)		:
--              : <32Character Program Description>
--
---------------------------------------------------------------------------------------------------
-- Header		: DOLBY_ENCODER_PROG_32_DESC_TEXT
--
-- MIB ref		: swCardEventLogSlotXX       .31.68.79.76.66.89.95.69.78.67.79.68.69.82.95.80.82.79.71.95.51.50.95.68.69.83.67.95.84.69.88.84
-- absolute OID	: 1.3.6.1.4.1.7995.2.6.1.1.XX.31.68.79.76.66.89.95.69.78.67.79.68.69.82.95.80.82.79.71.95.51.50.95.68.69.83.67.95.84.69.88.84
-- Vary			: YES
--
-- Value(s)		:
--              : <32Character Program Description>
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_2_DOLBY
--
-- MIB ref		: swCardEventLogSlotXX       .31.79.85.84.80.85.84.95.49.95.69.77.66.69.68.68.69.68.95.65.85.68.73.79.95.50.95.68.79.76.66.89
-- absolute OID	: 1.3.6.1.4.1.7995.2.6.1.1.XX.31.79.85.84.80.85.84.95.49.95.69.77.66.69.68.68.69.68.95.65.85.68.73.79.95.50.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_3_DOLBY
--
-- MIB ref		: swCardEventLogSlotXX       .31.79.85.84.80.85.84.95.49.95.69.77.66.69.68.68.69.68.95.65.85.68.73.79.95.51.95.68.79.76.66.89
-- absolute OID	: 1.3.6.1.4.1.7995.2.6.1.1.XX.31.79.85.84.80.85.84.95.49.95.69.77.66.69.68.68.69.68.95.65.85.68.73.79.95.51.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_4_DOLBY
--
-- MIB ref		: swCardEventLogSlotXX       .31.79.85.84.80.85.84.95.49.95.69.77.66.69.68.68.69.68.95.65.85.68.73.79.95.52.95.68.79.76.66.89
-- absolute OID	: 1.3.6.1.4.1.7995.2.6.1.1.XX.31.79.85.84.80.85.84.95.49.95.69.77.66.69.68.68.69.68.95.65.85.68.73.79.95.52.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_5_DOLBY
--
-- MIB ref		: swCardEventLogSlotXX       .31.79.85.84.80.85.84.95.49.95.69.77.66.69.68.68.69.68.95.65.85.68.73.79.95.53.95.68.79.76.66.89
-- absolute OID	: 1.3.6.1.4.1.7995.2.6.1.1.XX.31.79.85.84.80.85.84.95.49.95.69.77.66.69.68.68.69.68.95.65.85.68.73.79.95.53.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_6_DOLBY
--
-- MIB ref		: swCardEventLogSlotXX       .31.79.85.84.80.85.84.95.49.95.69.77.66.69.68.68.69.68.95.65.85.68.73.79.95.54.95.68.79.76.66.89
-- absolute OID	: 1.3.6.1.4.1.7995.2.6.1.1.XX.31.79.85.84.80.85.84.95.49.95.69.77.66.69.68.68.69.68.95.65.85.68.73.79.95.54.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_7_DOLBY
--
-- MIB ref		: swCardEventLogSlotXX       .31.79.85.84.80.85.84.95.49.95.69.77.66.69.68.68.69.68.95.65.85.68.73.79.95.55.95.68.79.76.66.89
-- absolute OID	: 1.3.6.1.4.1.7995.2.6.1.1.XX.31.79.85.84.80.85.84.95.49.95.69.77.66.69.68.68.69.68.95.65.85.68.73.79.95.55.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_8_DOLBY
--
-- MIB ref		: swCardEventLogSlotXX       .31.79.85.84.80.85.84.95.49.95.69.77.66.69.68.68.69.68.95.65.85.68.73.79.95.56.95.68.79.76.66.89
-- absolute OID	: 1.3.6.1.4.1.7995.2.6.1.1.XX.31.79.85.84.80.85.84.95.49.95.69.77.66.69.68.68.69.68.95.65.85.68.73.79.95.56.95.68.79.76.66.89
-- Vary			: YES
--
-- Value(s)		: NONE
--				: OK
--				: WARN:EARLY
--				: WARN:LATE
--				: ERROR:EARLY
--				: ERROR:LATE
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: WARN:No Input
--      		: LOST
--				: FAIL:Lost
--              : OK
--              : Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
-- Vary			: YES
--
-- Value(s)		: OK
--				: WARN:Silent
--              : WARN:Quiet
--              : WARN:Loud
--              : WARN:Overflow
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
-- Vary			: YES
--
-- Value(s)		: OK
--				: WARN:Silent
--              : WARN:Quiet
--              : WARN:Loud
--              : WARN:Overflow
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
-- Vary			: YES
--
-- Value(s)		: OK
--				: WARN:Silent
--              : WARN:Quiet
--              : WARN:Loud
--              : WARN:Overflow
-- Comments		:
--
---------------------------------------------------------------------------------------------------
