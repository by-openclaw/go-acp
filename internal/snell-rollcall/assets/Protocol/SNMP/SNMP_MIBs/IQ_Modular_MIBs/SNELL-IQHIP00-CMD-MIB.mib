-- ************************************************************************************
-- Snell&Wilcox Card:IQHIP00
--        Module Id#:484
--       Command Set:9
--          Filename:SNELL-IQHIP00-CMD-MIB.mib
--            Author:Jonathan Riches
--              Date:15/09/2008
--              Time:12:30
--
-- Copyright (c) 2008 Snell & Wilcox Ltd
-- All rights reserved.
--
-- ************************************************************************************

SNELL-IQHIP00-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQHIP00,
    moduleIQHIP00MIB
        FROM SNELL-WILCOX-PRODUCT-REG;

 moduleIQHIP00CmdMi MODULE-IDENTITY
    LAST-UPDATED "0809151130Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQHIP00MIB 1 }




--********************************************************************************
--*
--*  Snell Wilcox Card:
--*  command set:
--*  list commands/menus:
--*
--******************************************************************************
	iqhip00CmdTable OBJECT-TYPE
		SYNTAX			SEQUENCE OF Iqhip00CmdEntry
		MAX-ACCESS		not-accessible
		STATUS			current
		DESCRIPTION
				"Note the instance of this table is relected in the command set Version"
		::= { moduleIQHIP00 1 }

	iqhip00CmdEntry OBJECT-TYPE
		SYNTAX		Iqhip00CmdEntry
		MAX-ACCESS		not-accessible
		STATUS			current
		DESCRIPTION
				"Entry in command table."
		INDEX	{ iqhip00SlotIndex }
		::= { iqhip00CmdTable 1 }

	Iqhip00CmdEntry ::=
		SEQUENCE {
			iqhip00SlotIndex
				Unsigned32,
			iqhip00HyperionBlackishBlackBlackishLevel
				RollCallString,
			iqhip00HyperionBlackishBlackMinLevelThres
				INTEGER,
			iqhip00TemporalControlBlackishEnableAlarm
				INTEGER,
			iqhip00TemporalControlBlackishAlarm
				RollCallString,
			iqhip00TemporalControlBlackishFailCount
				INTEGER,
			iqhip00TemporalControlBlackishWarningCount
				INTEGER,
			iqhip00TemporalControlBlackishFailHoldCount
				INTEGER,
			iqhip00TemporalControlBlackishResetAlarm
				INTEGER,
			iqhip00TemporalControlBlackEnableAlarm
				INTEGER,
			iqhip00TemporalControlBlackAlarm
				RollCallString,
			iqhip00TemporalControlBlackFailCount
				INTEGER,
			iqhip00TemporalControlBlackWarningCount
				INTEGER,
			iqhip00TemporalControlBlackFailHoldCount
				INTEGER,
			iqhip00TemporalControlBlackResetAlarm
				INTEGER,
			iqhip00VideoMonitorAveragePictureLvlDisplayTimeout
				RollCallString,
			iqhip00VideoMonitorAveragePictureLvlHyperionDisplayEn
				INTEGER,
			iqhip00HyperionFreezeStillishStillishLevel
				RollCallString,
			iqhip00HyperionFreezeStillishMaxLevelThres
				INTEGER,
			iqhip00TemporalControlStillishEnableAlarm
				INTEGER,
			iqhip00TemporalControlStillishAlarm
				RollCallString,
			iqhip00TemporalControlStillishFailCount
				INTEGER,
			iqhip00TemporalControlStillishWarningCount
				INTEGER,
			iqhip00TemporalControlStillishFailHoldCount
				INTEGER,
			iqhip00TemporalControlStillishResetAlarm
				INTEGER,
			iqhip00TemporalControlFreezeEnableAlarm
				INTEGER,
		    iqhip00TemporalControlFreezeTolerance
		        INTEGER,
			iqhip00TemporalControlFreezeAlarm
				RollCallString,
			iqhip00TemporalControlFreezeFailCount
				INTEGER,
			iqhip00TemporalControlFreezeWarningCount
				INTEGER,
			iqhip00TemporalControlFreezeFailHoldCount
				INTEGER,
			iqhip00TemporalControlFreezeResetAlarm
				INTEGER,
			iqhip00VideoMonitorAveragePictureLvlEnableAlarm
				INTEGER,
			iqhip00VideoMonitorAveragePictureLvl
				RollCallString,
			iqhip00VideoMonitorAveragePictureLvlMaxLoggingThres
				INTEGER,
			iqhip00VideoMonitorAveragePictureLvlMinLoggingThres
				INTEGER,
			iqhip00LumaVideoLevelOverloadStatus
				RollCallString,
			iqhip00LumaVideoLevelOverloadMaximumReading
				RollCallString,
			iqhip00LumaVideoLevelOverloadEnableAlarm
				INTEGER,
			iqhip00LumaVideoLevelOverloadOverloadThreshold
				INTEGER,
			iqhip00LumaVideoLevelOverloadAvePicAboveThres
				INTEGER,
			iqhip00LumaVideoLevelUnderloadStatus
				RollCallString,
			iqhip00LumaVideoLevelUnderloadMinimumReading
				RollCallString,
			iqhip00LumaVideoLevelUnderloadEnableAlarm
				INTEGER,
			iqhip00LumaVideoLevelUnderloadUnderloadThreshold
				INTEGER,
			iqhip00LumaVideoLevelUnderloadAvePicBelowThres
				INTEGER,
			iqhip00ChromaVideoLevelOverloadStatus
				RollCallString,
			iqhip00ChromaVideoLevelOverloadMaximumReading
				RollCallString,
			iqhip00ChromaVideoLevelOverloadEnableAlarm
				INTEGER,
			iqhip00ChromaVideoLevelOverloadOverloadThreshold
				INTEGER,
			iqhip00ChromaVideoLevelOverloadAvePicAboveThres
				INTEGER,
			iqhip00ChromaVideoLevelUnderloadStatus
				RollCallString,
			iqhip00ChromaVideoLevelUnderloadMinimumReading
				RollCallString,
			iqhip00ChromaVideoLevelUnderloadEnableAlarm
				INTEGER,
			iqhip00ChromaVideoLevelUnderloadUnderloadThreshold
				INTEGER,
			iqhip00ChromaVideoLevelUnderloadAvePicBelowThres
				INTEGER,
			iqhip00HyperionVideoMonitorChromaBitDepth
				RollCallString,
			iqhip00HyperionVideoMonitorLumaBitDepth
				RollCallString,
			iqhip00ClosedCaptionsCCCEA608BState
				RollCallString,
			iqhip00ClosedCaptionsCCCEA608BTitle1
				RollCallString,
			iqhip00ClosedCaptionsCCCEA608BTitle2
				RollCallString,
			iqhip00ClosedCaptionsCCCEA708BField1
				RollCallString,
			iqhip00ClosedCaptionsCCCEA708BField2
				RollCallString,
			iqhip00ClosedCaptionsTemporalControlEnableAlarm
				INTEGER,
			iqhip00ClosedCaptionsTemporalControlAlarm
				RollCallString,
			iqhip00ClosedCaptionsTemporalControlFailCount
				INTEGER,
			iqhip00ClosedCaptionsTemporalControlWarningCount
				INTEGER,
			iqhip00ClosedCaptionsTemporalControlFailHoldCount
				INTEGER,
			iqhip00ClosedCaptionsTemporalControlResetAlarm
				INTEGER,
			iqhip00AncillaryDataContentAdvisoryEnableAlarm
				INTEGER,
			iqhip00AncillaryDataContentAdvisorySystem
				RollCallString,
			iqhip00AncillaryDataContentAdvisoryRating
				RollCallString,
			iqhip00TimeCodeAncTimeCodeEnableAlarm
				INTEGER,
			iqhip00TimeCodeAncTimeCodeField1
				RollCallString,
			iqhip00TimeCodeAncTimeCodeField2
				RollCallString,
			iqhip00TimeCodeVITCEnableAlarm
				INTEGER,
			iqhip00TimeCodeVITCField1
				RollCallString,
			iqhip00TimeCodeVITCField2
				RollCallString,
			iqhip00AncillaryDataTimeCodeCurrentTimeCode
				RollCallString,
			iqhip00AncillaryDataTimeCodeSDTimeCodeSel
				INTEGER,
			iqhip00AncillaryDataUserAncDet1EnableAlarm
				INTEGER,
			iqhip00AncillaryDataUserAncDet1DIDType
				INTEGER,
			iqhip00AncillaryDataUserAncDet1DIDselect
				INTEGER,
			iqhip00AncillaryDataUserAncDet1SDIDselect
				INTEGER,
			iqhip00AncillaryDataUserAncDet1Field1
				RollCallString,
			iqhip00AncillaryDataUserAncDet1Field2
				RollCallString,
			iqhip00AncillaryDataUserAncDet1Name
				RollCallString,
			iqhip00AncillaryDataUserAncDet2EnableAlarm
				INTEGER,
			iqhip00AncillaryDataUserAncDet2DIDType
				INTEGER,
			iqhip00AncillaryDataUserAncDet2DIDselect
				INTEGER,
			iqhip00AncillaryDataUserAncDet2SDIDselect
				INTEGER,
			iqhip00AncillaryDataUserAncDet2Field1
				RollCallString,
			iqhip00AncillaryDataUserAncDet2Field2
				RollCallString,
			iqhip00AncillaryDataUserAncDet2Name
				RollCallString,
			iqhip00AncillaryDataWSSVIInputWSSPresence
				RollCallString,
			iqhip00AncillaryDataWSSVIInputWSSEnableAlarm
				INTEGER,
			iqhip00AncillaryDataWSSVIInputWSSData
				RollCallString,
			iqhip00AncillaryDataWSSVIInputWSSScanSys
				RollCallString,
			iqhip00AncillaryDataWSSVIInputWSSType
				INTEGER,
			iqhip00AncillaryDataWSSVIInputVIPresence
				RollCallString,
			iqhip00AncillaryDataWSSVIInputVIEnableAlarm
				INTEGER,
			iqhip00AncillaryDataWSSVIInputVIType
				INTEGER,
			iqhip00AncillaryDataWSSVIInputVIData
				RollCallString,
			iqhip00AncillaryDataWSSVIInputVIScanSys
				RollCallString,
			iqhip00HyperionAudioDataActiveAudioCh
				RollCallString,
			iqhip00AudioDataGroup1EnableAlarmCh1
				INTEGER,
			iqhip00AudioDataGroup1TypeCh1
				RollCallString,
			iqhip00AudioDataGroup1BitdepthCh1
				RollCallString,
			iqhip00AudioDataGroup1EnableAlarmCh2
				INTEGER,
			iqhip00AudioDataGroup1TypeCh2
				RollCallString,
			iqhip00AudioDataGroup1BitdepthCh2
				RollCallString,
			iqhip00AudioDataGroup1EnableAlarmCh3
				INTEGER,
			iqhip00AudioDataGroup1TypeCh3
				RollCallString,
			iqhip00AudioDataGroup1BitdepthCh3
				RollCallString,
			iqhip00AudioDataGroup1EnableAlarmCh4
				INTEGER,
			iqhip00AudioDataGroup1TypeCh4
				RollCallString,
			iqhip00AudioDataGroup1BitdepthCh4
				RollCallString,
			iqhip00AudioDataGroup2EnableAlarmCh5
				INTEGER,
			iqhip00AudioDataGroup2TypeCh5
				RollCallString,
			iqhip00AudioDataGroup2BitdepthCh5
				RollCallString,
			iqhip00AudioDataGroup2EnableAlarmCh6
				INTEGER,
			iqhip00AudioDataGroup2TypeCh6
				RollCallString,
			iqhip00AudioDataGroup2BitdepthCh6
				RollCallString,
			iqhip00AudioDataGroup2EnableAlarmCh7
				INTEGER,
			iqhip00AudioDataGroup2TypeCh7
				RollCallString,
			iqhip00AudioDataGroup2BitdepthCh7
				RollCallString,
			iqhip00AudioDataGroup2EnableAlarmCh8
				INTEGER,
			iqhip00AudioDataGroup2TypeCh8
				RollCallString,
			iqhip00AudioDataGroup2BitdepthCh8
				RollCallString,
			iqhip00AudioDataGroup3EnableAlarmCh9
				INTEGER,
			iqhip00AudioDataGroup3TypeCh9
				RollCallString,
			iqhip00AudioDataGroup3BitdepthCh9
				RollCallString,
			iqhip00AudioDataGroup3EnableAlarmCh10
				INTEGER,
			iqhip00AudioDataGroup3TypeCh10
				RollCallString,
			iqhip00AudioDataGroup3BitdepthCh10
				RollCallString,
			iqhip00AudioDataGroup3EnableAlarmCh11
				INTEGER,
			iqhip00AudioDataGroup3TypeCh11
				RollCallString,
			iqhip00AudioDataGroup3BitdepthCh11
				RollCallString,
			iqhip00AudioDataGroup3EnableAlarmCh12
				INTEGER,
			iqhip00AudioDataGroup3TypeCh12
				RollCallString,
			iqhip00AudioDataGroup3BitdepthCh12
				RollCallString,
			iqhip00AudioDataGroup4EnableAlarmCh13
				INTEGER,
			iqhip00AudioDataGroup4TypeCh13
				RollCallString,
			iqhip00AudioDataGroup4BitdepthCh13
				RollCallString,
			iqhip00AudioDataGroup4EnableAlarmCh14
				INTEGER,
			iqhip00AudioDataGroup4TypeCh14
				RollCallString,
			iqhip00AudioDataGroup4BitdepthCh14
				RollCallString,
			iqhip00AudioDataGroup4EnableAlarmCh15
				INTEGER,
			iqhip00AudioDataGroup4TypeCh15
				RollCallString,
			iqhip00AudioDataGroup4BitdepthCh15
				RollCallString,
			iqhip00AudioDataGroup4EnableAlarmCh16
				INTEGER,
			iqhip00AudioDataGroup4TypeCh16
				RollCallString,
			iqhip00AudioDataGroup4BitdepthCh16
				RollCallString,
			iqhip00AudioDataDolbyEStatusEnableAlarmPair1
				INTEGER,
			iqhip00AudioDataDolbyEStatusStatusPair1
				RollCallString,
			iqhip00AudioDataDolbyEStatusEnableAlarmPair2
				INTEGER,
			iqhip00AudioDataDolbyEStatusStatusPair2
				RollCallString,
			iqhip00AudioDataDolbyEStatusEnableAlarmPair3
				INTEGER,
			iqhip00AudioDataDolbyEStatusStatusPair3
				RollCallString,
			iqhip00AudioDataDolbyEStatusEnableAlarmPair4
				INTEGER,
			iqhip00AudioDataDolbyEStatusStatusPair4
				RollCallString,
			iqhip00AudioDataDolbyEStatusEnableAlarmPair5
				INTEGER,
			iqhip00AudioDataDolbyEStatusStatusPair5
				RollCallString,
			iqhip00AudioDataDolbyEStatusEnableAlarmPair6
				INTEGER,
			iqhip00AudioDataDolbyEStatusStatusPair6
				RollCallString,
			iqhip00AudioDataDolbyEStatusEnableAlarmPair7
				INTEGER,
			iqhip00AudioDataDolbyEStatusStatusPair7
				RollCallString,
			iqhip00AudioDataDolbyEStatusEnableAlarmPair8
				INTEGER,
			iqhip00AudioDataDolbyEStatusStatusPair8
				RollCallString,
			iqhip00AudioLevelDetDuplicateSettingsChannelIndex
				INTEGER,
			iqhip00HyperionAudioLevelDetAverageAudioLevel
				RollCallString,
			iqhip00AudioLevelDetOverloadDetectorEnableAlarm
				INTEGER,
			iqhip00AudioLevelDetOverloadDetectorAlarm
				RollCallString,
			iqhip00AudioLevelDetOverloadDetectorLeveldB
				INTEGER,
			iqhip00AudioLevelDetOverloadDetectorWarningsecs
				INTEGER,
			iqhip00AudioLevelDetOverloadDetectorFailsecs
				INTEGER,
			iqhip00AudioLevelDetOverloadDetectorFailHoldsecs
				INTEGER,
			iqhip00AudioLevelDetOverloadDetectorAlarmReset
				INTEGER,
			iqhip00AudioLevelDetLoudDetectorEnableAlarm
				INTEGER,
			iqhip00AudioLevelDetLoudDetectorAlarm
				RollCallString,
			iqhip00AudioLevelDetLoudDetectorLeveldB
				INTEGER,
			iqhip00AudioLevelDetLoudDetectorWarningsecs
				INTEGER,
			iqhip00AudioLevelDetLoudDetectorFailsecs
				INTEGER,
			iqhip00AudioLevelDetLoudDetectorFailHoldsecs
				INTEGER,
			iqhip00AudioLevelDetQuietDetectorEnableAlarm
				INTEGER,
			iqhip00AudioLevelDetQuietDetectorAlarm
				RollCallString,
			iqhip00AudioLevelDetQuietDetectorLeveldB
				INTEGER,
			iqhip00AudioLevelDetQuietDetectorWarningsecs
				INTEGER,
			iqhip00AudioLevelDetQuietDetectorFailsecs
				INTEGER,
			iqhip00AudioLevelDetQuietDetectorFailHoldsecs
				INTEGER,
			iqhip00AudioLevelDetSilenceDetectorEnableAlarm
				INTEGER,
			iqhip00AudioLevelDetSilenceDetectorAlarm
				RollCallString,
			iqhip00AudioLevelDetSilenceDetectorLeveldB
				INTEGER,
			iqhip00AudioLevelDetSilenceDetectorWarningsecs
				INTEGER,
			iqhip00AudioLevelDetSilenceDetectorFailsecs
				INTEGER,
			iqhip00AudioLevelDetSilenceDetectorFailHoldsecs
				INTEGER,
			iqhip00AudioLevelDetDuplicateSettingsCopyFromChannel
				INTEGER,
			iqhip00AudioLevelDetDuplicateSettingsCopySettings
				INTEGER,
			iqhip00HyperionAudioLevelDet
				INTEGER,
			iqhip00HyperionAudioLevelIndRollMapAudLvlEn
				INTEGER,
			iqhip00HyperionAudioLevelIndOSDMarker
				INTEGER,
			iqhip00HyperionAudioLevelIndRollMapAudLvl
				RollCallString,
			iqhip00HyperionAudioLevelIndEnableChannel1
				INTEGER,
			iqhip00HyperionAudioLevelIndChannel1
				RollCallString,
			iqhip00HyperionAudioLevelIndEnableChannel2
				INTEGER,
			iqhip00HyperionAudioLevelIndChannel2
				RollCallString,
			iqhip00HyperionAudioLevelIndEnableChannel3
				INTEGER,
			iqhip00HyperionAudioLevelIndChannel3
				RollCallString,
			iqhip00HyperionAudioLevelIndEnableChannel4
				INTEGER,
			iqhip00HyperionAudioLevelIndChannel4
				RollCallString,
			iqhip00HyperionAudioLevelIndEnableChannel5
				INTEGER,
			iqhip00HyperionAudioLevelIndChannel5
				RollCallString,
			iqhip00HyperionAudioLevelIndEnableChannel6
				INTEGER,
			iqhip00HyperionAudioLevelIndChannel6
				RollCallString,
			iqhip00HyperionAudioLevelIndEnableChannel7
				INTEGER,
			iqhip00HyperionAudioLevelIndChannel7
				RollCallString,
			iqhip00HyperionAudioLevelIndEnableChannel8
				INTEGER,
			iqhip00HyperionAudioLevelIndChannel8
				RollCallString,
			iqhip00HyperionAudioLevelIndEnableChannel9
				INTEGER,
			iqhip00HyperionAudioLevelIndChannel9
				RollCallString,
			iqhip00HyperionAudioLevelIndEnableChannel10
				INTEGER,
			iqhip00HyperionAudioLevelIndChannel10
				RollCallString,
			iqhip00HyperionAudioLevelIndEnableChannel11
				INTEGER,
			iqhip00HyperionAudioLevelIndChannel11
				RollCallString,
			iqhip00HyperionAudioLevelIndEnableChannel12
				INTEGER,
			iqhip00HyperionAudioLevelIndChannel12
				RollCallString,
			iqhip00HyperionAudioLevelIndEnableChannel13
				INTEGER,
			iqhip00HyperionAudioLevelIndChannel13
				RollCallString,
			iqhip00HyperionAudioLevelIndEnableChannel14
				INTEGER,
			iqhip00HyperionAudioLevelIndChannel14
				RollCallString,
			iqhip00HyperionAudioLevelIndEnableChannel15
				INTEGER,
			iqhip00HyperionAudioLevelIndChannel15
				RollCallString,
			iqhip00HyperionAudioLevelIndEnableChannel16
				INTEGER,
			iqhip00HyperionAudioLevelIndChannel16
				RollCallString,
			iqhip00HyperionClippingDetectorThreshold
				INTEGER,
			iqhip00HyperionClippingDetectorSensitivity
				INTEGER,
			iqhip00HyperionClippingDetectorStatusCh1
				RollCallString,
			iqhip00HyperionClippingDetectorEnableAlarmCh1
				INTEGER,
			iqhip00HyperionClippingDetectorStatusCh2
				RollCallString,
			iqhip00HyperionClippingDetectorEnableAlarmCh2
				INTEGER,
			iqhip00HyperionClippingDetectorStatusCh3
				RollCallString,
			iqhip00HyperionClippingDetectorEnableAlarmCh3
				INTEGER,
			iqhip00HyperionClippingDetectorStatusCh4
				RollCallString,
			iqhip00HyperionClippingDetectorEnableAlarmCh4
				INTEGER,
			iqhip00HyperionClippingDetectorStatusCh5
				RollCallString,
			iqhip00HyperionClippingDetectorEnableAlarmCh5
				INTEGER,
			iqhip00HyperionClippingDetectorStatusCh6
				RollCallString,
			iqhip00HyperionClippingDetectorEnableAlarmCh6
				INTEGER,
			iqhip00HyperionClippingDetectorStatusCh7
				RollCallString,
			iqhip00HyperionClippingDetectorEnableAlarmCh7
				INTEGER,
			iqhip00HyperionClippingDetectorStatusCh8
				RollCallString,
			iqhip00HyperionClippingDetectorEnableAlarmCh8
				INTEGER,
			iqhip00HyperionClippingDetectorStatusCh9
				RollCallString,
			iqhip00HyperionClippingDetectorEnableAlarmCh9
				INTEGER,
			iqhip00HyperionClippingDetectorStatusCh10
				RollCallString,
			iqhip00HyperionClippingDetectorEnableAlarmCh10
				INTEGER,
			iqhip00HyperionClippingDetectorStatusCh11
				RollCallString,
			iqhip00HyperionClippingDetectorEnableAlarmCh11
				INTEGER,
			iqhip00HyperionClippingDetectorStatusCh12
				RollCallString,
			iqhip00HyperionClippingDetectorEnableAlarmCh12
				INTEGER,
			iqhip00HyperionClippingDetectorStatusCh13
				RollCallString,
			iqhip00HyperionClippingDetectorEnableAlarmCh13
				INTEGER,
			iqhip00HyperionClippingDetectorStatusCh14
				RollCallString,
			iqhip00HyperionClippingDetectorEnableAlarmCh14
				INTEGER,
			iqhip00HyperionClippingDetectorStatusCh15
				RollCallString,
			iqhip00HyperionClippingDetectorEnableAlarmCh15
				INTEGER,
			iqhip00HyperionClippingDetectorStatusCh16
				RollCallString,
			iqhip00HyperionClippingDetectorEnableAlarmCh16
				INTEGER,
			iqhip00AudioLikenessDetector1Likeness
				RollCallString,
			iqhip00AudioLikenessDetector1State
				RollCallString,
			iqhip00AudioLikenessDetector1SelectChannelA
				INTEGER,
			iqhip00AudioLikenessDetector1SelectChannelB
				INTEGER,
			iqhip00AudioLikenessDetector1EnableAlarm
				INTEGER,
			iqhip00AudioLikenessDetector2Likeness
				RollCallString,
			iqhip00AudioLikenessDetector2State
				RollCallString,
			iqhip00AudioLikenessDetector2SelectChannelA
				INTEGER,
			iqhip00AudioLikenessDetector2SelectChannelB
				INTEGER,
			iqhip00AudioLikenessDetector2AlarmEnable
				INTEGER,
			iqhip00AudioLikenessDetector3Likeness
				RollCallString,
			iqhip00AudioLikenessDetector3State
				RollCallString,
			iqhip00AudioLikenessDetector3SelectChannelA
				INTEGER,
			iqhip00AudioLikenessDetector3SelectChannelB
				INTEGER,
			iqhip00AudioLikenessDetector3AlarmEnable
				INTEGER,
			iqhip00AudioLikenessDetector4Likeness
				RollCallString,
			iqhip00AudioLikenessDetector4State
				RollCallString,
			iqhip00AudioLikenessDetector4SelectChannelA
				INTEGER,
			iqhip00AudioLikenessDetector4SelectChannelB
				INTEGER,
			iqhip00AudioLikenessDetector4AlarmEnable
				INTEGER,
			iqhip00UMIDReaderDetectonYOnly
				INTEGER,
			iqhip00UMIDReaderUMIDPresence
				RollCallString,
			iqhip00UMIDReaderFoundOnLine
				RollCallString,
			iqhip00ReaderUniversalLabelVersionNumber
				RollCallString,
			iqhip00ReaderUniversalLabelMaterialType
				RollCallString,
			iqhip00ReaderUniversalLabelIdentMatNumGen
				RollCallString,
			iqhip00ReaderUniversalLabelIdentInstNumGen
				RollCallString,
			iqhip00UMIDReaderInstanceNumber
				RollCallString,
			iqhip00ReaderMaterialNumber1_4
				RollCallString,
			iqhip00ReaderMaterialNumber5_8
				RollCallString,
			iqhip00ReaderMaterialNumber9_12
				RollCallString,
			iqhip00ReaderMaterialNumber13_16
				RollCallString,
			iqhip00UMIDReaderCount
				RollCallString,
			iqhip00HyperionUMIDUMIDDelete
				INTEGER,
			iqhip00UMIDGeneratorEnable
				INTEGER,
			iqhip00UMIDGeneratorGeneratorStatus
				RollCallString,
			iqhip00UMIDGeneratorGenerateonYOnly
				INTEGER,
			iqhip00UMIDGeneratorTake
				INTEGER,
			iqhip00UMIDGeneratorLineNumber
				INTEGER,
			iqhip00GeneratorUniversalLabelVersionNumber
				INTEGER,
			iqhip00GeneratorUniversalLabelMaterialType
				INTEGER,
			iqhip00GeneratorUniversalLabelIdentofMaterial
				INTEGER,
			iqhip00GeneratorUniversalLabelIdentofInstance
				INTEGER,
			iqhip00UMIDGeneratorInstanceNum
				RollCallString,
			iqhip00UMIDGeneratorMaterialNum1_4
				RollCallString,
			iqhip00UMIDGeneratorMaterialNum5_8
				RollCallString,
			iqhip00UMIDGeneratorMaterialNum9_12
				RollCallString,
			iqhip00UMIDGeneratorMaterialNum13_16
				RollCallString,
			iqhip00HyperionUMIDUMIDAlarmEnable
				INTEGER,
			iqhip00PIDReaderPIDPresence
				RollCallString,
			iqhip00PIDReaderFoundOnLine
				RollCallString,
			iqhip00PIDReaderHouseID
				RollCallString,
			iqhip00PIDReaderProgramTitle
				RollCallString,
			iqhip00PIDReaderSegmentNumber
				RollCallString,
			iqhip00PIDReaderDuration
				RollCallString,
			iqhip00PIDReaderFrameRate
				RollCallString,
			iqhip00PIDReaderCount
				RollCallString,
			iqhip00HyperionPIDPIDDelete
				INTEGER,
			iqhip00PIDGeneratorEnable
				INTEGER,
			iqhip00PIDGeneratorGeneratorStatus
				RollCallString,
			iqhip00PIDGeneratorTake
				INTEGER,
			iqhip00PIDGeneratorLineNumber
				INTEGER,
			iqhip00PIDGeneratorHouseID
				RollCallString,
			iqhip00PIDGeneratorProgramTitle
				RollCallString,
			iqhip00PIDGeneratorProgramTitleEn
				INTEGER,
			iqhip00PIDGeneratorSegmentNumber
				RollCallString,
			iqhip00PIDGeneratorSegmentNumberEn
				INTEGER,
			iqhip00PIDGeneratorDuration
				RollCallString,
			iqhip00PIDGeneratorDurationEn
				INTEGER,
			iqhip00PIDGeneratorFrameRateEn
				INTEGER,
			iqhip00PIDGeneratorFrameRate
				INTEGER,
			iqhip00HyperionPIDPIDAlarmEnable
				INTEGER,
			iqhip00HyperionOSDOSDPassword
				RollCallString,
			iqhip00HyperionOSDOSDEnable
				INTEGER,
			iqhip00HyperionOSDOSDEnableoutput7
				INTEGER,
			iqhip00OSDStillishDetWindowOSWinEn
				INTEGER,
			iqhip00OSDStillishDetWindowXPosition
				INTEGER,
			iqhip00OSDStillishDetWindowWidth
				INTEGER,
			iqhip00OSDStillishDetWindowYPosition
				INTEGER,
			iqhip00OSDStillishDetWindowHeight
				INTEGER,
			iqhip00OSDStillishDetWindowWindowMode
				INTEGER,
			iqhip00OSDStillishDetWindowDetectFullScreen
				INTEGER,
			iqhip00OSDBlackishDetWindowOSWinEn
				INTEGER,
			iqhip00OSDBlackishDetWindowXPosition
				INTEGER,
			iqhip00OSDBlackishDetWindowWidth
				INTEGER,
			iqhip00OSDBlackishDetWindowYPosition
				INTEGER,
			iqhip00OSDBlackishDetWindowHeight
				INTEGER,
			iqhip00OSDBlackishDetWindowWindowMode
				INTEGER,
			iqhip00OSDBlackishDetWindowDetectFullScreen
				INTEGER,
			iqhip00OSDOnScreenDispEnIndicators
				INTEGER,
			iqhip00OSDOnScreenDispEnAudioLevelInds
				INTEGER,
			iqhip00OSDOnScreenDispEnTimecode
				INTEGER,
			iqhip00OSDOnScreenDispEnGreyBackground
				INTEGER,
			iqhip00OSDOnScreenDispEnInput1Name
				INTEGER,
			iqhip00OSDOnScreenDispEnCaption1Edit
				RollCallString,
			iqhip00OSDOnScreenDispEnCaption1Enable
				INTEGER,
			iqhip00OSDOnScreenDispEnCaption2Edit
				RollCallString,
			iqhip00OSDOnScreenDispEnCaption2Enable
				INTEGER,
			iqhip00OSDOnScreenDispEnContentAdvisory
				INTEGER,
			iqhip00OSDOnScreenDispEnIncomingPID
				INTEGER,
			iqhip00OSDOnScreenDispEnOutgoingPID
				INTEGER,
			iqhip00OSDOnScreenDispEnAudioLvlIndZoom
				INTEGER,
			iqhip00HyperionHyperionDetStatus
				INTEGER,
			iqhip00MemoriesMemorySave
				INTEGER,
			iqhip00MemoriesMemoryRecall
				INTEGER,
			iqhip00MemoriesMemory1Name
				RollCallString,
			iqhip00MemoriesMemory2Name
				RollCallString,
			iqhip00MemoriesMemory3Name
				RollCallString,
			iqhip00MemoriesMemory4Name
				RollCallString,
			iqhip00MemoriesMemory5Name
				RollCallString,
			iqhip00MemoriesMemory6Name
				RollCallString,
			iqhip00MemoriesMemory7Name
				RollCallString,
			iqhip00MemoriesMemory8Name
				RollCallString,
			iqhip00MemoriesMemory9Name
				RollCallString,
			iqhip00MemoriesMemory10Name
				RollCallString,
			iqhip00MemoriesMemory11Name
				RollCallString,
			iqhip00MemoriesMemory12Name
				RollCallString,
			iqhip00MemoriesMemory13Name
				RollCallString,
			iqhip00MemoriesMemory14Name
				RollCallString,
			iqhip00MemoriesMemory15Name
				RollCallString,
			iqhip00MemoriesMemory16Name
				RollCallString,
			iqhip00LoggingMiscTimecodelogEnable
				INTEGER,
			iqhip00LoggingMiscLogSerialNoEnable
				INTEGER,
			iqhip00LoggingMiscSerialNo
				RollCallString,
			iqhip00LoggingMiscLogOSVersionEnable
				INTEGER,
			iqhip00LoggingMiscOSVersion
				RollCallString,
			iqhip00LoggingMiscLogBuildNoEnable
				INTEGER,
			iqhip00LoggingMiscBuildNo
				RollCallString,
			iqhip00LoggingMiscLogHardwareVerEnable
				INTEGER,
			iqhip00LoggingMiscHardwareVer
				RollCallString,
			iqhip00LoggingMiscLogFirmwareVerEnable
				INTEGER,
			iqhip00LoggingMiscFirmwareVer
				RollCallString,
			iqhip00LoggingMiscLogUpTimeEnable
				INTEGER,
			iqhip00LoggingMiscUpTime
				RollCallString,
			iqhip00LoggingMiscRollTracksEnable
				INTEGER,
			iqhip00LoggingMiscRollTracks
				RollCallString,
			iqhip00LoggingMiscOSDStatusEnable
				INTEGER,
			iqhip00LoggingMiscOSDStatus
				RollCallString,
			iqhip00LoggingInput1InputIdentEnable
				INTEGER,
			iqhip00LoggingInput1InputIdent
				RollCallString,
			iqhip00LoggingInput1InputNameEnable
				INTEGER,
			iqhip00LoggingInput1InputName
				RollCallString,
			iqhip00LoggingInput1InputTypeEnable
				INTEGER,
			iqhip00LoggingInput1InputType
				RollCallString,
			iqhip00LoggingInput1InputStateEnable
				INTEGER,
			iqhip00LoggingInput1InputState
				RollCallString,
			iqhip00LoggingInput1InputStandardEnable
				INTEGER,
			iqhip00LoggingInput1InputStandard
				RollCallString,
			iqhip00LoggingInput1EDHEnable
				INTEGER,
			iqhip00LoggingInput1EDH
				RollCallString,
			iqhip00LoggingInput1CRCEnable
				INTEGER,
			iqhip00LoggingInput1CRC
				RollCallString,
			iqhip00LoggingInp1Monitor1HyperionSummaryEnable
				INTEGER,
			iqhip00LoggingInp1Monitor1HyperionSummary
				RollCallString,
			iqhip00LoggingInp1Monitor1StillishEnable
				INTEGER,
			iqhip00LoggingInp1Monitor1Stillish
				RollCallString,
			iqhip00LoggingInp1Monitor1StillishLogOption
				INTEGER,
			iqhip00LoggingInp1Monitor1FreezeEnable
				INTEGER,
			iqhip00LoggingInp1Monitor1Freeze
				RollCallString,
			iqhip00LoggingInp1Monitor1FreezeLogOption
				INTEGER,
			iqhip00LoggingInp1Monitor1BlackEnable
				INTEGER,
			iqhip00LoggingInp1Monitor1Black
				RollCallString,
			iqhip00LoggingInp1Monitor1BlackLogOption
				INTEGER,
			iqhip00LoggingInp1Monitor1BlackishEnable
				INTEGER,
			iqhip00LoggingInp1Monitor1Blackish
				RollCallString,
			iqhip00LoggingInp1Monitor1BlackishLogOption
				INTEGER,
			iqhip00LoggingInp1Monitor1CldCapStateEnable
				INTEGER,
			iqhip00LoggingInp1Monitor1ClosedCapState
				RollCallString,
			iqhip00LoggingInp1Monitor1ClosedCapLogOption
				INTEGER,
			iqhip00LoggingInp1Monitor1CldCapTypeEnable
				INTEGER,
			iqhip00LoggingInp1Monitor1ClosedCapType
				RollCallString,
			iqhip00LoggingInp1Monitor1CldCapTitleEnable
				INTEGER,
			iqhip00LoggingInp1Monitor1ClosedCapTitle
				RollCallString,
			iqhip00LoggingInp1Monitor2YBitDepthEnable
				INTEGER,
			iqhip00LoggingInp1Monitor2YBitDepth
				RollCallString,
			iqhip00LoggingInp1Monitor2CBitDepthEnable
				INTEGER,
			iqhip00LoggingInp1Monitor2CBitDepth
				RollCallString,
			iqhip00LoggingInp1Monitor2VideoYLvlHighEnable
				INTEGER,
			iqhip00LoggingInp1Monitor2VideoYLevelHigh
				RollCallString,
			iqhip00LoggingInp1Monitor2VideoCLvlHighEnable
				INTEGER,
			iqhip00LoggingInp1Monitor2VideoCLevelHigh
				RollCallString,
			iqhip00LoggingInp1Monitor2VideoYLvlLowEnable
				INTEGER,
			iqhip00LoggingInp1Monitor2VideoYLevelLow
				RollCallString,
			iqhip00LoggingInp1Monitor2VideoCLvlLowEnable
				INTEGER,
			iqhip00LoggingInp1Monitor2VideoCLevelLow
				RollCallString,
			iqhip00LoggingInp1Monitor2APLEnable
				INTEGER,
			iqhip00LoggingInp1Monitor2APL
				RollCallString,
			iqhip00LoggingInp1Monitor2VITCStateEnable
				INTEGER,
			iqhip00LoggingInp1Monitor2VITCState
				RollCallString,
			iqhip00LoggingInp1Monitor2CAStateEnable
				INTEGER,
			iqhip00LoggingInp1Monitor2CAState
				RollCallString,
			iqhip00LoggingInp1Monitor2CASystemEnable
				INTEGER,
			iqhip00LoggingInp1Monitor2CASystem
				RollCallString,
			iqhip00LoggingInp1Monitor2CAAgeRatingEnable
				INTEGER,
			iqhip00LoggingInp1Monitor2CAAgeRating
				RollCallString,
			iqhip00LoggingInp1Monitor2ANCTimcodeStateEnable
				INTEGER,
			iqhip00LoggingInp1Monitor2ANCTimecodeState
				RollCallString,
			iqhip00LoggingInp1Monitor2User1DIDNameEnable
				INTEGER,
			iqhip00LoggingInp1Monitor2User1DIDName
				RollCallString,
			iqhip00LoggingInp1Monitor2User1DIDStateEnable
				INTEGER,
			iqhip00LoggingInp1Monitor2User1DIDState
				RollCallString,
			iqhip00LoggingInp1Monitor2User2DIDNameEnable
				INTEGER,
			iqhip00LoggingInp1Monitor2User2DIDName
				RollCallString,
			iqhip00LoggingInp1Monitor2User2DIDStateEnable
				INTEGER,
			iqhip00LoggingInp1Monitor2User2DIDState
				RollCallString,
			iqhip00LoggingInp1Monitor2WSSStateEnable
				INTEGER,
			iqhip00LoggingInp1Monitor2WSSState
				RollCallString,
			iqhip00LoggingInp1Monitor2VIStateEnable
				INTEGER,
			iqhip00LoggingInp1Monitor2VIState
				RollCallString,
			iqhip00LoggingInp1Monitor2WSSEnable
				INTEGER,
			iqhip00LoggingInp1Monitor2WSS
				RollCallString,
			iqhip00LoggingInp1Monitor2VIEnable
				INTEGER,
			iqhip00LoggingInp1Monitor2VI
				RollCallString,
			iqhip00LoggingInp1Monitor2WSSAspectEnable
				INTEGER,
			iqhip00LoggingInp1Monitor2WSSAspect
				RollCallString,
			iqhip00LoggingInp1Monitor2VIAspectEnable
				INTEGER,
			iqhip00LoggingInp1Monitor2VIAspect
				RollCallString,
			iqhip00LoggingInp1AudStateEmbCh1StateEnable
				INTEGER,
			iqhip00LoggingInp1AudStateEmbCh1State
				RollCallString,
			iqhip00LoggingInp1AudStateEmbCh2StateEnable
				INTEGER,
			iqhip00LoggingInp1AudStateEmbCh2State
				RollCallString,
			iqhip00LoggingInp1AudStateEmbCh3StateEnable
				INTEGER,
			iqhip00LoggingInp1AudStateEmbCh3State
				RollCallString,
			iqhip00LoggingInp1AudStateEmbCh4StateEnable
				INTEGER,
			iqhip00LoggingInp1AudStateEmbCh4State
				RollCallString,
			iqhip00LoggingInp1AudStateEmbCh5StateEnable
				INTEGER,
			iqhip00LoggingInp1AudStateEmbCh5State
				RollCallString,
			iqhip00LoggingInp1AudStateEmbCh6StateEnable
				INTEGER,
			iqhip00LoggingInp1AudStateEmbCh6State
				RollCallString,
			iqhip00LoggingInp1AudStateEmbCh7StateEnable
				INTEGER,
			iqhip00LoggingInp1AudStateEmbCh7State
				RollCallString,
			iqhip00LoggingInp1AudStateEmbCh8StateEnable
				INTEGER,
			iqhip00LoggingInp1AudStateEmbCh8State
				RollCallString,
			iqhip00LoggingInp1AudStateEmbCh9StateEnable
				INTEGER,
			iqhip00LoggingInp1AudStateEmbCh9State
				RollCallString,
			iqhip00LoggingInp1AudStateEmbCh10StateEnable
				INTEGER,
			iqhip00LoggingInp1AudStateEmbCh10State
				RollCallString,
			iqhip00LoggingInp1AudStateEmbCh11StateEnable
				INTEGER,
			iqhip00LoggingInp1AudStateEmbCh11State
				RollCallString,
			iqhip00LoggingInp1AudStateEmbCh12StateEnable
				INTEGER,
			iqhip00LoggingInp1AudStateEmbCh12State
				RollCallString,
			iqhip00LoggingInp1AudStateEmbCh13StateEnable
				INTEGER,
			iqhip00LoggingInp1AudStateEmbCh13State
				RollCallString,
			iqhip00LoggingInp1AudStateEmbCh14StateEnable
				INTEGER,
			iqhip00LoggingInp1AudStateEmbCh14State
				RollCallString,
			iqhip00LoggingInp1AudStateEmbCh15StateEnable
				INTEGER,
			iqhip00LoggingInp1AudStateEmbCh15State
				RollCallString,
			iqhip00LoggingInp1AudStateEmbCh16StateEnable
				INTEGER,
			iqhip00LoggingInp1AudStateEmbCh16State
				RollCallString,
			iqhip00LoggingInp1AudTypeEmbCh1TypeEnable
				INTEGER,
			iqhip00LoggingInp1AudTypeEmbCh1Type
				RollCallString,
			iqhip00LoggingInp1AudTypeEmbCh2TypeEnable
				INTEGER,
			iqhip00LoggingInp1AudTypeEmbCh2Type
				RollCallString,
			iqhip00LoggingInp1AudTypeEmbCh3TypeEnable
				INTEGER,
			iqhip00LoggingInp1AudTypeEmbCh3Type
				RollCallString,
			iqhip00LoggingInp1AudTypeEmbCh4TypeEnable
				INTEGER,
			iqhip00LoggingInp1AudTypeEmbCh4Type
				RollCallString,
			iqhip00LoggingInp1AudTypeEmbCh5TypeEnable
				INTEGER,
			iqhip00LoggingInp1AudTypeEmbCh5Type
				RollCallString,
			iqhip00LoggingInp1AudTypeEmbCh6TypeEnable
				INTEGER,
			iqhip00LoggingInp1AudTypeEmbCh6Type
				RollCallString,
			iqhip00LoggingInp1AudTypeEmbCh7TypeEnable
				INTEGER,
			iqhip00LoggingInp1AudTypeEmbCh7Type
				RollCallString,
			iqhip00LoggingInp1AudTypeEmbCh8TypeEnable
				INTEGER,
			iqhip00LoggingInp1AudTypeEmbCh8Type
				RollCallString,
			iqhip00LoggingInp1AudTypeEmbCh9TypeEnable
				INTEGER,
			iqhip00LoggingInp1AudTypeEmbCh9Type
				RollCallString,
			iqhip00LoggingInp1AudTypeEmbCh10TypeEnable
				INTEGER,
			iqhip00LoggingInp1AudTypeEmbCh10Type
				RollCallString,
			iqhip00LoggingInp1AudTypeEmbCh11TypeEnable
				INTEGER,
			iqhip00LoggingInp1AudTypeEmbCh11Type
				RollCallString,
			iqhip00LoggingInp1AudTypeEmbCh12TypeEnable
				INTEGER,
			iqhip00LoggingInp1AudTypeEmbCh12Type
				RollCallString,
			iqhip00LoggingInp1AudTypeEmbCh13TypeEnable
				INTEGER,
			iqhip00LoggingInp1AudTypeEmbCh13Type
				RollCallString,
			iqhip00LoggingInp1AudTypeEmbCh14TypeEnable
				INTEGER,
			iqhip00LoggingInp1AudTypeEmbCh14Type
				RollCallString,
			iqhip00LoggingInp1AudTypeEmbCh15TypeEnable
				INTEGER,
			iqhip00LoggingInp1AudTypeEmbCh15Type
				RollCallString,
			iqhip00LoggingInp1AudTypeEmbCh16TypeEnable
				INTEGER,
			iqhip00LoggingInp1AudTypeEmbCh16Type
				RollCallString,
			iqhip00LoggingInp1DolbyEStatePair1Enable
				INTEGER,
			iqhip00LoggingInp1DolbyEStatePair1State
				RollCallString,
			iqhip00LoggingInp1DolbyEStatePair2Enable
				INTEGER,
			iqhip00LoggingInp1DolbyEStatePair2State
				RollCallString,
			iqhip00LoggingInp1DolbyEStatePair3Enable
				INTEGER,
			iqhip00LoggingInp1DolbyEStatePair3State
				RollCallString,
			iqhip00LoggingInp1DolbyEStatePair4Enable
				INTEGER,
			iqhip00LoggingInp1DolbyEStatePair4State
				RollCallString,
			iqhip00LoggingInp1DolbyEStatePair5Enable
				INTEGER,
			iqhip00LoggingInp1DolbyEStatePair5State
				RollCallString,
			iqhip00LoggingInp1DolbyEStatePair6Enable
				INTEGER,
			iqhip00LoggingInp1DolbyEStatePair6State
				RollCallString,
			iqhip00LoggingInp1DolbyEStatePair7Enable
				INTEGER,
			iqhip00LoggingInp1DolbyEStatePair7State
				RollCallString,
			iqhip00LoggingInp1DolbyEStatePair8Enable
				INTEGER,
			iqhip00LoggingInp1DolbyEStatePair8State
				RollCallString,
			iqhip00LoggingInp1BitDepthEmbCh1BitDepthEnable
				INTEGER,
			iqhip00LoggingInp1BitDepthEmbCh1BitDepth
				RollCallString,
			iqhip00LoggingInp1BitDepthEmbCh2BitDepthEnable
				INTEGER,
			iqhip00LoggingInp1BitDepthEmbCh2BitDepth
				RollCallString,
			iqhip00LoggingInp1BitDepthEmbCh3BitDepthEnable
				INTEGER,
			iqhip00LoggingInp1BitDepthEmbCh3BitDepth
				RollCallString,
			iqhip00LoggingInp1BitDepthEmbCh4BitDepthEnable
				INTEGER,
			iqhip00LoggingInp1BitDepthEmbCh4BitDepth
				RollCallString,
			iqhip00LoggingInp1BitDepthEmbCh5BitDepthEnable
				INTEGER,
			iqhip00LoggingInp1BitDepthEmbCh5BitDepth
				RollCallString,
			iqhip00LoggingInp1BitDepthEmbCh6BitDepthEnable
				INTEGER,
			iqhip00LoggingInp1BitDepthEmbCh6BitDepth
				RollCallString,
			iqhip00LoggingInp1BitDepthEmbCh7BitDepthEnable
				INTEGER,
			iqhip00LoggingInp1BitDepthEmbCh7BitDepth
				RollCallString,
			iqhip00LoggingInp1BitDepthEmbCh8BitDepthEnable
				INTEGER,
			iqhip00LoggingInp1BitDepthEmbCh8BitDepth
				RollCallString,
			iqhip00LoggingInp1BitDepthEmbCh9BitDepthEnable
				INTEGER,
			iqhip00LoggingInp1BitDepthEmbCh9BitDepth
				RollCallString,
			iqhip00LoggingInp1BitDepthEmbCh10BitDepthEnable
				INTEGER,
			iqhip00LoggingInp1BitDepthEmbCh10BitDepth
				RollCallString,
			iqhip00LoggingInp1BitDepthEmbCh11BitDepthEnable
				INTEGER,
			iqhip00LoggingInp1BitDepthEmbCh11BitDepth
				RollCallString,
			iqhip00LoggingInp1BitDepthEmbCh12BitDepthEnable
				INTEGER,
			iqhip00LoggingInp1BitDepthEmbCh12BitDepth
				RollCallString,
			iqhip00LoggingInp1BitDepthEmbCh13BitDepthEnable
				INTEGER,
			iqhip00LoggingInp1BitDepthEmbCh13BitDepth
				RollCallString,
			iqhip00LoggingInp1BitDepthEmbCh14BitDepthEnable
				INTEGER,
			iqhip00LoggingInp1BitDepthEmbCh14BitDepth
				RollCallString,
			iqhip00LoggingInp1BitDepthEmbCh15BitDepthEnable
				INTEGER,
			iqhip00LoggingInp1BitDepthEmbCh15BitDepth
				RollCallString,
			iqhip00LoggingInp1BitDepthEmbCh16BitDepthEnable
				INTEGER,
			iqhip00LoggingInp1BitDepthEmbCh16BitDepth
				RollCallString,
			iqhip00LoggingInp1LevelEmbCh1LevelEnable
				INTEGER,
			iqhip00LoggingInp1LevelEmbCh1Level
				RollCallString,
			iqhip00LoggingInp1LevelEmbCh2LevelEnable
				INTEGER,
			iqhip00LoggingInp1LevelEmbCh2Level
				RollCallString,
			iqhip00LoggingInp1LevelEmbCh3LevelEnable
				INTEGER,
			iqhip00LoggingInp1LevelEmbCh3Level
				RollCallString,
			iqhip00LoggingInp1LevelEmbCh4LevelEnable
				INTEGER,
			iqhip00LoggingInp1LevelEmbCh4Level
				RollCallString,
			iqhip00LoggingInp1LevelEmbCh5LevelEnable
				INTEGER,
			iqhip00LoggingInp1LevelEmbCh5Level
				RollCallString,
			iqhip00LoggingInp1LevelEmbCh6LevelEnable
				INTEGER,
			iqhip00LoggingInp1LevelEmbCh6Level
				RollCallString,
			iqhip00LoggingInp1LevelEmbCh7LevelEnable
				INTEGER,
			iqhip00LoggingInp1LevelEmbCh7Level
				RollCallString,
			iqhip00LoggingInp1LevelEmbCh8LevelEnable
				INTEGER,
			iqhip00LoggingInp1LevelEmbCh8Level
				RollCallString,
			iqhip00LoggingInp1LevelEmbCh9LevelEnable
				INTEGER,
			iqhip00LoggingInp1LevelEmbCh9Level
				RollCallString,
			iqhip00LoggingInp1LevelEmbCh10LevelEnable
				INTEGER,
			iqhip00LoggingInp1LevelEmbCh10Level
				RollCallString,
			iqhip00LoggingInp1LevelEmbCh11LevelEnable
				INTEGER,
			iqhip00LoggingInp1LevelEmbCh11Level
				RollCallString,
			iqhip00LoggingInp1LevelEmbCh12LevelEnable
				INTEGER,
			iqhip00LoggingInp1LevelEmbCh12Level
				RollCallString,
			iqhip00LoggingInp1LevelEmbCh13LevelEnable
				INTEGER,
			iqhip00LoggingInp1LevelEmbCh13Level
				RollCallString,
			iqhip00LoggingInp1LevelEmbCh14LevelEnable
				INTEGER,
			iqhip00LoggingInp1LevelEmbCh14Level
				RollCallString,
			iqhip00LoggingInp1LevelEmbCh15LevelEnable
				INTEGER,
			iqhip00LoggingInp1LevelEmbCh15Level
				RollCallString,
			iqhip00LoggingInp1LevelEmbCh16LevelEnable
				INTEGER,
			iqhip00LoggingInp1LevelEmbCh16Level
				RollCallString,
			iqhip00LoggingInp1ClippingEmbCh1LevelEnable
				INTEGER,
			iqhip00LoggingInp1ClippingEmbCh1Level
				RollCallString,
			iqhip00LoggingInp1ClippingEmbCh2LevelEnable
				INTEGER,
			iqhip00LoggingInp1ClippingEmbCh2Level
				RollCallString,
			iqhip00LoggingInp1ClippingEmbCh3LevelEnable
				INTEGER,
			iqhip00LoggingInp1ClippingEmbCh3Level
				RollCallString,
			iqhip00LoggingInp1ClippingEmbCh4LevelEnable
				INTEGER,
			iqhip00LoggingInp1ClippingEmbCh4Level
				RollCallString,
			iqhip00LoggingInp1ClippingEmbCh5LevelEnable
				INTEGER,
			iqhip00LoggingInp1ClippingEmbCh5Level
				RollCallString,
			iqhip00LoggingInp1ClippingEmbCh6LevelEnable
				INTEGER,
			iqhip00LoggingInp1ClippingEmbCh6Level
				RollCallString,
			iqhip00LoggingInp1ClippingEmbCh7LevelEnable
				INTEGER,
			iqhip00LoggingInp1ClippingEmbCh7Level
				RollCallString,
			iqhip00LoggingInp1ClippingEmbCh8LevelEnable
				INTEGER,
			iqhip00LoggingInp1ClippingEmbCh8Level
				RollCallString,
			iqhip00LoggingInp1ClippingEmbCh9LevelEnable
				INTEGER,
			iqhip00LoggingInp1ClippingEmbCh9Level
				RollCallString,
			iqhip00LoggingInp1ClippingEmbCh10LevelEnable
				INTEGER,
			iqhip00LoggingInp1ClippingEmbCh10Level
				RollCallString,
			iqhip00LoggingInp1ClippingEmbCh11LevelEnable
				INTEGER,
			iqhip00LoggingInp1ClippingEmbCh11Level
				RollCallString,
			iqhip00LoggingInp1ClippingEmbCh12LevelEnable
				INTEGER,
			iqhip00LoggingInp1ClippingEmbCh12Level
				RollCallString,
			iqhip00LoggingInp1ClippingEmbCh13LevelEnable
				INTEGER,
			iqhip00LoggingInp1ClippingEmbCh13Level
				RollCallString,
			iqhip00LoggingInp1ClippingEmbCh14LevelEnable
				INTEGER,
			iqhip00LoggingInp1ClippingEmbCh14Level
				RollCallString,
			iqhip00LoggingInp1ClippingEmbCh15LevelEnable
				INTEGER,
			iqhip00LoggingInp1ClippingEmbCh15Level
				RollCallString,
			iqhip00LoggingInp1ClippingEmbCh16LevelEnable
				INTEGER,
			iqhip00LoggingInp1ClippingEmbCh16Level
				RollCallString,
			iqhip00LoggingInp1LikenessDetector1ChansEnable
				INTEGER,
			iqhip00LoggingInp1LikenessDetector1Chans
				RollCallString,
			iqhip00LoggingInp1LikenessDetector1StateEnable
				INTEGER,
			iqhip00LoggingInp1LikenessDetector1State
				RollCallString,
			iqhip00LoggingInp1LikenessDetector2ChansEnable
				INTEGER,
			iqhip00LoggingInp1LikenessDetector2Chans
				RollCallString,
			iqhip00LoggingInp1LikenessDetector2StateEnable
				INTEGER,
			iqhip00LoggingInp1LikenessDetector2State
				RollCallString,
			iqhip00LoggingInp1LikenessDetector3ChansEnable
				INTEGER,
			iqhip00LoggingInp1LikenessDetector3Chans
				RollCallString,
			iqhip00LoggingInp1LikenessDetector3StateEnable
				INTEGER,
			iqhip00LoggingInp1LikenessDetector3State
				RollCallString,
			iqhip00LoggingInp1LikenessDetector4ChansEnable
				INTEGER,
			iqhip00LoggingInp1LikenessDetector4Chans
				RollCallString,
			iqhip00LoggingInp1LikenessDetector4StateEnable
				INTEGER,
			iqhip00LoggingInp1LikenessDetector4State
				RollCallString,
			iqhip00LoggingOut1UMIDUMIDStateEnable
				INTEGER,
			iqhip00LoggingOut1UMIDUMIDState
				RollCallString,
			iqhip00LoggingOut1UMIDOutputUMIDEnable
				INTEGER,
			iqhip00LoggingOut1UMIDOutputUMID1_8
				RollCallString,
			iqhip00LoggingOut1UMIDOutputUMID9_16
				RollCallString,
			iqhip00LoggingOut1UMIDOutputUMID17_24
				RollCallString,
			iqhip00LoggingOut1UMIDOutputUMID25_32
				RollCallString,
			iqhip00LoggingInp1UMIDUMIDStateEnable
				INTEGER,
			iqhip00LoggingInp1UMIDUMIDState
				RollCallString,
			iqhip00LoggingInp1UMIDUMIDCurrentEnable
				INTEGER,
			iqhip00LoggingInp1UMIDUMIDCurrent1_8
				RollCallString,
			iqhip00LoggingInp1UMIDUMIDCurrent9_16
				RollCallString,
			iqhip00LoggingInp1UMIDUMIDCurrent17_24
				RollCallString,
			iqhip00LoggingInp1UMIDUMIDCurrent25_32
				RollCallString,
			iqhip00LoggingInp1UMIDUMIDPreviousEnable
				INTEGER,
			iqhip00LoggingInp1UMIDUMIDPrev1_8
				RollCallString,
			iqhip00LoggingInp1UMIDUMIDPrev9_16
				RollCallString,
			iqhip00LoggingInp1UMIDUMIDPrev17_24
				RollCallString,
			iqhip00LoggingInp1UMIDUMIDPrev25_32
				RollCallString,
			iqhip00LoggingInp1UMIDUMIDPreviousCountEnable
				INTEGER,
			iqhip00LoggingInp1UMIDUMIDPrevCount
				RollCallString,
			iqhip00LoggingOut1PIDPIDStateEnable
				INTEGER,
			iqhip00LoggingOut1PIDPIDState
				RollCallString,
			iqhip00LoggingOut1PIDPIDHouseIDEnable
				INTEGER,
			iqhip00LoggingOut1PIDPIDHouseID
				RollCallString,
			iqhip00LoggingOut1PIDPIDTitleEnable
				INTEGER,
			iqhip00LoggingOut1PIDPIDTitle
				RollCallString,
			iqhip00LoggingOut1PIDSegmentNumberEnable
				INTEGER,
			iqhip00LoggingOut1PIDSegmentNumber
				RollCallString,
			iqhip00LoggingOut1PIDDurationEnable
				INTEGER,
			iqhip00LoggingOut1PIDDuration
				RollCallString,
			iqhip00LoggingOut1PIDFrameRateEnable
				INTEGER,
			iqhip00LoggingOut1PIDFrameRate
				RollCallString,
			iqhip00LoggingInp1PIDPIDStateEnable
				INTEGER,
			iqhip00LoggingInp1PIDPIDState
				RollCallString,
			iqhip00LoggingInp1PIDPIDHouseIDEnable
				INTEGER,
			iqhip00LoggingInp1PIDPIDHouseID
				RollCallString,
			iqhip00LoggingInp1PIDPIDTitleEnable
				INTEGER,
			iqhip00LoggingInp1PIDPIDTitle
				RollCallString,
			iqhip00LoggingInp1PIDSegmentNumberEnable
				INTEGER,
			iqhip00LoggingInp1PIDSegmentNumber
				RollCallString,
			iqhip00LoggingInp1PIDDurationEnable
				INTEGER,
			iqhip00LoggingInp1PIDDuration
				RollCallString,
			iqhip00LoggingInp1PIDFrameRateEnable
				INTEGER,
			iqhip00LoggingInp1PIDFrameRate
				RollCallString,
			iqhip00LoggingInp1PIDPreviousHouseIDEnable
				INTEGER,
			iqhip00LoggingInp1PIDPreviousHouseID
				RollCallString,
			iqhip00LoggingInp1PIDPreviousTitleEnable
				INTEGER,
			iqhip00LoggingInp1PIDPreviousTitle
				RollCallString,
			iqhip00LoggingInp1PIDPreviousSegNumEnable
				INTEGER,
			iqhip00LoggingInp1PIDPreviousSegNum
				RollCallString,
			iqhip00LoggingInp1PIDPreviousDurationEnable
				INTEGER,
			iqhip00LoggingInp1PIDPreviousDuration
				RollCallString,
			iqhip00LoggingInp1PIDPreviousFrameRateEnable
				INTEGER,
			iqhip00LoggingInp1PIDPreviousFrameRate
				RollCallString,
			iqhip00LoggingInp1PIDPreviousCountEnable
				INTEGER,
			iqhip00LoggingInp1PIDPreviousCount
				RollCallString,
			iqhip00RollcallRollTrackDisableAll
				INTEGER,
			iqhip00RollcallRollTrackIndex
				INTEGER,
			iqhip00RollcallRollTrackSource
				INTEGER,
			iqhip00RollcallRollTrackAddress
				RollCallString,
			iqhip00RollcallRollTrackCommand
				RollCallString,
			iqhip00RollcallRollTrackStatus
				RollCallString,
			iqhip00RollcallRollTrackSending
				RollCallString,
			iqhip00SetupProduct
				RollCallString,
			iqhip00SetupProductRelease
				RollCallString,
			iqhip00SetupProductBuild
				RollCallString,
			iqhip00SetupProductKOS
				RollCallString,
			iqhip00SetupProductSerial
				RollCallString,
			iqhip00SetupProductFirmware
				RollCallString,
			iqhip00SetupProductPCB
				RollCallString,
			iqhip00SetupProductFactoryDefault
				INTEGER,
			iqhip00SetupProductRestart
				INTEGER,
			iqhip00SetupInput1Name
				RollCallString
		}

	iqhip00SlotIndex OBJECT-TYPE
		SYNTAX		Unsigned32
		MAX-ACCESS		not-accessible
		STATUS			current
		DESCRIPTION
				"The unique Index value for each slot.  Its value
					ranges between 1 and the value of slotNumber."
		::= { iqhip00CmdEntry 0 }


	iqhip00HyperionBlackishBlackBlackishLevel OBJECT-TYPE
		SYNTAX		RollCallString
		MAX-ACCESS		read-only
		STATUS			current
		DESCRIPTION
				"TYPE: - Display
				 PAGE: - Blackish/Black
					Blackish Level  cmdID= 1241  format=   "
		::= { iqhip00CmdEntry 1241 }


	iqhip00HyperionBlackishBlackMinLevelThres OBJECT-TYPE
		SYNTAX		INTEGER
		MAX-ACCESS		read-write
		STATUS			current
		DESCRIPTION
				"TYPE: - Number
				 PAGE: - Blackish/Black
					Min Level Thres  cmdID= 1226  min= 0  max= 100  step= 1  format= %0.0f  div_scale= 1
					Min = 0  Max = 100  Step = 1 "
		::= { iqhip00CmdEntry 1226 }


	iqhip00TemporalControlBlackishEnableAlarm OBJECT-TYPE
		SYNTAX		INTEGER { disable(0), enable(1) }
		MAX-ACCESS		read-write
		STATUS			current
		DESCRIPTION
				"TYPE: - Checkbox
				 PAGE: - Blackish/Black
					Enable Alarm  cmdID= 1236 "
		::= { iqhip00CmdEntry 1236 }


	iqhip00TemporalControlBlackishAlarm OBJECT-TYPE
		SYNTAX		RollCallString
		MAX-ACCESS		read-only
		STATUS			current
		DESCRIPTION
				"TYPE: - Display
				 PAGE: - Blackish/Black
					Alarm  cmdID= 1240  format=   "
		::= { iqhip00CmdEntry 1240 }


	iqhip00TemporalControlBlackishFailCount OBJECT-TYPE
		SYNTAX		INTEGER
		MAX-ACCESS		read-write
		STATUS			current
		DESCRIPTION
				"TYPE: - Number
				 PAGE: - Blackish/Black
					Fail Count  cmdID= 1237  min= 0  max= 16000  step= 1  format= %0.0f  div_scale= 1
					Min = 0  Max = 16000  Step = 1 "
		::= { iqhip00CmdEntry 1237 }


	iqhip00TemporalControlBlackishWarningCount OBJECT-TYPE
		SYNTAX		INTEGER
		MAX-ACCESS		read-write
		STATUS			current
		DESCRIPTION
				"TYPE: - Number
				 PAGE: - Blackish/Black
					Warning Count  cmdID= 1238  min= 0  max= 16000  step= 1  format= %0.0f  div_scale= 1
					Min = 0  Max = 16000  Step = 1 "
		::= { iqhip00CmdEntry 1238 }


	iqhip00TemporalControlBlackishFailHoldCount OBJECT-TYPE
		SYNTAX		INTEGER
		MAX-ACCESS		read-write
		STATUS			current
		DESCRIPTION
				"TYPE: - Number
				 PAGE: - Blackish/Black
					Fail Hold Count  cmdID= 1239  min= 0  max= 16000  step= 1  format= %0.0f  div_scale= 1
					Min = 0  Max = 16000  Step = 1 "
		::= { iqhip00CmdEntry 1239 }


	iqhip00TemporalControlBlackishResetAlarm OBJECT-TYPE
		SYNTAX		INTEGER { noAction(0),val_Reset_Alarm(1) }
		MAX-ACCESS		read-write
		STATUS			current
		DESCRIPTION
				"TYPE: - Button
				 PAGE: - Blackish/Black
					Reset Alarm  cmdID= 1244  value= 1  "
		::= { iqhip00CmdEntry 1244 }


	iqhip00TemporalControlBlackEnableAlarm OBJECT-TYPE
		SYNTAX		INTEGER { disable(0), enable(1) }
		MAX-ACCESS		read-write
		STATUS			current
		DESCRIPTION
				"TYPE: - Checkbox
				 PAGE: - Blackish/Black
					Enable Alarm  cmdID= 1231 "
		::= { iqhip00CmdEntry 1231 }


	iqhip00TemporalControlBlackAlarm OBJECT-TYPE
		SYNTAX		RollCallString
		MAX-ACCESS		read-only
		STATUS			current
		DESCRIPTION
				"TYPE: - Display
				 PAGE: - Blackish/Black
					Alarm  cmdID= 1235  format=   "
		::= { iqhip00CmdEntry 1235 }


	iqhip00TemporalControlBlackFailCount OBJECT-TYPE
		SYNTAX		INTEGER
		MAX-ACCESS		read-write
		STATUS			current
		DESCRIPTION
				"TYPE: - Number
				 PAGE: - Blackish/Black
					Fail Count  cmdID= 1232  min= 0  max= 16000  step= 1  format= %0.0f  div_scale= 1
					Min = 0  Max = 16000  Step = 1 "
		::= { iqhip00CmdEntry 1232 }


	iqhip00TemporalControlBlackWarningCount OBJECT-TYPE
		SYNTAX		INTEGER
		MAX-ACCESS		read-write
		STATUS			current
		DESCRIPTION
				"TYPE: - Number
				 PAGE: - Blackish/Black
					Warning Count  cmdID= 1233  min= 0  max= 16000  step= 1  format= %0.0f  div_scale= 1
					Min = 0  Max = 16000  Step = 1 "
		::= { iqhip00CmdEntry 1233 }


	iqhip00TemporalControlBlackFailHoldCount OBJECT-TYPE
		SYNTAX		INTEGER
		MAX-ACCESS		read-write
		STATUS			current
		DESCRIPTION
				"TYPE: - Number
				 PAGE: - Blackish/Black
					Fail Hold Count  cmdID= 1234  min= 0  max= 16000  step= 1  format= %0.0f  div_scale= 1
					Min = 0  Max = 16000  Step = 1 "
		::= { iqhip00CmdEntry 1234 }


	iqhip00TemporalControlBlackResetAlarm OBJECT-TYPE
		SYNTAX		INTEGER { noAction(0),val_Reset_Alarm(1) }
		MAX-ACCESS		read-write
		STATUS			current
		DESCRIPTION
				"TYPE: - Button
				 PAGE: - Blackish/Black
					Reset Alarm  cmdID= 1243  value= 1  "
		::= { iqhip00CmdEntry 1243 }


	iqhip00VideoMonitorAveragePictureLvlDisplayTimeout OBJECT-TYPE
		SYNTAX		RollCallString
		MAX-ACCESS		read-only
		STATUS			current
		DESCRIPTION
				"TYPE: - Display
				 PAGE: - Blackish/Black
					Display Timeout  cmdID= 1290  format=   "
		::= { iqhip00CmdEntry 1290 }


	iqhip00VideoMonitorAveragePictureLvlHyperionDisplayEn OBJECT-TYPE
		SYNTAX		INTEGER {
							val_Display_Off(0),
							val_Blackish_Black(1),
							val_Stillish_Freeze(2),
							val_Video_Monitor(3),
							val_Closed_Caption(4),
							val_Timecode(5),
							val_User_Anc_Det(6),
							val_Audio_Level_Det(7),
							val_Audio_Level_Ind(8),
							val_Audio_Likeness_Det(9),
							val_UMID(10),
							val_PID(11)
							}
		MAX-ACCESS		read-write
		STATUS			current
		DESCRIPTION
				"TYPE: - RadiobuttonList
				 PAGE: - Blackish/Black
					Hyperion Display En  cmdID= 1221
					Display Off  value= 0
					Blackish/Black  value= 1
					Hyperion Disp En  cmdID= 1221
					Display Off  value= 0
					Blackish/Black  value= 1
					Stillish/Freeze  value= 2
					Video Monitor  value= 3
					Closed Caption  value= 4
					Timecode  value= 5
					User Anc Det.  value= 6
					Audio Level Det  value= 7
					Audio Level Ind  value= 8
					Audio Likeness Det  value= 9
					UMID  value= 10
					PID  value= 11  "
		::= { iqhip00CmdEntry 1221 }


	iqhip00HyperionFreezeStillishStillishLevel OBJECT-TYPE
		SYNTAX		RollCallString
		MAX-ACCESS		read-only
		STATUS			current
		DESCRIPTION
				"TYPE: - Display
				 PAGE: - Freeze/Stillish
					Stillish Level  cmdID= 1200  format=   "
		::= { iqhip00CmdEntry 1200 }


	iqhip00HyperionFreezeStillishMaxLevelThres OBJECT-TYPE
		SYNTAX		INTEGER
		MAX-ACCESS		read-write
		STATUS			current
		DESCRIPTION
				"TYPE: - Number
				 PAGE: - Freeze/Stillish
					Max Level Thres  cmdID= 1203  min= 0  max= 100  step= 1  format= %0.0f  div_scale= 1
					Min = 0  Max = 100  Step = 1 "
		::= { iqhip00CmdEntry 1203 }


	iqhip00TemporalControlStillishEnableAlarm OBJECT-TYPE
		SYNTAX		INTEGER { disable(0), enable(1) }
		MAX-ACCESS		read-write
		STATUS			current
		DESCRIPTION
				"TYPE: - Checkbox
				 PAGE: - Freeze/Stillish
					Enable Alarm  cmdID= 1214 "
		::= { iqhip00CmdEntry 1214 }


	iqhip00TemporalControlStillishAlarm OBJECT-TYPE
		SYNTAX		RollCallString
		MAX-ACCESS		read-only
		STATUS			current
		DESCRIPTION
				"TYPE: - Display
				 PAGE: - Freeze/Stillish
					Alarm  cmdID= 1218  format=   "
		::= { iqhip00CmdEntry 1218 }


	iqhip00TemporalControlStillishFailCount OBJECT-TYPE
		SYNTAX		INTEGER
		MAX-ACCESS		read-write
		STATUS			current
		DESCRIPTION
				"TYPE: - Number
				 PAGE: - Freeze/Stillish
					Fail Count  cmdID= 1215  min= 0  max= 16000  step= 1  format= %0.0f  div_scale= 1
					Min = 0  Max = 16000  Step = 1 "
		::= { iqhip00CmdEntry 1215 }


	iqhip00TemporalControlStillishWarningCount OBJECT-TYPE
		SYNTAX		INTEGER
		MAX-ACCESS		read-write
		STATUS			current
		DESCRIPTION
				"TYPE: - Number
				 PAGE: - Freeze/Stillish
					Warning Count  cmdID= 1216  min= 0  max= 16000  step= 1  format= %0.0f  div_scale= 1
					Min = 0  Max = 16000  Step = 1 "
		::= { iqhip00CmdEntry 1216 }


	iqhip00TemporalControlStillishFailHoldCount OBJECT-TYPE
		SYNTAX		INTEGER
		MAX-ACCESS		read-write
		STATUS			current
		DESCRIPTION
				"TYPE: - Number
				 PAGE: - Freeze/Stillish
					Fail Hold Count  cmdID= 1217  min= 0  max= 16000  step= 1  format= %0.0f  div_scale= 1
					Min = 0  Max = 16000  Step = 1 "
		::= { iqhip00CmdEntry 1217 }


	iqhip00TemporalControlStillishResetAlarm OBJECT-TYPE
		SYNTAX		INTEGER { noAction(0),val_Reset_Alarm(1) }
		MAX-ACCESS		read-write
		STATUS			current
		DESCRIPTION
				"TYPE: - Button
				 PAGE: - Freeze/Stillish
					Reset Alarm  cmdID= 1219  value= 1  "
		::= { iqhip00CmdEntry 1219 }


	iqhip00TemporalControlFreezeEnableAlarm OBJECT-TYPE
		SYNTAX		INTEGER { disable(0), enable(1) }
		MAX-ACCESS		read-write
		STATUS			current
		DESCRIPTION
				"TYPE: - Checkbox
				 PAGE: - Freeze/Stillish
					Enable Alarm  cmdID= 1655 "
		::= { iqhip00CmdEntry 1655 }

	iqhip00TemporalControlFreezeTolerance OBJECT-TYPE
		SYNTAX		INTEGER
		MAX-ACCESS		read-write
		STATUS			current
		DESCRIPTION
				"TYPE: - Number
				 PAGE: - Freeze/Stillish
					Freeze Tolerance (number of frames)  cmdID= 1656  min= 0  max= 10  step= 1  format= %0.0f  div_scale= 1
					Min = 0  Max = 10  Step = 1 "
		::= { iqhip00CmdEntry 1656 }


	iqhip00TemporalControlFreezeAlarm OBJECT-TYPE
		SYNTAX		RollCallString
		MAX-ACCESS		read-only
		STATUS			current
		DESCRIPTION
				"TYPE: - Display
				 PAGE: - Freeze/Stillish
					Alarm  cmdID= 1653  format=   "
		::= { iqhip00CmdEntry 1653 }


	iqhip00TemporalControlFreezeFailCount OBJECT-TYPE
		SYNTAX		INTEGER
		MAX-ACCESS		read-write
		STATUS			current
		DESCRIPTION
				"TYPE: - Number
				 PAGE: - Freeze/Stillish
					Fail Count  cmdID= 1650  min= 2  max= 16000  step= 1  format= %0.0f  div_scale= 1
					Min = 2  Max = 16000  Step = 1 "
		::= { iqhip00CmdEntry 1650 }


	iqhip00TemporalControlFreezeWarningCount OBJECT-TYPE
		SYNTAX		INTEGER
		MAX-ACCESS		read-write
		STATUS			current
		DESCRIPTION
				"TYPE: - Number
				 PAGE: - Freeze/Stillish
					Warning Count  cmdID= 1651  min= 2  max= 16000  step= 1  format= %0.0f  div_scale= 1
					Min = 2  Max = 16000  Step = 1 "
		::= { iqhip00CmdEntry 1651 }


	iqhip00TemporalControlFreezeFailHoldCount OBJECT-TYPE
		SYNTAX		INTEGER
		MAX-ACCESS		read-write
		STATUS			current
		DESCRIPTION
				"TYPE: - Number
				 PAGE: - Freeze/Stillish
					Fail Hold Count  cmdID= 1652  min= 1  max= 16000  step= 1  format= %0.0f  div_scale= 1
					Min = 1  Max = 16000  Step = 1 "
		::= { iqhip00CmdEntry 1652 }


	iqhip00TemporalControlFreezeResetAlarm OBJECT-TYPE
		SYNTAX		INTEGER { noAction(0),val_Reset_Alarm(1) }
		MAX-ACCESS		read-write
		STATUS			current
		DESCRIPTION
				"TYPE: - Button
				 PAGE: - Freeze/Stillish
					Reset Alarm  cmdID= 1654  value= 1  "
		::= { iqhip00CmdEntry 1654 }


	iqhip00VideoMonitorAveragePictureLvlEnableAlarm OBJECT-TYPE
		SYNTAX		INTEGER { disable(0), enable(1) }
		MAX-ACCESS		read-write
		STATUS			current
		DESCRIPTION
				"TYPE: - Checkbox
				 PAGE: - Video Monitor
					Enable Alarm  cmdID= 1326 "
		::= { iqhip00CmdEntry 1326 }


	iqhip00VideoMonitorAveragePictureLvl OBJECT-TYPE
		SYNTAX		RollCallString
		MAX-ACCESS		read-only
		STATUS			current
		DESCRIPTION
				"TYPE: - Display
				 PAGE: - Video Monitor
					Average Picture Lvl  cmdID= 1320  format=   "
		::= { iqhip00CmdEntry 1320 }


	iqhip00VideoMonitorAveragePictureLvlMaxLoggingThres OBJECT-TYPE
		SYNTAX		INTEGER
		MAX-ACCESS		read-write
		STATUS			current
		DESCRIPTION
				"TYPE: - Number
				 PAGE: - Video Monitor
					Max Logging Thres  cmdID= 1324  min= 0  max= 100  step= 1  format= %0.0f  div_scale= 1
					Min = 0  Max = 100  Step = 1 "
		::= { iqhip00CmdEntry 1324 }


	iqhip00VideoMonitorAveragePictureLvlMinLoggingThres OBJECT-TYPE
		SYNTAX		INTEGER
		MAX-ACCESS		read-write
		STATUS			current
		DESCRIPTION
				"TYPE: - Number
				 PAGE: - Video Monitor
					Min Logging Thres  cmdID= 1323  min= 0  max= 100  step= 1  format= %0.0f  div_scale= 1
					Min = 0  Max = 100  Step = 1 "
		::= { iqhip00CmdEntry 1323 }


	iqhip00LumaVideoLevelOverloadStatus OBJECT-TYPE
		SYNTAX		RollCallString
		MAX-ACCESS		read-only
		STATUS			current
		DESCRIPTION
				"TYPE: - Display
				 PAGE: - Video Monitor
					Status  cmdID= 1343  format=   "
		::= { iqhip00CmdEntry 1343 }


	iqhip00LumaVideoLevelOverloadMaximumReading OBJECT-TYPE
		SYNTAX		RollCallString
		MAX-ACCESS		read-only
		STATUS			current
		DESCRIPTION
				"TYPE: - Display
				 PAGE: - Video Monitor
					Maximum Reading  cmdID= 1352  format=   "
		::= { iqhip00CmdEntry 1352 }


	iqhip00LumaVideoLevelOverloadEnableAlarm OBJECT-TYPE
		SYNTAX		INTEGER { disable(0), enable(1) }
		MAX-ACCESS		read-write
		STATUS			current
		DESCRIPTION
				"TYPE: - Checkbox
				 PAGE: - Video Monitor
					Enable Alarm   cmdID= 1349 "
		::= { iqhip00CmdEntry 1349 }


	iqhip00LumaVideoLevelOverloadOverloadThreshold OBJECT-TYPE
		SYNTAX		INTEGER
		MAX-ACCESS		read-write
		STATUS			current
		DESCRIPTION
				"TYPE: - Number
				 PAGE: - Video Monitor
					Overload Threshold  cmdID= 1341  min= 0  max= 1023  step= 1  format= %0.0f  div_scale= 1
					Min = 0  Max = 1023  Step = 1 "
		::= { iqhip00CmdEntry 1341 }


	iqhip00LumaVideoLevelOverloadAvePicAboveThres OBJECT-TYPE
		SYNTAX		INTEGER
		MAX-ACCESS		read-write
		STATUS			current
		DESCRIPTION
				"TYPE: - Number
				 PAGE: - Video Monitor
					Ave Pic Above Thres  cmdID= 1356  min= 0  max= 99  step= 1  format= %0.0f  div_scale= 1
					Min = 0  Max = 99  Step = 1 "
		::= { iqhip00CmdEntry 1356 }


	iqhip00LumaVideoLevelUnderloadStatus OBJECT-TYPE
		SYNTAX		RollCallString
		MAX-ACCESS		read-only
		STATUS			current
		DESCRIPTION
				"TYPE: - Display
				 PAGE: - Video Monitor
					Status  cmdID= 1347  format=   "
		::= { iqhip00CmdEntry 1347 }


	iqhip00LumaVideoLevelUnderloadMinimumReading OBJECT-TYPE
		SYNTAX		RollCallString
		MAX-ACCESS		read-only
		STATUS			current
		DESCRIPTION
				"TYPE: - Display
				 PAGE: - Video Monitor
					Minimum Reading  cmdID= 1353  format=   "
		::= { iqhip00CmdEntry 1353 }


	iqhip00LumaVideoLevelUnderloadEnableAlarm OBJECT-TYPE
		SYNTAX		INTEGER { disable(0), enable(1) }
		MAX-ACCESS		read-write
		STATUS			current
		DESCRIPTION
				"TYPE: - Checkbox
				 PAGE: - Video Monitor
					Enable Alarm  cmdID= 1348 "
		::= { iqhip00CmdEntry 1348 }


	iqhip00LumaVideoLevelUnderloadUnderloadThreshold OBJECT-TYPE
		SYNTAX		INTEGER
		MAX-ACCESS		read-write
		STATUS			current
		DESCRIPTION
				"TYPE: - Number
				 PAGE: - Video Monitor
					Underload Threshold  cmdID= 1345  min= 0  max= 1023  step= 1  format= %0.0f  div_scale= 1
					Min = 0  Max = 1023  Step = 1 "
		::= { iqhip00CmdEntry 1345 }


	iqhip00LumaVideoLevelUnderloadAvePicBelowThres OBJECT-TYPE
		SYNTAX		INTEGER
		MAX-ACCESS		read-write
		STATUS			current
		DESCRIPTION
				"TYPE: - Number
				 PAGE: - Video Monitor
					Ave Pic Below Thres  cmdID= 1357  min= 0  max= 99  step= 1  format= %0.0f  div_scale= 1
					Min = 0  Max = 99  Step = 1 "
		::= { iqhip00CmdEntry 1357 }


	iqhip00ChromaVideoLevelOverloadStatus OBJECT-TYPE
		SYNTAX		RollCallString
		MAX-ACCESS		read-only
		STATUS			current
		DESCRIPTION
				"TYPE: - Display
				 PAGE: - Video Monitor
					Status  cmdID= 1342  format=   "
		::= { iqhip00CmdEntry 1342 }


	iqhip00ChromaVideoLevelOverloadMaximumReading OBJECT-TYPE
		SYNTAX		RollCallString
		MAX-ACCESS		read-only
		STATUS			current
		DESCRIPTION
				"TYPE: - Display
				 PAGE: - Video Monitor
					Maximum Reading  cmdID= 1354  format=   "
		::= { iqhip00CmdEntry 1354 }


	iqhip00ChromaVideoLevelOverloadEnableAlarm OBJECT-TYPE
		SYNTAX		INTEGER { disable(0), enable(1) }
		MAX-ACCESS		read-write
		STATUS			current
		DESCRIPTION
				"TYPE: - Checkbox
				 PAGE: - Video Monitor
					Enable Alarm  cmdID= 1351 "
		::= { iqhip00CmdEntry 1351 }


	iqhip00ChromaVideoLevelOverloadOverloadThreshold OBJECT-TYPE
		SYNTAX		INTEGER
		MAX-ACCESS		read-write
		STATUS			current
		DESCRIPTION
				"TYPE: - Number
				 PAGE: - Video Monitor
					Overload Threshold  cmdID= 1340  min= 0  max= 1023  step= 1  format= %0.0f  div_scale= 1
					Min = 0  Max = 1023  Step = 1 "
		::= { iqhip00CmdEntry 1340 }


	iqhip00ChromaVideoLevelOverloadAvePicAboveThres OBJECT-TYPE
		SYNTAX		INTEGER
		MAX-ACCESS		read-write
		STATUS			current
		DESCRIPTION
				"TYPE: - Number
				 PAGE: - Video Monitor
					Ave Pic Above Thres  cmdID= 1358  min= 0  max= 99  step= 1  format= %0.0f  div_scale= 1
					Min = 0  Max = 99  Step = 1 "
		::= { iqhip00CmdEntry 1358 }


	iqhip00ChromaVideoLevelUnderloadStatus OBJECT-TYPE
		SYNTAX		RollCallString
		MAX-ACCESS		read-only
		STATUS			current
		DESCRIPTION
				"TYPE: - Display
				 PAGE: - Video Monitor
					Status  cmdID= 1346  format=   "
		::= { iqhip00CmdEntry 1346 }


	iqhip00ChromaVideoLevelUnderloadMinimumReading OBJECT-TYPE
		SYNTAX		RollCallString
		MAX-ACCESS		read-only
		STATUS			current
		DESCRIPTION
				"TYPE: - Display
				 PAGE: - Video Monitor
					Minimum Reading  cmdID= 1355  format=   "
		::= { iqhip00CmdEntry 1355 }


	iqhip00ChromaVideoLevelUnderloadEnableAlarm OBJECT-TYPE
		SYNTAX		INTEGER { disable(0), enable(1) }
		MAX-ACCESS		read-write
		STATUS			current
		DESCRIPTION
				"TYPE: - Checkbox
				 PAGE: - Video Monitor
					Enable Alarm  cmdID= 1350 "
		::= { iqhip00CmdEntry 1350 }


	iqhip00ChromaVideoLevelUnderloadUnderloadThreshold OBJECT-TYPE
		SYNTAX		INTEGER
		MAX-ACCESS		read-write
		STATUS			current
		DESCRIPTION
				"TYPE: - Number
				 PAGE: - Video Monitor
					Underload Threshold  cmdID= 1344  min= 0  max= 1023  step= 1  format= %0.0f  div_scale= 1
					Min = 0  Max = 1023  Step = 1 "
		::= { iqhip00CmdEntry 1344 }


	iqhip00ChromaVideoLevelUnderloadAvePicBelowThres OBJECT-TYPE
		SYNTAX		INTEGER
		MAX-ACCESS		read-write
		STATUS			current
		DESCRIPTION
				"TYPE: - Number
				 PAGE: - Video Monitor
					Ave Pic Below Thres  cmdID= 1359  min= 0  max= 99  step= 1  format= %0.0f  div_scale= 1
					Min = 0  Max = 99  Step = 1 "
		::= { iqhip00CmdEntry 1359 }


	iqhip00HyperionVideoMonitorChromaBitDepth OBJECT-TYPE
		SYNTAX		RollCallString
		MAX-ACCESS		read-only
		STATUS			current
		DESCRIPTION
				"TYPE: - Display
				 PAGE: - Video Monitor
					Chroma Bit Depth  cmdID= 1330  format=   "
		::= { iqhip00CmdEntry 1330 }


	iqhip00HyperionVideoMonitorLumaBitDepth OBJECT-TYPE
		SYNTAX		RollCallString
		MAX-ACCESS		read-only
		STATUS			current
		DESCRIPTION
				"TYPE: - Display
				 PAGE: - Video Monitor
					Luma Bit Depth  cmdID= 1331  format=   "
		::= { iqhip00CmdEntry 1331 }


	iqhip00ClosedCaptionsCCCEA608BState OBJECT-TYPE
		SYNTAX		RollCallString
		MAX-ACCESS		read-only
		STATUS			current
		DESCRIPTION
				"TYPE: - Display
				 PAGE: - Closed Captions
					State  cmdID= 1368  format=   "
		::= { iqhip00CmdEntry 1368 }


	iqhip00ClosedCaptionsCCCEA608BTitle1 OBJECT-TYPE
		SYNTAX		RollCallString
		MAX-ACCESS		read-only
		STATUS			current
		DESCRIPTION
				"TYPE: - Display
				 PAGE: - Closed Captions
					Title 1  cmdID= 1371  format=   "
		::= { iqhip00CmdEntry 1371 }


	iqhip00ClosedCaptionsCCCEA608BTitle2 OBJECT-TYPE
		SYNTAX		RollCallString
		MAX-ACCESS		read-only
		STATUS			current
		DESCRIPTION
				"TYPE: - Display
				 PAGE: - Closed Captions
					Title 2  cmdID= 1372  format=   "
		::= { iqhip00CmdEntry 1372 }


	iqhip00ClosedCaptionsCCCEA708BField1 OBJECT-TYPE
		SYNTAX		RollCallString
		MAX-ACCESS		read-only
		STATUS			current
		DESCRIPTION
				"TYPE: - Display
				 PAGE: - Closed Captions
					Field 1  cmdID= 1366  format=   "
		::= { iqhip00CmdEntry 1366 }


	iqhip00ClosedCaptionsCCCEA708BField2 OBJECT-TYPE
		SYNTAX		RollCallString
		MAX-ACCESS		read-only
		STATUS			current
		DESCRIPTION
				"TYPE: - Display
				 PAGE: - Closed Captions
					Field 2  cmdID= 1367  format=   "
		::= { iqhip00CmdEntry 1367 }


	iqhip00ClosedCaptionsTemporalControlEnableAlarm OBJECT-TYPE
		SYNTAX		INTEGER { disable(0), enable(1) }
		MAX-ACCESS		read-write
		STATUS			current
		DESCRIPTION
				"TYPE: - Checkbox
				 PAGE: - Closed Captions
					Enable Alarm  cmdID= 1370 "
		::= { iqhip00CmdEntry 1370 }


	iqhip00ClosedCaptionsTemporalControlAlarm OBJECT-TYPE
		SYNTAX		RollCallString
		MAX-ACCESS		read-only
		STATUS			current
		DESCRIPTION
				"TYPE: - Display
				 PAGE: - Closed Captions
					Alarm  cmdID= 1365  format=   "
		::= { iqhip00CmdEntry 1365 }


	iqhip00ClosedCaptionsTemporalControlFailCount OBJECT-TYPE
		SYNTAX		INTEGER
		MAX-ACCESS		read-write
		STATUS			current
		DESCRIPTION
				"TYPE: - Number
				 PAGE: - Closed Captions
					Fail Count  cmdID= 1362  min= 0  max= 16000  step= 1  format= %0.0f  div_scale= 1
					Min = 0  Max = 16000  Step = 1 "
		::= { iqhip00CmdEntry 1362 }


	iqhip00ClosedCaptionsTemporalControlWarningCount OBJECT-TYPE
		SYNTAX		INTEGER
		MAX-ACCESS		read-write
		STATUS			current
		DESCRIPTION
				"TYPE: - Number
				 PAGE: - Closed Captions
					Warning Count  cmdID= 1363  min= 0  max= 16000  step= 1  format= %0.0f  div_scale= 1
					Min = 0  Max = 16000  Step = 1 "
		::= { iqhip00CmdEntry 1363 }


	iqhip00ClosedCaptionsTemporalControlFailHoldCount OBJECT-TYPE
		SYNTAX		INTEGER
		MAX-ACCESS		read-write
		STATUS			current
		DESCRIPTION
				"TYPE: - Number
				 PAGE: - Closed Captions
					Fail Hold Count  cmdID= 1364  min= 0  max= 16000  step= 1  format= %0.0f  div_scale= 1
					Min = 0  Max = 16000  Step = 1 "
		::= { iqhip00CmdEntry 1364 }


	iqhip00ClosedCaptionsTemporalControlResetAlarm OBJECT-TYPE
		SYNTAX		INTEGER { noAction(0),val_Reset_Alarm(1) }
		MAX-ACCESS		read-write
		STATUS			current
		DESCRIPTION
				"TYPE: - Button
				 PAGE: - Closed Captions
					Reset Alarm  cmdID= 1369  value= 1  "
		::= { iqhip00CmdEntry 1369 }


	iqhip00AncillaryDataContentAdvisoryEnableAlarm OBJECT-TYPE
		SYNTAX		INTEGER { disable(0), enable(1) }
		MAX-ACCESS		read-write
		STATUS			current
		DESCRIPTION
				"TYPE: - Checkbox
				 PAGE: - Ancillary Data
					Enable Alarm  cmdID= 1402 "
		::= { iqhip00CmdEntry 1402 }


	iqhip00AncillaryDataContentAdvisorySystem OBJECT-TYPE
		SYNTAX		RollCallString
		MAX-ACCESS		read-only
		STATUS			current
		DESCRIPTION
				"TYPE: - Display
				 PAGE: - Ancillary Data
					System  cmdID= 1400  format=   "
		::= { iqhip00CmdEntry 1400 }


	iqhip00AncillaryDataContentAdvisoryRating OBJECT-TYPE
		SYNTAX		RollCallString
		MAX-ACCESS		read-only
		STATUS			current
		DESCRIPTION
				"TYPE: - Display
				 PAGE: - Ancillary Data
					Rating  cmdID= 1401  format=   "
		::= { iqhip00CmdEntry 1401 }


	iqhip00TimeCodeAncTimeCodeEnableAlarm OBJECT-TYPE
		SYNTAX		INTEGER { disable(0), enable(1) }
		MAX-ACCESS		read-write
		STATUS			current
		DESCRIPTION
				"TYPE: - Checkbox
				 PAGE: - Ancillary Data
					Enable Alarm  cmdID= 1337 "
		::= { iqhip00CmdEntry 1337 }


	iqhip00TimeCodeAncTimeCodeField1 OBJECT-TYPE
		SYNTAX		RollCallString
		MAX-ACCESS		read-only
		STATUS			current
		DESCRIPTION
				"TYPE: - Display
				 PAGE: - Ancillary Data
					Field 1  cmdID= 1333  format=   "
		::= { iqhip00CmdEntry 1333 }


	iqhip00TimeCodeAncTimeCodeField2 OBJECT-TYPE
		SYNTAX		RollCallString
		MAX-ACCESS		read-only
		STATUS			current
		DESCRIPTION
				"TYPE: - Display
				 PAGE: - Ancillary Data
					Field 2  cmdID= 1334  format=   "
		::= { iqhip00CmdEntry 1334 }


	iqhip00TimeCodeVITCEnableAlarm OBJECT-TYPE
		SYNTAX		INTEGER { disable(0), enable(1) }
		MAX-ACCESS		read-write
		STATUS			current
		DESCRIPTION
				"TYPE: - Checkbox
				 PAGE: - Ancillary Data
					Enable Alarm  cmdID= 1802 "
		::= { iqhip00CmdEntry 1802 }


	iqhip00TimeCodeVITCField1 OBJECT-TYPE
		SYNTAX		RollCallString
		MAX-ACCESS		read-only
		STATUS			current
		DESCRIPTION
				"TYPE: - Display
				 PAGE: - Ancillary Data
					Field 1  cmdID= 1800  format=   "
		::= { iqhip00CmdEntry 1800 }


	iqhip00TimeCodeVITCField2 OBJECT-TYPE
		SYNTAX		RollCallString
		MAX-ACCESS		read-only
		STATUS			current
		DESCRIPTION
				"TYPE: - Display
				 PAGE: - Ancillary Data
					Field 2  cmdID= 1801  format=   "
		::= { iqhip00CmdEntry 1801 }


	iqhip00AncillaryDataTimeCodeCurrentTimeCode OBJECT-TYPE
		SYNTAX		RollCallString
		MAX-ACCESS		read-only
		STATUS			current
		DESCRIPTION
				"TYPE: - Display
				 PAGE: - Ancillary Data
					Current Time Code  cmdID= 1338  format=   "
		::= { iqhip00CmdEntry 1338 }


	iqhip00AncillaryDataTimeCodeSDTimeCodeSel OBJECT-TYPE
		SYNTAX		INTEGER {
							val_Auto(0),
							val_VITC(1),
							val_Anc(2)
							}
		MAX-ACCESS		read-write
		STATUS			current
		DESCRIPTION
				"TYPE: - RadiobuttonList
				 PAGE: - Ancillary Data
					SD Time Code Sel  cmdID= 1820
					Auto  value= 0
					VITC  value= 1
					Anc  value= 2  "
		::= { iqhip00CmdEntry 1820 }


	iqhip00AncillaryDataUserAncDet1EnableAlarm OBJECT-TYPE
		SYNTAX		INTEGER { disable(0), enable(1) }
		MAX-ACCESS		read-write
		STATUS			current
		DESCRIPTION
				"TYPE: - Checkbox
				 PAGE: - Ancillary Data
					Enable Alarm  cmdID= 1390 "
		::= { iqhip00CmdEntry 1390 }


	iqhip00AncillaryDataUserAncDet1DIDType OBJECT-TYPE
		SYNTAX		INTEGER {
							val_Type_1(1),
							val_Type_2(0)
							}
		MAX-ACCESS		read-write
		STATUS			current
		DESCRIPTION
				"TYPE: - RadiobuttonList
				 PAGE: - Ancillary Data
					DID Type  cmdID= 1382
					Type 1  value= 1
					Type 2  value= 0  "
		::= { iqhip00CmdEntry 1382 }


	iqhip00AncillaryDataUserAncDet1DIDselect OBJECT-TYPE
		SYNTAX		INTEGER
		MAX-ACCESS		read-write
		STATUS			current
		DESCRIPTION
				"TYPE: - Number
				 PAGE: - Ancillary Data
					DID select  cmdID= 1380  min= 0  max= 255  step= 1  format= %0.0f  div_scale= 1
					Min = 0  Max = 255  Step = 1 "
		::= { iqhip00CmdEntry 1380 }


	iqhip00AncillaryDataUserAncDet1SDIDselect OBJECT-TYPE
		SYNTAX		INTEGER
		MAX-ACCESS		read-write
		STATUS			current
		DESCRIPTION
				"TYPE: - Number
				 PAGE: - Ancillary Data
					SDID select  cmdID= 1381  min= 0  max= 255  step= 1  format= %0.0f  div_scale= 1
					Min = 0  Max = 255  Step = 1 "
		::= { iqhip00CmdEntry 1381 }


	iqhip00AncillaryDataUserAncDet1Field1 OBJECT-TYPE
		SYNTAX		RollCallString
		MAX-ACCESS		read-only
		STATUS			current
		DESCRIPTION
				"TYPE: - Display
				 PAGE: - Ancillary Data
					Field 1  cmdID= 1386  format=   "
		::= { iqhip00CmdEntry 1386 }


	iqhip00AncillaryDataUserAncDet1Field2 OBJECT-TYPE
		SYNTAX		RollCallString
		MAX-ACCESS		read-only
		STATUS			current
		DESCRIPTION
				"TYPE: - Display
				 PAGE: - Ancillary Data
					Field 2  cmdID= 1387  format=   "
		::= { iqhip00CmdEntry 1387 }


	iqhip00AncillaryDataUserAncDet1Name OBJECT-TYPE
		SYNTAX		RollCallString
		MAX-ACCESS		read-write
		STATUS			current
		DESCRIPTION
				"TYPE: - Editstring
				 PAGE: - Ancillary Data
					Name  cmdID= 1391  "
		::= { iqhip00CmdEntry 1391 }


	iqhip00AncillaryDataUserAncDet2EnableAlarm OBJECT-TYPE
		SYNTAX		INTEGER { disable(0), enable(1) }
		MAX-ACCESS		read-write
		STATUS			current
		DESCRIPTION
				"TYPE: - Checkbox
				 PAGE: - Ancillary Data
					Enable Alarm  cmdID= 1392 "
		::= { iqhip00CmdEntry 1392 }


	iqhip00AncillaryDataUserAncDet2DIDType OBJECT-TYPE
		SYNTAX		INTEGER {
							val_Type_1(1),
							val_Type_2(0)
							}
		MAX-ACCESS		read-write
		STATUS			current
		DESCRIPTION
				"TYPE: - RadiobuttonList
				 PAGE: - Ancillary Data
					DID Type  cmdID= 1385
					Type 1  value= 1
					Type 2  value= 0  "
		::= { iqhip00CmdEntry 1385 }


	iqhip00AncillaryDataUserAncDet2DIDselect OBJECT-TYPE
		SYNTAX		INTEGER
		MAX-ACCESS		read-write
		STATUS			current
		DESCRIPTION
				"TYPE: - Number
				 PAGE: - Ancillary Data
					DID select  cmdID= 1383  min= 0  max= 255  step= 1  format= %0.0f  div_scale= 1
					Min = 0  Max = 255  Step = 1 "
		::= { iqhip00CmdEntry 1383 }


	iqhip00AncillaryDataUserAncDet2SDIDselect OBJECT-TYPE
		SYNTAX		INTEGER
		MAX-ACCESS		read-write
		STATUS			current
		DESCRIPTION
				"TYPE: - Number
				 PAGE: - Ancillary Data
					SDID select  cmdID= 1384  min= 0  max= 255  step= 1  format= %0.0f  div_scale= 1
					Min = 0  Max = 255  Step = 1 "
		::= { iqhip00CmdEntry 1384 }


	iqhip00AncillaryDataUserAncDet2Field1 OBJECT-TYPE
		SYNTAX		RollCallString
		MAX-ACCESS		read-only
		STATUS			current
		DESCRIPTION
				"TYPE: - Display
				 PAGE: - Ancillary Data
					Field 1  cmdID= 1388  format=   "
		::= { iqhip00CmdEntry 1388 }


	iqhip00AncillaryDataUserAncDet2Field2 OBJECT-TYPE
		SYNTAX		RollCallString
		MAX-ACCESS		read-only
		STATUS			current
		DESCRIPTION
				"TYPE: - Display
				 PAGE: - Ancillary Data
					Field 2  cmdID= 1389  format=   "
		::= { iqhip00CmdEntry 1389 }


	iqhip00AncillaryDataUserAncDet2Name OBJECT-TYPE
		SYNTAX		RollCallString
		MAX-ACCESS		read-write
		STATUS			current
		DESCRIPTION
				"TYPE: - Editstring
				 PAGE: - Ancillary Data
					Name  cmdID= 1393  "
		::= { iqhip00CmdEntry 1393 }


	iqhip00AncillaryDataWSSVIInputWSSPresence OBJECT-TYPE
		SYNTAX		RollCallString
		MAX-ACCESS		read-only
		STATUS			current
		DESCRIPTION
				"TYPE: - Display
				 PAGE: - Ancillary Data
					WSS Presence   cmdID= 1420  format=   "
		::= { iqhip00CmdEntry 1420 }


	iqhip00AncillaryDataWSSVIInputWSSEnableAlarm OBJECT-TYPE
		SYNTAX		INTEGER { disable(0), enable(1) }
		MAX-ACCESS		read-write
		STATUS			current
		DESCRIPTION
				"TYPE: - Checkbox
				 PAGE: - Ancillary Data
					WSS Enable Alarm  cmdID= 1421 "
		::= { iqhip00CmdEntry 1421 }


	iqhip00AncillaryDataWSSVIInputWSSData OBJECT-TYPE
		SYNTAX		RollCallString
		MAX-ACCESS		read-only
		STATUS			current
		DESCRIPTION
				"TYPE: - Display
				 PAGE: - Ancillary Data
					WSS Data  cmdID= 1425  format=   "
		::= { iqhip00CmdEntry 1425 }


	iqhip00AncillaryDataWSSVIInputWSSScanSys OBJECT-TYPE
		SYNTAX		RollCallString
		MAX-ACCESS		read-only
		STATUS			current
		DESCRIPTION
				"TYPE: - Display
				 PAGE: - Ancillary Data
					WSS Scan Sys  cmdID= 1426  format=   "
		::= { iqhip00CmdEntry 1426 }


	iqhip00AncillaryDataWSSVIInputWSSType OBJECT-TYPE
		SYNTAX		INTEGER {
							val_ETSI(1),
							val_AFD(2),
							val_AFD_and_ScanSys(3)
							}
		MAX-ACCESS		read-write
		STATUS			current
		DESCRIPTION
				"TYPE: - RadiobuttonList
				 PAGE: - Ancillary Data
					WSS Type  cmdID= 1424
					ETSI  value= 1
					AFD  value= 2
					AFD and ScanSys  value= 3  "
		::= { iqhip00CmdEntry 1424 }


	iqhip00AncillaryDataWSSVIInputVIPresence OBJECT-TYPE
		SYNTAX		RollCallString
		MAX-ACCESS		read-only
		STATUS			current
		DESCRIPTION
				"TYPE: - Display
				 PAGE: - Ancillary Data
					VI Presence   cmdID= 1422  format=   "
		::= { iqhip00CmdEntry 1422 }


	iqhip00AncillaryDataWSSVIInputVIEnableAlarm OBJECT-TYPE
		SYNTAX		INTEGER { disable(0), enable(1) }
		MAX-ACCESS		read-write
		STATUS			current
		DESCRIPTION
				"TYPE: - Checkbox
				 PAGE: - Ancillary Data
					VI Enable Alarm  cmdID= 1423 "
		::= { iqhip00CmdEntry 1423 }


	iqhip00AncillaryDataWSSVIInputVIType OBJECT-TYPE
		SYNTAX		INTEGER {
							val_SMPTE(1),
							val_AFD(2),
							val_Legacy_AFD(3),
							val_Legacy_AFD_and_SS(4)
							}
		MAX-ACCESS		read-write
		STATUS			current
		DESCRIPTION
				"TYPE: - RadiobuttonList
				 PAGE: - Ancillary Data
					VI Type  cmdID= 1427
					SMPTE  value= 1
					AFD  value= 2
					Legacy AFD  value= 3
					Legacy AFD and SS  value= 4  "
		::= { iqhip00CmdEntry 1427 }


	iqhip00AncillaryDataWSSVIInputVIData OBJECT-TYPE
		SYNTAX		RollCallString
		MAX-ACCESS		read-only
		STATUS			current
		DESCRIPTION
				"TYPE: - Display
				 PAGE: - Ancillary Data
					VI Data  cmdID= 1429  format=   "
		::= { iqhip00CmdEntry 1429 }


	iqhip00AncillaryDataWSSVIInputVIScanSys OBJECT-TYPE
		SYNTAX		RollCallString
		MAX-ACCESS		read-only
		STATUS			current
		DESCRIPTION
				"TYPE: - Display
				 PAGE: - Ancillary Data
					VI Scan Sys  cmdID= 1428  format=   "
		::= { iqhip00CmdEntry 1428 }


	iqhip00HyperionAudioDataActiveAudioCh OBJECT-TYPE
		SYNTAX		RollCallString
		MAX-ACCESS		read-only
		STATUS			current
		DESCRIPTION
				"TYPE: - Display
				 PAGE: - Audio Data
					Active Audio Ch  cmdID= 1332  format=   "
		::= { iqhip00CmdEntry 1332 }


	iqhip00AudioDataGroup1EnableAlarmCh1 OBJECT-TYPE
		SYNTAX		INTEGER { disable(0), enable(1) }
		MAX-ACCESS		read-write
		STATUS			current
		DESCRIPTION
				"TYPE: - Checkbox
				 PAGE: - Audio Data
					Enable Alarm Ch 1  cmdID= 1520 "
		::= { iqhip00CmdEntry 1520 }


	iqhip00AudioDataGroup1TypeCh1 OBJECT-TYPE
		SYNTAX		RollCallString
		MAX-ACCESS		read-only
		STATUS			current
		DESCRIPTION
				"TYPE: - Display
				 PAGE: - Audio Data
					Type Ch 1  cmdID= 1500  format=   "
		::= { iqhip00CmdEntry 1500 }


	iqhip00AudioDataGroup1BitdepthCh1 OBJECT-TYPE
		SYNTAX		RollCallString
		MAX-ACCESS		read-only
		STATUS			current
		DESCRIPTION
				"TYPE: - Display
				 PAGE: - Audio Data
					Bit depth Ch 1  cmdID= 1550  format=   "
		::= { iqhip00CmdEntry 1550 }


	iqhip00AudioDataGroup1EnableAlarmCh2 OBJECT-TYPE
		SYNTAX		INTEGER { disable(0), enable(1) }
		MAX-ACCESS		read-write
		STATUS			current
		DESCRIPTION
				"TYPE: - Checkbox
				 PAGE: - Audio Data
					Enable Alarm Ch 2  cmdID= 1521 "
		::= { iqhip00CmdEntry 1521 }


	iqhip00AudioDataGroup1TypeCh2 OBJECT-TYPE
		SYNTAX		RollCallString
		MAX-ACCESS		read-only
		STATUS			current
		DESCRIPTION
				"TYPE: - Display
				 PAGE: - Audio Data
					Type Ch 2  cmdID= 1501  format=   "
		::= { iqhip00CmdEntry 1501 }


	iqhip00AudioDataGroup1BitdepthCh2 OBJECT-TYPE
		SYNTAX		RollCallString
		MAX-ACCESS		read-only
		STATUS			current
		DESCRIPTION
				"TYPE: - Display
				 PAGE: - Audio Data
					Bit depth Ch2  cmdID= 1551  format=   "
		::= { iqhip00CmdEntry 1551 }


	iqhip00AudioDataGroup1EnableAlarmCh3 OBJECT-TYPE
		SYNTAX		INTEGER { disable(0), enable(1) }
		MAX-ACCESS		read-write
		STATUS			current
		DESCRIPTION
				"TYPE: - Checkbox
				 PAGE: - Audio Data
					Enable Alarm Ch 3  cmdID= 1522 "
		::= { iqhip00CmdEntry 1522 }


	iqhip00AudioDataGroup1TypeCh3 OBJECT-TYPE
		SYNTAX		RollCallString
		MAX-ACCESS		read-only
		STATUS			current
		DESCRIPTION
				"TYPE: - Display
				 PAGE: - Audio Data
					Type Ch 3  cmdID= 1502  format=   "
		::= { iqhip00CmdEntry 1502 }


	iqhip00AudioDataGroup1BitdepthCh3 OBJECT-TYPE
		SYNTAX		RollCallString
		MAX-ACCESS		read-only
		STATUS			current
		DESCRIPTION
				"TYPE: - Display
				 PAGE: - Audio Data
					Bit depth Ch3  cmdID= 1552  format=   "
		::= { iqhip00CmdEntry 1552 }


	iqhip00AudioDataGroup1EnableAlarmCh4 OBJECT-TYPE
		SYNTAX		INTEGER { disable(0), enable(1) }
		MAX-ACCESS		read-write
		STATUS			current
		DESCRIPTION
				"TYPE: - Checkbox
				 PAGE: - Audio Data
					Enable Alarm Ch 4  cmdID= 1523 "
		::= { iqhip00CmdEntry 1523 }


	iqhip00AudioDataGroup1TypeCh4 OBJECT-TYPE
		SYNTAX		RollCallString
		MAX-ACCESS		read-only
		STATUS			current
		DESCRIPTION
				"TYPE: - Display
				 PAGE: - Audio Data
					Type Ch 4  cmdID= 1503  format=   "
		::= { iqhip00CmdEntry 1503 }


	iqhip00AudioDataGroup1BitdepthCh4 OBJECT-TYPE
		SYNTAX		RollCallString
		MAX-ACCESS		read-only
		STATUS			current
		DESCRIPTION
				"TYPE: - Display
				 PAGE: - Audio Data
					Bit depth Ch4  cmdID= 1553  format=   "
		::= { iqhip00CmdEntry 1553 }


	iqhip00AudioDataGroup2EnableAlarmCh5 OBJECT-TYPE
		SYNTAX		INTEGER { disable(0), enable(1) }
		MAX-ACCESS		read-write
		STATUS			current
		DESCRIPTION
				"TYPE: - Checkbox
				 PAGE: - Audio Data
					Enable Alarm Ch 5  cmdID= 1524 "
		::= { iqhip00CmdEntry 1524 }


	iqhip00AudioDataGroup2TypeCh5 OBJECT-TYPE
		SYNTAX		RollCallString
		MAX-ACCESS		read-only
		STATUS			current
		DESCRIPTION
				"TYPE: - Display
				 PAGE: - Audio Data
					Type Ch 5  cmdID= 1504  format=   "
		::= { iqhip00CmdEntry 1504 }


	iqhip00AudioDataGroup2BitdepthCh5 OBJECT-TYPE
		SYNTAX		RollCallString
		MAX-ACCESS		read-only
		STATUS			current
		DESCRIPTION
				"TYPE: - Display
				 PAGE: - Audio Data
					Bit depth Ch 5  cmdID= 1554  format=   "
		::= { iqhip00CmdEntry 1554 }


	iqhip00AudioDataGroup2EnableAlarmCh6 OBJECT-TYPE
		SYNTAX		INTEGER { disable(0), enable(1) }
		MAX-ACCESS		read-write
		STATUS			current
		DESCRIPTION
				"TYPE: - Checkbox
				 PAGE: - Audio Data
					Enable Alarm Ch 6  cmdID= 1525 "
		::= { iqhip00CmdEntry 1525 }


	iqhip00AudioDataGroup2TypeCh6 OBJECT-TYPE
		SYNTAX		RollCallString
		MAX-ACCESS		read-only
		STATUS			current
		DESCRIPTION
				"TYPE: - Display
				 PAGE: - Audio Data
					Type Ch 6  cmdID= 1505  format=   "
		::= { iqhip00CmdEntry 1505 }


	iqhip00AudioDataGroup2BitdepthCh6 OBJECT-TYPE
		SYNTAX		RollCallString
		MAX-ACCESS		read-only
		STATUS			current
		DESCRIPTION
				"TYPE: - Display
				 PAGE: - Audio Data
					Bit depth Ch 6  cmdID= 1555  format=   "
		::= { iqhip00CmdEntry 1555 }


	iqhip00AudioDataGroup2EnableAlarmCh7 OBJECT-TYPE
		SYNTAX		INTEGER { disable(0), enable(1) }
		MAX-ACCESS		read-write
		STATUS			current
		DESCRIPTION
				"TYPE: - Checkbox
				 PAGE: - Audio Data
					Enable Alarm Ch 7  cmdID= 1526 "
		::= { iqhip00CmdEntry 1526 }


	iqhip00AudioDataGroup2TypeCh7 OBJECT-TYPE
		SYNTAX		RollCallString
		MAX-ACCESS		read-only
		STATUS			current
		DESCRIPTION
				"TYPE: - Display
				 PAGE: - Audio Data
					Type Ch 7  cmdID= 1506  format=   "
		::= { iqhip00CmdEntry 1506 }


	iqhip00AudioDataGroup2BitdepthCh7 OBJECT-TYPE
		SYNTAX		RollCallString
		MAX-ACCESS		read-only
		STATUS			current
		DESCRIPTION
				"TYPE: - Display
				 PAGE: - Audio Data
					Bit depth Ch 7  cmdID= 1556  format=   "
		::= { iqhip00CmdEntry 1556 }


	iqhip00AudioDataGroup2EnableAlarmCh8 OBJECT-TYPE
		SYNTAX		INTEGER { disable(0), enable(1) }
		MAX-ACCESS		read-write
		STATUS			current
		DESCRIPTION
				"TYPE: - Checkbox
				 PAGE: - Audio Data
					Enable Alarm Ch 8  cmdID= 1527 "
		::= { iqhip00CmdEntry 1527 }


	iqhip00AudioDataGroup2TypeCh8 OBJECT-TYPE
		SYNTAX		RollCallString
		MAX-ACCESS		read-only
		STATUS			current
		DESCRIPTION
				"TYPE: - Display
				 PAGE: - Audio Data
					Type Ch 8  cmdID= 1507  format=   "
		::= { iqhip00CmdEntry 1507 }


	iqhip00AudioDataGroup2BitdepthCh8 OBJECT-TYPE
		SYNTAX		RollCallString
		MAX-ACCESS		read-only
		STATUS			current
		DESCRIPTION
				"TYPE: - Display
				 PAGE: - Audio Data
					Bit depth Ch 8  cmdID= 1557  format=   "
		::= { iqhip00CmdEntry 1557 }


	iqhip00AudioDataGroup3EnableAlarmCh9 OBJECT-TYPE
		SYNTAX		INTEGER { disable(0), enable(1) }
		MAX-ACCESS		read-write
		STATUS			current
		DESCRIPTION
				"TYPE: - Checkbox
				 PAGE: - Audio Data
					Enable Alarm Ch 9  cmdID= 1528 "
		::= { iqhip00CmdEntry 1528 }


	iqhip00AudioDataGroup3TypeCh9 OBJECT-TYPE
		SYNTAX		RollCallString
		MAX-ACCESS		read-only
		STATUS			current
		DESCRIPTION
				"TYPE: - Display
				 PAGE: - Audio Data
					Type Ch 9  cmdID= 1508  format=   "
		::= { iqhip00CmdEntry 1508 }


	iqhip00AudioDataGroup3BitdepthCh9 OBJECT-TYPE
		SYNTAX		RollCallString
		MAX-ACCESS		read-only
		STATUS			current
		DESCRIPTION
				"TYPE: - Display
				 PAGE: - Audio Data
					Bit depth Ch 9  cmdID= 1558  format=   "
		::= { iqhip00CmdEntry 1558 }


	iqhip00AudioDataGroup3EnableAlarmCh10 OBJECT-TYPE
		SYNTAX		INTEGER { disable(0), enable(1) }
		MAX-ACCESS		read-write
		STATUS			current
		DESCRIPTION
				"TYPE: - Checkbox
				 PAGE: - Audio Data
					Enable Alarm Ch 10  cmdID= 1529 "
		::= { iqhip00CmdEntry 1529 }


	iqhip00AudioDataGroup3TypeCh10 OBJECT-TYPE
		SYNTAX		RollCallString
		MAX-ACCESS		read-only
		STATUS			current
		DESCRIPTION
				"TYPE: - Display
				 PAGE: - Audio Data
					Type Ch 10  cmdID= 1509  format=   "
		::= { iqhip00CmdEntry 1509 }


	iqhip00AudioDataGroup3BitdepthCh10 OBJECT-TYPE
		SYNTAX		RollCallString
		MAX-ACCESS		read-only
		STATUS			current
		DESCRIPTION
				"TYPE: - Display
				 PAGE: - Audio Data
					Bit depth Ch 10  cmdID= 1559  format=   "
		::= { iqhip00CmdEntry 1559 }


	iqhip00AudioDataGroup3EnableAlarmCh11 OBJECT-TYPE
		SYNTAX		INTEGER { disable(0), enable(1) }
		MAX-ACCESS		read-write
		STATUS			current
		DESCRIPTION
				"TYPE: - Checkbox
				 PAGE: - Audio Data
					Enable Alarm Ch 11  cmdID= 1530 "
		::= { iqhip00CmdEntry 1530 }


	iqhip00AudioDataGroup3TypeCh11 OBJECT-TYPE
		SYNTAX		RollCallString
		MAX-ACCESS		read-only
		STATUS			current
		DESCRIPTION
				"TYPE: - Display
				 PAGE: - Audio Data
					Type Ch 11  cmdID= 1510  format=   "
		::= { iqhip00CmdEntry 1510 }


	iqhip00AudioDataGroup3BitdepthCh11 OBJECT-TYPE
		SYNTAX		RollCallString
		MAX-ACCESS		read-only
		STATUS			current
		DESCRIPTION
				"TYPE: - Display
				 PAGE: - Audio Data
					Bit depth Ch 11  cmdID= 1560  format=   "
		::= { iqhip00CmdEntry 1560 }


	iqhip00AudioDataGroup3EnableAlarmCh12 OBJECT-TYPE
		SYNTAX		INTEGER { disable(0), enable(1) }
		MAX-ACCESS		read-write
		STATUS			current
		DESCRIPTION
				"TYPE: - Checkbox
				 PAGE: - Audio Data
					Enable Alarm Ch 12  cmdID= 1531 "
		::= { iqhip00CmdEntry 1531 }


	iqhip00AudioDataGroup3TypeCh12 OBJECT-TYPE
		SYNTAX		RollCallString
		MAX-ACCESS		read-only
		STATUS			current
		DESCRIPTION
				"TYPE: - Display
				 PAGE: - Audio Data
					Type Ch 12  cmdID= 1511  format=   "
		::= { iqhip00CmdEntry 1511 }


	iqhip00AudioDataGroup3BitdepthCh12 OBJECT-TYPE
		SYNTAX		RollCallString
		MAX-ACCESS		read-only
		STATUS			current
		DESCRIPTION
				"TYPE: - Display
				 PAGE: - Audio Data
					Bit depth Ch 12  cmdID= 1561  format=   "
		::= { iqhip00CmdEntry 1561 }


	iqhip00AudioDataGroup4EnableAlarmCh13 OBJECT-TYPE
		SYNTAX		INTEGER { disable(0), enable(1) }
		MAX-ACCESS		read-write
		STATUS			current
		DESCRIPTION
				"TYPE: - Checkbox
				 PAGE: - Audio Data
					Enable Alarm Ch 13  cmdID= 1532 "
		::= { iqhip00CmdEntry 1532 }


	iqhip00AudioDataGroup4TypeCh13 OBJECT-TYPE
		SYNTAX		RollCallString
		MAX-ACCESS		read-only
		STATUS			current
		DESCRIPTION
				"TYPE: - Display
				 PAGE: - Audio Data
					Type Ch 13  cmdID= 1512  format=   "
		::= { iqhip00CmdEntry 1512 }


	iqhip00AudioDataGroup4BitdepthCh13 OBJECT-TYPE
		SYNTAX		RollCallString
		MAX-ACCESS		read-only
		STATUS			current
		DESCRIPTION
				"TYPE: - Display
				 PAGE: - Audio Data
					Bit depth Ch 13  cmdID= 1562  format=   "
		::= { iqhip00CmdEntry 1562 }


	iqhip00AudioDataGroup4EnableAlarmCh14 OBJECT-TYPE
		SYNTAX		INTEGER { disable(0), enable(1) }
		MAX-ACCESS		read-write
		STATUS			current
		DESCRIPTION
				"TYPE: - Checkbox
				 PAGE: - Audio Data
					Enable Alarm Ch 14  cmdID= 1533 "
		::= { iqhip00CmdEntry 1533 }


	iqhip00AudioDataGroup4TypeCh14 OBJECT-TYPE
		SYNTAX		RollCallString
		MAX-ACCESS		read-only
		STATUS			current
		DESCRIPTION
				"TYPE: - Display
				 PAGE: - Audio Data
					Type Ch 14  cmdID= 1513  format=   "
		::= { iqhip00CmdEntry 1513 }


	iqhip00AudioDataGroup4BitdepthCh14 OBJECT-TYPE
		SYNTAX		RollCallString
		MAX-ACCESS		read-only
		STATUS			current
		DESCRIPTION
				"TYPE: - Display
				 PAGE: - Audio Data
					Bit depth Ch 14  cmdID= 1563  format=   "
		::= { iqhip00CmdEntry 1563 }


	iqhip00AudioDataGroup4EnableAlarmCh15 OBJECT-TYPE
		SYNTAX		INTEGER { disable(0), enable(1) }
		MAX-ACCESS		read-write
		STATUS			current
		DESCRIPTION
				"TYPE: - Checkbox
				 PAGE: - Audio Data
					Enable Alarm Ch 15  cmdID= 1534 "
		::= { iqhip00CmdEntry 1534 }


	iqhip00AudioDataGroup4TypeCh15 OBJECT-TYPE
		SYNTAX		RollCallString
		MAX-ACCESS		read-only
		STATUS			current
		DESCRIPTION
				"TYPE: - Display
				 PAGE: - Audio Data
					Type Ch 15  cmdID= 1514  format=   "
		::= { iqhip00CmdEntry 1514 }


	iqhip00AudioDataGroup4BitdepthCh15 OBJECT-TYPE
		SYNTAX		RollCallString
		MAX-ACCESS		read-only
		STATUS			current
		DESCRIPTION
				"TYPE: - Display
				 PAGE: - Audio Data
					Bit depth Ch 15  cmdID= 1564  format=   "
		::= { iqhip00CmdEntry 1564 }


	iqhip00AudioDataGroup4EnableAlarmCh16 OBJECT-TYPE
		SYNTAX		INTEGER { disable(0), enable(1) }
		MAX-ACCESS		read-write
		STATUS			current
		DESCRIPTION
				"TYPE: - Checkbox
				 PAGE: - Audio Data
					Enable Alarm Ch 16  cmdID= 1535 "
		::= { iqhip00CmdEntry 1535 }


	iqhip00AudioDataGroup4TypeCh16 OBJECT-TYPE
		SYNTAX		RollCallString
		MAX-ACCESS		read-only
		STATUS			current
		DESCRIPTION
				"TYPE: - Display
				 PAGE: - Audio Data
					Type Ch 16  cmdID= 1515  format=   "
		::= { iqhip00CmdEntry 1515 }


	iqhip00AudioDataGroup4BitdepthCh16 OBJECT-TYPE
		SYNTAX		RollCallString
		MAX-ACCESS		read-only
		STATUS			current
		DESCRIPTION
				"TYPE: - Display
				 PAGE: - Audio Data
					Bit depth Ch 16  cmdID= 1565  format=   "
		::= { iqhip00CmdEntry 1565 }


	iqhip00AudioDataDolbyEStatusEnableAlarmPair1 OBJECT-TYPE
		SYNTAX		INTEGER { disable(0), enable(1) }
		MAX-ACCESS		read-write
		STATUS			current
		DESCRIPTION
				"TYPE: - Checkbox
				 PAGE: - Audio Data
					Enable Alarm Pair 1  cmdID= 1490 "
		::= { iqhip00CmdEntry 1490 }


	iqhip00AudioDataDolbyEStatusStatusPair1 OBJECT-TYPE
		SYNTAX		RollCallString
		MAX-ACCESS		read-only
		STATUS			current
		DESCRIPTION
				"TYPE: - Display
				 PAGE: - Audio Data
					Status Pair 1  cmdID= 1480  format=   "
		::= { iqhip00CmdEntry 1480 }


	iqhip00AudioDataDolbyEStatusEnableAlarmPair2 OBJECT-TYPE
		SYNTAX		INTEGER { disable(0), enable(1) }
		MAX-ACCESS		read-write
		STATUS			current
		DESCRIPTION
				"TYPE: - Checkbox
				 PAGE: - Audio Data
					Enable Alarm Pair 2  cmdID= 1491 "
		::= { iqhip00CmdEntry 1491 }


	iqhip00AudioDataDolbyEStatusStatusPair2 OBJECT-TYPE
		SYNTAX		RollCallString
		MAX-ACCESS		read-only
		STATUS			current
		DESCRIPTION
				"TYPE: - Display
				 PAGE: - Audio Data
					Status Pair 2  cmdID= 1481  format=   "
		::= { iqhip00CmdEntry 1481 }


	iqhip00AudioDataDolbyEStatusEnableAlarmPair3 OBJECT-TYPE
		SYNTAX		INTEGER { disable(0), enable(1) }
		MAX-ACCESS		read-write
		STATUS			current
		DESCRIPTION
				"TYPE: - Checkbox
				 PAGE: - Audio Data
					Enable Alarm Pair 3  cmdID= 1492 "
		::= { iqhip00CmdEntry 1492 }


	iqhip00AudioDataDolbyEStatusStatusPair3 OBJECT-TYPE
		SYNTAX		RollCallString
		MAX-ACCESS		read-only
		STATUS			current
		DESCRIPTION
				"TYPE: - Display
				 PAGE: - Audio Data
					Status Pair 3  cmdID= 1482  format=   "
		::= { iqhip00CmdEntry 1482 }


	iqhip00AudioDataDolbyEStatusEnableAlarmPair4 OBJECT-TYPE
		SYNTAX		INTEGER { disable(0), enable(1) }
		MAX-ACCESS		read-write
		STATUS			current
		DESCRIPTION
				"TYPE: - Checkbox
				 PAGE: - Audio Data
					Enable Alarm Pair 4  cmdID= 1493 "
		::= { iqhip00CmdEntry 1493 }


	iqhip00AudioDataDolbyEStatusStatusPair4 OBJECT-TYPE
		SYNTAX		RollCallString
		MAX-ACCESS		read-only
		STATUS			current
		DESCRIPTION
				"TYPE: - Display
				 PAGE: - Audio Data
					Status Pair 4  cmdID= 1483  format=   "
		::= { iqhip00CmdEntry 1483 }


	iqhip00AudioDataDolbyEStatusEnableAlarmPair5 OBJECT-TYPE
		SYNTAX		INTEGER { disable(0), enable(1) }
		MAX-ACCESS		read-write
		STATUS			current
		DESCRIPTION
				"TYPE: - Checkbox
				 PAGE: - Audio Data
					Enable Alarm Pair 5  cmdID= 1494 "
		::= { iqhip00CmdEntry 1494 }


	iqhip00AudioDataDolbyEStatusStatusPair5 OBJECT-TYPE
		SYNTAX		RollCallString
		MAX-ACCESS		read-only
		STATUS			current
		DESCRIPTION
				"TYPE: - Display
				 PAGE: - Audio Data
					Status Pair 5  cmdID= 1484  format=   "
		::= { iqhip00CmdEntry 1484 }


	iqhip00AudioDataDolbyEStatusEnableAlarmPair6 OBJECT-TYPE
		SYNTAX		INTEGER { disable(0), enable(1) }
		MAX-ACCESS		read-write
		STATUS			current
		DESCRIPTION
				"TYPE: - Checkbox
				 PAGE: - Audio Data
					Enable Alarm Pair 6  cmdID= 1495 "
		::= { iqhip00CmdEntry 1495 }


	iqhip00AudioDataDolbyEStatusStatusPair6 OBJECT-TYPE
		SYNTAX		RollCallString
		MAX-ACCESS		read-only
		STATUS			current
		DESCRIPTION
				"TYPE: - Display
				 PAGE: - Audio Data
					Status Pair 6  cmdID= 1485  format=   "
		::= { iqhip00CmdEntry 1485 }


	iqhip00AudioDataDolbyEStatusEnableAlarmPair7 OBJECT-TYPE
		SYNTAX		INTEGER { disable(0), enable(1) }
		MAX-ACCESS		read-write
		STATUS			current
		DESCRIPTION
				"TYPE: - Checkbox
				 PAGE: - Audio Data
					Enable Alarm Pair 7  cmdID= 1496 "
		::= { iqhip00CmdEntry 1496 }


	iqhip00AudioDataDolbyEStatusStatusPair7 OBJECT-TYPE
		SYNTAX		RollCallString
		MAX-ACCESS		read-only
		STATUS			current
		DESCRIPTION
				"TYPE: - Display
				 PAGE: - Audio Data
					Status Pair 7  cmdID= 1486  format=   "
		::= { iqhip00CmdEntry 1486 }


	iqhip00AudioDataDolbyEStatusEnableAlarmPair8 OBJECT-TYPE
		SYNTAX		INTEGER { disable(0), enable(1) }
		MAX-ACCESS		read-write
		STATUS			current
		DESCRIPTION
				"TYPE: - Checkbox
				 PAGE: - Audio Data
					Enable Alarm Pair 8  cmdID= 1497 "
		::= { iqhip00CmdEntry 1497 }


	iqhip00AudioDataDolbyEStatusStatusPair8 OBJECT-TYPE
		SYNTAX		RollCallString
		MAX-ACCESS		read-only
		STATUS			current
		DESCRIPTION
				"TYPE: - Display
				 PAGE: - Audio Data
					Status Pair 8  cmdID= 1487  format=   "
		::= { iqhip00CmdEntry 1487 }


	iqhip00AudioLevelDetDuplicateSettingsChannelIndex OBJECT-TYPE
		SYNTAX		INTEGER
		MAX-ACCESS		read-write
		STATUS			current
		DESCRIPTION
				"TYPE: - Number
				 PAGE: - Audio Level Det
					Channel Index  cmdID= 3001  min= 1  max= 16  step= 1  format= %0.0f  div_scale= 1
					Min = 1  Max = 16  Step = 1 "
		::= { iqhip00CmdEntry 3001 }


	iqhip00HyperionAudioLevelDetAverageAudioLevel OBJECT-TYPE
		SYNTAX		RollCallString
		MAX-ACCESS		read-only
		STATUS			current
		DESCRIPTION
				"TYPE: - Display
				 PAGE: - Audio Level Det
					Average Audio Level  cmdID= 3000  format=   "
		::= { iqhip00CmdEntry 3000 }


	iqhip00AudioLevelDetOverloadDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3006 "
		::= { iqhip00CmdEntry 3006 }


	iqhip00AudioLevelDetOverloadDetectorAlarm OBJECT-TYPE
		SYNTAX		RollCallString
		MAX-ACCESS		read-only
		STATUS			current
		DESCRIPTION
				"TYPE: - Display
				 PAGE: - Audio Level Det
					Alarm  cmdID= 3007  format=   "
		::= { iqhip00CmdEntry 3007 }


	iqhip00AudioLevelDetOverloadDetectorLeveldB OBJECT-TYPE
		SYNTAX		INTEGER
		MAX-ACCESS		read-write
		STATUS			current
		DESCRIPTION
				"TYPE: - Number
				 PAGE: - Audio Level Det
					Level (dB)  cmdID= 3002  min= -15  max= 0  step= 1  format= %0.0f  div_scale= 1
					Min = -15  Max = 0  Step = 1 "
		::= { iqhip00CmdEntry 3002 }


	iqhip00AudioLevelDetOverloadDetectorWarningsecs OBJECT-TYPE
		SYNTAX		INTEGER
		MAX-ACCESS		read-write
		STATUS			current
		DESCRIPTION
				"TYPE: - Number
				 PAGE: - Audio Level Det
					Warning (secs)  cmdID= 3003  min= 1  max= 120  step= 1  format= %0.0f  div_scale= 1
					Min = 1  Max = 120  Step = 1 "
		::= { iqhip00CmdEntry 3003 }


	iqhip00AudioLevelDetOverloadDetectorFailsecs OBJECT-TYPE
		SYNTAX		INTEGER
		MAX-ACCESS		read-write
		STATUS			current
		DESCRIPTION
				"TYPE: - Number
				 PAGE: - Audio Level Det
					Fail (secs)  cmdID= 3004  min= 1  max= 120  step= 1  format= %0.0f  div_scale= 1
					Min = 1  Max = 120  Step = 1 "
		::= { iqhip00CmdEntry 3004 }


	iqhip00AudioLevelDetOverloadDetectorFailHoldsecs OBJECT-TYPE
		SYNTAX		INTEGER
		MAX-ACCESS		read-write
		STATUS			current
		DESCRIPTION
				"TYPE: - Number
				 PAGE: - Audio Level Det
					Fail Hold (secs)  cmdID= 3005  min= 1  max= 120  step= 1  format= %0.0f  div_scale= 1
					Min = 1  Max = 120  Step = 1 "
		::= { iqhip00CmdEntry 3005 }


	iqhip00AudioLevelDetOverloadDetectorAlarmReset OBJECT-TYPE
		SYNTAX		INTEGER {
							val_Alarm_Reset_Ch1(1),
							val_Alarm_Reset_Ch2(2),
							val_Alarm_Reset_Ch3(3),
							val_Alarm_Reset_Ch4(4)
							}
		MAX-ACCESS		read-write
		STATUS			current
		DESCRIPTION
				"TYPE: - Button
				 PAGE: - Audio Level Det
					Alarm Reset  cmdID= 3032  value= 1
					Alarm Reset  cmdID= 3032  value= 2
					Alarm Reset  cmdID= 3032  value= 3
					Alarm Reset  cmdID= 3032  value= 4  "
		::= { iqhip00CmdEntry 3032 }


	iqhip00AudioLevelDetLoudDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3012 "
		::= { iqhip00CmdEntry 3012 }


	iqhip00AudioLevelDetLoudDetectorAlarm OBJECT-TYPE
		SYNTAX		RollCallString
		MAX-ACCESS		read-only
		STATUS			current
		DESCRIPTION
				"TYPE: - Display
				 PAGE: - Audio Level Det
					Alarm  cmdID= 3013  format=   "
		::= { iqhip00CmdEntry 3013 }


	iqhip00AudioLevelDetLoudDetectorLeveldB OBJECT-TYPE
		SYNTAX		INTEGER
		MAX-ACCESS		read-write
		STATUS			current
		DESCRIPTION
				"TYPE: - Number
				 PAGE: - Audio Level Det
					Level (dB)  cmdID= 3008  min= -25  max= 0  step= 1  format= %0.0f  div_scale= 1
					Min = -25  Max = 0  Step = 1 "
		::= { iqhip00CmdEntry 3008 }


	iqhip00AudioLevelDetLoudDetectorWarningsecs OBJECT-TYPE
		SYNTAX		INTEGER
		MAX-ACCESS		read-write
		STATUS			current
		DESCRIPTION
				"TYPE: - Number
				 PAGE: - Audio Level Det
					Warning (secs)  cmdID= 3009  min= 1  max= 120  step= 1  format= %0.0f  div_scale= 1
					Min = 1  Max = 120  Step = 1 "
		::= { iqhip00CmdEntry 3009 }


	iqhip00AudioLevelDetLoudDetectorFailsecs OBJECT-TYPE
		SYNTAX		INTEGER
		MAX-ACCESS		read-write
		STATUS			current
		DESCRIPTION
				"TYPE: - Number
				 PAGE: - Audio Level Det
					Fail (secs)  cmdID= 3010  min= 1  max= 120  step= 1  format= %0.0f  div_scale= 1
					Min = 1  Max = 120  Step = 1 "
		::= { iqhip00CmdEntry 3010 }


	iqhip00AudioLevelDetLoudDetectorFailHoldsecs OBJECT-TYPE
		SYNTAX		INTEGER
		MAX-ACCESS		read-write
		STATUS			current
		DESCRIPTION
				"TYPE: - Number
				 PAGE: - Audio Level Det
					Fail Hold (secs)  cmdID= 3011  min= 1  max= 120  step= 1  format= %0.0f  div_scale= 1
					Min = 1  Max = 120  Step = 1 "
		::= { iqhip00CmdEntry 3011 }


	iqhip00AudioLevelDetQuietDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3018 "
		::= { iqhip00CmdEntry 3018 }


	iqhip00AudioLevelDetQuietDetectorAlarm OBJECT-TYPE
		SYNTAX		RollCallString
		MAX-ACCESS		read-only
		STATUS			current
		DESCRIPTION
				"TYPE: - Display
				 PAGE: - Audio Level Det
					Alarm  cmdID= 3019  format=   "
		::= { iqhip00CmdEntry 3019 }


	iqhip00AudioLevelDetQuietDetectorLeveldB OBJECT-TYPE
		SYNTAX		INTEGER
		MAX-ACCESS		read-write
		STATUS			current
		DESCRIPTION
				"TYPE: - Number
				 PAGE: - Audio Level Det
					Level (dB)  cmdID= 3014  min= -50  max= -10  step= 1  format= %0.0f  div_scale= 1
					Min = -50  Max = -10  Step = 1 "
		::= { iqhip00CmdEntry 3014 }


	iqhip00AudioLevelDetQuietDetectorWarningsecs OBJECT-TYPE
		SYNTAX		INTEGER
		MAX-ACCESS		read-write
		STATUS			current
		DESCRIPTION
				"TYPE: - Number
				 PAGE: - Audio Level Det
					Warning (secs)  cmdID= 3015  min= 1  max= 120  step= 1  format= %0.0f  div_scale= 1
					Min = 1  Max = 120  Step = 1 "
		::= { iqhip00CmdEntry 3015 }


	iqhip00AudioLevelDetQuietDetectorFailsecs OBJECT-TYPE
		SYNTAX		INTEGER
		MAX-ACCESS		read-write
		STATUS			current
		DESCRIPTION
				"TYPE: - Number
				 PAGE: - Audio Level Det
					Fail (secs)  cmdID= 3016  min= 1  max= 120  step= 1  format= %0.0f  div_scale= 1
					Min = 1  Max = 120  Step = 1 "
		::= { iqhip00CmdEntry 3016 }


	iqhip00AudioLevelDetQuietDetectorFailHoldsecs OBJECT-TYPE
		SYNTAX		INTEGER
		MAX-ACCESS		read-write
		STATUS			current
		DESCRIPTION
				"TYPE: - Number
				 PAGE: - Audio Level Det
					Fail Hold (secs)  cmdID= 3017  min= 1  max= 120  step= 1  format= %0.0f  div_scale= 1
					Min = 1  Max = 120  Step = 1 "
		::= { iqhip00CmdEntry 3017 }


	iqhip00AudioLevelDetSilenceDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3024 "
		::= { iqhip00CmdEntry 3024 }


	iqhip00AudioLevelDetSilenceDetectorAlarm OBJECT-TYPE
		SYNTAX		RollCallString
		MAX-ACCESS		read-only
		STATUS			current
		DESCRIPTION
				"TYPE: - Display
				 PAGE: - Audio Level Det
					Alarm  cmdID= 3025  format=   "
		::= { iqhip00CmdEntry 3025 }


	iqhip00AudioLevelDetSilenceDetectorLeveldB OBJECT-TYPE
		SYNTAX		INTEGER
		MAX-ACCESS		read-write
		STATUS			current
		DESCRIPTION
				"TYPE: - Number
				 PAGE: - Audio Level Det
					Level (dB)  cmdID= 3020  min= -99  max= -60  step= 1  format= %0.0f  div_scale= 1
					Min = -99  Max = -60  Step = 1 "
		::= { iqhip00CmdEntry 3020 }


	iqhip00AudioLevelDetSilenceDetectorWarningsecs OBJECT-TYPE
		SYNTAX		INTEGER
		MAX-ACCESS		read-write
		STATUS			current
		DESCRIPTION
				"TYPE: - Number
				 PAGE: - Audio Level Det
					Warning (secs)  cmdID= 3021  min= 1  max= 120  step= 1  format= %0.0f  div_scale= 1
					Min = 1  Max = 120  Step = 1 "
		::= { iqhip00CmdEntry 3021 }


	iqhip00AudioLevelDetSilenceDetectorFailsecs OBJECT-TYPE
		SYNTAX		INTEGER
		MAX-ACCESS		read-write
		STATUS			current
		DESCRIPTION
				"TYPE: - Number
				 PAGE: - Audio Level Det
					Fail (secs)  cmdID= 3022  min= 1  max= 120  step= 1  format= %0.0f  div_scale= 1
					Min = 1  Max = 120  Step = 1 "
		::= { iqhip00CmdEntry 3022 }


	iqhip00AudioLevelDetSilenceDetectorFailHoldsecs OBJECT-TYPE
		SYNTAX		INTEGER
		MAX-ACCESS		read-write
		STATUS			current
		DESCRIPTION
				"TYPE: - Number
				 PAGE: - Audio Level Det
					Fail Hold (secs)  cmdID= 3023  min= 1  max= 120  step= 1  format= %0.0f  div_scale= 1
					Min = 1  Max = 120  Step = 1 "
		::= { iqhip00CmdEntry 3023 }


	iqhip00AudioLevelDetDuplicateSettingsCopyFromChannel OBJECT-TYPE
		SYNTAX		INTEGER
		MAX-ACCESS		read-write
		STATUS			current
		DESCRIPTION
				"TYPE: - Number
				 PAGE: - Audio Level Det
					Copy From Channel  cmdID= 3030  min= 1  max= 16  step= 1  format= %0.0f  div_scale= 1
					Min = 1  Max = 16  Step = 1 "
		::= { iqhip00CmdEntry 3030 }


	iqhip00AudioLevelDetDuplicateSettingsCopySettings OBJECT-TYPE
		SYNTAX		INTEGER { noAction(0),val_Copy_Settings(1) }
		MAX-ACCESS		read-write
		STATUS			current
		DESCRIPTION
				"TYPE: - Button
				 PAGE: - Audio Level Det
					Copy Settings  cmdID= 3031  value= 1  "
		::= { iqhip00CmdEntry 3031 }


	iqhip00HyperionAudioLevelDet OBJECT-TYPE
		SYNTAX		INTEGER {
							val_Enable_All_Chan_Det(17),
							val_Disable_All_Chan_De(16),
							}
		MAX-ACCESS		read-write
		STATUS			current
		DESCRIPTION
				"TYPE: - RadiobuttonList
				 PAGE: - Audio Level Det
					Alarm All Chans  cmdID= 3040
					Enable All Chan Det  value= 17
					Disable All Chan De  value= 16
					Alarm Indexed Chan  cmdID= 3040 "
		::= { iqhip00CmdEntry 3040 }


	iqhip00HyperionAudioLevelIndRollMapAudLvlEn OBJECT-TYPE
		SYNTAX		INTEGER { disable(0), enable(1) }
		MAX-ACCESS		read-write
		STATUS			current
		DESCRIPTION
				"TYPE: - Checkbox
				 PAGE: - Audio Level Ind
					RollMap Aud Lvl En  cmdID= 38275 "
		::= { iqhip00CmdEntry 38275 }


	iqhip00HyperionAudioLevelIndOSDMarker OBJECT-TYPE
		SYNTAX		INTEGER
		MAX-ACCESS		read-write
		STATUS			current
		DESCRIPTION
				"TYPE: - Number
				 PAGE: - Audio Level Ind
					OSD Marker  cmdID= 3150  min= -102  max= 0  step= 1  format= %0.0f  div_scale= 1
					Min = -102  Max = 0  Step = 1 "
		::= { iqhip00CmdEntry 3150 }


	iqhip00HyperionAudioLevelIndRollMapAudLvl OBJECT-TYPE
		SYNTAX		RollCallString
		MAX-ACCESS		read-only
		STATUS			current
		DESCRIPTION
				"TYPE: - Display
				 PAGE: - Audio Level Ind
					RollMap Aud Lvl  cmdID= 38276  format=   "
		::= { iqhip00CmdEntry 38276 }


	iqhip00HyperionAudioLevelIndEnableChannel1 OBJECT-TYPE
		SYNTAX		INTEGER { disable(0), enable(1) }
		MAX-ACCESS		read-write
		STATUS			current
		DESCRIPTION
				"TYPE: - Checkbox
				 PAGE: - Audio Level Ind
					Enable Channel 1  cmdID= 1582 "
		::= { iqhip00CmdEntry 1582 }


	iqhip00HyperionAudioLevelIndChannel1 OBJECT-TYPE
		SYNTAX		RollCallString
		MAX-ACCESS		read-only
		STATUS			current
		DESCRIPTION
				"TYPE: - Display
				 PAGE: - Audio Level Ind
					Channel 1  cmdID= 1566  format=   "
		::= { iqhip00CmdEntry 1566 }


	iqhip00HyperionAudioLevelIndEnableChannel2 OBJECT-TYPE
		SYNTAX		INTEGER { disable(0), enable(1) }
		MAX-ACCESS		read-write
		STATUS			current
		DESCRIPTION
				"TYPE: - Checkbox
				 PAGE: - Audio Level Ind
					Enable Channel 2  cmdID= 1583 "
		::= { iqhip00CmdEntry 1583 }


	iqhip00HyperionAudioLevelIndChannel2 OBJECT-TYPE
		SYNTAX		RollCallString
		MAX-ACCESS		read-only
		STATUS			current
		DESCRIPTION
				"TYPE: - Display
				 PAGE: - Audio Level Ind
					Channel 2  cmdID= 1567  format=   "
		::= { iqhip00CmdEntry 1567 }


	iqhip00HyperionAudioLevelIndEnableChannel3 OBJECT-TYPE
		SYNTAX		INTEGER { disable(0), enable(1) }
		MAX-ACCESS		read-write
		STATUS			current
		DESCRIPTION
				"TYPE: - Checkbox
				 PAGE: - Audio Level Ind
					Enable Channel 3  cmdID= 1584 "
		::= { iqhip00CmdEntry 1584 }


	iqhip00HyperionAudioLevelIndChannel3 OBJECT-TYPE
		SYNTAX		RollCallString
		MAX-ACCESS		read-only
		STATUS			current
		DESCRIPTION
				"TYPE: - Display
				 PAGE: - Audio Level Ind
					Channel 3  cmdID= 1568  format=   "
		::= { iqhip00CmdEntry 1568 }


	iqhip00HyperionAudioLevelIndEnableChannel4 OBJECT-TYPE
		SYNTAX		INTEGER { disable(0), enable(1) }
		MAX-ACCESS		read-write
		STATUS			current
		DESCRIPTION
				"TYPE: - Checkbox
				 PAGE: - Audio Level Ind
					Enable Channel 4  cmdID= 1585 "
		::= { iqhip00CmdEntry 1585 }


	iqhip00HyperionAudioLevelIndChannel4 OBJECT-TYPE
		SYNTAX		RollCallString
		MAX-ACCESS		read-only
		STATUS			current
		DESCRIPTION
				"TYPE: - Display
				 PAGE: - Audio Level Ind
					Channel 4  cmdID= 1569  format=   "
		::= { iqhip00CmdEntry 1569 }


	iqhip00HyperionAudioLevelIndEnableChannel5 OBJECT-TYPE
		SYNTAX		INTEGER { disable(0), enable(1) }
		MAX-ACCESS		read-write
		STATUS			current
		DESCRIPTION
				"TYPE: - Checkbox
				 PAGE: - Audio Level Ind
					Enable Channel 5  cmdID= 1586 "
		::= { iqhip00CmdEntry 1586 }


	iqhip00HyperionAudioLevelIndChannel5 OBJECT-TYPE
		SYNTAX		RollCallString
		MAX-ACCESS		read-only
		STATUS			current
		DESCRIPTION
				"TYPE: - Display
				 PAGE: - Audio Level Ind
					Channel 5  cmdID= 1570  format=   "
		::= { iqhip00CmdEntry 1570 }


	iqhip00HyperionAudioLevelIndEnableChannel6 OBJECT-TYPE
		SYNTAX		INTEGER { disable(0), enable(1) }
		MAX-ACCESS		read-write
		STATUS			current
		DESCRIPTION
				"TYPE: - Checkbox
				 PAGE: - Audio Level Ind
					Enable Channel 6  cmdID= 1587 "
		::= { iqhip00CmdEntry 1587 }


	iqhip00HyperionAudioLevelIndChannel6 OBJECT-TYPE
		SYNTAX		RollCallString
		MAX-ACCESS		read-only
		STATUS			current
		DESCRIPTION
				"TYPE: - Display
				 PAGE: - Audio Level Ind
					Channel 6  cmdID= 1571  format=   "
		::= { iqhip00CmdEntry 1571 }


	iqhip00HyperionAudioLevelIndEnableChannel7 OBJECT-TYPE
		SYNTAX		INTEGER { disable(0), enable(1) }
		MAX-ACCESS		read-write
		STATUS			current
		DESCRIPTION
				"TYPE: - Checkbox
				 PAGE: - Audio Level Ind
					Enable Channel 7  cmdID= 1588 "
		::= { iqhip00CmdEntry 1588 }


	iqhip00HyperionAudioLevelIndChannel7 OBJECT-TYPE
		SYNTAX		RollCallString
		MAX-ACCESS		read-only
		STATUS			current
		DESCRIPTION
				"TYPE: - Display
				 PAGE: - Audio Level Ind
					Channel 7  cmdID= 1572  format=   "
		::= { iqhip00CmdEntry 1572 }


	iqhip00HyperionAudioLevelIndEnableChannel8 OBJECT-TYPE
		SYNTAX		INTEGER { disable(0), enable(1) }
		MAX-ACCESS		read-write
		STATUS			current
		DESCRIPTION
				"TYPE: - Checkbox
				 PAGE: - Audio Level Ind
					Enable Channel 8  cmdID= 1589 "
		::= { iqhip00CmdEntry 1589 }


	iqhip00HyperionAudioLevelIndChannel8 OBJECT-TYPE
		SYNTAX		RollCallString
		MAX-ACCESS		read-only
		STATUS			current
		DESCRIPTION
				"TYPE: - Display
				 PAGE: - Audio Level Ind
					Channel 8  cmdID= 1573  format=   "
		::= { iqhip00CmdEntry 1573 }


	iqhip00HyperionAudioLevelIndEnableChannel9 OBJECT-TYPE
		SYNTAX		INTEGER { disable(0), enable(1) }
		MAX-ACCESS		read-write
		STATUS			current
		DESCRIPTION
				"TYPE: - Checkbox
				 PAGE: - Audio Level Ind
					Enable Channel 9  cmdID= 1590 "
		::= { iqhip00CmdEntry 1590 }


	iqhip00HyperionAudioLevelIndChannel9 OBJECT-TYPE
		SYNTAX		RollCallString
		MAX-ACCESS		read-only
		STATUS			current
		DESCRIPTION
				"TYPE: - Display
				 PAGE: - Audio Level Ind
					Channel 9  cmdID= 1574  format=   "
		::= { iqhip00CmdEntry 1574 }


	iqhip00HyperionAudioLevelIndEnableChannel10 OBJECT-TYPE
		SYNTAX		INTEGER { disable(0), enable(1) }
		MAX-ACCESS		read-write
		STATUS			current
		DESCRIPTION
				"TYPE: - Checkbox
				 PAGE: - Audio Level Ind
					Enable Channel 10  cmdID= 1591 "
		::= { iqhip00CmdEntry 1591 }


	iqhip00HyperionAudioLevelIndChannel10 OBJECT-TYPE
		SYNTAX		RollCallString
		MAX-ACCESS		read-only
		STATUS			current
		DESCRIPTION
				"TYPE: - Display
				 PAGE: - Audio Level Ind
					Channel 10  cmdID= 1575  format=   "
		::= { iqhip00CmdEntry 1575 }


	iqhip00HyperionAudioLevelIndEnableChannel11 OBJECT-TYPE
		SYNTAX		INTEGER { disable(0), enable(1) }
		MAX-ACCESS		read-write
		STATUS			current
		DESCRIPTION
				"TYPE: - Checkbox
				 PAGE: - Audio Level Ind
					Enable Channel 11  cmdID= 1592 "
		::= { iqhip00CmdEntry 1592 }


	iqhip00HyperionAudioLevelIndChannel11 OBJECT-TYPE
		SYNTAX		RollCallString
		MAX-ACCESS		read-only
		STATUS			current
		DESCRIPTION
				"TYPE: - Display
				 PAGE: - Audio Level Ind
					Channel 11  cmdID= 1576  format=   "
		::= { iqhip00CmdEntry 1576 }


	iqhip00HyperionAudioLevelIndEnableChannel12 OBJECT-TYPE
		SYNTAX		INTEGER { disable(0), enable(1) }
		MAX-ACCESS		read-write
		STATUS			current
		DESCRIPTION
				"TYPE: - Checkbox
				 PAGE: - Audio Level Ind
					Enable Channel 12  cmdID= 1593 "
		::= { iqhip00CmdEntry 1593 }


	iqhip00HyperionAudioLevelIndChannel12 OBJECT-TYPE
		SYNTAX		RollCallString
		MAX-ACCESS		read-only
		STATUS			current
		DESCRIPTION
				"TYPE: - Display
				 PAGE: - Audio Level Ind
					Channel 12  cmdID= 1577  format=   "
		::= { iqhip00CmdEntry 1577 }


	iqhip00HyperionAudioLevelIndEnableChannel13 OBJECT-TYPE
		SYNTAX		INTEGER { disable(0), enable(1) }
		MAX-ACCESS		read-write
		STATUS			current
		DESCRIPTION
				"TYPE: - Checkbox
				 PAGE: - Audio Level Ind
					Enable Channel 13  cmdID= 1594 "
		::= { iqhip00CmdEntry 1594 }


	iqhip00HyperionAudioLevelIndChannel13 OBJECT-TYPE
		SYNTAX		RollCallString
		MAX-ACCESS		read-only
		STATUS			current
		DESCRIPTION
				"TYPE: - Display
				 PAGE: - Audio Level Ind
					Channel 13  cmdID= 1578  format=   "
		::= { iqhip00CmdEntry 1578 }


	iqhip00HyperionAudioLevelIndEnableChannel14 OBJECT-TYPE
		SYNTAX		INTEGER { disable(0), enable(1) }
		MAX-ACCESS		read-write
		STATUS			current
		DESCRIPTION
				"TYPE: - Checkbox
				 PAGE: - Audio Level Ind
					Enable Channel 14  cmdID= 1595 "
		::= { iqhip00CmdEntry 1595 }


	iqhip00HyperionAudioLevelIndChannel14 OBJECT-TYPE
		SYNTAX		RollCallString
		MAX-ACCESS		read-only
		STATUS			current
		DESCRIPTION
				"TYPE: - Display
				 PAGE: - Audio Level Ind
					Channel 14  cmdID= 1579  format=   "
		::= { iqhip00CmdEntry 1579 }


	iqhip00HyperionAudioLevelIndEnableChannel15 OBJECT-TYPE
		SYNTAX		INTEGER { disable(0), enable(1) }
		MAX-ACCESS		read-write
		STATUS			current
		DESCRIPTION
				"TYPE: - Checkbox
				 PAGE: - Audio Level Ind
					Enable Channel 15  cmdID= 1596 "
		::= { iqhip00CmdEntry 1596 }


	iqhip00HyperionAudioLevelIndChannel15 OBJECT-TYPE
		SYNTAX		RollCallString
		MAX-ACCESS		read-only
		STATUS			current
		DESCRIPTION
				"TYPE: - Display
				 PAGE: - Audio Level Ind
					Channel 15  cmdID= 1580  format=   "
		::= { iqhip00CmdEntry 1580 }


	iqhip00HyperionAudioLevelIndEnableChannel16 OBJECT-TYPE
		SYNTAX		INTEGER { disable(0), enable(1) }
		MAX-ACCESS		read-write
		STATUS			current
		DESCRIPTION
				"TYPE: - Checkbox
				 PAGE: - Audio Level Ind
					Enable Channel 16  cmdID= 1597 "
		::= { iqhip00CmdEntry 1597 }


	iqhip00HyperionAudioLevelIndChannel16 OBJECT-TYPE
		SYNTAX		RollCallString
		MAX-ACCESS		read-only
		STATUS			current
		DESCRIPTION
				"TYPE: - Display
				 PAGE: - Audio Level Ind
					Channel 16  cmdID= 1581  format=   "
		::= { iqhip00CmdEntry 1581 }


	iqhip00HyperionClippingDetectorThreshold OBJECT-TYPE
		SYNTAX		INTEGER
		MAX-ACCESS		read-write
		STATUS			current
		DESCRIPTION
				"TYPE: - Number
				 PAGE: - Clipping Detector
					Threshold  cmdID= 3140  min= 0  max= 4  step= 1  format= %0.0f  div_scale= 1
					Min = 0  Max = 4  Step = 1 "
		::= { iqhip00CmdEntry 3140 }


	iqhip00HyperionClippingDetectorSensitivity OBJECT-TYPE
		SYNTAX		INTEGER
		MAX-ACCESS		read-write
		STATUS			current
		DESCRIPTION
				"TYPE: - Number
				 PAGE: - Clipping Detector
					Sensitivity  cmdID= 3141  min= 1  max= 100  step= 1  format= %0.0f  div_scale= 1
					Min = 1  Max = 100  Step = 1 "
		::= { iqhip00CmdEntry 3141 }


	iqhip00HyperionClippingDetectorStatusCh1 OBJECT-TYPE
		SYNTAX		RollCallString
		MAX-ACCESS		read-only
		STATUS			current
		DESCRIPTION
				"TYPE: - Display
				 PAGE: - Clipping Detector
					Status Ch 1  cmdID= 3180  format=   "
		::= { iqhip00CmdEntry 3180 }


	iqhip00HyperionClippingDetectorEnableAlarmCh1 OBJECT-TYPE
		SYNTAX		INTEGER { disable(0), enable(1) }
		MAX-ACCESS		read-write
		STATUS			current
		DESCRIPTION
				"TYPE: - Checkbox
				 PAGE: - Clipping Detector
					Enable Alarm Ch 1  cmdID= 3220 "
		::= { iqhip00CmdEntry 3220 }


	iqhip00HyperionClippingDetectorStatusCh2 OBJECT-TYPE
		SYNTAX		RollCallString
		MAX-ACCESS		read-only
		STATUS			current
		DESCRIPTION
				"TYPE: - Display
				 PAGE: - Clipping Detector
					Status Ch 2  cmdID= 3181  format=   "
		::= { iqhip00CmdEntry 3181 }


	iqhip00HyperionClippingDetectorEnableAlarmCh2 OBJECT-TYPE
		SYNTAX		INTEGER { disable(0), enable(1) }
		MAX-ACCESS		read-write
		STATUS			current
		DESCRIPTION
				"TYPE: - Checkbox
				 PAGE: - Clipping Detector
					Enable Alarm Ch 2  cmdID= 3221 "
		::= { iqhip00CmdEntry 3221 }


	iqhip00HyperionClippingDetectorStatusCh3 OBJECT-TYPE
		SYNTAX		RollCallString
		MAX-ACCESS		read-only
		STATUS			current
		DESCRIPTION
				"TYPE: - Display
				 PAGE: - Clipping Detector
					Status Ch 3  cmdID= 3182  format=   "
		::= { iqhip00CmdEntry 3182 }


	iqhip00HyperionClippingDetectorEnableAlarmCh3 OBJECT-TYPE
		SYNTAX		INTEGER { disable(0), enable(1) }
		MAX-ACCESS		read-write
		STATUS			current
		DESCRIPTION
				"TYPE: - Checkbox
				 PAGE: - Clipping Detector
					Enable Alarm Ch 3  cmdID= 3222 "
		::= { iqhip00CmdEntry 3222 }


	iqhip00HyperionClippingDetectorStatusCh4 OBJECT-TYPE
		SYNTAX		RollCallString
		MAX-ACCESS		read-only
		STATUS			current
		DESCRIPTION
				"TYPE: - Display
				 PAGE: - Clipping Detector
					Status Ch 4  cmdID= 3183  format=   "
		::= { iqhip00CmdEntry 3183 }


	iqhip00HyperionClippingDetectorEnableAlarmCh4 OBJECT-TYPE
		SYNTAX		INTEGER { disable(0), enable(1) }
		MAX-ACCESS		read-write
		STATUS			current
		DESCRIPTION
				"TYPE: - Checkbox
				 PAGE: - Clipping Detector
					Enable Alarm Ch 4  cmdID= 3223 "
		::= { iqhip00CmdEntry 3223 }


	iqhip00HyperionClippingDetectorStatusCh5 OBJECT-TYPE
		SYNTAX		RollCallString
		MAX-ACCESS		read-only
		STATUS			current
		DESCRIPTION
				"TYPE: - Display
				 PAGE: - Clipping Detector
					Status Ch 5  cmdID= 3184  format=   "
		::= { iqhip00CmdEntry 3184 }


	iqhip00HyperionClippingDetectorEnableAlarmCh5 OBJECT-TYPE
		SYNTAX		INTEGER { disable(0), enable(1) }
		MAX-ACCESS		read-write
		STATUS			current
		DESCRIPTION
				"TYPE: - Checkbox
				 PAGE: - Clipping Detector
					Enable Alarm Ch 5  cmdID= 3224 "
		::= { iqhip00CmdEntry 3224 }


	iqhip00HyperionClippingDetectorStatusCh6 OBJECT-TYPE
		SYNTAX		RollCallString
		MAX-ACCESS		read-only
		STATUS			current
		DESCRIPTION
				"TYPE: - Display
				 PAGE: - Clipping Detector
					Status Ch 6  cmdID= 3185  format=   "
		::= { iqhip00CmdEntry 3185 }


	iqhip00HyperionClippingDetectorEnableAlarmCh6 OBJECT-TYPE
		SYNTAX		INTEGER { disable(0), enable(1) }
		MAX-ACCESS		read-write
		STATUS			current
		DESCRIPTION
				"TYPE: - Checkbox
				 PAGE: - Clipping Detector
					Enable Alarm Ch 6  cmdID= 3225 "
		::= { iqhip00CmdEntry 3225 }


	iqhip00HyperionClippingDetectorStatusCh7 OBJECT-TYPE
		SYNTAX		RollCallString
		MAX-ACCESS		read-only
		STATUS			current
		DESCRIPTION
				"TYPE: - Display
				 PAGE: - Clipping Detector
					Status Ch 7  cmdID= 3186  format=   "
		::= { iqhip00CmdEntry 3186 }


	iqhip00HyperionClippingDetectorEnableAlarmCh7 OBJECT-TYPE
		SYNTAX		INTEGER { disable(0), enable(1) }
		MAX-ACCESS		read-write
		STATUS			current
		DESCRIPTION
				"TYPE: - Checkbox
				 PAGE: - Clipping Detector
					Enable Alarm Ch 7  cmdID= 3226 "
		::= { iqhip00CmdEntry 3226 }


	iqhip00HyperionClippingDetectorStatusCh8 OBJECT-TYPE
		SYNTAX		RollCallString
		MAX-ACCESS		read-only
		STATUS			current
		DESCRIPTION
				"TYPE: - Display
				 PAGE: - Clipping Detector
					Status Ch 8  cmdID= 3187  format=   "
		::= { iqhip00CmdEntry 3187 }


	iqhip00HyperionClippingDetectorEnableAlarmCh8 OBJECT-TYPE
		SYNTAX		INTEGER { disable(0), enable(1) }
		MAX-ACCESS		read-write
		STATUS			current
		DESCRIPTION
				"TYPE: - Checkbox
				 PAGE: - Clipping Detector
					Enable Alarm Ch 8  cmdID= 3227 "
		::= { iqhip00CmdEntry 3227 }


	iqhip00HyperionClippingDetectorStatusCh9 OBJECT-TYPE
		SYNTAX		RollCallString
		MAX-ACCESS		read-only
		STATUS			current
		DESCRIPTION
				"TYPE: - Display
				 PAGE: - Clipping Detector
					Status Ch 9  cmdID= 3188  format=   "
		::= { iqhip00CmdEntry 3188 }


	iqhip00HyperionClippingDetectorEnableAlarmCh9 OBJECT-TYPE
		SYNTAX		INTEGER { disable(0), enable(1) }
		MAX-ACCESS		read-write
		STATUS			current
		DESCRIPTION
				"TYPE: - Checkbox
				 PAGE: - Clipping Detector
					Enable Alarm Ch 9  cmdID= 3228 "
		::= { iqhip00CmdEntry 3228 }


	iqhip00HyperionClippingDetectorStatusCh10 OBJECT-TYPE
		SYNTAX		RollCallString
		MAX-ACCESS		read-only
		STATUS			current
		DESCRIPTION
				"TYPE: - Display
				 PAGE: - Clipping Detector
					Status Ch 10  cmdID= 3189  format=   "
		::= { iqhip00CmdEntry 3189 }


	iqhip00HyperionClippingDetectorEnableAlarmCh10 OBJECT-TYPE
		SYNTAX		INTEGER { disable(0), enable(1) }
		MAX-ACCESS		read-write
		STATUS			current
		DESCRIPTION
				"TYPE: - Checkbox
				 PAGE: - Clipping Detector
					Enable Alarm Ch 10  cmdID= 3229 "
		::= { iqhip00CmdEntry 3229 }


	iqhip00HyperionClippingDetectorStatusCh11 OBJECT-TYPE
		SYNTAX		RollCallString
		MAX-ACCESS		read-only
		STATUS			current
		DESCRIPTION
				"TYPE: - Display
				 PAGE: - Clipping Detector
					Status Ch 11  cmdID= 3190  format=   "
		::= { iqhip00CmdEntry 3190 }


	iqhip00HyperionClippingDetectorEnableAlarmCh11 OBJECT-TYPE
		SYNTAX		INTEGER { disable(0), enable(1) }
		MAX-ACCESS		read-write
		STATUS			current
		DESCRIPTION
				"TYPE: - Checkbox
				 PAGE: - Clipping Detector
					Enable Alarm Ch 11  cmdID= 3230 "
		::= { iqhip00CmdEntry 3230 }


	iqhip00HyperionClippingDetectorStatusCh12 OBJECT-TYPE
		SYNTAX		RollCallString
		MAX-ACCESS		read-only
		STATUS			current
		DESCRIPTION
				"TYPE: - Display
				 PAGE: - Clipping Detector
					Status Ch 12  cmdID= 3191  format=   "
		::= { iqhip00CmdEntry 3191 }


	iqhip00HyperionClippingDetectorEnableAlarmCh12 OBJECT-TYPE
		SYNTAX		INTEGER { disable(0), enable(1) }
		MAX-ACCESS		read-write
		STATUS			current
		DESCRIPTION
				"TYPE: - Checkbox
				 PAGE: - Clipping Detector
					Enable Alarm Ch 12  cmdID= 3231 "
		::= { iqhip00CmdEntry 3231 }


	iqhip00HyperionClippingDetectorStatusCh13 OBJECT-TYPE
		SYNTAX		RollCallString
		MAX-ACCESS		read-only
		STATUS			current
		DESCRIPTION
				"TYPE: - Display
				 PAGE: - Clipping Detector
					Status Ch 13  cmdID= 3192  format=   "
		::= { iqhip00CmdEntry 3192 }


	iqhip00HyperionClippingDetectorEnableAlarmCh13 OBJECT-TYPE
		SYNTAX		INTEGER { disable(0), enable(1) }
		MAX-ACCESS		read-write
		STATUS			current
		DESCRIPTION
				"TYPE: - Checkbox
				 PAGE: - Clipping Detector
					Enable Alarm Ch 13  cmdID= 3232 "
		::= { iqhip00CmdEntry 3232 }


	iqhip00HyperionClippingDetectorStatusCh14 OBJECT-TYPE
		SYNTAX		RollCallString
		MAX-ACCESS		read-only
		STATUS			current
		DESCRIPTION
				"TYPE: - Display
				 PAGE: - Clipping Detector
					Status Ch 14  cmdID= 3193  format=   "
		::= { iqhip00CmdEntry 3193 }


	iqhip00HyperionClippingDetectorEnableAlarmCh14 OBJECT-TYPE
		SYNTAX		INTEGER { disable(0), enable(1) }
		MAX-ACCESS		read-write
		STATUS			current
		DESCRIPTION
				"TYPE: - Checkbox
				 PAGE: - Clipping Detector
					Enable Alarm Ch 14  cmdID= 3233 "
		::= { iqhip00CmdEntry 3233 }


	iqhip00HyperionClippingDetectorStatusCh15 OBJECT-TYPE
		SYNTAX		RollCallString
		MAX-ACCESS		read-only
		STATUS			current
		DESCRIPTION
				"TYPE: - Display
				 PAGE: - Clipping Detector
					Status Ch 15  cmdID= 3194  format=   "
		::= { iqhip00CmdEntry 3194 }


	iqhip00HyperionClippingDetectorEnableAlarmCh15 OBJECT-TYPE
		SYNTAX		INTEGER { disable(0), enable(1) }
		MAX-ACCESS		read-write
		STATUS			current
		DESCRIPTION
				"TYPE: - Checkbox
				 PAGE: - Clipping Detector
					Enable Alarm Ch 15  cmdID= 3234 "
		::= { iqhip00CmdEntry 3234 }


	iqhip00HyperionClippingDetectorStatusCh16 OBJECT-TYPE
		SYNTAX		RollCallString
		MAX-ACCESS		read-only
		STATUS			current
		DESCRIPTION
				"TYPE: - Display
				 PAGE: - Clipping Detector
					Status Ch 16  cmdID= 3195  format=   "
		::= { iqhip00CmdEntry 3195 }


	iqhip00HyperionClippingDetectorEnableAlarmCh16 OBJECT-TYPE
		SYNTAX		INTEGER { disable(0), enable(1) }
		MAX-ACCESS		read-write
		STATUS			current
		DESCRIPTION
				"TYPE: - Checkbox
				 PAGE: - Clipping Detector
					Enable Alarm Ch 16  cmdID= 3235 "
		::= { iqhip00CmdEntry 3235 }


	iqhip00AudioLikenessDetector1Likeness OBJECT-TYPE
		SYNTAX		RollCallString
		MAX-ACCESS		read-only
		STATUS			current
		DESCRIPTION
				"TYPE: - Display
				 PAGE: - Audio Likeness
					Likeness  cmdID= 3120  format=   "
		::= { iqhip00CmdEntry 3120 }


	iqhip00AudioLikenessDetector1State OBJECT-TYPE
		SYNTAX		RollCallString
		MAX-ACCESS		read-only
		STATUS			current
		DESCRIPTION
				"TYPE: - Display
				 PAGE: - Audio Likeness
					State  cmdID= 3130  format=   "
		::= { iqhip00CmdEntry 3130 }


	iqhip00AudioLikenessDetector1SelectChannelA OBJECT-TYPE
		SYNTAX		INTEGER
		MAX-ACCESS		read-write
		STATUS			current
		DESCRIPTION
				"TYPE: - Number
				 PAGE: - Audio Likeness
					Select Channel A  cmdID= 3100  min= 1  max= 16  step= 1  format= %0.0f  div_scale= 1
					Min = 1  Max = 16  Step = 1 "
		::= { iqhip00CmdEntry 3100 }


	iqhip00AudioLikenessDetector1SelectChannelB OBJECT-TYPE
		SYNTAX		INTEGER
		MAX-ACCESS		read-write
		STATUS			current
		DESCRIPTION
				"TYPE: - Number
				 PAGE: - Audio Likeness
					Select Channel B  cmdID= 3101  min= 1  max= 16  step= 1  format= %0.0f  div_scale= 1
					Min = 1  Max = 16  Step = 1 "
		::= { iqhip00CmdEntry 3101 }


	iqhip00AudioLikenessDetector1EnableAlarm OBJECT-TYPE
		SYNTAX		INTEGER { disable(0), enable(1) }
		MAX-ACCESS		read-write
		STATUS			current
		DESCRIPTION
				"TYPE: - Checkbox
				 PAGE: - Audio Likeness
					Enable Alarm  cmdID= 3108 "
		::= { iqhip00CmdEntry 3108 }


	iqhip00AudioLikenessDetector2Likeness OBJECT-TYPE
		SYNTAX		RollCallString
		MAX-ACCESS		read-only
		STATUS			current
		DESCRIPTION
				"TYPE: - Display
				 PAGE: - Audio Likeness
					Likeness  cmdID= 3121  format=   "
		::= { iqhip00CmdEntry 3121 }


	iqhip00AudioLikenessDetector2State OBJECT-TYPE
		SYNTAX		RollCallString
		MAX-ACCESS		read-only
		STATUS			current
		DESCRIPTION
				"TYPE: - Display
				 PAGE: - Audio Likeness
					State  cmdID= 3131  format=   "
		::= { iqhip00CmdEntry 3131 }


	iqhip00AudioLikenessDetector2SelectChannelA OBJECT-TYPE
		SYNTAX		INTEGER
		MAX-ACCESS		read-write
		STATUS			current
		DESCRIPTION
				"TYPE: - Number
				 PAGE: - Audio Likeness
					Select Channel A  cmdID= 3102  min= 1  max= 16  step= 1  format= %0.0f  div_scale= 1
					Min = 1  Max = 16  Step = 1 "
		::= { iqhip00CmdEntry 3102 }


	iqhip00AudioLikenessDetector2SelectChannelB OBJECT-TYPE
		SYNTAX		INTEGER
		MAX-ACCESS		read-write
		STATUS			current
		DESCRIPTION
				"TYPE: - Number
				 PAGE: - Audio Likeness
					Select Channel B  cmdID= 3103  min= 1  max= 16  step= 1  format= %0.0f  div_scale= 1
					Min = 1  Max = 16  Step = 1 "
		::= { iqhip00CmdEntry 3103 }


	iqhip00AudioLikenessDetector2AlarmEnable OBJECT-TYPE
		SYNTAX		INTEGER { disable(0), enable(1) }
		MAX-ACCESS		read-write
		STATUS			current
		DESCRIPTION
				"TYPE: - Checkbox
				 PAGE: - Audio Likeness
					Alarm Enable  cmdID= 3109 "
		::= { iqhip00CmdEntry 3109 }


	iqhip00AudioLikenessDetector3Likeness OBJECT-TYPE
		SYNTAX		RollCallString
		MAX-ACCESS		read-only
		STATUS			current
		DESCRIPTION
				"TYPE: - Display
				 PAGE: - Audio Likeness
					Likeness  cmdID= 3122  format=   "
		::= { iqhip00CmdEntry 3122 }


	iqhip00AudioLikenessDetector3State OBJECT-TYPE
		SYNTAX		RollCallString
		MAX-ACCESS		read-only
		STATUS			current
		DESCRIPTION
				"TYPE: - Display
				 PAGE: - Audio Likeness
					State  cmdID= 3132  format=   "
		::= { iqhip00CmdEntry 3132 }


	iqhip00AudioLikenessDetector3SelectChannelA OBJECT-TYPE
		SYNTAX		INTEGER
		MAX-ACCESS		read-write
		STATUS			current
		DESCRIPTION
				"TYPE: - Number
				 PAGE: - Audio Likeness
					Select Channel A  cmdID= 3104  min= 1  max= 16  step= 1  format= %0.0f  div_scale= 1
					Min = 1  Max = 16  Step = 1 "
		::= { iqhip00CmdEntry 3104 }


	iqhip00AudioLikenessDetector3SelectChannelB OBJECT-TYPE
		SYNTAX		INTEGER
		MAX-ACCESS		read-write
		STATUS			current
		DESCRIPTION
				"TYPE: - Number
				 PAGE: - Audio Likeness
					Select Channel B  cmdID= 3105  min= 1  max= 16  step= 1  format= %0.0f  div_scale= 1
					Min = 1  Max = 16  Step = 1 "
		::= { iqhip00CmdEntry 3105 }


	iqhip00AudioLikenessDetector3AlarmEnable OBJECT-TYPE
		SYNTAX		INTEGER { disable(0), enable(1) }
		MAX-ACCESS		read-write
		STATUS			current
		DESCRIPTION
				"TYPE: - Checkbox
				 PAGE: - Audio Likeness
					Alarm Enable  cmdID= 3110 "
		::= { iqhip00CmdEntry 3110 }


	iqhip00AudioLikenessDetector4Likeness OBJECT-TYPE
		SYNTAX		RollCallString
		MAX-ACCESS		read-only
		STATUS			current
		DESCRIPTION
				"TYPE: - Display
				 PAGE: - Audio Likeness
					Likeness  cmdID= 3123  format=   "
		::= { iqhip00CmdEntry 3123 }


	iqhip00AudioLikenessDetector4State OBJECT-TYPE
		SYNTAX		RollCallString
		MAX-ACCESS		read-only
		STATUS			current
		DESCRIPTION
				"TYPE: - Display
				 PAGE: - Audio Likeness
					State  cmdID= 3133  format=   "
		::= { iqhip00CmdEntry 3133 }


	iqhip00AudioLikenessDetector4SelectChannelA OBJECT-TYPE
		SYNTAX		INTEGER
		MAX-ACCESS		read-write
		STATUS			current
		DESCRIPTION
				"TYPE: - Number
				 PAGE: - Audio Likeness
					Select Channel A  cmdID= 3106  min= 1  max= 16  step= 1  format= %0.0f  div_scale= 1
					Min = 1  Max = 16  Step = 1 "
		::= { iqhip00CmdEntry 3106 }


	iqhip00AudioLikenessDetector4SelectChannelB OBJECT-TYPE
		SYNTAX		INTEGER
		MAX-ACCESS		read-write
		STATUS			current
		DESCRIPTION
				"TYPE: - Number
				 PAGE: - Audio Likeness
					Select Channel B  cmdID= 3107  min= 1  max= 16  step= 1  format= %0.0f  div_scale= 1
					Min = 1  Max = 16  Step = 1 "
		::= { iqhip00CmdEntry 3107 }


	iqhip00AudioLikenessDetector4AlarmEnable OBJECT-TYPE
		SYNTAX		INTEGER { disable(0), enable(1) }
		MAX-ACCESS		read-write
		STATUS			current
		DESCRIPTION
				"TYPE: - Checkbox
				 PAGE: - Audio Likeness
					Alarm Enable  cmdID= 3111 "
		::= { iqhip00CmdEntry 3111 }


	iqhip00UMIDReaderDetectonYOnly OBJECT-TYPE
		SYNTAX		INTEGER { disable(0), enable(1) }
		MAX-ACCESS		read-write
		STATUS			current
		DESCRIPTION
				"TYPE: - Checkbox
				 PAGE: - UMID
					Detect on Y Only  cmdID= 1742 "
		::= { iqhip00CmdEntry 1742 }


	iqhip00UMIDReaderUMIDPresence OBJECT-TYPE
		SYNTAX		RollCallString
		MAX-ACCESS		read-only
		STATUS			current
		DESCRIPTION
				"TYPE: - Display
				 PAGE: - UMID
					UMID Presence  cmdID= 1730  format=   "
		::= { iqhip00CmdEntry 1730 }


	iqhip00UMIDReaderFoundOnLine OBJECT-TYPE
		SYNTAX		RollCallString
		MAX-ACCESS		read-only
		STATUS			current
		DESCRIPTION
				"TYPE: - Display
				 PAGE: - UMID
					Found On Line:  cmdID= 1731  format=   "
		::= { iqhip00CmdEntry 1731 }


	iqhip00ReaderUniversalLabelVersionNumber OBJECT-TYPE
		SYNTAX		RollCallString
		MAX-ACCESS		read-only
		STATUS			current
		DESCRIPTION
				"TYPE: - Display
				 PAGE: - UMID
					Version Number  cmdID= 1732  format=   "
		::= { iqhip00CmdEntry 1732 }


	iqhip00ReaderUniversalLabelMaterialType OBJECT-TYPE
		SYNTAX		RollCallString
		MAX-ACCESS		read-only
		STATUS			current
		DESCRIPTION
				"TYPE: - Display
				 PAGE: - UMID
					Material Type  cmdID= 1733  format=   "
		::= { iqhip00CmdEntry 1733 }


	iqhip00ReaderUniversalLabelIdentMatNumGen OBJECT-TYPE
		SYNTAX		RollCallString
		MAX-ACCESS		read-only
		STATUS			current
		DESCRIPTION
				"TYPE: - Display
				 PAGE: - UMID
					Ident Mat Num Gen  cmdID= 1734  format=   "
		::= { iqhip00CmdEntry 1734 }


	iqhip00ReaderUniversalLabelIdentInstNumGen OBJECT-TYPE
		SYNTAX		RollCallString
		MAX-ACCESS		read-only
		STATUS			current
		DESCRIPTION
				"TYPE: - Display
				 PAGE: - UMID
					Ident Inst Num Gen  cmdID= 1735  format=   "
		::= { iqhip00CmdEntry 1735 }


	iqhip00UMIDReaderInstanceNumber OBJECT-TYPE
		SYNTAX		RollCallString
		MAX-ACCESS		read-only
		STATUS			current
		DESCRIPTION
				"TYPE: - Display
				 PAGE: - UMID
					Instance Number  cmdID= 1736  format=   "
		::= { iqhip00CmdEntry 1736 }


	iqhip00ReaderMaterialNumber1_4 OBJECT-TYPE
		SYNTAX		RollCallString
		MAX-ACCESS		read-only
		STATUS			current
		DESCRIPTION
				"TYPE: - Display
				 PAGE: - UMID
					Material Num 1-4  cmdID= 1737  format=   "
		::= { iqhip00CmdEntry 1737 }


	iqhip00ReaderMaterialNumber5_8 OBJECT-TYPE
		SYNTAX		RollCallString
		MAX-ACCESS		read-only
		STATUS			current
		DESCRIPTION
				"TYPE: - Display
				 PAGE: - UMID
					Material Num 5-8  cmdID= 1738  format=   "
		::= { iqhip00CmdEntry 1738 }


	iqhip00ReaderMaterialNumber9_12 OBJECT-TYPE
		SYNTAX		RollCallString
		MAX-ACCESS		read-only
		STATUS			current
		DESCRIPTION
				"TYPE: - Display
				 PAGE: - UMID
					Material Num 9-12  cmdID= 1739  format=   "
		::= { iqhip00CmdEntry 1739 }


	iqhip00ReaderMaterialNumber13_16 OBJECT-TYPE
		SYNTAX		RollCallString
		MAX-ACCESS		read-only
		STATUS			current
		DESCRIPTION
				"TYPE: - Display
				 PAGE: - UMID
					Material Num 13-16  cmdID= 1740  format=   "
		::= { iqhip00CmdEntry 1740 }


	iqhip00UMIDReaderCount OBJECT-TYPE
		SYNTAX		RollCallString
		MAX-ACCESS		read-only
		STATUS			current
		DESCRIPTION
				"TYPE: - Display
				 PAGE: - UMID
					Count  cmdID= 1741  format=   "
		::= { iqhip00CmdEntry 1741 }


	iqhip00HyperionUMIDUMIDDelete OBJECT-TYPE
		SYNTAX		INTEGER { disable(0), enable(1) }
		MAX-ACCESS		read-write
		STATUS			current
		DESCRIPTION
				"TYPE: - Checkbox
				 PAGE: - UMID
					UMID Delete  cmdID= 1720 "
		::= { iqhip00CmdEntry 1720 }


	iqhip00UMIDGeneratorEnable OBJECT-TYPE
		SYNTAX		INTEGER { disable(0), enable(1) }
		MAX-ACCESS		read-write
		STATUS			current
		DESCRIPTION
				"TYPE: - Checkbox
				 PAGE: - UMID
					Enable  cmdID= 1700 "
		::= { iqhip00CmdEntry 1700 }


	iqhip00UMIDGeneratorGeneratorStatus OBJECT-TYPE
		SYNTAX		RollCallString
		MAX-ACCESS		read-only
		STATUS			current
		DESCRIPTION
				"TYPE: - Display
				 PAGE: - UMID
					Generator Status  cmdID= 1713  format=   "
		::= { iqhip00CmdEntry 1713 }


	iqhip00UMIDGeneratorGenerateonYOnly OBJECT-TYPE
		SYNTAX		INTEGER { disable(0), enable(1) }
		MAX-ACCESS		read-write
		STATUS			current
		DESCRIPTION
				"TYPE: - Checkbox
				 PAGE: - UMID
					Generate on Y Only  cmdID= 1712 "
		::= { iqhip00CmdEntry 1712 }


	iqhip00UMIDGeneratorTake OBJECT-TYPE
		SYNTAX		INTEGER { noAction(0),val_Take(1) }
		MAX-ACCESS		read-write
		STATUS			current
		DESCRIPTION
				"TYPE: - Button
				 PAGE: - UMID
					Take  cmdID= 1711  value= 1  "
		::= { iqhip00CmdEntry 1711 }


	iqhip00UMIDGeneratorLineNumber OBJECT-TYPE
		SYNTAX		INTEGER {
							val_Line_8(8),
							val_Line_9(9),
							val_Line_10(10),
							val_Line_11(11),
							val_Line_12(12),
							val_Line_13(13),
							val_Line_14(14),
							val_Line_15(15),
							val_Line_16(16),
							val_Line_17(17),
							val_Line_18(18),
							val_Line_19(19),
							val_Line_20(20)
							}
		MAX-ACCESS		read-write
		STATUS			current
		DESCRIPTION
				"TYPE: - RadiobuttonList
				 PAGE: - UMID
					Line Number  cmdID= 1701
					Line 8  value= 8
					Line 9  value= 9
					Line 10  value= 10
					Line 11  value= 11
					Line 12  value= 12
					Line 13  value= 13
					Line 14  value= 14
					Line 15  value= 15
					Line 16  value= 16
					Line 17  value= 17
					Line 18  value= 18
					Line 19  value= 19
					Line 20  value= 20  "
		::= { iqhip00CmdEntry 1701 }


	iqhip00GeneratorUniversalLabelVersionNumber OBJECT-TYPE
		SYNTAX		INTEGER
		MAX-ACCESS		read-write
		STATUS			current
		DESCRIPTION
				"TYPE: - Number
				 PAGE: - UMID
					Version Number  cmdID= 1703  min= 0  max= 255  step= 1  format= %0.0f  div_scale= 1
					Min = 0  Max = 255  Step = 1 "
		::= { iqhip00CmdEntry 1703 }


	iqhip00GeneratorUniversalLabelMaterialType OBJECT-TYPE
		SYNTAX		INTEGER
		MAX-ACCESS		read-write
		STATUS			current
		DESCRIPTION
				"TYPE: - Number
				 PAGE: - UMID
					Material Type  cmdID= 1704  min= 1  max= 15  step= 1  format= %0.0f  div_scale= 1
					Min = 1  Max = 15  Step = 1 "
		::= { iqhip00CmdEntry 1704 }


	iqhip00GeneratorUniversalLabelIdentofMaterial OBJECT-TYPE
		SYNTAX		INTEGER
		MAX-ACCESS		read-write
		STATUS			current
		DESCRIPTION
				"TYPE: - Number
				 PAGE: - UMID
					Ident of Material  cmdID= 1705  min= 0  max= 7  step= 1  format= %0.0f  div_scale= 1
					Min = 0  Max = 7  Step = 1 "
		::= { iqhip00CmdEntry 1705 }


	iqhip00GeneratorUniversalLabelIdentofInstance OBJECT-TYPE
		SYNTAX		INTEGER
		MAX-ACCESS		read-write
		STATUS			current
		DESCRIPTION
				"TYPE: - Number
				 PAGE: - UMID
					Ident of Instance  cmdID= 1706  min= 0  max= 15  step= 1  format= %0.0f  div_scale= 1
					Min = 0  Max = 15  Step = 1 "
		::= { iqhip00CmdEntry 1706 }


	iqhip00UMIDGeneratorInstanceNum OBJECT-TYPE
		SYNTAX		RollCallString
		MAX-ACCESS		read-write
		STATUS			current
		DESCRIPTION
				"TYPE: - Editstring
				 PAGE: - UMID
					Instance Num  cmdID= 1702  "
		::= { iqhip00CmdEntry 1702 }


	iqhip00UMIDGeneratorMaterialNum1_4 OBJECT-TYPE
		SYNTAX		RollCallString
		MAX-ACCESS		read-write
		STATUS			current
		DESCRIPTION
				"TYPE: - Editstring
				 PAGE: - UMID
					Material Num 1-4  cmdID= 1707  "
		::= { iqhip00CmdEntry 1707 }


	iqhip00UMIDGeneratorMaterialNum5_8 OBJECT-TYPE
		SYNTAX		RollCallString
		MAX-ACCESS		read-write
		STATUS			current
		DESCRIPTION
				"TYPE: - Editstring
				 PAGE: - UMID
					Material Num 5-8  cmdID= 1708  "
		::= { iqhip00CmdEntry 1708 }


	iqhip00UMIDGeneratorMaterialNum9_12 OBJECT-TYPE
		SYNTAX		RollCallString
		MAX-ACCESS		read-write
		STATUS			current
		DESCRIPTION
				"TYPE: - Editstring
				 PAGE: - UMID
					Material Num 9-12  cmdID= 1709  "
		::= { iqhip00CmdEntry 1709 }


	iqhip00UMIDGeneratorMaterialNum13_16 OBJECT-TYPE
		SYNTAX		RollCallString
		MAX-ACCESS		read-write
		STATUS			current
		DESCRIPTION
				"TYPE: - Editstring
				 PAGE: - UMID
					Material Num 13-16  cmdID= 1710  "
		::= { iqhip00CmdEntry 1710 }


	iqhip00HyperionUMIDUMIDAlarmEnable OBJECT-TYPE
		SYNTAX		INTEGER { disable(0), enable(1) }
		MAX-ACCESS		read-write
		STATUS			current
		DESCRIPTION
				"TYPE: - Checkbox
				 PAGE: - UMID
					UMID Alarm Enable  cmdID= 1744 "
		::= { iqhip00CmdEntry 1744 }


	iqhip00PIDReaderPIDPresence OBJECT-TYPE
		SYNTAX		RollCallString
		MAX-ACCESS		read-only
		STATUS			current
		DESCRIPTION
				"TYPE: - Display
				 PAGE: - PID
					PID Presence  cmdID= 1930  format=   "
		::= { iqhip00CmdEntry 1930 }


	iqhip00PIDReaderFoundOnLine OBJECT-TYPE
		SYNTAX		RollCallString
		MAX-ACCESS		read-only
		STATUS			current
		DESCRIPTION
				"TYPE: - Display
				 PAGE: - PID
					Found On Line:  cmdID= 1932  format=   "
		::= { iqhip00CmdEntry 1932 }


	iqhip00PIDReaderHouseID OBJECT-TYPE
		SYNTAX		RollCallString
		MAX-ACCESS		read-only
		STATUS			current
		DESCRIPTION
				"TYPE: - Display
				 PAGE: - PID
					House ID  cmdID= 1931  format=   "
		::= { iqhip00CmdEntry 1931 }


	iqhip00PIDReaderProgramTitle OBJECT-TYPE
		SYNTAX		RollCallString
		MAX-ACCESS		read-only
		STATUS			current
		DESCRIPTION
				"TYPE: - Display
				 PAGE: - PID
					Program Title  cmdID= 1933  format=   "
		::= { iqhip00CmdEntry 1933 }


	iqhip00PIDReaderSegmentNumber OBJECT-TYPE
		SYNTAX		RollCallString
		MAX-ACCESS		read-only
		STATUS			current
		DESCRIPTION
				"TYPE: - Display
				 PAGE: - PID
					Segment Number  cmdID= 1934  format=   "
		::= { iqhip00CmdEntry 1934 }


	iqhip00PIDReaderDuration OBJECT-TYPE
		SYNTAX		RollCallString
		MAX-ACCESS		read-only
		STATUS			current
		DESCRIPTION
				"TYPE: - Display
				 PAGE: - PID
					Duration  cmdID= 1935  format=   "
		::= { iqhip00CmdEntry 1935 }


	iqhip00PIDReaderFrameRate OBJECT-TYPE
		SYNTAX		RollCallString
		MAX-ACCESS		read-only
		STATUS			current
		DESCRIPTION
				"TYPE: - Display
				 PAGE: - PID
					Frame Rate  cmdID= 1936  format=   "
		::= { iqhip00CmdEntry 1936 }


	iqhip00PIDReaderCount OBJECT-TYPE
		SYNTAX		RollCallString
		MAX-ACCESS		read-only
		STATUS			current
		DESCRIPTION
				"TYPE: - Display
				 PAGE: - PID
					Count  cmdID= 1937  format=   "
		::= { iqhip00CmdEntry 1937 }


	iqhip00HyperionPIDPIDDelete OBJECT-TYPE
		SYNTAX		INTEGER { disable(0), enable(1) }
		MAX-ACCESS		read-write
		STATUS			current
		DESCRIPTION
				"TYPE: - Checkbox
				 PAGE: - PID
					PID Delete  cmdID= 1920 "
		::= { iqhip00CmdEntry 1920 }


	iqhip00PIDGeneratorEnable OBJECT-TYPE
		SYNTAX		INTEGER { disable(0), enable(1) }
		MAX-ACCESS		read-write
		STATUS			current
		DESCRIPTION
				"TYPE: - Checkbox
				 PAGE: - PID
					Enable  cmdID= 1900 "
		::= { iqhip00CmdEntry 1900 }


	iqhip00PIDGeneratorGeneratorStatus OBJECT-TYPE
		SYNTAX		RollCallString
		MAX-ACCESS		read-only
		STATUS			current
		DESCRIPTION
				"TYPE: - Display
				 PAGE: - PID
					Generator Status  cmdID= 1912  format=   "
		::= { iqhip00CmdEntry 1912 }


	iqhip00PIDGeneratorTake OBJECT-TYPE
		SYNTAX		INTEGER { noAction(0),val_Take(1) }
		MAX-ACCESS		read-write
		STATUS			current
		DESCRIPTION
				"TYPE: - Button
				 PAGE: - PID
					Take  cmdID= 1911  value= 1  "
		::= { iqhip00CmdEntry 1911 }


	iqhip00PIDGeneratorLineNumber OBJECT-TYPE
		SYNTAX		INTEGER {
							val_Line_8(8),
							val_Line_9(9),
							val_Line_10(10),
							val_Line_11(11),
							val_Line_12(12),
							val_Line_13(13),
							val_Line_14(14),
							val_Line_15(15),
							val_Line_16(16),
							val_Line_17(17),
							val_Line_18(18),
							val_Line_19(19),
							val_Line_20(20)
							}
		MAX-ACCESS		read-write
		STATUS			current
		DESCRIPTION
				"TYPE: - RadiobuttonList
				 PAGE: - PID
					Line Number  cmdID= 1901
					Line 8  value= 8
					Line 9  value= 9
					Line 10  value= 10
					Line 11  value= 11
					Line 12  value= 12
					Line 13  value= 13
					Line 14  value= 14
					Line 15  value= 15
					Line 16  value= 16
					Line 17  value= 17
					Line 18  value= 18
					Line 19  value= 19
					Line 20  value= 20  "
		::= { iqhip00CmdEntry 1901 }


	iqhip00PIDGeneratorHouseID OBJECT-TYPE
		SYNTAX		RollCallString
		MAX-ACCESS		read-write
		STATUS			current
		DESCRIPTION
				"TYPE: - Editstring
				 PAGE: - PID
					House ID  cmdID= 1902  "
		::= { iqhip00CmdEntry 1902 }


	iqhip00PIDGeneratorProgramTitle OBJECT-TYPE
		SYNTAX		RollCallString
		MAX-ACCESS		read-write
		STATUS			current
		DESCRIPTION
				"TYPE: - Editstring
				 PAGE: - PID
					Program Title  cmdID= 1903  "
		::= { iqhip00CmdEntry 1903 }


	iqhip00PIDGeneratorProgramTitleEn OBJECT-TYPE
		SYNTAX		INTEGER { disable(0), enable(1) }
		MAX-ACCESS		read-write
		STATUS			current
		DESCRIPTION
				"TYPE: - Checkbox
				 PAGE: - PID
					Program Title En  cmdID= 1907 "
		::= { iqhip00CmdEntry 1907 }


	iqhip00PIDGeneratorSegmentNumber OBJECT-TYPE
		SYNTAX		RollCallString
		MAX-ACCESS		read-write
		STATUS			current
		DESCRIPTION
				"TYPE: - Editstring
				 PAGE: - PID
					Segment Number  cmdID= 1904  "
		::= { iqhip00CmdEntry 1904 }


	iqhip00PIDGeneratorSegmentNumberEn OBJECT-TYPE
		SYNTAX		INTEGER { disable(0), enable(1) }
		MAX-ACCESS		read-write
		STATUS			current
		DESCRIPTION
				"TYPE: - Checkbox
				 PAGE: - PID
					Segment Number En  cmdID= 1908 "
		::= { iqhip00CmdEntry 1908 }


	iqhip00PIDGeneratorDuration OBJECT-TYPE
		SYNTAX		RollCallString
		MAX-ACCESS		read-write
		STATUS			current
		DESCRIPTION
				"TYPE: - Editstring
				 PAGE: - PID
					Duration  cmdID= 1905  "
		::= { iqhip00CmdEntry 1905 }


	iqhip00PIDGeneratorDurationEn OBJECT-TYPE
		SYNTAX		INTEGER { disable(0), enable(1) }
		MAX-ACCESS		read-write
		STATUS			current
		DESCRIPTION
				"TYPE: - Checkbox
				 PAGE: - PID
					Duration En  cmdID= 1909 "
		::= { iqhip00CmdEntry 1909 }


	iqhip00PIDGeneratorFrameRateEn OBJECT-TYPE
		SYNTAX		INTEGER { disable(0), enable(1) }
		MAX-ACCESS		read-write
		STATUS			current
		DESCRIPTION
				"TYPE: - Checkbox
				 PAGE: - PID
					Frame Rate En  cmdID= 1910 "
		::= { iqhip00CmdEntry 1910 }


	iqhip00PIDGeneratorFrameRate OBJECT-TYPE
		SYNTAX		INTEGER {
							val_Follow_Input(0),
							val_23_976(1),
							val_24_000(2),
							val_25_000(3),
							val_29_970(4),
							val_30_000(5),
							val_50_000(6),
							val_59_940(7),
							val_60_000(8)
							}
		MAX-ACCESS		read-write
		STATUS			current
		DESCRIPTION
				"TYPE: - RadiobuttonList
				 PAGE: - PID
					Frame Rate  cmdID= 1906
					Follow Input  value= 0
					23.976  value= 1
					24.000  value= 2
					25.000  value= 3
					29.970  value= 4
					30.000  value= 5
					50.000  value= 6
					59.940  value= 7
					60.000  value= 8  "
		::= { iqhip00CmdEntry 1906 }


	iqhip00HyperionPIDPIDAlarmEnable OBJECT-TYPE
		SYNTAX		INTEGER { disable(0), enable(1) }
		MAX-ACCESS		read-write
		STATUS			current
		DESCRIPTION
				"TYPE: - Checkbox
				 PAGE: - PID
					PID Alarm Enable  cmdID= 1938 "
		::= { iqhip00CmdEntry 1938 }


	iqhip00HyperionOSDOSDPassword OBJECT-TYPE
		SYNTAX		RollCallString
		MAX-ACCESS		read-write
		STATUS			current
		DESCRIPTION
				"TYPE: - Editstring
				 PAGE: - OSD
					OSD Password: !!!  cmdID= 5001  "
		::= { iqhip00CmdEntry 5001 }


	iqhip00HyperionOSDOSDEnable OBJECT-TYPE
		SYNTAX		INTEGER { disable(0), enable(1) }
		MAX-ACCESS		read-write
		STATUS			current
		DESCRIPTION
				"TYPE: - Checkbox
				 PAGE: - OSD
					OSD Enable  cmdID= 5000 "
		::= { iqhip00CmdEntry 5000 }


	iqhip00HyperionOSDOSDEnableoutput7 OBJECT-TYPE
		SYNTAX		INTEGER { disable(0), enable(1) }
		MAX-ACCESS		read-write
		STATUS			current
		DESCRIPTION
				"TYPE: - Checkbox
				 PAGE: - OSD
					OSD Enable output 7  cmdID= 5019 "
		::= { iqhip00CmdEntry 5019 }


	iqhip00OSDStillishDetWindowOSWinEn OBJECT-TYPE
		SYNTAX		INTEGER { disable(0), enable(1) }
		MAX-ACCESS		read-write
		STATUS			current
		DESCRIPTION
				"TYPE: - Checkbox
				 PAGE: - OSD
					OS Win En  cmdID= 1212 "
		::= { iqhip00CmdEntry 1212 }


	iqhip00OSDStillishDetWindowXPosition OBJECT-TYPE
		SYNTAX		INTEGER
		MAX-ACCESS		read-write
		STATUS			current
		DESCRIPTION
				"TYPE: - Number
				 PAGE: - OSD
					X Position  cmdID= 1208  min= 0  max= 3000  step= 1  format= %0.0f  div_scale= 1
					Min = 0  Max = 3000  Step = 1 "
		::= { iqhip00CmdEntry 1208 }


	iqhip00OSDStillishDetWindowWidth OBJECT-TYPE
		SYNTAX		INTEGER
		MAX-ACCESS		read-write
		STATUS			current
		DESCRIPTION
				"TYPE: - Number
				 PAGE: - OSD
					Width  cmdID= 1209  min= 0  max= 3000  step= 1  format= %0.0f  div_scale= 1
					Min = 0  Max = 3000  Step = 1 "
		::= { iqhip00CmdEntry 1209 }


	iqhip00OSDStillishDetWindowYPosition OBJECT-TYPE
		SYNTAX		INTEGER
		MAX-ACCESS		read-write
		STATUS			current
		DESCRIPTION
				"TYPE: - Number
				 PAGE: - OSD
					Y Position  cmdID= 1206  min= 0  max= 25000  step= 1  format= %0.0f  div_scale= 1
					Min = 0  Max = 25000  Step = 1 "
		::= { iqhip00CmdEntry 1206 }


	iqhip00OSDStillishDetWindowHeight OBJECT-TYPE
		SYNTAX		INTEGER
		MAX-ACCESS		read-write
		STATUS			current
		DESCRIPTION
				"TYPE: - Number
				 PAGE: - OSD
					Height  cmdID= 1207  min= 0  max= 25000  step= 1  format= %0.0f  div_scale= 1
					Min = 0  Max = 25000  Step = 1 "
		::= { iqhip00CmdEntry 1207 }


	iqhip00OSDStillishDetWindowWindowMode OBJECT-TYPE
		SYNTAX		INTEGER {
							val_Inside_Window(0),
							val_Outside_Window(1)
							}
		MAX-ACCESS		read-write
		STATUS			current
		DESCRIPTION
				"TYPE: - RadiobuttonList
				 PAGE: - OSD
					Window Mode  cmdID= 1205
					Inside Window  value= 0
					Outside Window  value= 1  "
		::= { iqhip00CmdEntry 1205 }


	iqhip00OSDStillishDetWindowDetectFullScreen OBJECT-TYPE
		SYNTAX		INTEGER { noAction(0),val_Detect_Full_Screen(1) }
		MAX-ACCESS		read-write
		STATUS			current
		DESCRIPTION
				"TYPE: - Button
				 PAGE: - OSD
					Detect Full Screen  cmdID= 1220  value= 1  "
		::= { iqhip00CmdEntry 1220 }


	iqhip00OSDBlackishDetWindowOSWinEn OBJECT-TYPE
		SYNTAX		INTEGER { disable(0), enable(1) }
		MAX-ACCESS		read-write
		STATUS			current
		DESCRIPTION
				"TYPE: - Checkbox
				 PAGE: - OSD
					OS Win En  cmdID= 1227 "
		::= { iqhip00CmdEntry 1227 }


	iqhip00OSDBlackishDetWindowXPosition OBJECT-TYPE
		SYNTAX		INTEGER
		MAX-ACCESS		read-write
		STATUS			current
		DESCRIPTION
				"TYPE: - Number
				 PAGE: - OSD
					X Position  cmdID= 1222  min= 0  max= 3000  step= 1  format= %0.0f  div_scale= 1
					Min = 0  Max = 3000  Step = 1 "
		::= { iqhip00CmdEntry 1222 }


	iqhip00OSDBlackishDetWindowWidth OBJECT-TYPE
		SYNTAX		INTEGER
		MAX-ACCESS		read-write
		STATUS			current
		DESCRIPTION
				"TYPE: - Number
				 PAGE: - OSD
					Width  cmdID= 1223  min= 0  max= 3000  step= 1  format= %0.0f  div_scale= 1
					Min = 0  Max = 3000  Step = 1 "
		::= { iqhip00CmdEntry 1223 }


	iqhip00OSDBlackishDetWindowYPosition OBJECT-TYPE
		SYNTAX		INTEGER
		MAX-ACCESS		read-write
		STATUS			current
		DESCRIPTION
				"TYPE: - Number
				 PAGE: - OSD
					Y Position  cmdID= 1224  min= 0  max= 25000  step= 1  format= %0.0f  div_scale= 1
					Min = 0  Max = 25000  Step = 1 "
		::= { iqhip00CmdEntry 1224 }


	iqhip00OSDBlackishDetWindowHeight OBJECT-TYPE
		SYNTAX		INTEGER
		MAX-ACCESS		read-write
		STATUS			current
		DESCRIPTION
				"TYPE: - Number
				 PAGE: - OSD
					Height  cmdID= 1225  min= 0  max= 25000  step= 1  format= %0.0f  div_scale= 1
					Min = 0  Max = 25000  Step = 1 "
		::= { iqhip00CmdEntry 1225 }


	iqhip00OSDBlackishDetWindowWindowMode OBJECT-TYPE
		SYNTAX		INTEGER {
							val_Inside_Window(0),
							val_Outside_Window(1)
							}
		MAX-ACCESS		read-write
		STATUS			current
		DESCRIPTION
				"TYPE: - RadiobuttonList
				 PAGE: - OSD
					Window Mode  cmdID= 1229
					Inside Window  value= 0
					Outside Window  value= 1  "
		::= { iqhip00CmdEntry 1229 }


	iqhip00OSDBlackishDetWindowDetectFullScreen OBJECT-TYPE
		SYNTAX		INTEGER { noAction(0),val_Detect_Full_Screen(1) }
		MAX-ACCESS		read-write
		STATUS			current
		DESCRIPTION
				"TYPE: - Button
				 PAGE: - OSD
					Detect Full Screen  cmdID= 1242  value= 1  "
		::= { iqhip00CmdEntry 1242 }


	iqhip00OSDOnScreenDispEnIndicators OBJECT-TYPE
		SYNTAX		INTEGER { disable(0), enable(1) }
		MAX-ACCESS		read-write
		STATUS			current
		DESCRIPTION
				"TYPE: - Checkbox
				 PAGE: - OSD
					Indicators   cmdID= 5002 "
		::= { iqhip00CmdEntry 5002 }


	iqhip00OSDOnScreenDispEnAudioLevelInds OBJECT-TYPE
		SYNTAX		INTEGER { disable(0), enable(1) }
		MAX-ACCESS		read-write
		STATUS			current
		DESCRIPTION
				"TYPE: - Checkbox
				 PAGE: - OSD
					Audio Level Inds  cmdID= 5004 "
		::= { iqhip00CmdEntry 5004 }


	iqhip00OSDOnScreenDispEnTimecode OBJECT-TYPE
		SYNTAX		INTEGER { disable(0), enable(1) }
		MAX-ACCESS		read-write
		STATUS			current
		DESCRIPTION
				"TYPE: - Checkbox
				 PAGE: - OSD
					Timecode  cmdID= 5007 "
		::= { iqhip00CmdEntry 5007 }


	iqhip00OSDOnScreenDispEnGreyBackground OBJECT-TYPE
		SYNTAX		INTEGER { disable(0), enable(1) }
		MAX-ACCESS		read-write
		STATUS			current
		DESCRIPTION
				"TYPE: - Checkbox
				 PAGE: - OSD
					Grey Background  cmdID= 5015 "
		::= { iqhip00CmdEntry 5015 }


	iqhip00OSDOnScreenDispEnInput1Name OBJECT-TYPE
		SYNTAX		INTEGER { disable(0), enable(1) }
		MAX-ACCESS		read-write
		STATUS			current
		DESCRIPTION
				"TYPE: - Checkbox
				 PAGE: - OSD
					Input 1 Name  cmdID= 5010 "
		::= { iqhip00CmdEntry 5010 }


	iqhip00OSDOnScreenDispEnCaption1Edit OBJECT-TYPE
		SYNTAX		RollCallString
		MAX-ACCESS		read-write
		STATUS			current
		DESCRIPTION
				"TYPE: - Editstring
				 PAGE: - OSD
					Caption 1 Edit  cmdID= 5012  "
		::= { iqhip00CmdEntry 5012 }


	iqhip00OSDOnScreenDispEnCaption1Enable OBJECT-TYPE
		SYNTAX		INTEGER { disable(0), enable(1) }
		MAX-ACCESS		read-write
		STATUS			current
		DESCRIPTION
				"TYPE: - Checkbox
				 PAGE: - OSD
					Caption 1 Enable  cmdID= 5011 "
		::= { iqhip00CmdEntry 5011 }


	iqhip00OSDOnScreenDispEnCaption2Edit OBJECT-TYPE
		SYNTAX		RollCallString
		MAX-ACCESS		read-write
		STATUS			current
		DESCRIPTION
				"TYPE: - Editstring
				 PAGE: - OSD
					Caption 2 Edit  cmdID= 5014  "
		::= { iqhip00CmdEntry 5014 }


	iqhip00OSDOnScreenDispEnCaption2Enable OBJECT-TYPE
		SYNTAX		INTEGER { disable(0), enable(1) }
		MAX-ACCESS		read-write
		STATUS			current
		DESCRIPTION
				"TYPE: - Checkbox
				 PAGE: - OSD
					Caption 2 Enable  cmdID= 5013 "
		::= { iqhip00CmdEntry 5013 }


	iqhip00OSDOnScreenDispEnContentAdvisory OBJECT-TYPE
		SYNTAX		INTEGER { disable(0), enable(1) }
		MAX-ACCESS		read-write
		STATUS			current
		DESCRIPTION
				"TYPE: - Checkbox
				 PAGE: - OSD
					Content Advisory  cmdID= 5016 "
		::= { iqhip00CmdEntry 5016 }


	iqhip00OSDOnScreenDispEnIncomingPID OBJECT-TYPE
		SYNTAX		INTEGER { disable(0), enable(1) }
		MAX-ACCESS		read-write
		STATUS			current
		DESCRIPTION
				"TYPE: - Checkbox
				 PAGE: - OSD
					Incoming PID  cmdID= 5017 "
		::= { iqhip00CmdEntry 5017 }


	iqhip00OSDOnScreenDispEnOutgoingPID OBJECT-TYPE
		SYNTAX		INTEGER { disable(0), enable(1) }
		MAX-ACCESS		read-write
		STATUS			current
		DESCRIPTION
				"TYPE: - Checkbox
				 PAGE: - OSD
					Outgoing PID  cmdID= 5018 "
		::= { iqhip00CmdEntry 5018 }


	iqhip00OSDOnScreenDispEnAudioLvlIndZoom OBJECT-TYPE
		SYNTAX		INTEGER { disable(0), enable(1) }
		MAX-ACCESS		read-write
		STATUS			current
		DESCRIPTION
				"TYPE: - Checkbox
				 PAGE: - OSD
					Audio Lvl Ind Zoom  cmdID= 5003 "
		::= { iqhip00CmdEntry 5003 }


	iqhip00HyperionHyperionDetStatus OBJECT-TYPE
		SYNTAX		INTEGER
		MAX-ACCESS		read-write
		STATUS			current
		DESCRIPTION
				"TYPE: - Number
					Hyperion Det Status  cmdID= 5050  min= 0  max= 63  step= 1  format= %0.0f  div_scale= 1
					Min = 0  Max = 63  Step = 1 "
		::= { iqhip00CmdEntry 5050 }


	iqhip00MemoriesMemorySave OBJECT-TYPE
		SYNTAX		INTEGER {
							val_Save_1(1),
							val_Save_2(2),
							val_Save_3(3),
							val_Save_4(4),
							val_Save_5(5),
							val_Save_6(6),
							val_Save_7(7),
							val_Save_8(8),
							val_Save_9(9),
							val_Save_10(10),
							val_Save_11(11),
							val_Save_12(12),
							val_Save_13(13),
							val_Save_14(14),
							val_Save_15(15),
							val_Save_16(16)
							}
		MAX-ACCESS		read-write
		STATUS			current
		DESCRIPTION
				"TYPE: - Button
				 PAGE: - Memories
					Save 1  cmdID= 1600  value= 1
					Save 2  cmdID= 1600  value= 2
					Save 3  cmdID= 1600  value= 3
					Save 4  cmdID= 1600  value= 4
					Save 5  cmdID= 1600  value= 5
					Save 6  cmdID= 1600  value= 6
					Save 7  cmdID= 1600  value= 7
					Save 8  cmdID= 1600  value= 8
					Save 9  cmdID= 1600  value= 9
					Save 10  cmdID= 1600  value= 10
					Save 11  cmdID= 1600  value= 11
					Save 12  cmdID= 1600  value= 12
					Save 13  cmdID= 1600  value= 13
					Save 14  cmdID= 1600  value= 14
					Save 15  cmdID= 1600  value= 15
					Save 16  cmdID= 1600  value= 16  "
		::= { iqhip00CmdEntry 1600 }


	iqhip00MemoriesMemoryRecall OBJECT-TYPE
		SYNTAX		INTEGER {
							val_Recall_1(1),
							val_Recall_2(2),
							val_Recall_3(3),
							val_Recall_4(4),
							val_Recall_5(5),
							val_Recall_6(6),
							val_Recall_7(7),
							val_Recall_8(8),
							val_Recall_9(9),
							val_Recall_10(10),
							val_Recall_11(11),
							val_Recall_12(12),
							val_Recall_13(13),
							val_Recall_14(14),
							val_Recall_15(15),
							val_Recall_16(16)
							}
		MAX-ACCESS		read-write
		STATUS			current
		DESCRIPTION
				"TYPE: - Button
				 PAGE: - Memories
					Recall 1  cmdID= 1601  value= 1
					Recall 2  cmdID= 1601  value= 2
					Recall 3  cmdID= 1601  value= 3
					Recall 4  cmdID= 1601  value= 4
					Recall 5  cmdID= 1601  value= 5
					Recall 6  cmdID= 1601  value= 6
					Recall 7  cmdID= 1601  value= 7
					Recall 8  cmdID= 1601  value= 8
					Recall 9  cmdID= 1601  value= 9
					Recall 10  cmdID= 1601  value= 10
					Recall 11  cmdID= 1601  value= 11
					Recall 12  cmdID= 1601  value= 12
					Recall 13  cmdID= 1601  value= 13
					Recall 14  cmdID= 1601  value= 14
					Recall 15  cmdID= 1601  value= 15
					Recall 16  cmdID= 1601  value= 16  "
		::= { iqhip00CmdEntry 1601 }


	iqhip00MemoriesMemory1Name OBJECT-TYPE
		SYNTAX		RollCallString
		MAX-ACCESS		read-write
		STATUS			current
		DESCRIPTION
				"TYPE: - Editstring
				 PAGE: - Memories
					Name 1  cmdID= 5541  "
		::= { iqhip00CmdEntry 5541 }


	iqhip00MemoriesMemory2Name OBJECT-TYPE
		SYNTAX		RollCallString
		MAX-ACCESS		read-write
		STATUS			current
		DESCRIPTION
				"TYPE: - Editstring
				 PAGE: - Memories
					Name 2  cmdID= 5542  "
		::= { iqhip00CmdEntry 5542 }


	iqhip00MemoriesMemory3Name OBJECT-TYPE
		SYNTAX		RollCallString
		MAX-ACCESS		read-write
		STATUS			current
		DESCRIPTION
				"TYPE: - Editstring
				 PAGE: - Memories
					Name 3  cmdID= 5543  "
		::= { iqhip00CmdEntry 5543 }


	iqhip00MemoriesMemory4Name OBJECT-TYPE
		SYNTAX		RollCallString
		MAX-ACCESS		read-write
		STATUS			current
		DESCRIPTION
				"TYPE: - Editstring
				 PAGE: - Memories
					Name 4  cmdID= 5544  "
		::= { iqhip00CmdEntry 5544 }


	iqhip00MemoriesMemory5Name OBJECT-TYPE
		SYNTAX		RollCallString
		MAX-ACCESS		read-write
		STATUS			current
		DESCRIPTION
				"TYPE: - Editstring
				 PAGE: - Memories
					Name 5  cmdID= 5545  "
		::= { iqhip00CmdEntry 5545 }


	iqhip00MemoriesMemory6Name OBJECT-TYPE
		SYNTAX		RollCallString
		MAX-ACCESS		read-write
		STATUS			current
		DESCRIPTION
				"TYPE: - Editstring
				 PAGE: - Memories
					Name 6  cmdID= 5546  "
		::= { iqhip00CmdEntry 5546 }


	iqhip00MemoriesMemory7Name OBJECT-TYPE
		SYNTAX		RollCallString
		MAX-ACCESS		read-write
		STATUS			current
		DESCRIPTION
				"TYPE: - Editstring
				 PAGE: - Memories
					Name 7  cmdID= 5547  "
		::= { iqhip00CmdEntry 5547 }


	iqhip00MemoriesMemory8Name OBJECT-TYPE
		SYNTAX		RollCallString
		MAX-ACCESS		read-write
		STATUS			current
		DESCRIPTION
				"TYPE: - Editstring
				 PAGE: - Memories
					Name 8  cmdID= 5548  "
		::= { iqhip00CmdEntry 5548 }


	iqhip00MemoriesMemory9Name OBJECT-TYPE
		SYNTAX		RollCallString
		MAX-ACCESS		read-write
		STATUS			current
		DESCRIPTION
				"TYPE: - Editstring
				 PAGE: - Memories
					Name 9  cmdID= 5549  "
		::= { iqhip00CmdEntry 5549 }


	iqhip00MemoriesMemory10Name OBJECT-TYPE
		SYNTAX		RollCallString
		MAX-ACCESS		read-write
		STATUS			current
		DESCRIPTION
				"TYPE: - Editstring
				 PAGE: - Memories
					Name 10  cmdID= 5550  "
		::= { iqhip00CmdEntry 5550 }


	iqhip00MemoriesMemory11Name OBJECT-TYPE
		SYNTAX		RollCallString
		MAX-ACCESS		read-write
		STATUS			current
		DESCRIPTION
				"TYPE: - Editstring
				 PAGE: - Memories
					Name 11  cmdID= 5551  "
		::= { iqhip00CmdEntry 5551 }


	iqhip00MemoriesMemory12Name OBJECT-TYPE
		SYNTAX		RollCallString
		MAX-ACCESS		read-write
		STATUS			current
		DESCRIPTION
				"TYPE: - Editstring
				 PAGE: - Memories
					Name 12  cmdID= 5552  "
		::= { iqhip00CmdEntry 5552 }


	iqhip00MemoriesMemory13Name OBJECT-TYPE
		SYNTAX		RollCallString
		MAX-ACCESS		read-write
		STATUS			current
		DESCRIPTION
				"TYPE: - Editstring
				 PAGE: - Memories
					Name 13  cmdID= 5553  "
		::= { iqhip00CmdEntry 5553 }


	iqhip00MemoriesMemory14Name OBJECT-TYPE
		SYNTAX		RollCallString
		MAX-ACCESS		read-write
		STATUS			current
		DESCRIPTION
				"TYPE: - Editstring
				 PAGE: - Memories
					Name 14  cmdID= 5554  "
		::= { iqhip00CmdEntry 5554 }


	iqhip00MemoriesMemory15Name OBJECT-TYPE
		SYNTAX		RollCallString
		MAX-ACCESS		read-write
		STATUS			current
		DESCRIPTION
				"TYPE: - Editstring
				 PAGE: - Memories
					Name 15  cmdID= 5555  "
		::= { iqhip00CmdEntry 5555 }


	iqhip00MemoriesMemory16Name OBJECT-TYPE
		SYNTAX		RollCallString
		MAX-ACCESS		read-write
		STATUS			current
		DESCRIPTION
				"TYPE: - Editstring
				 PAGE: - Memories
					Name 16  cmdID= 5556  "
		::= { iqhip00CmdEntry 5556 }


	iqhip00LoggingMiscTimecodelogEnable OBJECT-TYPE
		SYNTAX		INTEGER { disable(0), enable(1) }
		MAX-ACCESS		read-write
		STATUS			current
		DESCRIPTION
				"TYPE: - Checkbox
				 PAGE: - Logging
					Timecode log En  cmdID= 35999 "
		::= { iqhip00CmdEntry 35999 }


	iqhip00LoggingMiscLogSerialNoEnable OBJECT-TYPE
		SYNTAX		INTEGER { disable(0), enable(1) }
		MAX-ACCESS		read-write
		STATUS			current
		DESCRIPTION
				"TYPE: - Checkbox
				 PAGE: - Logging
					Log Serial No.  cmdID= 1000 "
		::= { iqhip00CmdEntry 1000 }


	iqhip00LoggingMiscSerialNo OBJECT-TYPE
		SYNTAX		RollCallString
		MAX-ACCESS		read-only
		STATUS			current
		DESCRIPTION
				"TYPE: - Display
				 PAGE: - Logging
					Serial No.=  cmdID= 2000  format=   "
		::= { iqhip00CmdEntry 2000 }


	iqhip00LoggingMiscLogOSVersionEnable OBJECT-TYPE
		SYNTAX		INTEGER { disable(0), enable(1) }
		MAX-ACCESS		read-write
		STATUS			current
		DESCRIPTION
				"TYPE: - Checkbox
				 PAGE: - Logging
					Log OS Version  cmdID= 1001 "
		::= { iqhip00CmdEntry 1001 }


	iqhip00LoggingMiscOSVersion OBJECT-TYPE
		SYNTAX		RollCallString
		MAX-ACCESS		read-only
		STATUS			current
		DESCRIPTION
				"TYPE: - Display
				 PAGE: - Logging
					OS Version=  cmdID= 2001  format=   "
		::= { iqhip00CmdEntry 2001 }


	iqhip00LoggingMiscLogBuildNoEnable OBJECT-TYPE
		SYNTAX		INTEGER { disable(0), enable(1) }
		MAX-ACCESS		read-write
		STATUS			current
		DESCRIPTION
				"TYPE: - Checkbox
				 PAGE: - Logging
					Log Build No.  cmdID= 1002 "
		::= { iqhip00CmdEntry 1002 }


	iqhip00LoggingMiscBuildNo OBJECT-TYPE
		SYNTAX		RollCallString
		MAX-ACCESS		read-only
		STATUS			current
		DESCRIPTION
				"TYPE: - Display
				 PAGE: - Logging
					Build No.=  cmdID= 2002  format=   "
		::= { iqhip00CmdEntry 2002 }


	iqhip00LoggingMiscLogHardwareVerEnable OBJECT-TYPE
		SYNTAX		INTEGER { disable(0), enable(1) }
		MAX-ACCESS		read-write
		STATUS			current
		DESCRIPTION
				"TYPE: - Checkbox
				 PAGE: - Logging
					Log Hardware Ver.  cmdID= 1003 "
		::= { iqhip00CmdEntry 1003 }


	iqhip00LoggingMiscHardwareVer OBJECT-TYPE
		SYNTAX		RollCallString
		MAX-ACCESS		read-only
		STATUS			current
		DESCRIPTION
				"TYPE: - Display
				 PAGE: - Logging
					Hardware Ver.=  cmdID= 2003  format=   "
		::= { iqhip00CmdEntry 2003 }


	iqhip00LoggingMiscLogFirmwareVerEnable OBJECT-TYPE
		SYNTAX		INTEGER { disable(0), enable(1) }
		MAX-ACCESS		read-write
		STATUS			current
		DESCRIPTION
				"TYPE: - Checkbox
				 PAGE: - Logging
					Log Firmware Ver.  cmdID= 1004 "
		::= { iqhip00CmdEntry 1004 }


	iqhip00LoggingMiscFirmwareVer OBJECT-TYPE
		SYNTAX		RollCallString
		MAX-ACCESS		read-only
		STATUS			current
		DESCRIPTION
				"TYPE: - Display
				 PAGE: - Logging
					Firmware Ver.=  cmdID= 2004  format=   "
		::= { iqhip00CmdEntry 2004 }


	iqhip00LoggingMiscLogUpTimeEnable OBJECT-TYPE
		SYNTAX		INTEGER { disable(0), enable(1) }
		MAX-ACCESS		read-write
		STATUS			current
		DESCRIPTION
				"TYPE: - Checkbox
				 PAGE: - Logging
					Log Up Time  cmdID= 1005 "
		::= { iqhip00CmdEntry 1005 }


	iqhip00LoggingMiscUpTime OBJECT-TYPE
		SYNTAX		RollCallString
		MAX-ACCESS		read-only
		STATUS			current
		DESCRIPTION
				"TYPE: - Display
				 PAGE: - Logging
					Up Time=  cmdID= 2005  format=   "
		::= { iqhip00CmdEntry 2005 }


	iqhip00LoggingMiscRollTracksEnable OBJECT-TYPE
		SYNTAX		INTEGER { disable(0), enable(1) }
		MAX-ACCESS		read-write
		STATUS			current
		DESCRIPTION
				"TYPE: - Checkbox
				 PAGE: - Logging
					RollTracks  cmdID= 1158 "
		::= { iqhip00CmdEntry 1158 }


	iqhip00LoggingMiscRollTracks OBJECT-TYPE
		SYNTAX		RollCallString
		MAX-ACCESS		read-only
		STATUS			current
		DESCRIPTION
				"TYPE: - Display
				 PAGE: - Logging
					RollTracks=  cmdID= 2158  format=   "
		::= { iqhip00CmdEntry 2158 }


	iqhip00LoggingMiscOSDStatusEnable OBJECT-TYPE
		SYNTAX		INTEGER { disable(0), enable(1) }
		MAX-ACCESS		read-write
		STATUS			current
		DESCRIPTION
				"TYPE: - Checkbox
				 PAGE: - Logging
					OSD Status  cmdID= 1159 "
		::= { iqhip00CmdEntry 1159 }


	iqhip00LoggingMiscOSDStatus OBJECT-TYPE
		SYNTAX		RollCallString
		MAX-ACCESS		read-only
		STATUS			current
		DESCRIPTION
				"TYPE: - Display
				 PAGE: - Logging
					OSD Status=  cmdID= 2159  format=   "
		::= { iqhip00CmdEntry 2159 }


	iqhip00LoggingInput1InputIdentEnable OBJECT-TYPE
		SYNTAX		INTEGER { disable(0), enable(1) }
		MAX-ACCESS		read-write
		STATUS			current
		DESCRIPTION
				"TYPE: - Checkbox
				 PAGE: - Logging
					Input Ident  cmdID= 1130 "
		::= { iqhip00CmdEntry 1130 }


	iqhip00LoggingInput1InputIdent OBJECT-TYPE
		SYNTAX		RollCallString
		MAX-ACCESS		read-only
		STATUS			current
		DESCRIPTION
				"TYPE: - Display
				 PAGE: - Logging
					Input Ident=  cmdID= 2130  format=   "
		::= { iqhip00CmdEntry 2130 }


	iqhip00LoggingInput1InputNameEnable OBJECT-TYPE
		SYNTAX		INTEGER { disable(0), enable(1) }
		MAX-ACCESS		read-write
		STATUS			current
		DESCRIPTION
				"TYPE: - Checkbox
				 PAGE: - Logging
					Input Name  cmdID= 1095 "
		::= { iqhip00CmdEntry 1095 }


	iqhip00LoggingInput1InputName OBJECT-TYPE
		SYNTAX		RollCallString
		MAX-ACCESS		read-only
		STATUS			current
		DESCRIPTION
				"TYPE: - Display
				 PAGE: - Logging
					Input Name=  cmdID= 2095  format=   "
		::= { iqhip00CmdEntry 2095 }


	iqhip00LoggingInput1InputTypeEnable OBJECT-TYPE
		SYNTAX		INTEGER { disable(0), enable(1) }
		MAX-ACCESS		read-write
		STATUS			current
		DESCRIPTION
				"TYPE: - Checkbox
				 PAGE: - Logging
					Input Type  cmdID= 1096 "
		::= { iqhip00CmdEntry 1096 }


	iqhip00LoggingInput1InputType OBJECT-TYPE
		SYNTAX		RollCallString
		MAX-ACCESS		read-only
		STATUS			current
		DESCRIPTION
				"TYPE: - Display
				 PAGE: - Logging
					Input Type=  cmdID= 2096  format=   "
		::= { iqhip00CmdEntry 2096 }


	iqhip00LoggingInput1InputStateEnable OBJECT-TYPE
		SYNTAX		INTEGER { disable(0), enable(1) }
		MAX-ACCESS		read-write
		STATUS			current
		DESCRIPTION
				"TYPE: - Checkbox
				 PAGE: - Logging
					Input State  cmdID= 1006 "
		::= { iqhip00CmdEntry 1006 }


	iqhip00LoggingInput1InputState OBJECT-TYPE
		SYNTAX		RollCallString
		MAX-ACCESS		read-only
		STATUS			current
		DESCRIPTION
				"TYPE: - Display
				 PAGE: - Logging
					Input State=  cmdID= 2006  format=   "
		::= { iqhip00CmdEntry 2006 }


	iqhip00LoggingInput1InputStandardEnable OBJECT-TYPE
		SYNTAX		INTEGER { disable(0), enable(1) }
		MAX-ACCESS		read-write
		STATUS			current
		DESCRIPTION
				"TYPE: - Checkbox
				 PAGE: - Logging
					Input Standard  cmdID= 1007 "
		::= { iqhip00CmdEntry 1007 }


	iqhip00LoggingInput1InputStandard OBJECT-TYPE
		SYNTAX		RollCallString
		MAX-ACCESS		read-only
		STATUS			current
		DESCRIPTION
				"TYPE: - Display
				 PAGE: - Logging
					Input Standard=  cmdID= 2007  format=   "
		::= { iqhip00CmdEntry 2007 }


	iqhip00LoggingInput1EDHEnable OBJECT-TYPE
		SYNTAX		INTEGER { disable(0), enable(1) }
		MAX-ACCESS		read-write
		STATUS			current
		DESCRIPTION
				"TYPE: - Checkbox
				 PAGE: - Logging
					EDH  cmdID= 1093 "
		::= { iqhip00CmdEntry 1093 }


	iqhip00LoggingInput1EDH OBJECT-TYPE
		SYNTAX		RollCallString
		MAX-ACCESS		read-only
		STATUS			current
		DESCRIPTION
				"TYPE: - Display
				 PAGE: - Logging
					EDH=  cmdID= 2093  format=   "
		::= { iqhip00CmdEntry 2093 }


	iqhip00LoggingInput1CRCEnable OBJECT-TYPE
		SYNTAX		INTEGER { disable(0), enable(1) }
		MAX-ACCESS		read-write
		STATUS			current
		DESCRIPTION
				"TYPE: - Checkbox
				 PAGE: - Logging
					CRC  cmdID= 1094 "
		::= { iqhip00CmdEntry 1094 }


	iqhip00LoggingInput1CRC OBJECT-TYPE
		SYNTAX		RollCallString
		MAX-ACCESS		read-only
		STATUS			current
		DESCRIPTION
				"TYPE: - Display
				 PAGE: - Logging
					CRC=  cmdID= 2094  format=   "
		::= { iqhip00CmdEntry 2094 }


	iqhip00LoggingInp1Monitor1HyperionSummaryEnable OBJECT-TYPE
		SYNTAX		INTEGER { disable(0), enable(1) }
		MAX-ACCESS		read-write
		STATUS			current
		DESCRIPTION
				"TYPE: - Checkbox
				 PAGE: - Logging
					Hyperion Summary  cmdID= 1129 "
		::= { iqhip00CmdEntry 1129 }


	iqhip00LoggingInp1Monitor1HyperionSummary OBJECT-TYPE
		SYNTAX		RollCallString
		MAX-ACCESS		read-only
		STATUS			current
		DESCRIPTION
				"TYPE: - Display
				 PAGE: - Logging
					Hyperion Summary =  cmdID= 2129  format=   "
		::= { iqhip00CmdEntry 2129 }


	iqhip00LoggingInp1Monitor1StillishEnable OBJECT-TYPE
		SYNTAX		INTEGER { disable(0), enable(1) }
		MAX-ACCESS		read-write
		STATUS			current
		DESCRIPTION
				"TYPE: - Checkbox
				 PAGE: - Logging
					Stillish Enable  cmdID= 1008 "
		::= { iqhip00CmdEntry 1008 }


	iqhip00LoggingInp1Monitor1Stillish OBJECT-TYPE
		SYNTAX		RollCallString
		MAX-ACCESS		read-only
		STATUS			current
		DESCRIPTION
				"TYPE: - Display
				 PAGE: - Logging
					Stillish=  cmdID= 2008  format=   "
		::= { iqhip00CmdEntry 2008 }


	iqhip00LoggingInp1Monitor1StillishLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Stillish Log Option  cmdID= 3300
					Timecode At Start  value= 0
					Timecode At Fail  value= 1  "
		::= { iqhip00CmdEntry 3300 }


	iqhip00LoggingInp1Monitor1FreezeEnable OBJECT-TYPE
		SYNTAX		INTEGER { disable(0), enable(1) }
		MAX-ACCESS		read-write
		STATUS			current
		DESCRIPTION
				"TYPE: - Checkbox
				 PAGE: - Logging
					Freeze Enable  cmdID= 1131 "
		::= { iqhip00CmdEntry 1131 }


	iqhip00LoggingInp1Monitor1Freeze OBJECT-TYPE
		SYNTAX		RollCallString
		MAX-ACCESS		read-only
		STATUS			current
		DESCRIPTION
				"TYPE: - Display
				 PAGE: - Logging
					Freeze=  cmdID= 2131  format=   "
		::= { iqhip00CmdEntry 2131 }


	iqhip00LoggingInp1Monitor1FreezeLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Freeze Log Option  cmdID= 3301
					Timecode At Start  value= 0
					Timecode At Fail  value= 1  "
		::= { iqhip00CmdEntry 3301 }


	iqhip00LoggingInp1Monitor1BlackEnable OBJECT-TYPE
		SYNTAX		INTEGER { disable(0), enable(1) }
		MAX-ACCESS		read-write
		STATUS			current
		DESCRIPTION
				"TYPE: - Checkbox
				 PAGE: - Logging
					Black Enable  cmdID= 1009 "
		::= { iqhip00CmdEntry 1009 }


	iqhip00LoggingInp1Monitor1Black OBJECT-TYPE
		SYNTAX		RollCallString
		MAX-ACCESS		read-only
		STATUS			current
		DESCRIPTION
				"TYPE: - Display
				 PAGE: - Logging
					Black=  cmdID= 2009  format=   "
		::= { iqhip00CmdEntry 2009 }


	iqhip00LoggingInp1Monitor1BlackLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Black Log Option  cmdID= 3302
					Timecode At Start  value= 0
					Timecode At Fail  value= 1  "
		::= { iqhip00CmdEntry 3302 }


	iqhip00LoggingInp1Monitor1BlackishEnable OBJECT-TYPE
		SYNTAX		INTEGER { disable(0), enable(1) }
		MAX-ACCESS		read-write
		STATUS			current
		DESCRIPTION
				"TYPE: - Checkbox
				 PAGE: - Logging
					Blackish Enable  cmdID= 1010 "
		::= { iqhip00CmdEntry 1010 }


	iqhip00LoggingInp1Monitor1Blackish OBJECT-TYPE
		SYNTAX		RollCallString
		MAX-ACCESS		read-only
		STATUS			current
		DESCRIPTION
				"TYPE: - Display
				 PAGE: - Logging
					Blackish=  cmdID= 2010  format=   "
		::= { iqhip00CmdEntry 2010 }


	iqhip00LoggingInp1Monitor1BlackishLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Blackish Log Option  cmdID= 3303
					Timecode At Start  value= 0
					Timecode At Fail  value= 1  "
		::= { iqhip00CmdEntry 3303 }


	iqhip00LoggingInp1Monitor1CldCapStateEnable OBJECT-TYPE
		SYNTAX		INTEGER { disable(0), enable(1) }
		MAX-ACCESS		read-write
		STATUS			current
		DESCRIPTION
				"TYPE: - Checkbox
				 PAGE: - Logging
					Cld. Cap.State En  cmdID= 1011 "
		::= { iqhip00CmdEntry 1011 }


	iqhip00LoggingInp1Monitor1ClosedCapState OBJECT-TYPE
		SYNTAX		RollCallString
		MAX-ACCESS		read-only
		STATUS			current
		DESCRIPTION
				"TYPE: - Display
				 PAGE: - Logging
					Closed Cap. State =  cmdID= 2011  format=   "
		::= { iqhip00CmdEntry 2011 }


	iqhip00LoggingInp1Monitor1ClosedCapLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Closed Cap Log Opt  cmdID= 3304
					Timecode At Start  value= 0
					Timecode At Fail  value= 1  "
		::= { iqhip00CmdEntry 3304 }


	iqhip00LoggingInp1Monitor1CldCapTypeEnable OBJECT-TYPE
		SYNTAX		INTEGER { disable(0), enable(1) }
		MAX-ACCESS		read-write
		STATUS			current
		DESCRIPTION
				"TYPE: - Checkbox
				 PAGE: - Logging
					Cld. Cap.Type En  cmdID= 1012 "
		::= { iqhip00CmdEntry 1012 }


	iqhip00LoggingInp1Monitor1ClosedCapType OBJECT-TYPE
		SYNTAX		RollCallString
		MAX-ACCESS		read-only
		STATUS			current
		DESCRIPTION
				"TYPE: - Display
				 PAGE: - Logging
					Closed Cap.Type=  cmdID= 2012  format=   "
		::= { iqhip00CmdEntry 2012 }


	iqhip00LoggingInp1Monitor1CldCapTitleEnable OBJECT-TYPE
		SYNTAX		INTEGER { disable(0), enable(1) }
		MAX-ACCESS		read-write
		STATUS			current
		DESCRIPTION
				"TYPE: - Checkbox
				 PAGE: - Logging
					Cld. Cap.Title En  cmdID= 1164 "
		::= { iqhip00CmdEntry 1164 }


	iqhip00LoggingInp1Monitor1ClosedCapTitle OBJECT-TYPE
		SYNTAX		RollCallString
		MAX-ACCESS		read-only
		STATUS			current
		DESCRIPTION
				"TYPE: - Display
				 PAGE: - Logging
					Closed Cap.Title=  cmdID= 2164  format=   "
		::= { iqhip00CmdEntry 2164 }


	iqhip00LoggingInp1Monitor2YBitDepthEnable OBJECT-TYPE
		SYNTAX		INTEGER { disable(0), enable(1) }
		MAX-ACCESS		read-write
		STATUS			current
		DESCRIPTION
				"TYPE: - Checkbox
				 PAGE: - Logging
					Y Bit Depth Enable  cmdID= 1017 "
		::= { iqhip00CmdEntry 1017 }


	iqhip00LoggingInp1Monitor2YBitDepth OBJECT-TYPE
		SYNTAX		RollCallString
		MAX-ACCESS		read-only
		STATUS			current
		DESCRIPTION
				"TYPE: - Display
				 PAGE: - Logging
					Y Bit Depth=  cmdID= 2017  format=   "
		::= { iqhip00CmdEntry 2017 }


	iqhip00LoggingInp1Monitor2CBitDepthEnable OBJECT-TYPE
		SYNTAX		INTEGER { disable(0), enable(1) }
		MAX-ACCESS		read-write
		STATUS			current
		DESCRIPTION
				"TYPE: - Checkbox
				 PAGE: - Logging
					C Bit Depth Enable  cmdID= 1018 "
		::= { iqhip00CmdEntry 1018 }


	iqhip00LoggingInp1Monitor2CBitDepth OBJECT-TYPE
		SYNTAX		RollCallString
		MAX-ACCESS		read-only
		STATUS			current
		DESCRIPTION
				"TYPE: - Display
				 PAGE: - Logging
					C Bit Depth=  cmdID= 2018  format=   "
		::= { iqhip00CmdEntry 2018 }


	iqhip00LoggingInp1Monitor2VideoYLvlHighEnable OBJECT-TYPE
		SYNTAX		INTEGER { disable(0), enable(1) }
		MAX-ACCESS		read-write
		STATUS			current
		DESCRIPTION
				"TYPE: - Checkbox
				 PAGE: - Logging
					Video Y Lvl. High E  cmdID= 1019 "
		::= { iqhip00CmdEntry 1019 }


	iqhip00LoggingInp1Monitor2VideoYLevelHigh OBJECT-TYPE
		SYNTAX		RollCallString
		MAX-ACCESS		read-only
		STATUS			current
		DESCRIPTION
				"TYPE: - Display
				 PAGE: - Logging
					Video Y Level High=  cmdID= 2019  format=   "
		::= { iqhip00CmdEntry 2019 }


	iqhip00LoggingInp1Monitor2VideoCLvlHighEnable OBJECT-TYPE
		SYNTAX		INTEGER { disable(0), enable(1) }
		MAX-ACCESS		read-write
		STATUS			current
		DESCRIPTION
				"TYPE: - Checkbox
				 PAGE: - Logging
					Video C Lvl. High E  cmdID= 1020 "
		::= { iqhip00CmdEntry 1020 }


	iqhip00LoggingInp1Monitor2VideoCLevelHigh OBJECT-TYPE
		SYNTAX		RollCallString
		MAX-ACCESS		read-only
		STATUS			current
		DESCRIPTION
				"TYPE: - Display
				 PAGE: - Logging
					Video C Level High=  cmdID= 2020  format=   "
		::= { iqhip00CmdEntry 2020 }


	iqhip00LoggingInp1Monitor2VideoYLvlLowEnable OBJECT-TYPE
		SYNTAX		INTEGER { disable(0), enable(1) }
		MAX-ACCESS		read-write
		STATUS			current
		DESCRIPTION
				"TYPE: - Checkbox
				 PAGE: - Logging
					Video Y Lvl. Low En  cmdID= 1021 "
		::= { iqhip00CmdEntry 1021 }


	iqhip00LoggingInp1Monitor2VideoYLevelLow OBJECT-TYPE
		SYNTAX		RollCallString
		MAX-ACCESS		read-only
		STATUS			current
		DESCRIPTION
				"TYPE: - Display
				 PAGE: - Logging
					Video Y Level Low=  cmdID= 2021  format=   "
		::= { iqhip00CmdEntry 2021 }


	iqhip00LoggingInp1Monitor2VideoCLvlLowEnable OBJECT-TYPE
		SYNTAX		INTEGER { disable(0), enable(1) }
		MAX-ACCESS		read-write
		STATUS			current
		DESCRIPTION
				"TYPE: - Checkbox
				 PAGE: - Logging
					Video C Lvl. Low En  cmdID= 1022 "
		::= { iqhip00CmdEntry 1022 }


	iqhip00LoggingInp1Monitor2VideoCLevelLow OBJECT-TYPE
		SYNTAX		RollCallString
		MAX-ACCESS		read-only
		STATUS			current
		DESCRIPTION
				"TYPE: - Display
				 PAGE: - Logging
					Video C Level Low=  cmdID= 2022  format=   "
		::= { iqhip00CmdEntry 2022 }


	iqhip00LoggingInp1Monitor2APLEnable OBJECT-TYPE
		SYNTAX		INTEGER { disable(0), enable(1) }
		MAX-ACCESS		read-write
		STATUS			current
		DESCRIPTION
				"TYPE: - Checkbox
				 PAGE: - Logging
					APL Enable  cmdID= 1023 "
		::= { iqhip00CmdEntry 1023 }


	iqhip00LoggingInp1Monitor2APL OBJECT-TYPE
		SYNTAX		RollCallString
		MAX-ACCESS		read-only
		STATUS			current
		DESCRIPTION
				"TYPE: - Display
				 PAGE: - Logging
					APL=  cmdID= 2023  format=   "
		::= { iqhip00CmdEntry 2023 }


	iqhip00LoggingInp1Monitor2VITCStateEnable OBJECT-TYPE
		SYNTAX		INTEGER { disable(0), enable(1) }
		MAX-ACCESS		read-write
		STATUS			current
		DESCRIPTION
				"TYPE: - Checkbox
				 PAGE: - Logging
					VITC State Enable  cmdID= 1024 "
		::= { iqhip00CmdEntry 1024 }


	iqhip00LoggingInp1Monitor2VITCState OBJECT-TYPE
		SYNTAX		RollCallString
		MAX-ACCESS		read-only
		STATUS			current
		DESCRIPTION
				"TYPE: - Display
				 PAGE: - Logging
					VITC State=  cmdID= 2024  format=   "
		::= { iqhip00CmdEntry 2024 }


	iqhip00LoggingInp1Monitor2CAStateEnable OBJECT-TYPE
		SYNTAX		INTEGER { disable(0), enable(1) }
		MAX-ACCESS		read-write
		STATUS			current
		DESCRIPTION
				"TYPE: - Checkbox
				 PAGE: - Logging
					CA State Enable  cmdID= 1025 "
		::= { iqhip00CmdEntry 1025 }


	iqhip00LoggingInp1Monitor2CAState OBJECT-TYPE
		SYNTAX		RollCallString
		MAX-ACCESS		read-only
		STATUS			current
		DESCRIPTION
				"TYPE: - Display
				 PAGE: - Logging
					CA State=  cmdID= 2025  format=   "
		::= { iqhip00CmdEntry 2025 }


	iqhip00LoggingInp1Monitor2CASystemEnable OBJECT-TYPE
		SYNTAX		INTEGER { disable(0), enable(1) }
		MAX-ACCESS		read-write
		STATUS			current
		DESCRIPTION
				"TYPE: - Checkbox
				 PAGE: - Logging
					CA System Enable  cmdID= 1026 "
		::= { iqhip00CmdEntry 1026 }


	iqhip00LoggingInp1Monitor2CASystem OBJECT-TYPE
		SYNTAX		RollCallString
		MAX-ACCESS		read-only
		STATUS			current
		DESCRIPTION
				"TYPE: - Display
				 PAGE: - Logging
					CA System=  cmdID= 2026  format=   "
		::= { iqhip00CmdEntry 2026 }


	iqhip00LoggingInp1Monitor2CAAgeRatingEnable OBJECT-TYPE
		SYNTAX		INTEGER { disable(0), enable(1) }
		MAX-ACCESS		read-write
		STATUS			current
		DESCRIPTION
				"TYPE: - Checkbox
				 PAGE: - Logging
					CA Age Rating En  cmdID= 1027 "
		::= { iqhip00CmdEntry 1027 }


	iqhip00LoggingInp1Monitor2CAAgeRating OBJECT-TYPE
		SYNTAX		RollCallString
		MAX-ACCESS		read-only
		STATUS			current
		DESCRIPTION
				"TYPE: - Display
				 PAGE: - Logging
					CA Age Rating=  cmdID= 2027  format=   "
		::= { iqhip00CmdEntry 2027 }


	iqhip00LoggingInp1Monitor2ANCTimcodeStateEnable OBJECT-TYPE
		SYNTAX		INTEGER { disable(0), enable(1) }
		MAX-ACCESS		read-write
		STATUS			current
		DESCRIPTION
				"TYPE: - Checkbox
				 PAGE: - Logging
					ANC Tim.code State   cmdID= 1092 "
		::= { iqhip00CmdEntry 1092 }


	iqhip00LoggingInp1Monitor2ANCTimecodeState OBJECT-TYPE
		SYNTAX		RollCallString
		MAX-ACCESS		read-only
		STATUS			current
		DESCRIPTION
				"TYPE: - Display
				 PAGE: - Logging
					ANC Timecode State=  cmdID= 2092  format=   "
		::= { iqhip00CmdEntry 2092 }


	iqhip00LoggingInp1Monitor2User1DIDNameEnable OBJECT-TYPE
		SYNTAX		INTEGER { disable(0), enable(1) }
		MAX-ACCESS		read-write
		STATUS			current
		DESCRIPTION
				"TYPE: - Checkbox
				 PAGE: - Logging
					User 1 DID Name En  cmdID= 1097 "
		::= { iqhip00CmdEntry 1097 }


	iqhip00LoggingInp1Monitor2User1DIDName OBJECT-TYPE
		SYNTAX		RollCallString
		MAX-ACCESS		read-only
		STATUS			current
		DESCRIPTION
				"TYPE: - Display
				 PAGE: - Logging
					User 1 DID Name=  cmdID= 2097  format=   "
		::= { iqhip00CmdEntry 2097 }


	iqhip00LoggingInp1Monitor2User1DIDStateEnable OBJECT-TYPE
		SYNTAX		INTEGER { disable(0), enable(1) }
		MAX-ACCESS		read-write
		STATUS			current
		DESCRIPTION
				"TYPE: - Checkbox
				 PAGE: - Logging
					User 1 DID State En  cmdID= 1098 "
		::= { iqhip00CmdEntry 1098 }


	iqhip00LoggingInp1Monitor2User1DIDState OBJECT-TYPE
		SYNTAX		RollCallString
		MAX-ACCESS		read-only
		STATUS			current
		DESCRIPTION
				"TYPE: - Display
				 PAGE: - Logging
					User 1 DID State=  cmdID= 2098  format=   "
		::= { iqhip00CmdEntry 2098 }


	iqhip00LoggingInp1Monitor2User2DIDNameEnable OBJECT-TYPE
		SYNTAX		INTEGER { disable(0), enable(1) }
		MAX-ACCESS		read-write
		STATUS			current
		DESCRIPTION
				"TYPE: - Checkbox
				 PAGE: - Logging
					User 2 DID Name En  cmdID= 1099 "
		::= { iqhip00CmdEntry 1099 }


	iqhip00LoggingInp1Monitor2User2DIDName OBJECT-TYPE
		SYNTAX		RollCallString
		MAX-ACCESS		read-only
		STATUS			current
		DESCRIPTION
				"TYPE: - Display
				 PAGE: - Logging
					User 2 DID Name=  cmdID= 2099  format=   "
		::= { iqhip00CmdEntry 2099 }


	iqhip00LoggingInp1Monitor2User2DIDStateEnable OBJECT-TYPE
		SYNTAX		INTEGER { disable(0), enable(1) }
		MAX-ACCESS		read-write
		STATUS			current
		DESCRIPTION
				"TYPE: - Checkbox
				 PAGE: - Logging
					User 2 DID State En  cmdID= 1100 "
		::= { iqhip00CmdEntry 1100 }


	iqhip00LoggingInp1Monitor2User2DIDState OBJECT-TYPE
		SYNTAX		RollCallString
		MAX-ACCESS		read-only
		STATUS			current
		DESCRIPTION
				"TYPE: - Display
				 PAGE: - Logging
					User 2 DID State=  cmdID= 2100  format=   "
		::= { iqhip00CmdEntry 2100 }


	iqhip00LoggingInp1Monitor2WSSStateEnable OBJECT-TYPE
		SYNTAX		INTEGER { disable(0), enable(1) }
		MAX-ACCESS		read-write
		STATUS			current
		DESCRIPTION
				"TYPE: - Checkbox
				 PAGE: - Logging
					WSS State Enable  cmdID= 1132 "
		::= { iqhip00CmdEntry 1132 }


	iqhip00LoggingInp1Monitor2WSSState OBJECT-TYPE
		SYNTAX		RollCallString
		MAX-ACCESS		read-only
		STATUS			current
		DESCRIPTION
				"TYPE: - Display
				 PAGE: - Logging
					WSS State=  cmdID= 2132  format=   "
		::= { iqhip00CmdEntry 2132 }


	iqhip00LoggingInp1Monitor2VIStateEnable OBJECT-TYPE
		SYNTAX		INTEGER { disable(0), enable(1) }
		MAX-ACCESS		read-write
		STATUS			current
		DESCRIPTION
				"TYPE: - Checkbox
				 PAGE: - Logging
					VI State Enable  cmdID= 1133 "
		::= { iqhip00CmdEntry 1133 }


	iqhip00LoggingInp1Monitor2VIState OBJECT-TYPE
		SYNTAX		RollCallString
		MAX-ACCESS		read-only
		STATUS			current
		DESCRIPTION
				"TYPE: - Display
				 PAGE: - Logging
					VI State=  cmdID= 2133  format=   "
		::= { iqhip00CmdEntry 2133 }


	iqhip00LoggingInp1Monitor2WSSEnable OBJECT-TYPE
		SYNTAX		INTEGER { disable(0), enable(1) }
		MAX-ACCESS		read-write
		STATUS			current
		DESCRIPTION
				"TYPE: - Checkbox
				 PAGE: - Logging
					WSS Enable  cmdID= 1160 "
		::= { iqhip00CmdEntry 1160 }


	iqhip00LoggingInp1Monitor2WSS OBJECT-TYPE
		SYNTAX		RollCallString
		MAX-ACCESS		read-only
		STATUS			current
		DESCRIPTION
				"TYPE: - Display
				 PAGE: - Logging
					WSS=  cmdID= 2160  format=   "
		::= { iqhip00CmdEntry 2160 }


	iqhip00LoggingInp1Monitor2VIEnable OBJECT-TYPE
		SYNTAX		INTEGER { disable(0), enable(1) }
		MAX-ACCESS		read-write
		STATUS			current
		DESCRIPTION
				"TYPE: - Checkbox
				 PAGE: - Logging
					VI Enable  cmdID= 1161 "
		::= { iqhip00CmdEntry 1161 }


	iqhip00LoggingInp1Monitor2VI OBJECT-TYPE
		SYNTAX		RollCallString
		MAX-ACCESS		read-only
		STATUS			current
		DESCRIPTION
				"TYPE: - Display
				 PAGE: - Logging
					VI=  cmdID= 2161  format=   "
		::= { iqhip00CmdEntry 2161 }


	iqhip00LoggingInp1Monitor2WSSAspectEnable OBJECT-TYPE
		SYNTAX		INTEGER { disable(0), enable(1) }
		MAX-ACCESS		read-write
		STATUS			current
		DESCRIPTION
				"TYPE: - Checkbox
				 PAGE: - Logging
					WSS Aspect Enable  cmdID= 1162 "
		::= { iqhip00CmdEntry 1162 }


	iqhip00LoggingInp1Monitor2WSSAspect OBJECT-TYPE
		SYNTAX		RollCallString
		MAX-ACCESS		read-only
		STATUS			current
		DESCRIPTION
				"TYPE: - Display
				 PAGE: - Logging
					WSS Aspect=  cmdID= 2162  format=   "
		::= { iqhip00CmdEntry 2162 }


	iqhip00LoggingInp1Monitor2VIAspectEnable OBJECT-TYPE
		SYNTAX		INTEGER { disable(0), enable(1) }
		MAX-ACCESS		read-write
		STATUS			current
		DESCRIPTION
				"TYPE: - Checkbox
				 PAGE: - Logging
					VI Aspect Enable  cmdID= 1163 "
		::= { iqhip00CmdEntry 1163 }


	iqhip00LoggingInp1Monitor2VIAspect OBJECT-TYPE
		SYNTAX		RollCallString
		MAX-ACCESS		read-only
		STATUS			current
		DESCRIPTION
				"TYPE: - Display
				 PAGE: - Logging
					VI Aspect=  cmdID= 2163  format=   "
		::= { iqhip00CmdEntry 2163 }


	iqhip00LoggingInp1AudStateEmbCh1StateEnable OBJECT-TYPE
		SYNTAX		INTEGER { disable(0), enable(1) }
		MAX-ACCESS		read-write
		STATUS			current
		DESCRIPTION
				"TYPE: - Checkbox
				 PAGE: - Logging- Inp 1 Aud State
					Emb Ch 1 State  cmdID= 1028 "
		::= { iqhip00CmdEntry 1028 }


	iqhip00LoggingInp1AudStateEmbCh1State OBJECT-TYPE
		SYNTAX		RollCallString
		MAX-ACCESS		read-only
		STATUS			current
		DESCRIPTION
				"TYPE: - Display
				 PAGE: - Logging- Inp 1 Aud State
					Emb Ch 1 State=  cmdID= 2028  format=   "
		::= { iqhip00CmdEntry 2028 }


	iqhip00LoggingInp1AudStateEmbCh2StateEnable OBJECT-TYPE
		SYNTAX		INTEGER { disable(0), enable(1) }
		MAX-ACCESS		read-write
		STATUS			current
		DESCRIPTION
				"TYPE: - Checkbox
				 PAGE: - Logging- Inp 1 Aud State
					Emb Ch 2 State  cmdID= 1029 "
		::= { iqhip00CmdEntry 1029 }


	iqhip00LoggingInp1AudStateEmbCh2State OBJECT-TYPE
		SYNTAX		RollCallString
		MAX-ACCESS		read-only
		STATUS			current
		DESCRIPTION
				"TYPE: - Display
				 PAGE: - Logging- Inp 1 Aud State
					Emb Ch 2 State=  cmdID= 2029  format=   "
		::= { iqhip00CmdEntry 2029 }


	iqhip00LoggingInp1AudStateEmbCh3StateEnable OBJECT-TYPE
		SYNTAX		INTEGER { disable(0), enable(1) }
		MAX-ACCESS		read-write
		STATUS			current
		DESCRIPTION
				"TYPE: - Checkbox
				 PAGE: - Logging- Inp 1 Aud State
					Emb Ch 3 State  cmdID= 1030 "
		::= { iqhip00CmdEntry 1030 }


	iqhip00LoggingInp1AudStateEmbCh3State OBJECT-TYPE
		SYNTAX		RollCallString
		MAX-ACCESS		read-only
		STATUS			current
		DESCRIPTION
				"TYPE: - Display
				 PAGE: - Logging- Inp 1 Aud State
					Emb Ch 3 State=  cmdID= 2030  format=   "
		::= { iqhip00CmdEntry 2030 }


	iqhip00LoggingInp1AudStateEmbCh4StateEnable OBJECT-TYPE
		SYNTAX		INTEGER { disable(0), enable(1) }
		MAX-ACCESS		read-write
		STATUS			current
		DESCRIPTION
				"TYPE: - Checkbox
				 PAGE: - Logging- Inp 1 Aud State
					Emb Ch 4 State  cmdID= 1031 "
		::= { iqhip00CmdEntry 1031 }


	iqhip00LoggingInp1AudStateEmbCh4State OBJECT-TYPE
		SYNTAX		RollCallString
		MAX-ACCESS		read-only
		STATUS			current
		DESCRIPTION
				"TYPE: - Display
				 PAGE: - Logging- Inp 1 Aud State
					Emb Ch 4 State=  cmdID= 2031  format=   "
		::= { iqhip00CmdEntry 2031 }


	iqhip00LoggingInp1AudStateEmbCh5StateEnable OBJECT-TYPE
		SYNTAX		INTEGER { disable(0), enable(1) }
		MAX-ACCESS		read-write
		STATUS			current
		DESCRIPTION
				"TYPE: - Checkbox
				 PAGE: - Logging- Inp 1 Aud State
					Emb Ch 5 State  cmdID= 1032 "
		::= { iqhip00CmdEntry 1032 }


	iqhip00LoggingInp1AudStateEmbCh5State OBJECT-TYPE
		SYNTAX		RollCallString
		MAX-ACCESS		read-only
		STATUS			current
		DESCRIPTION
				"TYPE: - Display
				 PAGE: - Logging- Inp 1 Aud State
					Emb Ch 5 State=  cmdID= 2032  format=   "
		::= { iqhip00CmdEntry 2032 }


	iqhip00LoggingInp1AudStateEmbCh6StateEnable OBJECT-TYPE
		SYNTAX		INTEGER { disable(0), enable(1) }
		MAX-ACCESS		read-write
		STATUS			current
		DESCRIPTION
				"TYPE: - Checkbox
				 PAGE: - Logging- Inp 1 Aud State
					Emb Ch 6 State  cmdID= 1033 "
		::= { iqhip00CmdEntry 1033 }


	iqhip00LoggingInp1AudStateEmbCh6State OBJECT-TYPE
		SYNTAX		RollCallString
		MAX-ACCESS		read-only
		STATUS			current
		DESCRIPTION
				"TYPE: - Display
				 PAGE: - Logging- Inp 1 Aud State
					Emb Ch 6 State=  cmdID= 2033  format=   "
		::= { iqhip00CmdEntry 2033 }


	iqhip00LoggingInp1AudStateEmbCh7StateEnable OBJECT-TYPE
		SYNTAX		INTEGER { disable(0), enable(1) }
		MAX-ACCESS		read-write
		STATUS			current
		DESCRIPTION
				"TYPE: - Checkbox
				 PAGE: - Logging- Inp 1 Aud State
					Emb Ch 7 State  cmdID= 1034 "
		::= { iqhip00CmdEntry 1034 }


	iqhip00LoggingInp1AudStateEmbCh7State OBJECT-TYPE
		SYNTAX		RollCallString
		MAX-ACCESS		read-only
		STATUS			current
		DESCRIPTION
				"TYPE: - Display
				 PAGE: - Logging- Inp 1 Aud State
					Emb Ch 7 State=  cmdID= 2034  format=   "
		::= { iqhip00CmdEntry 2034 }


	iqhip00LoggingInp1AudStateEmbCh8StateEnable OBJECT-TYPE
		SYNTAX		INTEGER { disable(0), enable(1) }
		MAX-ACCESS		read-write
		STATUS			current
		DESCRIPTION
				"TYPE: - Checkbox
				 PAGE: - Logging- Inp 1 Aud State
					Emb Ch 8 State  cmdID= 1035 "
		::= { iqhip00CmdEntry 1035 }


	iqhip00LoggingInp1AudStateEmbCh8State OBJECT-TYPE
		SYNTAX		RollCallString
		MAX-ACCESS		read-only
		STATUS			current
		DESCRIPTION
				"TYPE: - Display
				 PAGE: - Logging- Inp 1 Aud State
					Emb Ch 8 State=  cmdID= 2035  format=   "
		::= { iqhip00CmdEntry 2035 }


	iqhip00LoggingInp1AudStateEmbCh9StateEnable OBJECT-TYPE
		SYNTAX		INTEGER { disable(0), enable(1) }
		MAX-ACCESS		read-write
		STATUS			current
		DESCRIPTION
				"TYPE: - Checkbox
				 PAGE: - Logging- Inp 1 Aud State
					Emb Ch 9 State  cmdID= 1036 "
		::= { iqhip00CmdEntry 1036 }


	iqhip00LoggingInp1AudStateEmbCh9State OBJECT-TYPE
		SYNTAX		RollCallString
		MAX-ACCESS		read-only
		STATUS			current
		DESCRIPTION
				"TYPE: - Display
				 PAGE: - Logging- Inp 1 Aud State
					Emb Ch 9 State=  cmdID= 2036  format=   "
		::= { iqhip00CmdEntry 2036 }


	iqhip00LoggingInp1AudStateEmbCh10StateEnable OBJECT-TYPE
		SYNTAX		INTEGER { disable(0), enable(1) }
		MAX-ACCESS		read-write
		STATUS			current
		DESCRIPTION
				"TYPE: - Checkbox
				 PAGE: - Logging- Inp 1 Aud State
					Emb Ch 10 State  cmdID= 1037 "
		::= { iqhip00CmdEntry 1037 }


	iqhip00LoggingInp1AudStateEmbCh10State OBJECT-TYPE
		SYNTAX		RollCallString
		MAX-ACCESS		read-only
		STATUS			current
		DESCRIPTION
				"TYPE: - Display
				 PAGE: - Logging- Inp 1 Aud State
					Emb Ch 10 State=  cmdID= 2037  format=   "
		::= { iqhip00CmdEntry 2037 }


	iqhip00LoggingInp1AudStateEmbCh11StateEnable OBJECT-TYPE
		SYNTAX		INTEGER { disable(0), enable(1) }
		MAX-ACCESS		read-write
		STATUS			current
		DESCRIPTION
				"TYPE: - Checkbox
				 PAGE: - Logging- Inp 1 Aud State
					Emb Ch 11 State  cmdID= 1038 "
		::= { iqhip00CmdEntry 1038 }


	iqhip00LoggingInp1AudStateEmbCh11State OBJECT-TYPE
		SYNTAX		RollCallString
		MAX-ACCESS		read-only
		STATUS			current
		DESCRIPTION
				"TYPE: - Display
				 PAGE: - Logging- Inp 1 Aud State
					Emb Ch 11 State=  cmdID= 2038  format=   "
		::= { iqhip00CmdEntry 2038 }


	iqhip00LoggingInp1AudStateEmbCh12StateEnable OBJECT-TYPE
		SYNTAX		INTEGER { disable(0), enable(1) }
		MAX-ACCESS		read-write
		STATUS			current
		DESCRIPTION
				"TYPE: - Checkbox
				 PAGE: - Logging- Inp 1 Aud State
					Emb Ch 12 State  cmdID= 1039 "
		::= { iqhip00CmdEntry 1039 }


	iqhip00LoggingInp1AudStateEmbCh12State OBJECT-TYPE
		SYNTAX		RollCallString
		MAX-ACCESS		read-only
		STATUS			current
		DESCRIPTION
				"TYPE: - Display
				 PAGE: - Logging- Inp 1 Aud State
					Emb Ch 12 State=  cmdID= 2039  format=   "
		::= { iqhip00CmdEntry 2039 }


	iqhip00LoggingInp1AudStateEmbCh13StateEnable OBJECT-TYPE
		SYNTAX		INTEGER { disable(0), enable(1) }
		MAX-ACCESS		read-write
		STATUS			current
		DESCRIPTION
				"TYPE: - Checkbox
				 PAGE: - Logging- Inp 1 Aud State
					Emb Ch 13 State  cmdID= 1040 "
		::= { iqhip00CmdEntry 1040 }


	iqhip00LoggingInp1AudStateEmbCh13State OBJECT-TYPE
		SYNTAX		RollCallString
		MAX-ACCESS		read-only
		STATUS			current
		DESCRIPTION
				"TYPE: - Display
				 PAGE: - Logging- Inp 1 Aud State
					Emb Ch 13 State=  cmdID= 2040  format=   "
		::= { iqhip00CmdEntry 2040 }


	iqhip00LoggingInp1AudStateEmbCh14StateEnable OBJECT-TYPE
		SYNTAX		INTEGER { disable(0), enable(1) }
		MAX-ACCESS		read-write
		STATUS			current
		DESCRIPTION
				"TYPE: - Checkbox
				 PAGE: - Logging- Inp 1 Aud State
					Emb Ch 14 State  cmdID= 1041 "
		::= { iqhip00CmdEntry 1041 }


	iqhip00LoggingInp1AudStateEmbCh14State OBJECT-TYPE
		SYNTAX		RollCallString
		MAX-ACCESS		read-only
		STATUS			current
		DESCRIPTION
				"TYPE: - Display
				 PAGE: - Logging- Inp 1 Aud State
					Emb Ch 14 State=  cmdID= 2041  format=   "
		::= { iqhip00CmdEntry 2041 }


	iqhip00LoggingInp1AudStateEmbCh15StateEnable OBJECT-TYPE
		SYNTAX		INTEGER { disable(0), enable(1) }
		MAX-ACCESS		read-write
		STATUS			current
		DESCRIPTION
				"TYPE: - Checkbox
				 PAGE: - Logging- Inp 1 Aud State
					Emb Ch 15 State  cmdID= 1042 "
		::= { iqhip00CmdEntry 1042 }


	iqhip00LoggingInp1AudStateEmbCh15State OBJECT-TYPE
		SYNTAX		RollCallString
		MAX-ACCESS		read-only
		STATUS			current
		DESCRIPTION
				"TYPE: - Display
				 PAGE: - Logging- Inp 1 Aud State
					Emb Ch 15 State=  cmdID= 2042  format=   "
		::= { iqhip00CmdEntry 2042 }


	iqhip00LoggingInp1AudStateEmbCh16StateEnable OBJECT-TYPE
		SYNTAX		INTEGER { disable(0), enable(1) }
		MAX-ACCESS		read-write
		STATUS			current
		DESCRIPTION
				"TYPE: - Checkbox
				 PAGE: - Logging- Inp 1 Aud State
					Emb Ch 16 State  cmdID= 1043 "
		::= { iqhip00CmdEntry 1043 }


	iqhip00LoggingInp1AudStateEmbCh16State OBJECT-TYPE
		SYNTAX		RollCallString
		MAX-ACCESS		read-only
		STATUS			current
		DESCRIPTION
				"TYPE: - Display
				 PAGE: - Logging- Inp 1 Aud State
					Emb Ch 16 State=  cmdID= 2043  format=   "
		::= { iqhip00CmdEntry 2043 }


	iqhip00LoggingInp1AudTypeEmbCh1TypeEnable OBJECT-TYPE
		SYNTAX		INTEGER { disable(0), enable(1) }
		MAX-ACCESS		read-write
		STATUS			current
		DESCRIPTION
				"TYPE: - Checkbox
				 PAGE: - Logging- Inp 1 Aud Type
					Emb Ch 1 Type  cmdID= 1044 "
		::= { iqhip00CmdEntry 1044 }


	iqhip00LoggingInp1AudTypeEmbCh1Type OBJECT-TYPE
		SYNTAX		RollCallString
		MAX-ACCESS		read-only
		STATUS			current
		DESCRIPTION
				"TYPE: - Display
				 PAGE: - Logging- Inp 1 Aud Type
					Emb Ch 1 Type=  cmdID= 2044  format=   "
		::= { iqhip00CmdEntry 2044 }


	iqhip00LoggingInp1AudTypeEmbCh2TypeEnable OBJECT-TYPE
		SYNTAX		INTEGER { disable(0), enable(1) }
		MAX-ACCESS		read-write
		STATUS			current
		DESCRIPTION
				"TYPE: - Checkbox
				 PAGE: - Logging- Inp 1 Aud Type
					Emb Ch 2 Type  cmdID= 1045 "
		::= { iqhip00CmdEntry 1045 }


	iqhip00LoggingInp1AudTypeEmbCh2Type OBJECT-TYPE
		SYNTAX		RollCallString
		MAX-ACCESS		read-only
		STATUS			current
		DESCRIPTION
				"TYPE: - Display
				 PAGE: - Logging- Inp 1 Aud Type
					Emb Ch 2 Type=  cmdID= 2045  format=   "
		::= { iqhip00CmdEntry 2045 }


	iqhip00LoggingInp1AudTypeEmbCh3TypeEnable OBJECT-TYPE
		SYNTAX		INTEGER { disable(0), enable(1) }
		MAX-ACCESS		read-write
		STATUS			current
		DESCRIPTION
				"TYPE: - Checkbox
				 PAGE: - Logging- Inp 1 Aud Type
					Emb Ch 3 Type  cmdID= 1046 "
		::= { iqhip00CmdEntry 1046 }


	iqhip00LoggingInp1AudTypeEmbCh3Type OBJECT-TYPE
		SYNTAX		RollCallString
		MAX-ACCESS		read-only
		STATUS			current
		DESCRIPTION
				"TYPE: - Display
				 PAGE: - Logging- Inp 1 Aud Type
					Emb Ch 3 Type=  cmdID= 2046  format=   "
		::= { iqhip00CmdEntry 2046 }


	iqhip00LoggingInp1AudTypeEmbCh4TypeEnable OBJECT-TYPE
		SYNTAX		INTEGER { disable(0), enable(1) }
		MAX-ACCESS		read-write
		STATUS			current
		DESCRIPTION
				"TYPE: - Checkbox
				 PAGE: - Logging- Inp 1 Aud Type
					Emb Ch 4 Type  cmdID= 1047 "
		::= { iqhip00CmdEntry 1047 }


	iqhip00LoggingInp1AudTypeEmbCh4Type OBJECT-TYPE
		SYNTAX		RollCallString
		MAX-ACCESS		read-only
		STATUS			current
		DESCRIPTION
				"TYPE: - Display
				 PAGE: - Logging- Inp 1 Aud Type
					Emb Ch 4 Type=  cmdID= 2047  format=   "
		::= { iqhip00CmdEntry 2047 }


	iqhip00LoggingInp1AudTypeEmbCh5TypeEnable OBJECT-TYPE
		SYNTAX		INTEGER { disable(0), enable(1) }
		MAX-ACCESS		read-write
		STATUS			current
		DESCRIPTION
				"TYPE: - Checkbox
				 PAGE: - Logging- Inp 1 Aud Type
					Emb Ch 5 Type  cmdID= 1048 "
		::= { iqhip00CmdEntry 1048 }


	iqhip00LoggingInp1AudTypeEmbCh5Type OBJECT-TYPE
		SYNTAX		RollCallString
		MAX-ACCESS		read-only
		STATUS			current
		DESCRIPTION
				"TYPE: - Display
				 PAGE: - Logging- Inp 1 Aud Type
					Emb Ch 5 Type=  cmdID= 2048  format=   "
		::= { iqhip00CmdEntry 2048 }


	iqhip00LoggingInp1AudTypeEmbCh6TypeEnable OBJECT-TYPE
		SYNTAX		INTEGER { disable(0), enable(1) }
		MAX-ACCESS		read-write
		STATUS			current
		DESCRIPTION
				"TYPE: - Checkbox
				 PAGE: - Logging- Inp 1 Aud Type
					Emb Ch 6 Type  cmdID= 1049 "
		::= { iqhip00CmdEntry 1049 }


	iqhip00LoggingInp1AudTypeEmbCh6Type OBJECT-TYPE
		SYNTAX		RollCallString
		MAX-ACCESS		read-only
		STATUS			current
		DESCRIPTION
				"TYPE: - Display
				 PAGE: - Logging- Inp 1 Aud Type
					Emb Ch 6 Type=  cmdID= 2049  format=   "
		::= { iqhip00CmdEntry 2049 }


	iqhip00LoggingInp1AudTypeEmbCh7TypeEnable OBJECT-TYPE
		SYNTAX		INTEGER { disable(0), enable(1) }
		MAX-ACCESS		read-write
		STATUS			current
		DESCRIPTION
				"TYPE: - Checkbox
				 PAGE: - Logging- Inp 1 Aud Type
					Emb Ch 7 Type  cmdID= 1050 "
		::= { iqhip00CmdEntry 1050 }


	iqhip00LoggingInp1AudTypeEmbCh7Type OBJECT-TYPE
		SYNTAX		RollCallString
		MAX-ACCESS		read-only
		STATUS			current
		DESCRIPTION
				"TYPE: - Display
				 PAGE: - Logging- Inp 1 Aud Type
					Emb Ch 7 Type=  cmdID= 2050  format=   "
		::= { iqhip00CmdEntry 2050 }


	iqhip00LoggingInp1AudTypeEmbCh8TypeEnable OBJECT-TYPE
		SYNTAX		INTEGER { disable(0), enable(1) }
		MAX-ACCESS		read-write
		STATUS			current
		DESCRIPTION
				"TYPE: - Checkbox
				 PAGE: - Logging- Inp 1 Aud Type
					Emb Ch 8 Type  cmdID= 1051 "
		::= { iqhip00CmdEntry 1051 }


	iqhip00LoggingInp1AudTypeEmbCh8Type OBJECT-TYPE
		SYNTAX		RollCallString
		MAX-ACCESS		read-only
		STATUS			current
		DESCRIPTION
				"TYPE: - Display
				 PAGE: - Logging- Inp 1 Aud Type
					Emb Ch 8 Type=  cmdID= 2051  format=   "
		::= { iqhip00CmdEntry 2051 }


	iqhip00LoggingInp1AudTypeEmbCh9TypeEnable OBJECT-TYPE
		SYNTAX		INTEGER { disable(0), enable(1) }
		MAX-ACCESS		read-write
		STATUS			current
		DESCRIPTION
				"TYPE: - Checkbox
				 PAGE: - Logging- Inp 1 Aud Type
					Emb Ch 9 Type  cmdID= 1052 "
		::= { iqhip00CmdEntry 1052 }


	iqhip00LoggingInp1AudTypeEmbCh9Type OBJECT-TYPE
		SYNTAX		RollCallString
		MAX-ACCESS		read-only
		STATUS			current
		DESCRIPTION
				"TYPE: - Display
				 PAGE: - Logging- Inp 1 Aud Type
					Emb Ch 9 Type=  cmdID= 2052  format=   "
		::= { iqhip00CmdEntry 2052 }


	iqhip00LoggingInp1AudTypeEmbCh10TypeEnable OBJECT-TYPE
		SYNTAX		INTEGER { disable(0), enable(1) }
		MAX-ACCESS		read-write
		STATUS			current
		DESCRIPTION
				"TYPE: - Checkbox
				 PAGE: - Logging- Inp 1 Aud Type
					Emb Ch 10 Type  cmdID= 1053 "
		::= { iqhip00CmdEntry 1053 }


	iqhip00LoggingInp1AudTypeEmbCh10Type OBJECT-TYPE
		SYNTAX		RollCallString
		MAX-ACCESS		read-only
		STATUS			current
		DESCRIPTION
				"TYPE: - Display
				 PAGE: - Logging- Inp 1 Aud Type
					Emb Ch 10 Type=  cmdID= 2053  format=   "
		::= { iqhip00CmdEntry 2053 }


	iqhip00LoggingInp1AudTypeEmbCh11TypeEnable OBJECT-TYPE
		SYNTAX		INTEGER { disable(0), enable(1) }
		MAX-ACCESS		read-write
		STATUS			current
		DESCRIPTION
				"TYPE: - Checkbox
				 PAGE: - Logging- Inp 1 Aud Type
					Emb Ch 11 Type  cmdID= 1054 "
		::= { iqhip00CmdEntry 1054 }


	iqhip00LoggingInp1AudTypeEmbCh11Type OBJECT-TYPE
		SYNTAX		RollCallString
		MAX-ACCESS		read-only
		STATUS			current
		DESCRIPTION
				"TYPE: - Display
				 PAGE: - Logging- Inp 1 Aud Type
					Emb Ch 11 Type=  cmdID= 2054  format=   "
		::= { iqhip00CmdEntry 2054 }


	iqhip00LoggingInp1AudTypeEmbCh12TypeEnable OBJECT-TYPE
		SYNTAX		INTEGER { disable(0), enable(1) }
		MAX-ACCESS		read-write
		STATUS			current
		DESCRIPTION
				"TYPE: - Checkbox
				 PAGE: - Logging- Inp 1 Aud Type
					Emb Ch 12 Type  cmdID= 1055 "
		::= { iqhip00CmdEntry 1055 }


	iqhip00LoggingInp1AudTypeEmbCh12Type OBJECT-TYPE
		SYNTAX		RollCallString
		MAX-ACCESS		read-only
		STATUS			current
		DESCRIPTION
				"TYPE: - Display
				 PAGE: - Logging- Inp 1 Aud Type
					Emb Ch 12 Type=  cmdID= 2055  format=   "
		::= { iqhip00CmdEntry 2055 }


	iqhip00LoggingInp1AudTypeEmbCh13TypeEnable OBJECT-TYPE
		SYNTAX		INTEGER { disable(0), enable(1) }
		MAX-ACCESS		read-write
		STATUS			current
		DESCRIPTION
				"TYPE: - Checkbox
				 PAGE: - Logging- Inp 1 Aud Type
					Emb Ch 13 Type  cmdID= 1056 "
		::= { iqhip00CmdEntry 1056 }


	iqhip00LoggingInp1AudTypeEmbCh13Type OBJECT-TYPE
		SYNTAX		RollCallString
		MAX-ACCESS		read-only
		STATUS			current
		DESCRIPTION
				"TYPE: - Display
				 PAGE: - Logging- Inp 1 Aud Type
					Emb Ch 13 Type=  cmdID= 2056  format=   "
		::= { iqhip00CmdEntry 2056 }


	iqhip00LoggingInp1AudTypeEmbCh14TypeEnable OBJECT-TYPE
		SYNTAX		INTEGER { disable(0), enable(1) }
		MAX-ACCESS		read-write
		STATUS			current
		DESCRIPTION
				"TYPE: - Checkbox
				 PAGE: - Logging- Inp 1 Aud Type
					Emb Ch 14 Type  cmdID= 1057 "
		::= { iqhip00CmdEntry 1057 }


	iqhip00LoggingInp1AudTypeEmbCh14Type OBJECT-TYPE
		SYNTAX		RollCallString
		MAX-ACCESS		read-only
		STATUS			current
		DESCRIPTION
				"TYPE: - Display
				 PAGE: - Logging- Inp 1 Aud Type
					Emb Ch 14 Type=  cmdID= 2057  format=   "
		::= { iqhip00CmdEntry 2057 }


	iqhip00LoggingInp1AudTypeEmbCh15TypeEnable OBJECT-TYPE
		SYNTAX		INTEGER { disable(0), enable(1) }
		MAX-ACCESS		read-write
		STATUS			current
		DESCRIPTION
				"TYPE: - Checkbox
				 PAGE: - Logging- Inp 1 Aud Type
					Emb Ch 15 Type  cmdID= 1058 "
		::= { iqhip00CmdEntry 1058 }


	iqhip00LoggingInp1AudTypeEmbCh15Type OBJECT-TYPE
		SYNTAX		RollCallString
		MAX-ACCESS		read-only
		STATUS			current
		DESCRIPTION
				"TYPE: - Display
				 PAGE: - Logging- Inp 1 Aud Type
					Emb Ch 15 Type=  cmdID= 2058  format=   "
		::= { iqhip00CmdEntry 2058 }


	iqhip00LoggingInp1AudTypeEmbCh16TypeEnable OBJECT-TYPE
		SYNTAX		INTEGER { disable(0), enable(1) }
		MAX-ACCESS		read-write
		STATUS			current
		DESCRIPTION
				"TYPE: - Checkbox
				 PAGE: - Logging- Inp 1 Aud Type
					Emb Ch 16 Type  cmdID= 1059 "
		::= { iqhip00CmdEntry 1059 }


	iqhip00LoggingInp1AudTypeEmbCh16Type OBJECT-TYPE
		SYNTAX		RollCallString
		MAX-ACCESS		read-only
		STATUS			current
		DESCRIPTION
				"TYPE: - Display
				 PAGE: - Logging- Inp 1 Aud Type
					Emb Ch 16 Type=  cmdID= 2059  format=   "
		::= { iqhip00CmdEntry 2059 }


	iqhip00LoggingInp1DolbyEStatePair1Enable OBJECT-TYPE
		SYNTAX		INTEGER { disable(0), enable(1) }
		MAX-ACCESS		read-write
		STATUS			current
		DESCRIPTION
				"TYPE: - Checkbox
				 PAGE: - Logging- Inp 1 Dolby E State
					Pair 1 Enable  cmdID= 1150 "
		::= { iqhip00CmdEntry 1150 }


	iqhip00LoggingInp1DolbyEStatePair1State OBJECT-TYPE
		SYNTAX		RollCallString
		MAX-ACCESS		read-only
		STATUS			current
		DESCRIPTION
				"TYPE: - Display
				 PAGE: - Logging- Inp 1 Dolby E State
					Pair 1 State=  cmdID= 2150  format=   "
		::= { iqhip00CmdEntry 2150 }


	iqhip00LoggingInp1DolbyEStatePair2Enable OBJECT-TYPE
		SYNTAX		INTEGER { disable(0), enable(1) }
		MAX-ACCESS		read-write
		STATUS			current
		DESCRIPTION
				"TYPE: - Checkbox
				 PAGE: - Logging- Inp 1 Dolby E State
					Pair 2 Enable  cmdID= 1151 "
		::= { iqhip00CmdEntry 1151 }


	iqhip00LoggingInp1DolbyEStatePair2State OBJECT-TYPE
		SYNTAX		RollCallString
		MAX-ACCESS		read-only
		STATUS			current
		DESCRIPTION
				"TYPE: - Display
				 PAGE: - Logging- Inp 1 Dolby E State
					Pair 2 State=  cmdID= 2151  format=   "
		::= { iqhip00CmdEntry 2151 }


	iqhip00LoggingInp1DolbyEStatePair3Enable OBJECT-TYPE
		SYNTAX		INTEGER { disable(0), enable(1) }
		MAX-ACCESS		read-write
		STATUS			current
		DESCRIPTION
				"TYPE: - Checkbox
				 PAGE: - Logging- Inp 1 Dolby E State
					Pair 3 Enable  cmdID= 1152 "
		::= { iqhip00CmdEntry 1152 }


	iqhip00LoggingInp1DolbyEStatePair3State OBJECT-TYPE
		SYNTAX		RollCallString
		MAX-ACCESS		read-only
		STATUS			current
		DESCRIPTION
				"TYPE: - Display
				 PAGE: - Logging- Inp 1 Dolby E State
					Pair 3 State=  cmdID= 2152  format=   "
		::= { iqhip00CmdEntry 2152 }


	iqhip00LoggingInp1DolbyEStatePair4Enable OBJECT-TYPE
		SYNTAX		INTEGER { disable(0), enable(1) }
		MAX-ACCESS		read-write
		STATUS			current
		DESCRIPTION
				"TYPE: - Checkbox
				 PAGE: - Logging- Inp 1 Dolby E State
					Pair 4 Enable  cmdID= 1153 "
		::= { iqhip00CmdEntry 1153 }


	iqhip00LoggingInp1DolbyEStatePair4State OBJECT-TYPE
		SYNTAX		RollCallString
		MAX-ACCESS		read-only
		STATUS			current
		DESCRIPTION
				"TYPE: - Display
				 PAGE: - Logging- Inp 1 Dolby E State
					Pair 4 State=  cmdID= 2153  format=   "
		::= { iqhip00CmdEntry 2153 }


	iqhip00LoggingInp1DolbyEStatePair5Enable OBJECT-TYPE
		SYNTAX		INTEGER { disable(0), enable(1) }
		MAX-ACCESS		read-write
		STATUS			current
		DESCRIPTION
				"TYPE: - Checkbox
				 PAGE: - Logging- Inp 1 Dolby E State
					Pair 5 Enable  cmdID= 1154 "
		::= { iqhip00CmdEntry 1154 }


	iqhip00LoggingInp1DolbyEStatePair5State OBJECT-TYPE
		SYNTAX		RollCallString
		MAX-ACCESS		read-only
		STATUS			current
		DESCRIPTION
				"TYPE: - Display
				 PAGE: - Logging- Inp 1 Dolby E State
					Pair 5 State=  cmdID= 2154  format=   "
		::= { iqhip00CmdEntry 2154 }


	iqhip00LoggingInp1DolbyEStatePair6Enable OBJECT-TYPE
		SYNTAX		INTEGER { disable(0), enable(1) }
		MAX-ACCESS		read-write
		STATUS			current
		DESCRIPTION
				"TYPE: - Checkbox
				 PAGE: - Logging- Inp 1 Dolby E State
					Pair 6 Enable  cmdID= 1155 "
		::= { iqhip00CmdEntry 1155 }


	iqhip00LoggingInp1DolbyEStatePair6State OBJECT-TYPE
		SYNTAX		RollCallString
		MAX-ACCESS		read-only
		STATUS			current
		DESCRIPTION
				"TYPE: - Display
				 PAGE: - Logging- Inp 1 Dolby E State
					Pair 6 State=  cmdID= 2155  format=   "
		::= { iqhip00CmdEntry 2155 }


	iqhip00LoggingInp1DolbyEStatePair7Enable OBJECT-TYPE
		SYNTAX		INTEGER { disable(0), enable(1) }
		MAX-ACCESS		read-write
		STATUS			current
		DESCRIPTION
				"TYPE: - Checkbox
				 PAGE: - Logging- Inp 1 Dolby E State
					Pair 7 Enable  cmdID= 1156 "
		::= { iqhip00CmdEntry 1156 }


	iqhip00LoggingInp1DolbyEStatePair7State OBJECT-TYPE
		SYNTAX		RollCallString
		MAX-ACCESS		read-only
		STATUS			current
		DESCRIPTION
				"TYPE: - Display
				 PAGE: - Logging- Inp 1 Dolby E State
					Pair 7 State=  cmdID= 2156  format=   "
		::= { iqhip00CmdEntry 2156 }


	iqhip00LoggingInp1DolbyEStatePair8Enable OBJECT-TYPE
		SYNTAX		INTEGER { disable(0), enable(1) }
		MAX-ACCESS		read-write
		STATUS			current
		DESCRIPTION
				"TYPE: - Checkbox
				 PAGE: - Logging- Inp 1 Dolby E State
					Pair 8 Enable  cmdID= 1157 "
		::= { iqhip00CmdEntry 1157 }


	iqhip00LoggingInp1DolbyEStatePair8State OBJECT-TYPE
		SYNTAX		RollCallString
		MAX-ACCESS		read-only
		STATUS			current
		DESCRIPTION
				"TYPE: - Display
				 PAGE: - Logging- Inp 1 Dolby E State
					Pair 8 State=  cmdID= 2157  format=   "
		::= { iqhip00CmdEntry 2157 }


	iqhip00LoggingInp1BitDepthEmbCh1BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 1 Bit Depth  cmdID= 1060 "
		::= { iqhip00CmdEntry 1060 }


	iqhip00LoggingInp1BitDepthEmbCh1BitDepth OBJECT-TYPE
		SYNTAX		RollCallString
		MAX-ACCESS		read-only
		STATUS			current
		DESCRIPTION
				"TYPE: - Display
				 PAGE: - Logging- Inp 1 Bit Depth
					Emb Ch 1 Bit Depth=  cmdID= 2060  format=   "
		::= { iqhip00CmdEntry 2060 }


	iqhip00LoggingInp1BitDepthEmbCh2BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 2 Bit Depth  cmdID= 1061 "
		::= { iqhip00CmdEntry 1061 }


	iqhip00LoggingInp1BitDepthEmbCh2BitDepth OBJECT-TYPE
		SYNTAX		RollCallString
		MAX-ACCESS		read-only
		STATUS			current
		DESCRIPTION
				"TYPE: - Display
				 PAGE: - Logging- Inp 1 Bit Depth
					Emb Ch 2 Bit Depth=  cmdID= 2061  format=   "
		::= { iqhip00CmdEntry 2061 }


	iqhip00LoggingInp1BitDepthEmbCh3BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 3 Bit Depth  cmdID= 1062 "
		::= { iqhip00CmdEntry 1062 }


	iqhip00LoggingInp1BitDepthEmbCh3BitDepth OBJECT-TYPE
		SYNTAX		RollCallString
		MAX-ACCESS		read-only
		STATUS			current
		DESCRIPTION
				"TYPE: - Display
				 PAGE: - Logging- Inp 1 Bit Depth
					Emb Ch 3 Bit Depth=  cmdID= 2062  format=   "
		::= { iqhip00CmdEntry 2062 }


	iqhip00LoggingInp1BitDepthEmbCh4BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 4 Bit Depth  cmdID= 1063 "
		::= { iqhip00CmdEntry 1063 }


	iqhip00LoggingInp1BitDepthEmbCh4BitDepth OBJECT-TYPE
		SYNTAX		RollCallString
		MAX-ACCESS		read-only
		STATUS			current
		DESCRIPTION
				"TYPE: - Display
				 PAGE: - Logging- Inp 1 Bit Depth
					Emb Ch 4 Bit Depth=  cmdID= 2063  format=   "
		::= { iqhip00CmdEntry 2063 }


	iqhip00LoggingInp1BitDepthEmbCh5BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 5 Bit Depth  cmdID= 1064 "
		::= { iqhip00CmdEntry 1064 }


	iqhip00LoggingInp1BitDepthEmbCh5BitDepth OBJECT-TYPE
		SYNTAX		RollCallString
		MAX-ACCESS		read-only
		STATUS			current
		DESCRIPTION
				"TYPE: - Display
				 PAGE: - Logging- Inp 1 Bit Depth
					Emb Ch 5 Bit Depth=  cmdID= 2064  format=   "
		::= { iqhip00CmdEntry 2064 }


	iqhip00LoggingInp1BitDepthEmbCh6BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 6 Bit Depth  cmdID= 1065 "
		::= { iqhip00CmdEntry 1065 }


	iqhip00LoggingInp1BitDepthEmbCh6BitDepth OBJECT-TYPE
		SYNTAX		RollCallString
		MAX-ACCESS		read-only
		STATUS			current
		DESCRIPTION
				"TYPE: - Display
				 PAGE: - Logging- Inp 1 Bit Depth
					Emb Ch 6 Bit Depth=  cmdID= 2065  format=   "
		::= { iqhip00CmdEntry 2065 }


	iqhip00LoggingInp1BitDepthEmbCh7BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 7 Bit Depth  cmdID= 1066 "
		::= { iqhip00CmdEntry 1066 }


	iqhip00LoggingInp1BitDepthEmbCh7BitDepth OBJECT-TYPE
		SYNTAX		RollCallString
		MAX-ACCESS		read-only
		STATUS			current
		DESCRIPTION
				"TYPE: - Display
				 PAGE: - Logging- Inp 1 Bit Depth
					Emb Ch 7 Bit Depth=  cmdID= 2066  format=   "
		::= { iqhip00CmdEntry 2066 }


	iqhip00LoggingInp1BitDepthEmbCh8BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 8 Bit Depth  cmdID= 1067 "
		::= { iqhip00CmdEntry 1067 }


	iqhip00LoggingInp1BitDepthEmbCh8BitDepth OBJECT-TYPE
		SYNTAX		RollCallString
		MAX-ACCESS		read-only
		STATUS			current
		DESCRIPTION
				"TYPE: - Display
				 PAGE: - Logging- Inp 1 Bit Depth
					Emb Ch 8 Bit Depth=  cmdID= 2067  format=   "
		::= { iqhip00CmdEntry 2067 }


	iqhip00LoggingInp1BitDepthEmbCh9BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 9 Bit Depth  cmdID= 1068 "
		::= { iqhip00CmdEntry 1068 }


	iqhip00LoggingInp1BitDepthEmbCh9BitDepth OBJECT-TYPE
		SYNTAX		RollCallString
		MAX-ACCESS		read-only
		STATUS			current
		DESCRIPTION
				"TYPE: - Display
				 PAGE: - Logging- Inp 1 Bit Depth
					Emb Ch 9 Bit Depth=  cmdID= 2068  format=   "
		::= { iqhip00CmdEntry 2068 }


	iqhip00LoggingInp1BitDepthEmbCh10BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 10 Bit Depth  cmdID= 1069 "
		::= { iqhip00CmdEntry 1069 }


	iqhip00LoggingInp1BitDepthEmbCh10BitDepth OBJECT-TYPE
		SYNTAX		RollCallString
		MAX-ACCESS		read-only
		STATUS			current
		DESCRIPTION
				"TYPE: - Display
				 PAGE: - Logging- Inp 1 Bit Depth
					Emb Ch 10 Bit Dep=  cmdID= 2069  format=   "
		::= { iqhip00CmdEntry 2069 }


	iqhip00LoggingInp1BitDepthEmbCh11BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 11 Bit Depth  cmdID= 1070 "
		::= { iqhip00CmdEntry 1070 }


	iqhip00LoggingInp1BitDepthEmbCh11BitDepth OBJECT-TYPE
		SYNTAX		RollCallString
		MAX-ACCESS		read-only
		STATUS			current
		DESCRIPTION
				"TYPE: - Display
				 PAGE: - Logging- Inp 1 Bit Depth
					Emb Ch 11 Bit Dep=  cmdID= 2070  format=   "
		::= { iqhip00CmdEntry 2070 }


	iqhip00LoggingInp1BitDepthEmbCh12BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 12 Bit Depth  cmdID= 1071 "
		::= { iqhip00CmdEntry 1071 }


	iqhip00LoggingInp1BitDepthEmbCh12BitDepth OBJECT-TYPE
		SYNTAX		RollCallString
		MAX-ACCESS		read-only
		STATUS			current
		DESCRIPTION
				"TYPE: - Display
				 PAGE: - Logging- Inp 1 Bit Depth
					Emb Ch 12 Bit Dep=  cmdID= 2071  format=   "
		::= { iqhip00CmdEntry 2071 }


	iqhip00LoggingInp1BitDepthEmbCh13BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 13 Bit Depth  cmdID= 1072 "
		::= { iqhip00CmdEntry 1072 }


	iqhip00LoggingInp1BitDepthEmbCh13BitDepth OBJECT-TYPE
		SYNTAX		RollCallString
		MAX-ACCESS		read-only
		STATUS			current
		DESCRIPTION
				"TYPE: - Display
				 PAGE: - Logging- Inp 1 Bit Depth
					Emb Ch 13 Bit Dep=  cmdID= 2072  format=   "
		::= { iqhip00CmdEntry 2072 }


	iqhip00LoggingInp1BitDepthEmbCh14BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 14 Bit Depth  cmdID= 1073 "
		::= { iqhip00CmdEntry 1073 }


	iqhip00LoggingInp1BitDepthEmbCh14BitDepth OBJECT-TYPE
		SYNTAX		RollCallString
		MAX-ACCESS		read-only
		STATUS			current
		DESCRIPTION
				"TYPE: - Display
				 PAGE: - Logging- Inp 1 Bit Depth
					Emb Ch 14 Bit Dep=  cmdID= 2073  format=   "
		::= { iqhip00CmdEntry 2073 }


	iqhip00LoggingInp1BitDepthEmbCh15BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 15 Bit Depth  cmdID= 1074 "
		::= { iqhip00CmdEntry 1074 }


	iqhip00LoggingInp1BitDepthEmbCh15BitDepth OBJECT-TYPE
		SYNTAX		RollCallString
		MAX-ACCESS		read-only
		STATUS			current
		DESCRIPTION
				"TYPE: - Display
				 PAGE: - Logging- Inp 1 Bit Depth
					Emb Ch 15 Bit Dep=  cmdID= 2074  format=   "
		::= { iqhip00CmdEntry 2074 }


	iqhip00LoggingInp1BitDepthEmbCh16BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 16 Bit Depth  cmdID= 1075 "
		::= { iqhip00CmdEntry 1075 }


	iqhip00LoggingInp1BitDepthEmbCh16BitDepth OBJECT-TYPE
		SYNTAX		RollCallString
		MAX-ACCESS		read-only
		STATUS			current
		DESCRIPTION
				"TYPE: - Display
				 PAGE: - Logging- Inp 1 Bit Depth
					Emb Ch 16 Bit Dep=  cmdID= 2075  format=   "
		::= { iqhip00CmdEntry 2075 }


	iqhip00LoggingInp1LevelEmbCh1LevelEnable OBJECT-TYPE
		SYNTAX		INTEGER { disable(0), enable(1) }
		MAX-ACCESS		read-write
		STATUS			current
		DESCRIPTION
				"TYPE: - Checkbox
				 PAGE: - Logging- Inp 1 Level
					Emb Ch 1 Level  cmdID= 1076 "
		::= { iqhip00CmdEntry 1076 }


	iqhip00LoggingInp1LevelEmbCh1Level OBJECT-TYPE
		SYNTAX		RollCallString
		MAX-ACCESS		read-only
		STATUS			current
		DESCRIPTION
				"TYPE: - Display
				 PAGE: - Logging- Inp 1 Level
					Emb Ch 1 Level=  cmdID= 2076  format=   "
		::= { iqhip00CmdEntry 2076 }


	iqhip00LoggingInp1LevelEmbCh2LevelEnable OBJECT-TYPE
		SYNTAX		INTEGER { disable(0), enable(1) }
		MAX-ACCESS		read-write
		STATUS			current
		DESCRIPTION
				"TYPE: - Checkbox
				 PAGE: - Logging- Inp 1 Level
					Emb Ch 2 Level  cmdID= 1077 "
		::= { iqhip00CmdEntry 1077 }


	iqhip00LoggingInp1LevelEmbCh2Level OBJECT-TYPE
		SYNTAX		RollCallString
		MAX-ACCESS		read-only
		STATUS			current
		DESCRIPTION
				"TYPE: - Display
				 PAGE: - Logging- Inp 1 Level
					Emb Ch 2 Level=  cmdID= 2077  format=   "
		::= { iqhip00CmdEntry 2077 }


	iqhip00LoggingInp1LevelEmbCh3LevelEnable OBJECT-TYPE
		SYNTAX		INTEGER { disable(0), enable(1) }
		MAX-ACCESS		read-write
		STATUS			current
		DESCRIPTION
				"TYPE: - Checkbox
				 PAGE: - Logging- Inp 1 Level
					Emb Ch 3 Level  cmdID= 1078 "
		::= { iqhip00CmdEntry 1078 }


	iqhip00LoggingInp1LevelEmbCh3Level OBJECT-TYPE
		SYNTAX		RollCallString
		MAX-ACCESS		read-only
		STATUS			current
		DESCRIPTION
				"TYPE: - Display
				 PAGE: - Logging- Inp 1 Level
					Emb Ch 3 Level=  cmdID= 2078  format=   "
		::= { iqhip00CmdEntry 2078 }


	iqhip00LoggingInp1LevelEmbCh4LevelEnable OBJECT-TYPE
		SYNTAX		INTEGER { disable(0), enable(1) }
		MAX-ACCESS		read-write
		STATUS			current
		DESCRIPTION
				"TYPE: - Checkbox
				 PAGE: - Logging- Inp 1 Level
					Emb Ch 4 Level  cmdID= 1079 "
		::= { iqhip00CmdEntry 1079 }


	iqhip00LoggingInp1LevelEmbCh4Level OBJECT-TYPE
		SYNTAX		RollCallString
		MAX-ACCESS		read-only
		STATUS			current
		DESCRIPTION
				"TYPE: - Display
				 PAGE: - Logging- Inp 1 Level
					Emb Ch 4 Level=  cmdID= 2079  format=   "
		::= { iqhip00CmdEntry 2079 }


	iqhip00LoggingInp1LevelEmbCh5LevelEnable OBJECT-TYPE
		SYNTAX		INTEGER { disable(0), enable(1) }
		MAX-ACCESS		read-write
		STATUS			current
		DESCRIPTION
				"TYPE: - Checkbox
				 PAGE: - Logging- Inp 1 Level
					Emb Ch 5 Level  cmdID= 1080 "
		::= { iqhip00CmdEntry 1080 }


	iqhip00LoggingInp1LevelEmbCh5Level OBJECT-TYPE
		SYNTAX		RollCallString
		MAX-ACCESS		read-only
		STATUS			current
		DESCRIPTION
				"TYPE: - Display
				 PAGE: - Logging- Inp 1 Level
					Emb Ch 5 Level=  cmdID= 2080  format=   "
		::= { iqhip00CmdEntry 2080 }


	iqhip00LoggingInp1LevelEmbCh6LevelEnable OBJECT-TYPE
		SYNTAX		INTEGER { disable(0), enable(1) }
		MAX-ACCESS		read-write
		STATUS			current
		DESCRIPTION
				"TYPE: - Checkbox
				 PAGE: - Logging- Inp 1 Level
					Emb Ch 6 Level  cmdID= 1081 "
		::= { iqhip00CmdEntry 1081 }


	iqhip00LoggingInp1LevelEmbCh6Level OBJECT-TYPE
		SYNTAX		RollCallString
		MAX-ACCESS		read-only
		STATUS			current
		DESCRIPTION
				"TYPE: - Display
				 PAGE: - Logging- Inp 1 Level
					Emb Ch 6 Level=  cmdID= 2081  format=   "
		::= { iqhip00CmdEntry 2081 }


	iqhip00LoggingInp1LevelEmbCh7LevelEnable OBJECT-TYPE
		SYNTAX		INTEGER { disable(0), enable(1) }
		MAX-ACCESS		read-write
		STATUS			current
		DESCRIPTION
				"TYPE: - Checkbox
				 PAGE: - Logging- Inp 1 Level
					Emb Ch 7 Level  cmdID= 1082 "
		::= { iqhip00CmdEntry 1082 }


	iqhip00LoggingInp1LevelEmbCh7Level OBJECT-TYPE
		SYNTAX		RollCallString
		MAX-ACCESS		read-only
		STATUS			current
		DESCRIPTION
				"TYPE: - Display
				 PAGE: - Logging- Inp 1 Level
					Emb Ch 7 Level=  cmdID= 2082  format=   "
		::= { iqhip00CmdEntry 2082 }


	iqhip00LoggingInp1LevelEmbCh8LevelEnable OBJECT-TYPE
		SYNTAX		INTEGER { disable(0), enable(1) }
		MAX-ACCESS		read-write
		STATUS			current
		DESCRIPTION
				"TYPE: - Checkbox
				 PAGE: - Logging- Inp 1 Level
					Emb Ch 8 Level  cmdID= 1083 "
		::= { iqhip00CmdEntry 1083 }


	iqhip00LoggingInp1LevelEmbCh8Level OBJECT-TYPE
		SYNTAX		RollCallString
		MAX-ACCESS		read-only
		STATUS			current
		DESCRIPTION
				"TYPE: - Display
				 PAGE: - Logging- Inp 1 Level
					Emb Ch 8 Level=  cmdID= 2083  format=   "
		::= { iqhip00CmdEntry 2083 }


	iqhip00LoggingInp1LevelEmbCh9LevelEnable OBJECT-TYPE
		SYNTAX		INTEGER { disable(0), enable(1) }
		MAX-ACCESS		read-write
		STATUS			current
		DESCRIPTION
				"TYPE: - Checkbox
				 PAGE: - Logging- Inp 1 Level
					Emb Ch 9 Level  cmdID= 1084 "
		::= { iqhip00CmdEntry 1084 }


	iqhip00LoggingInp1LevelEmbCh9Level OBJECT-TYPE
		SYNTAX		RollCallString
		MAX-ACCESS		read-only
		STATUS			current
		DESCRIPTION
				"TYPE: - Display
				 PAGE: - Logging- Inp 1 Level
					Emb Ch 9 Level=  cmdID= 2084  format=   "
		::= { iqhip00CmdEntry 2084 }


	iqhip00LoggingInp1LevelEmbCh10LevelEnable OBJECT-TYPE
		SYNTAX		INTEGER { disable(0), enable(1) }
		MAX-ACCESS		read-write
		STATUS			current
		DESCRIPTION
				"TYPE: - Checkbox
				 PAGE: - Logging- Inp 1 Level
					Emb Ch 10 Level  cmdID= 1085 "
		::= { iqhip00CmdEntry 1085 }


	iqhip00LoggingInp1LevelEmbCh10Level OBJECT-TYPE
		SYNTAX		RollCallString
		MAX-ACCESS		read-only
		STATUS			current
		DESCRIPTION
				"TYPE: - Display
				 PAGE: - Logging- Inp 1 Level
					Emb Ch 10 Level=  cmdID= 2085  format=   "
		::= { iqhip00CmdEntry 2085 }


	iqhip00LoggingInp1LevelEmbCh11LevelEnable OBJECT-TYPE
		SYNTAX		INTEGER { disable(0), enable(1) }
		MAX-ACCESS		read-write
		STATUS			current
		DESCRIPTION
				"TYPE: - Checkbox
				 PAGE: - Logging- Inp 1 Level
					Emb Ch 11 Level  cmdID= 1086 "
		::= { iqhip00CmdEntry 1086 }


	iqhip00LoggingInp1LevelEmbCh11Level OBJECT-TYPE
		SYNTAX		RollCallString
		MAX-ACCESS		read-only
		STATUS			current
		DESCRIPTION
				"TYPE: - Display
				 PAGE: - Logging- Inp 1 Level
					Emb Ch 11 Level=  cmdID= 2086  format=   "
		::= { iqhip00CmdEntry 2086 }


	iqhip00LoggingInp1LevelEmbCh12LevelEnable OBJECT-TYPE
		SYNTAX		INTEGER { disable(0), enable(1) }
		MAX-ACCESS		read-write
		STATUS			current
		DESCRIPTION
				"TYPE: - Checkbox
				 PAGE: - Logging- Inp 1 Level
					Emb Ch 12 Level  cmdID= 1087 "
		::= { iqhip00CmdEntry 1087 }


	iqhip00LoggingInp1LevelEmbCh12Level OBJECT-TYPE
		SYNTAX		RollCallString
		MAX-ACCESS		read-only
		STATUS			current
		DESCRIPTION
				"TYPE: - Display
				 PAGE: - Logging- Inp 1 Level
					Emb Ch 12 Level=  cmdID= 2087  format=   "
		::= { iqhip00CmdEntry 2087 }


	iqhip00LoggingInp1LevelEmbCh13LevelEnable OBJECT-TYPE
		SYNTAX		INTEGER { disable(0), enable(1) }
		MAX-ACCESS		read-write
		STATUS			current
		DESCRIPTION
				"TYPE: - Checkbox
				 PAGE: - Logging- Inp 1 Level
					Emb Ch 13 Level  cmdID= 1088 "
		::= { iqhip00CmdEntry 1088 }


	iqhip00LoggingInp1LevelEmbCh13Level OBJECT-TYPE
		SYNTAX		RollCallString
		MAX-ACCESS		read-only
		STATUS			current
		DESCRIPTION
				"TYPE: - Display
				 PAGE: - Logging- Inp 1 Level
					Emb Ch 13 Level=  cmdID= 2088  format=   "
		::= { iqhip00CmdEntry 2088 }


	iqhip00LoggingInp1LevelEmbCh14LevelEnable OBJECT-TYPE
		SYNTAX		INTEGER { disable(0), enable(1) }
		MAX-ACCESS		read-write
		STATUS			current
		DESCRIPTION
				"TYPE: - Checkbox
				 PAGE: - Logging- Inp 1 Level
					Emb Ch 14 Level  cmdID= 1089 "
		::= { iqhip00CmdEntry 1089 }


	iqhip00LoggingInp1LevelEmbCh14Level OBJECT-TYPE
		SYNTAX		RollCallString
		MAX-ACCESS		read-only
		STATUS			current
		DESCRIPTION
				"TYPE: - Display
				 PAGE: - Logging- Inp 1 Level
					Emb Ch 14 Level=  cmdID= 2089  format=   "
		::= { iqhip00CmdEntry 2089 }


	iqhip00LoggingInp1LevelEmbCh15LevelEnable OBJECT-TYPE
		SYNTAX		INTEGER { disable(0), enable(1) }
		MAX-ACCESS		read-write
		STATUS			current
		DESCRIPTION
				"TYPE: - Checkbox
				 PAGE: - Logging- Inp 1 Level
					Emb Ch 15 Level  cmdID= 1090 "
		::= { iqhip00CmdEntry 1090 }


	iqhip00LoggingInp1LevelEmbCh15Level OBJECT-TYPE
		SYNTAX		RollCallString
		MAX-ACCESS		read-only
		STATUS			current
		DESCRIPTION
				"TYPE: - Display
				 PAGE: - Logging- Inp 1 Level
					Emb Ch 15 Level=  cmdID= 2090  format=   "
		::= { iqhip00CmdEntry 2090 }


	iqhip00LoggingInp1LevelEmbCh16LevelEnable OBJECT-TYPE
		SYNTAX		INTEGER { disable(0), enable(1) }
		MAX-ACCESS		read-write
		STATUS			current
		DESCRIPTION
				"TYPE: - Checkbox
				 PAGE: - Logging- Inp 1 Level
					Emb Ch 16 Level  cmdID= 1091 "
		::= { iqhip00CmdEntry 1091 }


	iqhip00LoggingInp1LevelEmbCh16Level OBJECT-TYPE
		SYNTAX		RollCallString
		MAX-ACCESS		read-only
		STATUS			current
		DESCRIPTION
				"TYPE: - Display
				 PAGE: - Logging- Inp 1 Level
					Emb Ch 16 Level=  cmdID= 2091  format=   "
		::= { iqhip00CmdEntry 2091 }


	iqhip00LoggingInp1ClippingEmbCh1LevelEnable OBJECT-TYPE
		SYNTAX		INTEGER { disable(0), enable(1) }
		MAX-ACCESS		read-write
		STATUS			current
		DESCRIPTION
				"TYPE: - Checkbox
				 PAGE: - Logging- Inp 1 Clipping
					Emb Ch 1 Level  cmdID= 1134 "
		::= { iqhip00CmdEntry 1134 }


	iqhip00LoggingInp1ClippingEmbCh1Level OBJECT-TYPE
		SYNTAX		RollCallString
		MAX-ACCESS		read-only
		STATUS			current
		DESCRIPTION
				"TYPE: - Display
				 PAGE: - Logging- Inp 1 Clipping
					Emb Ch 1 Level=  cmdID= 2134  format=   "
		::= { iqhip00CmdEntry 2134 }


	iqhip00LoggingInp1ClippingEmbCh2LevelEnable OBJECT-TYPE
		SYNTAX		INTEGER { disable(0), enable(1) }
		MAX-ACCESS		read-write
		STATUS			current
		DESCRIPTION
				"TYPE: - Checkbox
				 PAGE: - Logging- Inp 1 Clipping
					Emb Ch 2 Level  cmdID= 1135 "
		::= { iqhip00CmdEntry 1135 }


	iqhip00LoggingInp1ClippingEmbCh2Level OBJECT-TYPE
		SYNTAX		RollCallString
		MAX-ACCESS		read-only
		STATUS			current
		DESCRIPTION
				"TYPE: - Display
				 PAGE: - Logging- Inp 1 Clipping
					Emb Ch 2 Level=  cmdID= 2135  format=   "
		::= { iqhip00CmdEntry 2135 }


	iqhip00LoggingInp1ClippingEmbCh3LevelEnable OBJECT-TYPE
		SYNTAX		INTEGER { disable(0), enable(1) }
		MAX-ACCESS		read-write
		STATUS			current
		DESCRIPTION
				"TYPE: - Checkbox
				 PAGE: - Logging- Inp 1 Clipping
					Emb Ch 3 Level  cmdID= 1136 "
		::= { iqhip00CmdEntry 1136 }


	iqhip00LoggingInp1ClippingEmbCh3Level OBJECT-TYPE
		SYNTAX		RollCallString
		MAX-ACCESS		read-only
		STATUS			current
		DESCRIPTION
				"TYPE: - Display
				 PAGE: - Logging- Inp 1 Clipping
					Emb Ch 3 Level=  cmdID= 2136  format=   "
		::= { iqhip00CmdEntry 2136 }


	iqhip00LoggingInp1ClippingEmbCh4LevelEnable OBJECT-TYPE
		SYNTAX		INTEGER { disable(0), enable(1) }
		MAX-ACCESS		read-write
		STATUS			current
		DESCRIPTION
				"TYPE: - Checkbox
				 PAGE: - Logging- Inp 1 Clipping
					Emb Ch 4 Level  cmdID= 1137 "
		::= { iqhip00CmdEntry 1137 }


	iqhip00LoggingInp1ClippingEmbCh4Level OBJECT-TYPE
		SYNTAX		RollCallString
		MAX-ACCESS		read-only
		STATUS			current
		DESCRIPTION
				"TYPE: - Display
				 PAGE: - Logging- Inp 1 Clipping
					Emb Ch 4 Level=  cmdID= 2137  format=   "
		::= { iqhip00CmdEntry 2137 }


	iqhip00LoggingInp1ClippingEmbCh5LevelEnable OBJECT-TYPE
		SYNTAX		INTEGER { disable(0), enable(1) }
		MAX-ACCESS		read-write
		STATUS			current
		DESCRIPTION
				"TYPE: - Checkbox
				 PAGE: - Logging- Inp 1 Clipping
					Emb Ch 5 Level  cmdID= 1138 "
		::= { iqhip00CmdEntry 1138 }


	iqhip00LoggingInp1ClippingEmbCh5Level OBJECT-TYPE
		SYNTAX		RollCallString
		MAX-ACCESS		read-only
		STATUS			current
		DESCRIPTION
				"TYPE: - Display
				 PAGE: - Logging- Inp 1 Clipping
					Emb Ch 5 Level=  cmdID= 2138  format=   "
		::= { iqhip00CmdEntry 2138 }


	iqhip00LoggingInp1ClippingEmbCh6LevelEnable OBJECT-TYPE
		SYNTAX		INTEGER { disable(0), enable(1) }
		MAX-ACCESS		read-write
		STATUS			current
		DESCRIPTION
				"TYPE: - Checkbox
				 PAGE: - Logging- Inp 1 Clipping
					Emb Ch 6 Level  cmdID= 1139 "
		::= { iqhip00CmdEntry 1139 }


	iqhip00LoggingInp1ClippingEmbCh6Level OBJECT-TYPE
		SYNTAX		RollCallString
		MAX-ACCESS		read-only
		STATUS			current
		DESCRIPTION
				"TYPE: - Display
				 PAGE: - Logging- Inp 1 Clipping
					Emb Ch 6 Level=  cmdID= 2139  format=   "
		::= { iqhip00CmdEntry 2139 }


	iqhip00LoggingInp1ClippingEmbCh7LevelEnable OBJECT-TYPE
		SYNTAX		INTEGER { disable(0), enable(1) }
		MAX-ACCESS		read-write
		STATUS			current
		DESCRIPTION
				"TYPE: - Checkbox
				 PAGE: - Logging- Inp 1 Clipping
					Emb Ch 7 Level  cmdID= 1140 "
		::= { iqhip00CmdEntry 1140 }


	iqhip00LoggingInp1ClippingEmbCh7Level OBJECT-TYPE
		SYNTAX		RollCallString
		MAX-ACCESS		read-only
		STATUS			current
		DESCRIPTION
				"TYPE: - Display
				 PAGE: - Logging- Inp 1 Clipping
					Emb Ch 7 Level=  cmdID= 2140  format=   "
		::= { iqhip00CmdEntry 2140 }


	iqhip00LoggingInp1ClippingEmbCh8LevelEnable OBJECT-TYPE
		SYNTAX		INTEGER { disable(0), enable(1) }
		MAX-ACCESS		read-write
		STATUS			current
		DESCRIPTION
				"TYPE: - Checkbox
				 PAGE: - Logging- Inp 1 Clipping
					Emb Ch 8 Level  cmdID= 1141 "
		::= { iqhip00CmdEntry 1141 }


	iqhip00LoggingInp1ClippingEmbCh8Level OBJECT-TYPE
		SYNTAX		RollCallString
		MAX-ACCESS		read-only
		STATUS			current
		DESCRIPTION
				"TYPE: - Display
				 PAGE: - Logging- Inp 1 Clipping
					Emb Ch 8 Level=  cmdID= 2141  format=   "
		::= { iqhip00CmdEntry 2141 }


	iqhip00LoggingInp1ClippingEmbCh9LevelEnable OBJECT-TYPE
		SYNTAX		INTEGER { disable(0), enable(1) }
		MAX-ACCESS		read-write
		STATUS			current
		DESCRIPTION
				"TYPE: - Checkbox
				 PAGE: - Logging- Inp 1 Clipping
					Emb Ch 9 Level  cmdID= 1142 "
		::= { iqhip00CmdEntry 1142 }


	iqhip00LoggingInp1ClippingEmbCh9Level OBJECT-TYPE
		SYNTAX		RollCallString
		MAX-ACCESS		read-only
		STATUS			current
		DESCRIPTION
				"TYPE: - Display
				 PAGE: - Logging- Inp 1 Clipping
					Emb Ch 9 Level=  cmdID= 2142  format=   "
		::= { iqhip00CmdEntry 2142 }


	iqhip00LoggingInp1ClippingEmbCh10LevelEnable OBJECT-TYPE
		SYNTAX		INTEGER { disable(0), enable(1) }
		MAX-ACCESS		read-write
		STATUS			current
		DESCRIPTION
				"TYPE: - Checkbox
				 PAGE: - Logging- Inp 1 Clipping
					Emb Ch 10 Level  cmdID= 1143 "
		::= { iqhip00CmdEntry 1143 }


	iqhip00LoggingInp1ClippingEmbCh10Level OBJECT-TYPE
		SYNTAX		RollCallString
		MAX-ACCESS		read-only
		STATUS			current
		DESCRIPTION
				"TYPE: - Display
				 PAGE: - Logging- Inp 1 Clipping
					Emb Ch 10 Level=  cmdID= 2143  format=   "
		::= { iqhip00CmdEntry 2143 }


	iqhip00LoggingInp1ClippingEmbCh11LevelEnable OBJECT-TYPE
		SYNTAX		INTEGER { disable(0), enable(1) }
		MAX-ACCESS		read-write
		STATUS			current
		DESCRIPTION
				"TYPE: - Checkbox
				 PAGE: - Logging- Inp 1 Clipping
					Emb Ch 11 Level  cmdID= 1144 "
		::= { iqhip00CmdEntry 1144 }


	iqhip00LoggingInp1ClippingEmbCh11Level OBJECT-TYPE
		SYNTAX		RollCallString
		MAX-ACCESS		read-only
		STATUS			current
		DESCRIPTION
				"TYPE: - Display
				 PAGE: - Logging- Inp 1 Clipping
					Emb Ch 11 Level=  cmdID= 2144  format=   "
		::= { iqhip00CmdEntry 2144 }


	iqhip00LoggingInp1ClippingEmbCh12LevelEnable OBJECT-TYPE
		SYNTAX		INTEGER { disable(0), enable(1) }
		MAX-ACCESS		read-write
		STATUS			current
		DESCRIPTION
				"TYPE: - Checkbox
				 PAGE: - Logging- Inp 1 Clipping
					Emb Ch 12 Level  cmdID= 1145 "
		::= { iqhip00CmdEntry 1145 }


	iqhip00LoggingInp1ClippingEmbCh12Level OBJECT-TYPE
		SYNTAX		RollCallString
		MAX-ACCESS		read-only
		STATUS			current
		DESCRIPTION
				"TYPE: - Display
				 PAGE: - Logging- Inp 1 Clipping
					Emb Ch 12 Level=  cmdID= 2145  format=   "
		::= { iqhip00CmdEntry 2145 }


	iqhip00LoggingInp1ClippingEmbCh13LevelEnable OBJECT-TYPE
		SYNTAX		INTEGER { disable(0), enable(1) }
		MAX-ACCESS		read-write
		STATUS			current
		DESCRIPTION
				"TYPE: - Checkbox
				 PAGE: - Logging- Inp 1 Clipping
					Emb Ch 13 Level  cmdID= 1146 "
		::= { iqhip00CmdEntry 1146 }


	iqhip00LoggingInp1ClippingEmbCh13Level OBJECT-TYPE
		SYNTAX		RollCallString
		MAX-ACCESS		read-only
		STATUS			current
		DESCRIPTION
				"TYPE: - Display
				 PAGE: - Logging- Inp 1 Clipping
					Emb Ch 13 Level=  cmdID= 2146  format=   "
		::= { iqhip00CmdEntry 2146 }


	iqhip00LoggingInp1ClippingEmbCh14LevelEnable OBJECT-TYPE
		SYNTAX		INTEGER { disable(0), enable(1) }
		MAX-ACCESS		read-write
		STATUS			current
		DESCRIPTION
				"TYPE: - Checkbox
				 PAGE: - Logging- Inp 1 Clipping
					Emb Ch 14 Level  cmdID= 1147 "
		::= { iqhip00CmdEntry 1147 }


	iqhip00LoggingInp1ClippingEmbCh14Level OBJECT-TYPE
		SYNTAX		RollCallString
		MAX-ACCESS		read-only
		STATUS			current
		DESCRIPTION
				"TYPE: - Display
				 PAGE: - Logging- Inp 1 Clipping
					Emb Ch 14 Level=  cmdID= 2147  format=   "
		::= { iqhip00CmdEntry 2147 }


	iqhip00LoggingInp1ClippingEmbCh15LevelEnable OBJECT-TYPE
		SYNTAX		INTEGER { disable(0), enable(1) }
		MAX-ACCESS		read-write
		STATUS			current
		DESCRIPTION
				"TYPE: - Checkbox
				 PAGE: - Logging- Inp 1 Clipping
					Emb Ch 15 Level  cmdID= 1148 "
		::= { iqhip00CmdEntry 1148 }


	iqhip00LoggingInp1ClippingEmbCh15Level OBJECT-TYPE
		SYNTAX		RollCallString
		MAX-ACCESS		read-only
		STATUS			current
		DESCRIPTION
				"TYPE: - Display
				 PAGE: - Logging- Inp 1 Clipping
					Emb Ch 15 Level=  cmdID= 2148  format=   "
		::= { iqhip00CmdEntry 2148 }


	iqhip00LoggingInp1ClippingEmbCh16LevelEnable OBJECT-TYPE
		SYNTAX		INTEGER { disable(0), enable(1) }
		MAX-ACCESS		read-write
		STATUS			current
		DESCRIPTION
				"TYPE: - Checkbox
				 PAGE: - Logging- Inp 1 Clipping
					Emb Ch 16 Level  cmdID= 1149 "
		::= { iqhip00CmdEntry 1149 }


	iqhip00LoggingInp1ClippingEmbCh16Level OBJECT-TYPE
		SYNTAX		RollCallString
		MAX-ACCESS		read-only
		STATUS			current
		DESCRIPTION
				"TYPE: - Display
				 PAGE: - Logging- Inp 1 Clipping
					Emb Ch 16 Level=  cmdID= 2149  format=   "
		::= { iqhip00CmdEntry 2149 }


	iqhip00LoggingInp1LikenessDetector1ChansEnable OBJECT-TYPE
		SYNTAX		INTEGER { disable(0), enable(1) }
		MAX-ACCESS		read-write
		STATUS			current
		DESCRIPTION
				"TYPE: - Checkbox
				 PAGE: - Logging- Inp 1 Likeness
					Detector 1 Chans  cmdID= 1101 "
		::= { iqhip00CmdEntry 1101 }


	iqhip00LoggingInp1LikenessDetector1Chans OBJECT-TYPE
		SYNTAX		RollCallString
		MAX-ACCESS		read-only
		STATUS			current
		DESCRIPTION
				"TYPE: - Display
				 PAGE: - Logging- Inp 1 Likeness
					Detector 1 Chans=  cmdID= 2101  format=   "
		::= { iqhip00CmdEntry 2101 }


	iqhip00LoggingInp1LikenessDetector1StateEnable OBJECT-TYPE
		SYNTAX		INTEGER { disable(0), enable(1) }
		MAX-ACCESS		read-write
		STATUS			current
		DESCRIPTION
				"TYPE: - Checkbox
				 PAGE: - Logging- Inp 1 Likeness
					Detector 1 State  cmdID= 1105 "
		::= { iqhip00CmdEntry 1105 }


	iqhip00LoggingInp1LikenessDetector1State OBJECT-TYPE
		SYNTAX		RollCallString
		MAX-ACCESS		read-only
		STATUS			current
		DESCRIPTION
				"TYPE: - Display
				 PAGE: - Logging- Inp 1 Likeness
					Detector 1 State=  cmdID= 2105  format=   "
		::= { iqhip00CmdEntry 2105 }


	iqhip00LoggingInp1LikenessDetector2ChansEnable OBJECT-TYPE
		SYNTAX		INTEGER { disable(0), enable(1) }
		MAX-ACCESS		read-write
		STATUS			current
		DESCRIPTION
				"TYPE: - Checkbox
				 PAGE: - Logging- Inp 1 Likeness
					Detector 2 Chans  cmdID= 1102 "
		::= { iqhip00CmdEntry 1102 }


	iqhip00LoggingInp1LikenessDetector2Chans OBJECT-TYPE
		SYNTAX		RollCallString
		MAX-ACCESS		read-only
		STATUS			current
		DESCRIPTION
				"TYPE: - Display
				 PAGE: - Logging- Inp 1 Likeness
					Detector 2 Chans=  cmdID= 2102  format=   "
		::= { iqhip00CmdEntry 2102 }


	iqhip00LoggingInp1LikenessDetector2StateEnable OBJECT-TYPE
		SYNTAX		INTEGER { disable(0), enable(1) }
		MAX-ACCESS		read-write
		STATUS			current
		DESCRIPTION
				"TYPE: - Checkbox
				 PAGE: - Logging- Inp 1 Likeness
					Detector 2 State  cmdID= 1106 "
		::= { iqhip00CmdEntry 1106 }


	iqhip00LoggingInp1LikenessDetector2State OBJECT-TYPE
		SYNTAX		RollCallString
		MAX-ACCESS		read-only
		STATUS			current
		DESCRIPTION
				"TYPE: - Display
				 PAGE: - Logging- Inp 1 Likeness
					Detector 2 State=  cmdID= 2106  format=   "
		::= { iqhip00CmdEntry 2106 }


	iqhip00LoggingInp1LikenessDetector3ChansEnable OBJECT-TYPE
		SYNTAX		INTEGER { disable(0), enable(1) }
		MAX-ACCESS		read-write
		STATUS			current
		DESCRIPTION
				"TYPE: - Checkbox
				 PAGE: - Logging- Inp 1 Likeness
					Detector 3 Chans  cmdID= 1103 "
		::= { iqhip00CmdEntry 1103 }


	iqhip00LoggingInp1LikenessDetector3Chans OBJECT-TYPE
		SYNTAX		RollCallString
		MAX-ACCESS		read-only
		STATUS			current
		DESCRIPTION
				"TYPE: - Display
				 PAGE: - Logging- Inp 1 Likeness
					Detector 3 Chans=  cmdID= 2103  format=   "
		::= { iqhip00CmdEntry 2103 }


	iqhip00LoggingInp1LikenessDetector3StateEnable OBJECT-TYPE
		SYNTAX		INTEGER { disable(0), enable(1) }
		MAX-ACCESS		read-write
		STATUS			current
		DESCRIPTION
				"TYPE: - Checkbox
				 PAGE: - Logging- Inp 1 Likeness
					Detector 3 State  cmdID= 1107 "
		::= { iqhip00CmdEntry 1107 }


	iqhip00LoggingInp1LikenessDetector3State OBJECT-TYPE
		SYNTAX		RollCallString
		MAX-ACCESS		read-only
		STATUS			current
		DESCRIPTION
				"TYPE: - Display
				 PAGE: - Logging- Inp 1 Likeness
					Detector 3 State=  cmdID= 2107  format=   "
		::= { iqhip00CmdEntry 2107 }


	iqhip00LoggingInp1LikenessDetector4ChansEnable OBJECT-TYPE
		SYNTAX		INTEGER { disable(0), enable(1) }
		MAX-ACCESS		read-write
		STATUS			current
		DESCRIPTION
				"TYPE: - Checkbox
				 PAGE: - Logging- Inp 1 Likeness
					Detector 4 Chans  cmdID= 1104 "
		::= { iqhip00CmdEntry 1104 }


	iqhip00LoggingInp1LikenessDetector4Chans OBJECT-TYPE
		SYNTAX		RollCallString
		MAX-ACCESS		read-only
		STATUS			current
		DESCRIPTION
				"TYPE: - Display
				 PAGE: - Logging- Inp 1 Likeness
					Detector 4 Chans=  cmdID= 2104  format=   "
		::= { iqhip00CmdEntry 2104 }


	iqhip00LoggingInp1LikenessDetector4StateEnable OBJECT-TYPE
		SYNTAX		INTEGER { disable(0), enable(1) }
		MAX-ACCESS		read-write
		STATUS			current
		DESCRIPTION
				"TYPE: - Checkbox
				 PAGE: - Logging- Inp 1 Likeness
					Detector 4 State  cmdID= 1108 "
		::= { iqhip00CmdEntry 1108 }


	iqhip00LoggingInp1LikenessDetector4State OBJECT-TYPE
		SYNTAX		RollCallString
		MAX-ACCESS		read-only
		STATUS			current
		DESCRIPTION
				"TYPE: - Display
				 PAGE: - Logging- Inp 1 Likeness
					Detector 4 State=  cmdID= 2108  format=   "
		::= { iqhip00CmdEntry 2108 }


	iqhip00LoggingOut1UMIDUMIDStateEnable OBJECT-TYPE
		SYNTAX		INTEGER { disable(0), enable(1) }
		MAX-ACCESS		read-write
		STATUS			current
		DESCRIPTION
				"TYPE: - Checkbox
				 PAGE: - Logging
					UMID State  cmdID= 1121 "
		::= { iqhip00CmdEntry 1121 }


	iqhip00LoggingOut1UMIDUMIDState OBJECT-TYPE
		SYNTAX		RollCallString
		MAX-ACCESS		read-only
		STATUS			current
		DESCRIPTION
				"TYPE: - Display
				 PAGE: - Logging
					UMID State=  cmdID= 2121  format=   "
		::= { iqhip00CmdEntry 2121 }


	iqhip00LoggingOut1UMIDOutputUMIDEnable OBJECT-TYPE
		SYNTAX		INTEGER { disable(0), enable(1) }
		MAX-ACCESS		read-write
		STATUS			current
		DESCRIPTION
				"TYPE: - Checkbox
				 PAGE: - Logging
					Output UMID  cmdID= 1122 "
		::= { iqhip00CmdEntry 1122 }


	iqhip00LoggingOut1UMIDOutputUMID1_8 OBJECT-TYPE
		SYNTAX		RollCallString
		MAX-ACCESS		read-only
		STATUS			current
		DESCRIPTION
				"TYPE: - Display
				 PAGE: - Logging
					Output UMID 1-8=  cmdID= 2122  format=   "
		::= { iqhip00CmdEntry 2122 }


	iqhip00LoggingOut1UMIDOutputUMID9_16 OBJECT-TYPE
		SYNTAX		RollCallString
		MAX-ACCESS		read-only
		STATUS			current
		DESCRIPTION
				"TYPE: - Display
				 PAGE: - Logging
					Output UMID 9-16=  cmdID= 4101  format=   "
		::= { iqhip00CmdEntry 4101 }


	iqhip00LoggingOut1UMIDOutputUMID17_24 OBJECT-TYPE
		SYNTAX		RollCallString
		MAX-ACCESS		read-only
		STATUS			current
		DESCRIPTION
				"TYPE: - Display
				 PAGE: - Logging
					Output UMID 17-24=  cmdID= 4102  format=   "
		::= { iqhip00CmdEntry 4102 }


	iqhip00LoggingOut1UMIDOutputUMID25_32 OBJECT-TYPE
		SYNTAX		RollCallString
		MAX-ACCESS		read-only
		STATUS			current
		DESCRIPTION
				"TYPE: - Display
				 PAGE: - Logging
					Output UMID 25-32=  cmdID= 4103  format=   "
		::= { iqhip00CmdEntry 4103 }


	iqhip00LoggingInp1UMIDUMIDStateEnable OBJECT-TYPE
		SYNTAX		INTEGER { disable(0), enable(1) }
		MAX-ACCESS		read-write
		STATUS			current
		DESCRIPTION
				"TYPE: - Checkbox
				 PAGE: - Logging
					UMID State  cmdID= 1013 "
		::= { iqhip00CmdEntry 1013 }


	iqhip00LoggingInp1UMIDUMIDState OBJECT-TYPE
		SYNTAX		RollCallString
		MAX-ACCESS		read-only
		STATUS			current
		DESCRIPTION
				"TYPE: - Display
				 PAGE: - Logging
					UMID State=  cmdID= 2013  format=   "
		::= { iqhip00CmdEntry 2013 }


	iqhip00LoggingInp1UMIDUMIDCurrentEnable OBJECT-TYPE
		SYNTAX		INTEGER { disable(0), enable(1) }
		MAX-ACCESS		read-write
		STATUS			current
		DESCRIPTION
				"TYPE: - Checkbox
				 PAGE: - Logging
					UMID Current 1-8  cmdID= 1014 "
		::= { iqhip00CmdEntry 1014 }


	iqhip00LoggingInp1UMIDUMIDCurrent1_8 OBJECT-TYPE
		SYNTAX		RollCallString
		MAX-ACCESS		read-only
		STATUS			current
		DESCRIPTION
				"TYPE: - Display
				 PAGE: - Logging
					UMID Current 1-8=  cmdID= 2014  format=   "
		::= { iqhip00CmdEntry 2014 }


	iqhip00LoggingInp1UMIDUMIDCurrent9_16 OBJECT-TYPE
		SYNTAX		RollCallString
		MAX-ACCESS		read-only
		STATUS			current
		DESCRIPTION
				"TYPE: - Display
				 PAGE: - Logging
					UMID Current 9-16=  cmdID= 4104  format=   "
		::= { iqhip00CmdEntry 4104 }


	iqhip00LoggingInp1UMIDUMIDCurrent17_24 OBJECT-TYPE
		SYNTAX		RollCallString
		MAX-ACCESS		read-only
		STATUS			current
		DESCRIPTION
				"TYPE: - Display
				 PAGE: - Logging
					UMID Current 17-24=  cmdID= 4105  format=   "
		::= { iqhip00CmdEntry 4105 }


	iqhip00LoggingInp1UMIDUMIDCurrent25_32 OBJECT-TYPE
		SYNTAX		RollCallString
		MAX-ACCESS		read-only
		STATUS			current
		DESCRIPTION
				"TYPE: - Display
				 PAGE: - Logging
					UMID Current 25-32=  cmdID= 4106  format=   "
		::= { iqhip00CmdEntry 4106 }


	iqhip00LoggingInp1UMIDUMIDPreviousEnable OBJECT-TYPE
		SYNTAX		INTEGER { disable(0), enable(1) }
		MAX-ACCESS		read-write
		STATUS			current
		DESCRIPTION
				"TYPE: - Checkbox
				 PAGE: - Logging
					UMID Previous 1-8  cmdID= 1015 "
		::= { iqhip00CmdEntry 1015 }


	iqhip00LoggingInp1UMIDUMIDPrev1_8 OBJECT-TYPE
		SYNTAX		RollCallString
		MAX-ACCESS		read-only
		STATUS			current
		DESCRIPTION
				"TYPE: - Display
				 PAGE: - Logging
					UMID Prev 1-8=  cmdID= 2015  format=   "
		::= { iqhip00CmdEntry 2015 }


	iqhip00LoggingInp1UMIDUMIDPrev9_16 OBJECT-TYPE
		SYNTAX		RollCallString
		MAX-ACCESS		read-only
		STATUS			current
		DESCRIPTION
				"TYPE: - Display
				 PAGE: - Logging
					UMID Prev 9-16=  cmdID= 4107  format=   "
		::= { iqhip00CmdEntry 4107 }


	iqhip00LoggingInp1UMIDUMIDPrev17_24 OBJECT-TYPE
		SYNTAX		RollCallString
		MAX-ACCESS		read-only
		STATUS			current
		DESCRIPTION
				"TYPE: - Display
				 PAGE: - Logging
					UMID Prev 17-24=  cmdID= 4108  format=   "
		::= { iqhip00CmdEntry 4108 }


	iqhip00LoggingInp1UMIDUMIDPrev25_32 OBJECT-TYPE
		SYNTAX		RollCallString
		MAX-ACCESS		read-only
		STATUS			current
		DESCRIPTION
				"TYPE: - Display
				 PAGE: - Logging
					UMID Prev 25-32=  cmdID= 4109  format=   "
		::= { iqhip00CmdEntry 4109 }


	iqhip00LoggingInp1UMIDUMIDPreviousCountEnable OBJECT-TYPE
		SYNTAX		INTEGER { disable(0), enable(1) }
		MAX-ACCESS		read-write
		STATUS			current
		DESCRIPTION
				"TYPE: - Checkbox
				 PAGE: - Logging
					UMID Previous Count  cmdID= 1016 "
		::= { iqhip00CmdEntry 1016 }


	iqhip00LoggingInp1UMIDUMIDPrevCount OBJECT-TYPE
		SYNTAX		RollCallString
		MAX-ACCESS		read-only
		STATUS			current
		DESCRIPTION
				"TYPE: - Display
				 PAGE: - Logging
					UMID Prev Count=  cmdID= 2016  format=   "
		::= { iqhip00CmdEntry 2016 }


	iqhip00LoggingOut1PIDPIDStateEnable OBJECT-TYPE
		SYNTAX		INTEGER { disable(0), enable(1) }
		MAX-ACCESS		read-write
		STATUS			current
		DESCRIPTION
				"TYPE: - Checkbox
				 PAGE: - Logging
					PID State  cmdID= 1123 "
		::= { iqhip00CmdEntry 1123 }


	iqhip00LoggingOut1PIDPIDState OBJECT-TYPE
		SYNTAX		RollCallString
		MAX-ACCESS		read-only
		STATUS			current
		DESCRIPTION
				"TYPE: - Display
				 PAGE: - Logging
					PID State=  cmdID= 2123  format=   "
		::= { iqhip00CmdEntry 2123 }


	iqhip00LoggingOut1PIDPIDHouseIDEnable OBJECT-TYPE
		SYNTAX		INTEGER { disable(0), enable(1) }
		MAX-ACCESS		read-write
		STATUS			current
		DESCRIPTION
				"TYPE: - Checkbox
				 PAGE: - Logging
					PID House ID  cmdID= 1124 "
		::= { iqhip00CmdEntry 1124 }


	iqhip00LoggingOut1PIDPIDHouseID OBJECT-TYPE
		SYNTAX		RollCallString
		MAX-ACCESS		read-only
		STATUS			current
		DESCRIPTION
				"TYPE: - Display
				 PAGE: - Logging
					PID House ID=  cmdID= 2124  format=   "
		::= { iqhip00CmdEntry 2124 }


	iqhip00LoggingOut1PIDPIDTitleEnable OBJECT-TYPE
		SYNTAX		INTEGER { disable(0), enable(1) }
		MAX-ACCESS		read-write
		STATUS			current
		DESCRIPTION
				"TYPE: - Checkbox
				 PAGE: - Logging
					PID Title  cmdID= 1125 "
		::= { iqhip00CmdEntry 1125 }


	iqhip00LoggingOut1PIDPIDTitle OBJECT-TYPE
		SYNTAX		RollCallString
		MAX-ACCESS		read-only
		STATUS			current
		DESCRIPTION
				"TYPE: - Display
				 PAGE: - Logging
					PID Title=  cmdID= 2125  format=   "
		::= { iqhip00CmdEntry 2125 }


	iqhip00LoggingOut1PIDSegmentNumberEnable OBJECT-TYPE
		SYNTAX		INTEGER { disable(0), enable(1) }
		MAX-ACCESS		read-write
		STATUS			current
		DESCRIPTION
				"TYPE: - Checkbox
				 PAGE: - Logging
					Segment Number  cmdID= 1126 "
		::= { iqhip00CmdEntry 1126 }


	iqhip00LoggingOut1PIDSegmentNumber OBJECT-TYPE
		SYNTAX		RollCallString
		MAX-ACCESS		read-only
		STATUS			current
		DESCRIPTION
				"TYPE: - Display
				 PAGE: - Logging
					Segment Number=  cmdID= 2126  format=   "
		::= { iqhip00CmdEntry 2126 }


	iqhip00LoggingOut1PIDDurationEnable OBJECT-TYPE
		SYNTAX		INTEGER { disable(0), enable(1) }
		MAX-ACCESS		read-write
		STATUS			current
		DESCRIPTION
				"TYPE: - Checkbox
				 PAGE: - Logging
					Duration  cmdID= 1127 "
		::= { iqhip00CmdEntry 1127 }


	iqhip00LoggingOut1PIDDuration OBJECT-TYPE
		SYNTAX		RollCallString
		MAX-ACCESS		read-only
		STATUS			current
		DESCRIPTION
				"TYPE: - Display
				 PAGE: - Logging
					Duration=  cmdID= 2127  format=   "
		::= { iqhip00CmdEntry 2127 }


	iqhip00LoggingOut1PIDFrameRateEnable OBJECT-TYPE
		SYNTAX		INTEGER { disable(0), enable(1) }
		MAX-ACCESS		read-write
		STATUS			current
		DESCRIPTION
				"TYPE: - Checkbox
				 PAGE: - Logging
					Frame Rate  cmdID= 1128 "
		::= { iqhip00CmdEntry 1128 }


	iqhip00LoggingOut1PIDFrameRate OBJECT-TYPE
		SYNTAX		RollCallString
		MAX-ACCESS		read-only
		STATUS			current
		DESCRIPTION
				"TYPE: - Display
				 PAGE: - Logging
					Frame Rate=  cmdID= 2128  format=   "
		::= { iqhip00CmdEntry 2128 }


	iqhip00LoggingInp1PIDPIDStateEnable OBJECT-TYPE
		SYNTAX		INTEGER { disable(0), enable(1) }
		MAX-ACCESS		read-write
		STATUS			current
		DESCRIPTION
				"TYPE: - Checkbox
				 PAGE: - Logging
					PID State  cmdID= 1109 "
		::= { iqhip00CmdEntry 1109 }


	iqhip00LoggingInp1PIDPIDState OBJECT-TYPE
		SYNTAX		RollCallString
		MAX-ACCESS		read-only
		STATUS			current
		DESCRIPTION
				"TYPE: - Display
				 PAGE: - Logging
					PID State=  cmdID= 2109  format=   "
		::= { iqhip00CmdEntry 2109 }


	iqhip00LoggingInp1PIDPIDHouseIDEnable OBJECT-TYPE
		SYNTAX		INTEGER { disable(0), enable(1) }
		MAX-ACCESS		read-write
		STATUS			current
		DESCRIPTION
				"TYPE: - Checkbox
				 PAGE: - Logging
					PID House ID  cmdID= 1110 "
		::= { iqhip00CmdEntry 1110 }


	iqhip00LoggingInp1PIDPIDHouseID OBJECT-TYPE
		SYNTAX		RollCallString
		MAX-ACCESS		read-only
		STATUS			current
		DESCRIPTION
				"TYPE: - Display
				 PAGE: - Logging
					PID House ID=  cmdID= 2110  format=   "
		::= { iqhip00CmdEntry 2110 }


	iqhip00LoggingInp1PIDPIDTitleEnable OBJECT-TYPE
		SYNTAX		INTEGER { disable(0), enable(1) }
		MAX-ACCESS		read-write
		STATUS			current
		DESCRIPTION
				"TYPE: - Checkbox
				 PAGE: - Logging
					PID Title  cmdID= 1111 "
		::= { iqhip00CmdEntry 1111 }


	iqhip00LoggingInp1PIDPIDTitle OBJECT-TYPE
		SYNTAX		RollCallString
		MAX-ACCESS		read-only
		STATUS			current
		DESCRIPTION
				"TYPE: - Display
				 PAGE: - Logging
					PID Title=  cmdID= 2111  format=   "
		::= { iqhip00CmdEntry 2111 }


	iqhip00LoggingInp1PIDSegmentNumberEnable OBJECT-TYPE
		SYNTAX		INTEGER { disable(0), enable(1) }
		MAX-ACCESS		read-write
		STATUS			current
		DESCRIPTION
				"TYPE: - Checkbox
				 PAGE: - Logging
					Segment Number  cmdID= 1112 "
		::= { iqhip00CmdEntry 1112 }


	iqhip00LoggingInp1PIDSegmentNumber OBJECT-TYPE
		SYNTAX		RollCallString
		MAX-ACCESS		read-only
		STATUS			current
		DESCRIPTION
				"TYPE: - Display
				 PAGE: - Logging
					Segment Number=  cmdID= 2112  format=   "
		::= { iqhip00CmdEntry 2112 }


	iqhip00LoggingInp1PIDDurationEnable OBJECT-TYPE
		SYNTAX		INTEGER { disable(0), enable(1) }
		MAX-ACCESS		read-write
		STATUS			current
		DESCRIPTION
				"TYPE: - Checkbox
				 PAGE: - Logging
					Duration  cmdID= 1113 "
		::= { iqhip00CmdEntry 1113 }


	iqhip00LoggingInp1PIDDuration OBJECT-TYPE
		SYNTAX		RollCallString
		MAX-ACCESS		read-only
		STATUS			current
		DESCRIPTION
				"TYPE: - Display
				 PAGE: - Logging
					Duration=  cmdID= 2113  format=   "
		::= { iqhip00CmdEntry 2113 }


	iqhip00LoggingInp1PIDFrameRateEnable OBJECT-TYPE
		SYNTAX		INTEGER { disable(0), enable(1) }
		MAX-ACCESS		read-write
		STATUS			current
		DESCRIPTION
				"TYPE: - Checkbox
				 PAGE: - Logging
					Frame Rate  cmdID= 1114 "
		::= { iqhip00CmdEntry 1114 }


	iqhip00LoggingInp1PIDFrameRate OBJECT-TYPE
		SYNTAX		RollCallString
		MAX-ACCESS		read-only
		STATUS			current
		DESCRIPTION
				"TYPE: - Display
				 PAGE: - Logging
					Frame Rate=  cmdID= 2114  format=   "
		::= { iqhip00CmdEntry 2114 }


	iqhip00LoggingInp1PIDPreviousHouseIDEnable OBJECT-TYPE
		SYNTAX		INTEGER { disable(0), enable(1) }
		MAX-ACCESS		read-write
		STATUS			current
		DESCRIPTION
				"TYPE: - Checkbox
				 PAGE: - Logging
					Previous House ID  cmdID= 1115 "
		::= { iqhip00CmdEntry 1115 }


	iqhip00LoggingInp1PIDPreviousHouseID OBJECT-TYPE
		SYNTAX		RollCallString
		MAX-ACCESS		read-only
		STATUS			current
		DESCRIPTION
				"TYPE: - Display
				 PAGE: - Logging
					Previous House ID=  cmdID= 2115  format=   "
		::= { iqhip00CmdEntry 2115 }


	iqhip00LoggingInp1PIDPreviousTitleEnable OBJECT-TYPE
		SYNTAX		INTEGER { disable(0), enable(1) }
		MAX-ACCESS		read-write
		STATUS			current
		DESCRIPTION
				"TYPE: - Checkbox
				 PAGE: - Logging
					Previous Title  cmdID= 1116 "
		::= { iqhip00CmdEntry 1116 }


	iqhip00LoggingInp1PIDPreviousTitle OBJECT-TYPE
		SYNTAX		RollCallString
		MAX-ACCESS		read-only
		STATUS			current
		DESCRIPTION
				"TYPE: - Display
				 PAGE: - Logging
					Previous Title=  cmdID= 2116  format=   "
		::= { iqhip00CmdEntry 2116 }


	iqhip00LoggingInp1PIDPreviousSegNumEnable OBJECT-TYPE
		SYNTAX		INTEGER { disable(0), enable(1) }
		MAX-ACCESS		read-write
		STATUS			current
		DESCRIPTION
				"TYPE: - Checkbox
				 PAGE: - Logging
					Previous Seg Num  cmdID= 1117 "
		::= { iqhip00CmdEntry 1117 }


	iqhip00LoggingInp1PIDPreviousSegNum OBJECT-TYPE
		SYNTAX		RollCallString
		MAX-ACCESS		read-only
		STATUS			current
		DESCRIPTION
				"TYPE: - Display
				 PAGE: - Logging
					Previous Seg Num=  cmdID= 2117  format=   "
		::= { iqhip00CmdEntry 2117 }


	iqhip00LoggingInp1PIDPreviousDurationEnable OBJECT-TYPE
		SYNTAX		INTEGER { disable(0), enable(1) }
		MAX-ACCESS		read-write
		STATUS			current
		DESCRIPTION
				"TYPE: - Checkbox
				 PAGE: - Logging
					Previous Duration  cmdID= 1118 "
		::= { iqhip00CmdEntry 1118 }


	iqhip00LoggingInp1PIDPreviousDuration OBJECT-TYPE
		SYNTAX		RollCallString
		MAX-ACCESS		read-only
		STATUS			current
		DESCRIPTION
				"TYPE: - Display
				 PAGE: - Logging
					Previous Duration=  cmdID= 2118  format=   "
		::= { iqhip00CmdEntry 2118 }


	iqhip00LoggingInp1PIDPreviousFrameRateEnable OBJECT-TYPE
		SYNTAX		INTEGER { disable(0), enable(1) }
		MAX-ACCESS		read-write
		STATUS			current
		DESCRIPTION
				"TYPE: - Checkbox
				 PAGE: - Logging
					Previous FrameRate  cmdID= 1119 "
		::= { iqhip00CmdEntry 1119 }


	iqhip00LoggingInp1PIDPreviousFrameRate OBJECT-TYPE
		SYNTAX		RollCallString
		MAX-ACCESS		read-only
		STATUS			current
		DESCRIPTION
				"TYPE: - Display
				 PAGE: - Logging
					Previous FrameRate=  cmdID= 2119  format=   "
		::= { iqhip00CmdEntry 2119 }


	iqhip00LoggingInp1PIDPreviousCountEnable OBJECT-TYPE
		SYNTAX		INTEGER { disable(0), enable(1) }
		MAX-ACCESS		read-write
		STATUS			current
		DESCRIPTION
				"TYPE: - Checkbox
				 PAGE: - Logging
					Previous Count  cmdID= 1120 "
		::= { iqhip00CmdEntry 1120 }


	iqhip00LoggingInp1PIDPreviousCount OBJECT-TYPE
		SYNTAX		RollCallString
		MAX-ACCESS		read-only
		STATUS			current
		DESCRIPTION
				"TYPE: - Display
				 PAGE: - Logging
					Previous Count=  cmdID= 2120  format=   "
		::= { iqhip00CmdEntry 2120 }


	iqhip00RollcallRollTrackDisableAll OBJECT-TYPE
		SYNTAX		INTEGER { disable(0), enable(1) }
		MAX-ACCESS		read-write
		STATUS			current
		DESCRIPTION
				"TYPE: - Checkbox
				 PAGE: - Rollcall
					Disable All  cmdID= 1413 "
		::= { iqhip00CmdEntry 1413 }


	iqhip00RollcallRollTrackIndex OBJECT-TYPE
		SYNTAX		INTEGER
		MAX-ACCESS		read-write
		STATUS			current
		DESCRIPTION
				"TYPE: - BarGraph
				 PAGE: - Rollcall
					Index  cmdID= 1415  min= 1  max= 16   step= 1  format= %0.0f  div_scale= 1
					Min = 1  Max = 16  Step = 1 "
		::= { iqhip00CmdEntry 1415 }


	iqhip00RollcallRollTrackSource OBJECT-TYPE
		SYNTAX		INTEGER {
							val_Unused(-1),
							val_Input_OK(0),
							val_Input_None(1),
							val_IP1_1125_1035_30I(2),
							val_IP1_1125_1035_29I(3),
							val_IP1_1125_1080_30I(4),
							val_IP1_1125_1080_29I(5),
							val_IP1_1125_1080_25I(6),
							val_IP1_1125_1080_30P(7),
							val_IP1_1125_1080_29P(8),
							val_IP1_1125_1080_25P(9),
							val_IP1_1125_1080_24P(10),
							val_IP1_1125_1080_23P(11),
							val_IP1_750_720_60P(12),
							val_IP1_750_720_59P(13),
							val_IP1_525_480_29I(14),
							val_IP1_625_576_25I(15),
							val_IP1_1125_1080_24sF(16),
							val_IP1_1125_1080_23sF(17),
							val_IP1_750_720_50P(18),
							val_IP1_750_720_30P(19),
							val_IP1_750_720_29P(20),
							val_IP1_750_720_25P(21),
							val_Hyperion_OK(22),
							val_Hyperion_WARN(23),
							val_Hyperion_FAIL(24),
							val_Hyperion_N_A(25)
							}
		MAX-ACCESS		read-write
		STATUS			current
		DESCRIPTION
				"TYPE: - RadiobuttonList
				 PAGE: - Rollcall
					Source  cmdID= 1416
					Unused  value= -1
					Input OK  value= 0
					Input None  value= 1
					IP1 1125(1035)/30I  value= 2
					IP1 1125(1035)/29I  value= 3
					IP1 1125(1080)/30I  value= 4
					IP1 1125(1080)/29I  value= 5
					IP1 1125(1080)/25I  value= 6
					IP1 1125(1080)/30P  value= 7
					IP1 1125(1080)/29P  value= 8
					IP1 1125(1080)/25P  value= 9
					IP1 1125(1080)/24P  value= 10
					IP1 1125(1080)/23P  value= 11
					IP1 750(720)/60P  value= 12
					IP1 750(720)/59P  value= 13
					IP1 525(480)/29I  value= 14
					IP1 625(576)/25I  value= 15
					IP1 1125(1080)/24sF  value= 16
					IP1 1125(1080)/23sF  value= 17
					IP1 750(720)/50P  value= 18
					IP1 750(720)/30P  value= 19
					IP1 750(720)/29P  value= 20
					IP1 750(720)/25P  value= 21
					Hyperion OK  value= 22
					Hyperion WARN  value= 23
					Hyperion FAIL  value= 24
					Hyperion N/A  value= 25  "
		::= { iqhip00CmdEntry 1416 }


	iqhip00RollcallRollTrackAddress OBJECT-TYPE
		SYNTAX		RollCallString
		MAX-ACCESS		read-write
		STATUS			current
		DESCRIPTION
				"TYPE: - Editstring
				 PAGE: - Rollcall
					Address  cmdID= 1417  "
		::= { iqhip00CmdEntry 1417 }


	iqhip00RollcallRollTrackCommand OBJECT-TYPE
		SYNTAX		RollCallString
		MAX-ACCESS		read-write
		STATUS			current
		DESCRIPTION
				"TYPE: - Editstring
				 PAGE: - Rollcall
					Command  cmdID= 1418  "
		::= { iqhip00CmdEntry 1418 }


	iqhip00RollcallRollTrackStatus OBJECT-TYPE
		SYNTAX		RollCallString
		MAX-ACCESS		read-only
		STATUS			current
		DESCRIPTION
				"TYPE: - Display
				 PAGE: - Rollcall
					Status  cmdID= 1411  format=   "
		::= { iqhip00CmdEntry 1411 }


	iqhip00RollcallRollTrackSending OBJECT-TYPE
		SYNTAX		RollCallString
		MAX-ACCESS		read-only
		STATUS			current
		DESCRIPTION
				"TYPE: - Display
				 PAGE: - Rollcall
					Sending  cmdID= 1414  format=   "
		::= { iqhip00CmdEntry 1414 }


	iqhip00SetupProduct OBJECT-TYPE
		SYNTAX		RollCallString
		MAX-ACCESS		read-only
		STATUS			current
		DESCRIPTION
				"TYPE: - Display
					Product  cmdID= 32771  format=   "
		::= { iqhip00CmdEntry 32771 }


	iqhip00SetupProductRelease OBJECT-TYPE
		SYNTAX		RollCallString
		MAX-ACCESS		read-only
		STATUS			current
		DESCRIPTION
				"TYPE: - Display
					Release  cmdID= 2  format=   "
		::= { iqhip00CmdEntry 2 }


	iqhip00SetupProductBuild OBJECT-TYPE
		SYNTAX		RollCallString
		MAX-ACCESS		read-only
		STATUS			current
		DESCRIPTION
				"TYPE: - Display
					Build  cmdID= 5  format=   "
		::= { iqhip00CmdEntry 5 }


	iqhip00SetupProductKOS OBJECT-TYPE
		SYNTAX		RollCallString
		MAX-ACCESS		read-only
		STATUS			current
		DESCRIPTION
				"TYPE: - Display
					KOS  cmdID= 32772  format=   "
		::= { iqhip00CmdEntry 32772 }


	iqhip00SetupProductSerial OBJECT-TYPE
		SYNTAX		RollCallString
		MAX-ACCESS		read-only
		STATUS			current
		DESCRIPTION
				"TYPE: - Display
					Serial  cmdID= 1  format=   "
		::= { iqhip00CmdEntry 1 }


	iqhip00SetupProductFirmware OBJECT-TYPE
		SYNTAX		RollCallString
		MAX-ACCESS		read-only
		STATUS			current
		DESCRIPTION
				"TYPE: - Display
					Firmware  cmdID= 5100  format=   "
		::= { iqhip00CmdEntry 5100 }


	iqhip00SetupProductPCB OBJECT-TYPE
		SYNTAX		RollCallString
		MAX-ACCESS		read-only
		STATUS			current
		DESCRIPTION
				"TYPE: - Display
					PCB  cmdID= 5101  format=   "
		::= { iqhip00CmdEntry 5101 }


	iqhip00SetupProductFactoryDefault OBJECT-TYPE
		SYNTAX		INTEGER { noAction(0),val_Factory_Default(1) }
		MAX-ACCESS		read-write
		STATUS			current
		DESCRIPTION
				"TYPE: - Button
					Factory Default  cmdID= 5520  value= 1  "
		::= { iqhip00CmdEntry 5520 }


	iqhip00SetupProductRestart OBJECT-TYPE
		SYNTAX		INTEGER {
							val_Restart_Soft_Only(1),
							val_Restart_Soft_Hard(2)
							}
		MAX-ACCESS		read-write
		STATUS			current
		DESCRIPTION
				"TYPE: - Button
					Restart Soft. Only  cmdID= 4  value= 1
					Restart Soft/Hard.  cmdID= 4  value= 2  "
		::= { iqhip00CmdEntry 4 }


	iqhip00SetupInput1Name OBJECT-TYPE
		SYNTAX		RollCallString
		MAX-ACCESS		read-write
		STATUS			current
		DESCRIPTION
				"TYPE: - Editstring
					Name  cmdID= 1336  "
		::= { iqhip00CmdEntry 1336 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: s36093244
--				:
-- Comments		: Serial Number of module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:12:00
--				:
-- Comments		: Uptime Days:Hours:Mins:Sec
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number or current control sessions.
--
---------------------------------------------------------------------------------------------------
-- Header		: INPUT_1_VI
--
-- MIB ref		: swCardEventLogSlotXX       .10.73.78.80.85.84.95.49.95.86.73
-- absolute OID	: 1.3.6.1.4.1.7995.2.6.1.1.XX.10.73.78.80.85.84.95.49.95.86.73
-- Vary			: YES
--
-- Value(s)		: -
--  Not available
--    =-
--
--  VI Type SMPTE selected
--    =SMPTE
--
--  VI Type is "AFD:SMPTE 2016" selected
--  input is 4x3
--    =AFD:LB 16:9 Top
--    =AFD:LB 14:9 Top
--    =AFD:LB > 16:9 VC
--    =AFD:FF 4:3
--    =AFD:LB 16:9 VC
--    =AFD:LB 14:9 VC
--    =AFD:FF 4:3 alt 14:9 C
--    =AFD:LB 16:9 alt 14:9 C
--    =AFD:LB 16:9 alt 4: C
--
--  input is 16x9
--    =FF 16:9
--    =AFD:PB 14:9 HC
--    =AFD:LB > 16:9 VC
--    =AFD:FF 16:9
--    =AFD:PB 4:3 HC
--    =AFD:FF 16:9 Pro
--    =AFD:PB 14:9 HC
--    =AFD:PB 4:3 alt 14:9 C
--    =AFD:FF 16:9 alt 14:9 C
--    =AFD:FF 16:9 alt 4: C
--
--  VI Type is "Legacy AFD" or "Legacy AFD and ScanSys"
--    =AFD0:CodedFrame
--    =AFD1:4:3
--    =AFD2:16:9
--    =AFD3:14:9
--    =AFD4:(AFD=4)
--    =AFD5:4:3 SP 14:9 C
--    =AFD6:16:9 SP 14:9 C
--    =AFD7:16:9 SP 4:3
-- Comments		:
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: Disabled
--          No logging info
--              : -
--          No Errors found
--              : OK
--          List of failed RollTracks e.g.
--              : FAIL:1,3,5
-- Comments		:
--
---------------------------------------------------------------------------------------------------
-- Header		: INPUT_1_APL
--
-- MIB ref		: swCardEventLogSlotXX       .11.73.78.80.85.84.95.49.95.65.80.76
-- absolute OID	: 1.3.6.1.4.1.7995.2.6.1.1.XX.11.73.78.80.85.84.95.49.95.65.80.76
-- Vary			: YES
--
-- Value(s)		: OK
--				: Info:OK
--				: WARN:MIN APL
--				: WARN:MAX APL
--				: Info:MIN APL
--				: Info:MAX APL
--				:
-- Comments		:
--
---------------------------------------------------------------------------------------------------
-- Header		: INPUT_1_CRC
--
-- MIB ref		: swCardEventLogSlotXX       .11.73.78.80.85.84.95.49.95.67.82.67
-- absolute OID	: 1.3.6.1.4.1.7995.2.6.1.1.XX.11.73.78.80.85.84.95.49.95.67.82.67
-- Vary			: YES
--
-- Value(s)		: -
--				: OK
--				: WARN:CRC Error
--				:
-- Comments		: This is active with a HD input only
--
---------------------------------------------------------------------------------------------------
-- Header		: INPUT_1_EDH
--
-- MIB ref		: swCardEventLogSlotXX       .11.73.78.80.85.84.95.49.95.69.68.72
-- absolute OID	: 1.3.6.1.4.1.7995.2.6.1.1.XX.11.73.78.80.85.84.95.49.95.69.68.72
-- Vary			: YES
--
-- Value(s)		: OK
--				: NONE
--				: WARN:EDH Error
--				:
-- Comments		: This is active with a SD input only
--
---------------------------------------------------------------------------------------------------
-- Header		: INPUT_1_WSS
--
-- MIB ref		: swCardEventLogSlotXX       .11.73.78.80.85.84.95.49.95.87.83.83
-- absolute OID	: 1.3.6.1.4.1.7995.2.6.1.1.XX.11.73.78.80.85.84.95.49.95.87.83.83
-- Vary			: YES
--
-- Value(s)		:
--          Not available
--              : -
--
--          WSS Type is "ETSI"
--              : ETSI:Parity Error
--              : ETSI:Box 14:9 C
--              : ETSI:Box 14:9 Top
--              : ETSI:Box 16:9 Top
--              : ETSI:FF 16:9 Ana
--              : ETSI:FF 4:3
--              : ETSI:Box 16:9
--              : ETSI:Box > 16:9 C
--              : ETSI:FF4:3 SP 14:9C
--
--          WSS Type is "AFD" or "AFD and ScanSys"
--              : AFD0:CodedFrame
--              : AFD1:4:3
--              : AFD2:16:9
--              : AFD3:14:9
--              : AFD4:(AFD=4)
--              : AFD5:4:3 SP 14:9 C
--              : AFD6:16:9 SP 14:9 C
--              : AFD7:16:9 SP 4:3
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: NO
--
-- Value(s)		: 0006502725
--				:
-- Comments		: Software build verion number
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
-- Vary			: YES
--
-- Value(s)		: INPUT 1 SERIAL IN
--				:
-- Comments		: Edit box, default shown
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: NO
--
-- Value(s)		: HD/SD SDI
--				:
-- Comments		: Fixed, describes the input type
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2008-03-06T17:04:02Z
--				:
-- Comments		: Date/Time of last known restart
--
---------------------------------------------------------------------------------------------------
-- Header		: INPUT_1_BLACK
--
-- MIB ref		: swCardEventLogSlotXX       .13.73.78.80.85.84.95.49.95.66.76.65.67.75
-- absolute OID	: 1.3.6.1.4.1.7995.2.6.1.1.XX.13.73.78.80.85.84.95.49.95.66.76.65.67.75
-- Vary			: YES
--
-- Value(s)		: OK
--				: WARN:BLACK
--				: FAIL:BLACK
--				: Info:OK
--				: Info:BLACK
--				:
-- Comments		:
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: NO
--
-- Value(s)		: SERIAL IN
--				:
-- Comments		: Fixed
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: OK
--				: FAIL:Lost
--				:
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 2008-03-06T17:04:02Z
-- Comments		: Date/Time of last control modification
--
---------------------------------------------------------------------------------------------------
-- Header		: OUTPUT_1_UMID
--
-- MIB ref		: swCardEventLogSlotXX       .13.79.85.84.80.85.84.95.49.95.85.77.73.68
-- absolute OID	: 1.3.6.1.4.1.7995.2.6.1.1.XX.13.79.85.84.80.85.84.95.49.95.85.77.73.68
-- Vary			: YES
--
-- Value(s)		: <X........X>
--				: WARN:No UMID
--				: Info:No UMID
--				:
-- Comments		: 64 hex digits to represent 32 byte UMID
--
---------------------------------------------------------------------------------------------------
-- Header		: INPUT_1_FREEZE
--
-- MIB ref		: swCardEventLogSlotXX       .14.73.78.80.85.84.95.49.95.70.82.69.69.90.69
-- absolute OID	: 1.3.6.1.4.1.7995.2.6.1.1.XX.14.73.78.80.85.84.95.49.95.70.82.69.69.90.69
-- Vary			: YES
--
-- Value(s)		:
--          Detector not enabled
--              : Info:OK
--              : Info:Freeze
--
--          Detector enabled
--              : OK
--              : WARN:Freeze
--              : FAIL:Freeze
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: NO
--
-- Value(s)		: 3.6
--				:
-- Comments		: Variable dependant on the Firmware Build
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: NO
--
-- Value(s)		: RDHDAI2X.000
--				:
-- Comments		: Variable dependant on the Hardware Build
--
---------------------------------------------------------------------------------------------------
-- Header		: INPUT_1_BLACKISH
--
-- MIB ref		: swCardEventLogSlotXX       .16.73.78.80.85.84.95.49.95.66.76.65.67.75.73.83.72
-- absolute OID	: 1.3.6.1.4.1.7995.2.6.1.1.XX.16.73.78.80.85.84.95.49.95.66.76.65.67.75.73.83.72
-- Vary			: YES
--
-- Value(s)		: OK
--				: WARN:BLACKISH
--				: FAIL:BLACKISH
--				: Info:OK
--				: Info:BLACKISH
--				:
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: unknown
--				: 1125(1035)/30I
--				: 1125(1035)/29I
--				: 1125(1080)/60P
--				: 1125(1080)/59P
--				: 1125(1080)/50P
--				: 1125(1080)/30I
--				: 1125(1080)/29I
--				: 1125(1080)/25I
--				: 1125(1080)/30P
--				: 1125(1080)/29P
--				: 1125(1080)/25P
--				: 1125(1080)/24P
--				: 1125(1080)/23P
--				: 1250(1080)/50P
--				: 1250(1080)/25I
--				: 750(720)/60P
--				: 750(720)/59P
--				: 525(480)/59P
--				: 525(480)/29I
--				: 625(576)/25I
--				: 525(480)/29I
--				: 625(576)/25I
--				: 1125(1080)/24sF
--				: 1125(1080)/23sF
--				: 525(480)/60P
--				: 525(480)/59P
--				: 625(576)/24sF
--				: 625(576)/23sF
--				: 1250(1152)/25I
--				: 750(720)/50P
--				: 625(576)/50P
--				: 525(480)/60P
--				: 525(480)/59P
--				: 1125(1080)/30sF
--				: 1125(1080)/29sF
--				: 1125(1080)/25sF
--				: 750(720)/30P
--				: 750(720)/29P
--				: 750(720)/25P
--				: 750(720)/24P
--				: 750(720)/23P
--				: 525(480)/29I
--				: 625(576)/25I
--				: 625(576)/24I
--				: 625(576)/23I
--				:
-- Comments		:
--
---------------------------------------------------------------------------------------------------
-- Header		: INPUT_1_STILLISH
--
-- MIB ref		: swCardEventLogSlotXX       .16.73.78.80.85.84.95.49.95.83.84.73.76.76.73.83.72
-- absolute OID	: 1.3.6.1.4.1.7995.2.6.1.1.XX.16.73.78.80.85.84.95.49.95.83.84.73.76.76.73.83.72
-- Vary			: YES
--
-- Value(s)		: OK
--				: WARN:Stillish
--				: FAIL:Stillish
--				: Info:OK
--				: Info:Stillish
--				:
-- Comments		:
--
---------------------------------------------------------------------------------------------------
-- Header		: INPUT_1_VI_STATE
--
-- MIB ref		: swCardEventLogSlotXX       .16.73.78.80.85.84.95.49.95.86.73.95.83.84.65.84.69
-- absolute OID	: 1.3.6.1.4.1.7995.2.6.1.1.XX.16.73.78.80.85.84.95.49.95.86.73.95.83.84.65.84.69
-- Vary			: YES
--
-- Value(s)		: -
--				: OK
--				: FAIL:No VI
--				: Info:OK
--				: Info:No VI
-- Comments		:
--
---------------------------------------------------------------------------------------------------
-- Header		: INPUT_1_PID_STATE
--
-- MIB ref		: swCardEventLogSlotXX       .17.73.78.80.85.84.95.49.95.80.73.68.95.83.84.65.84.69
-- absolute OID	: 1.3.6.1.4.1.7995.2.6.1.1.XX.17.73.78.80.85.84.95.49.95.80.73.68.95.83.84.65.84.69
-- Vary			: YES
--
-- Value(s)		: OK
--              : WARN:No PID
--              : WARN:Multiple Line Error
--              : WARN:Length Error
--              : WARN:Inc House ID
--              : WARN:Illegal Tag Value
--              : WARN:Inc Seg Num Len
--              : WARN:Inc Duration Len
--              : WARN:Inc Frame Rate Len
--              : WARN:Inc Data Count
--              : WARN:Checksum Error
--              : WARN:Not Hyperion PID
--              : WARN:Changing
--              : Info:No PID
--              : Info:Multiple Line Error
--              : Info:Length Error
--              : Info:Inc House ID
--              : Info:Illegal Tag Value
--              : Info:Inc Seg Num Len
--              : Info:Inc Duration Len
--              : Info:Inc Frame Rate Len
--              : Info:Inc Data Count
--              : Info:Checksum Error
--              : Info:Not Hyperion PID
--              : Info:Changing
--				:
-- Comments		:
--
---------------------------------------------------------------------------------------------------
-- Header		: INPUT_1_PID_TITLE
--
-- MIB ref		: swCardEventLogSlotXX       .17.73.78.80.85.84.95.49.95.80.73.68.95.84.73.84.76.69
-- absolute OID	: 1.3.6.1.4.1.7995.2.6.1.1.XX.17.73.78.80.85.84.95.49.95.80.73.68.95.84.73.84.76.69
-- Vary			: YES
--
-- Value(s)		: <19 Characters>
--				: WARN:No PID
--				: Info:No PID
-- Comments		:
--
---------------------------------------------------------------------------------------------------
-- Header		: INPUT_1_VI_ASPECT
--
-- MIB ref		: swCardEventLogSlotXX       .17.73.78.80.85.84.95.49.95.86.73.95.65.83.80.69.67.84
-- absolute OID	: 1.3.6.1.4.1.7995.2.6.1.1.XX.17.73.78.80.85.84.95.49.95.86.73.95.65.83.80.69.67.84
-- Vary			: YES
--
-- Value(s)		: -
--				: 4:3
--				: 16:9
--				: No Info
--				: N/A
-- Comments		:
--
---------------------------------------------------------------------------------------------------
-- Header		: INPUT_1_WSS_STATE
--
-- MIB ref		: swCardEventLogSlotXX       .17.73.78.80.85.84.95.49.95.87.83.83.95.83.84.65.84.69
-- absolute OID	: 1.3.6.1.4.1.7995.2.6.1.1.XX.17.73.78.80.85.84.95.49.95.87.83.83.95.83.84.65.84.69
-- Vary			: YES
--
-- Value(s)		: OK
--              : WARN:Error
--              : FAIL:No WSS
--              : Info:OK
--              : Info:Error
--              : Info:No WSS
--              : -
--				:
-- Comments		:
--
---------------------------------------------------------------------------------------------------
-- Header		: INPUT_1_UMID_STATE
--
-- MIB ref		: swCardEventLogSlotXX       .18.73.78.80.85.84.95.49.95.85.77.73.68.95.83.84.65.84.69
-- absolute OID	: 1.3.6.1.4.1.7995.2.6.1.1.XX.18.73.78.80.85.84.95.49.95.85.77.73.68.95.83.84.65.84.69
-- Vary			: YES
--
-- Value(s)		: OK
--				: WARN:Multiple Line Error
--				: WARN:Length Error
--				: WARN:Checksum Error
--				: WARN:Changing
--				: WARN:No UMID
--				: Info:Multiple Line Error
--				: Info:Length Error
--				: Info:Checksum Error
--				: Info:Changing
--				: Info:No UMID
--				:
-- Comments		:
--
---------------------------------------------------------------------------------------------------
-- Header		: INPUT_1_VITC_STATE
--
-- MIB ref		: swCardEventLogSlotXX       .18.73.78.80.85.84.95.49.95.86.73.84.67.95.83.84.65.84.69
-- absolute OID	: 1.3.6.1.4.1.7995.2.6.1.1.XX.18.73.78.80.85.84.95.49.95.86.73.84.67.95.83.84.65.84.69
-- Vary			: YES
--
-- Value(s)		: OK
--				: FAIL:No VITC
--				: FAIL:No VITC Field 1
--				: FAIL:No VITC Field 2
--				: Info:OK
--				: Info:No VITC
--				: Info:No VITC Field 1
--				: Info:No VITC Field 2
-- Comments		:
--
---------------------------------------------------------------------------------------------------
-- Header		: INPUT_1_WSS_ASPECT
--
-- MIB ref		: swCardEventLogSlotXX       .18.73.78.80.85.84.95.49.95.87.83.83.95.65.83.80.69.67.84
-- absolute OID	: 1.3.6.1.4.1.7995.2.6.1.1.XX.18.73.78.80.85.84.95.49.95.87.83.83.95.65.83.80.69.67.84
-- Vary			: YES
--
-- Value(s)		: -
--				: 4:3
--				: 16:9
--				: No Info
--				: N/A
-- Comments		:
--
---------------------------------------------------------------------------------------------------
-- Header		: OUPUT_1_OSD_STATUS
--
-- MIB ref		: swCardEventLogSlotXX       .18.79.85.80.85.84.95.49.95.79.83.68.95.83.84.65.84.85.83
-- absolute OID	: 1.3.6.1.4.1.7995.2.6.1.1.XX.18.79.85.80.85.84.95.49.95.79.83.68.95.83.84.65.84.85.83
-- Vary			: YES
--
-- Value(s)		: OFF
--				: WARN:ON
-- Comments		:
--
---------------------------------------------------------------------------------------------------
-- Header		: OUTPUT_1_PID_STATE
--
-- MIB ref		: swCardEventLogSlotXX       .18.79.85.84.80.85.84.95.49.95.80.73.68.95.83.84.65.84.69
-- absolute OID	: 1.3.6.1.4.1.7995.2.6.1.1.XX.18.79.85.84.80.85.84.95.49.95.80.73.68.95.83.84.65.84.69
-- Vary			: YES
--
-- Value(s)		: OK
--				: Pass
--				: Overwrite
--				: Deleted
--				: WARN:Multiple Lines
--				: WARN:No PID
--				: Info:Multiple Lines
--				: Info:No PID
--				:
-- Comments		:
--
---------------------------------------------------------------------------------------------------
-- Header		: OUTPUT_1_PID_TITLE
--
-- MIB ref		: swCardEventLogSlotXX       .18.79.85.84.80.85.84.95.49.95.80.73.68.95.84.73.84.76.69
-- absolute OID	: 1.3.6.1.4.1.7995.2.6.1.1.XX.18.79.85.84.80.85.84.95.49.95.80.73.68.95.84.73.84.76.69
-- Vary			: YES
--
-- Value(s)		: <19 Characters>
--				: WARN:No PID
--				: Info:No PID
--				:
-- Comments		:
--
---------------------------------------------------------------------------------------------------
-- Header		: INPUT_1_C_BIT_DEPTH
--
-- MIB ref		: swCardEventLogSlotXX       .19.73.78.80.85.84.95.49.95.67.95.66.73.84.95.68.69.80.84.72
-- absolute OID	: 1.3.6.1.4.1.7995.2.6.1.1.XX.19.73.78.80.85.84.95.49.95.67.95.66.73.84.95.68.69.80.84.72
-- Vary			: YES
--
-- Value(s)		: UNKNOWN
--				: 8
--				: 9
--				: 10
--				:
-- Comments		:
--
---------------------------------------------------------------------------------------------------
-- Header		: INPUT_1_C_VIDEO_LOW
--
-- MIB ref		: swCardEventLogSlotXX       .19.73.78.80.85.84.95.49.95.67.95.86.73.68.69.79.95.76.79.87
-- absolute OID	: 1.3.6.1.4.1.7995.2.6.1.1.XX.19.73.78.80.85.84.95.49.95.67.95.86.73.68.69.79.95.76.79.87
-- Vary			: YES
--
-- Value(s)		: OK
--				: Info:OK
--				: FAIL:Low
--				: Info:Low
--				:
-- Comments		:
--
---------------------------------------------------------------------------------------------------
-- Header		: INPUT_1_PID_SEG_NUM
--
-- MIB ref		: swCardEventLogSlotXX       .19.73.78.80.85.84.95.49.95.80.73.68.95.83.69.71.95.78.85.77
-- absolute OID	: 1.3.6.1.4.1.7995.2.6.1.1.XX.19.73.78.80.85.84.95.49.95.80.73.68.95.83.69.71.95.78.85.77
-- Vary			: YES
--
-- Value(s)		: <0 to 65535>
--				: WARN:No PID
--				: Info:No PID
--				:
-- Comments		:
--
---------------------------------------------------------------------------------------------------
-- Header		: INPUT_1_Y_BIT_DEPTH
--
-- MIB ref		: swCardEventLogSlotXX       .19.73.78.80.85.84.95.49.95.89.95.66.73.84.95.68.69.80.84.72
-- absolute OID	: 1.3.6.1.4.1.7995.2.6.1.1.XX.19.73.78.80.85.84.95.49.95.89.95.66.73.84.95.68.69.80.84.72
-- Vary			: YES
--
-- Value(s)		: UNKNOWN
--				: 8
--				: 9
--				: 10
--				:
-- Comments		:
--
---------------------------------------------------------------------------------------------------
-- Header		: INPUT_1_Y_VIDEO_LOW
--
-- MIB ref		: swCardEventLogSlotXX       .19.73.78.80.85.84.95.49.95.89.95.86.73.68.69.79.95.76.79.87
-- absolute OID	: 1.3.6.1.4.1.7995.2.6.1.1.XX.19.73.78.80.85.84.95.49.95.89.95.86.73.68.69.79.95.76.79.87
-- Vary			: YES
--
-- Value(s)		: OK
--				: Info:OK
--				: FAIL:Low
--				: Info:Low
--				:
-- Comments		:
--
---------------------------------------------------------------------------------------------------
-- Header		: OUTPUT_1_UMID_STATE
--
-- MIB ref		: swCardEventLogSlotXX       .19.79.85.84.80.85.84.95.49.95.85.77.73.68.95.83.84.65.84.69
-- absolute OID	: 1.3.6.1.4.1.7995.2.6.1.1.XX.19.79.85.84.80.85.84.95.49.95.85.77.73.68.95.83.84.65.84.69
-- Vary			: YES
--
-- Value(s)		: **
-- Value(s)		: OK
--				: Pass
--				: Overwrite
--				: Deleted
--				: WARN:Multiple Lines
--				: WARN:No UMID
--				: Info:Multiple Lines
--				: Info:No UMID
--				:
-- Comments		:
--
---------------------------------------------------------------------------------------------------
-- Header		: INPUT_1_C_VIDEO_HIGH
--
-- MIB ref		: swCardEventLogSlotXX       .20.73.78.80.85.84.95.49.95.67.95.86.73.68.69.79.95.72.73.71.72
-- absolute OID	: 1.3.6.1.4.1.7995.2.6.1.1.XX.20.73.78.80.85.84.95.49.95.67.95.86.73.68.69.79.95.72.73.71.72
-- Vary			: YES
--
-- Value(s)		: OK
--				: Info:OK
--				: FAIL:High
--				: Info:High
--				:
-- Comments		:
--
---------------------------------------------------------------------------------------------------
-- Header		: INPUT_1_PID_DURATION
--
-- MIB ref		: swCardEventLogSlotXX       .20.73.78.80.85.84.95.49.95.80.73.68.95.68.85.82.65.84.73.79.78
-- absolute OID	: 1.3.6.1.4.1.7995.2.6.1.1.XX.20.73.78.80.85.84.95.49.95.80.73.68.95.68.85.82.65.84.73.79.78
-- Vary			: YES
--
-- Value(s)		: <0 to 9999999999999999999>
-- Value(s)		: WARN:No PID
-- Value(s)		: Info:No PID
--				:
-- Comments		:
--
---------------------------------------------------------------------------------------------------
-- Header		: INPUT_1_PID_HOUSE_ID
--
-- MIB ref		: swCardEventLogSlotXX       .20.73.78.80.85.84.95.49.95.80.73.68.95.72.79.85.83.69.95.73.68
-- absolute OID	: 1.3.6.1.4.1.7995.2.6.1.1.XX.20.73.78.80.85.84.95.49.95.80.73.68.95.72.79.85.83.69.95.73.68
-- Vary			: YES
--
-- Value(s)		: <19 Characters>
--				: WARN:No PID
--				: Info:No PID
--				:
-- Comments		:
--
---------------------------------------------------------------------------------------------------
-- Header		: INPUT_1_UMID_CURRENT
--
-- MIB ref		: swCardEventLogSlotXX       .20.73.78.80.85.84.95.49.95.85.77.73.68.95.67.85.82.82.69.78.84
-- absolute OID	: 1.3.6.1.4.1.7995.2.6.1.1.XX.20.73.78.80.85.84.95.49.95.85.77.73.68.95.67.85.82.82.69.78.84
-- Vary			: YES
--
-- Value(s)		: <X........X>
--				: WARN:No UMID
--				: Info:No UMID
--				:
-- Comments		: 64 hex digits to represent 32 byte UMID
--
---------------------------------------------------------------------------------------------------
-- Header		: INPUT_1_Y_VIDEO_HIGH
--
-- MIB ref		: swCardEventLogSlotXX       .20.73.78.80.85.84.95.49.95.89.95.86.73.68.69.79.95.72.73.71.72
-- absolute OID	: 1.3.6.1.4.1.7995.2.6.1.1.XX.20.73.78.80.85.84.95.49.95.89.95.86.73.68.69.79.95.72.73.71.72
-- Vary			: YES
--
-- Value(s)		: OK
--				: Info:OK
--				: FAIL:High
--				: Info:High
--				:
-- Comments		:
--
---------------------------------------------------------------------------------------------------
-- Header		: OUTPUT_1_PID_SEG_NUM
--
-- MIB ref		: swCardEventLogSlotXX       .20.79.85.84.80.85.84.95.49.95.80.73.68.95.83.69.71.95.78.85.77
-- absolute OID	: 1.3.6.1.4.1.7995.2.6.1.1.XX.20.79.85.84.80.85.84.95.49.95.80.73.68.95.83.69.71.95.78.85.77
-- Vary			: YES
--
-- Value(s)		: <0 to 65535>
--				: WARN:No PID
--				: Info:No PID
--				:
-- Comments		:
--
---------------------------------------------------------------------------------------------------
-- Header		: INPUT_1_UMID_PREVIOUS
--
-- MIB ref		: swCardEventLogSlotXX       .21.73.78.80.85.84.95.49.95.85.77.73.68.95.80.82.69.86.73.79.85.83
-- absolute OID	: 1.3.6.1.4.1.7995.2.6.1.1.XX.21.73.78.80.85.84.95.49.95.85.77.73.68.95.80.82.69.86.73.79.85.83
-- Vary			: YES
--
-- Value(s)		: <X........X>
--				: WARN:No UMID
--				: Info:No UMID
--				:
-- Comments		: 64 hex digits to represent 32 byte UMID
--
---------------------------------------------------------------------------------------------------
-- Header		: OUTPUT_1_PID_DURATION
--
-- MIB ref		: swCardEventLogSlotXX       .21.79.85.84.80.85.84.95.49.95.80.73.68.95.68.85.82.65.84.73.79.78
-- absolute OID	: 1.3.6.1.4.1.7995.2.6.1.1.XX.21.79.85.84.80.85.84.95.49.95.80.73.68.95.68.85.82.65.84.73.79.78
-- Vary			: YES
--
-- Value(s)		: <0 to 9999999999999999999>
-- Value(s)		: WARN:No PID
-- Value(s)		: Info:No PID
--				:
-- Comments		:
--
---------------------------------------------------------------------------------------------------
-- Header		: OUTPUT_1_PID_HOUSE_ID
--
-- MIB ref		: swCardEventLogSlotXX       .21.79.85.84.80.85.84.95.49.95.80.73.68.95.72.79.85.83.69.95.73.68
-- absolute OID	: 1.3.6.1.4.1.7995.2.6.1.1.XX.21.79.85.84.80.85.84.95.49.95.80.73.68.95.72.79.85.83.69.95.73.68
-- Vary			: YES
--
-- Value(s)		: <19 Characters>
--				: WARN:No PID
--				: Info:No PID
--				:
-- Comments		:
--
---------------------------------------------------------------------------------------------------
-- Header		: INPUT_1_PID_FRAME_RATE
--
-- MIB ref		: swCardEventLogSlotXX       .22.73.78.80.85.84.95.49.95.80.73.68.95.70.82.65.77.69.95.82.65.84.69
-- absolute OID	: 1.3.6.1.4.1.7995.2.6.1.1.XX.22.73.78.80.85.84.95.49.95.80.73.68.95.70.82.65.77.69.95.82.65.84.69
-- Vary			: YES
--
-- Value(s)		: 23.976
--				: 24.000
--				: 25.000
--				: 29.970
--				: 30.000
--				: 50.000
--				: 59.940
--				: 60.000
--				: WARN:No PID
--				: Info:No PID
--				:
-- Comments		:
--
---------------------------------------------------------------------------------------------------
-- Header		: OUTPUT_1_PID_FRAME_RATE
--
-- MIB ref		: swCardEventLogSlotXX       .23.79.85.84.80.85.84.95.49.95.80.73.68.95.70.82.65.77.69.95.82.65.84.69
-- absolute OID	: 1.3.6.1.4.1.7995.2.6.1.1.XX.23.79.85.84.80.85.84.95.49.95.80.73.68.95.70.82.65.77.69.95.82.65.84.69
-- Vary			: YES
--
-- Value(s)		: 23.976
--				: 24.000
--				: 25.000
--				: 29.970
--				: 30.000
--				: 50.000
--				: 59.940
--				: 60.000
--				: WARN:No PID
--				: Info:No PID
--				:
-- Comments		:
--
---------------------------------------------------------------------------------------------------
-- Header		: INPUT_1_HYPERION_SUMMARY
--
-- MIB ref		: swCardEventLogSlotXX       .24.73.78.80.85.84.95.49.95.72.89.80.69.82.73.79.78.95.83.85.77.77.65.82.89
-- absolute OID	: 1.3.6.1.4.1.7995.2.6.1.1.XX.24.73.78.80.85.84.95.49.95.72.89.80.69.82.73.79.78.95.83.85.77.77.65.82.89
-- Vary			: YES
--
-- Value(s)		: OK
--				: UNSUPPORTED
--				: WARN
--				: FAIL
--				:
-- Comments		:
--
---------------------------------------------------------------------------------------------------
-- Header		: INPUT_1_PID_PREVIOUS_COUNT
--
-- MIB ref		: swCardEventLogSlotXX       .26.73.78.80.85.84.95.49.95.80.73.68.95.80.82.69.86.73.79.85.83.95.67.79.85.78.84
-- absolute OID	: 1.3.6.1.4.1.7995.2.6.1.1.XX.26.73.78.80.85.84.95.49.95.80.73.68.95.80.82.69.86.73.79.85.83.95.67.79.85.78.84
-- Vary			: YES
--
-- Value(s)		: -
--				: <100-4294967295>
--				:
-- Comments		:
--
---------------------------------------------------------------------------------------------------
-- Header		: INPUT_1_PID_PREVIOUS_TITLE
--
-- MIB ref		: swCardEventLogSlotXX       .26.73.78.80.85.84.95.49.95.80.73.68.95.80.82.69.86.73.79.85.83.95.84.73.84.76.69
-- absolute OID	: 1.3.6.1.4.1.7995.2.6.1.1.XX.26.73.78.80.85.84.95.49.95.80.73.68.95.80.82.69.86.73.79.85.83.95.84.73.84.76.69
-- Vary			: YES
--
-- Value(s)		: <19 Characters>
--				: WARN:No PID
--				: Info:No PID
--				:
-- Comments		:
--
---------------------------------------------------------------------------------------------------
-- Header		: INPUT_1_CLOSED_CAPTION_TYPE
--
-- MIB ref		: swCardEventLogSlotXX       .27.73.78.80.85.84.95.49.95.67.76.79.83.69.68.95.67.65.80.84.73.79.78.95.84.89.80.69
-- absolute OID	: 1.3.6.1.4.1.7995.2.6.1.1.XX.27.73.78.80.85.84.95.49.95.67.76.79.83.69.68.95.67.65.80.84.73.79.78.95.84.89.80.69
-- Vary			: YES
--
-- Value(s)		: -
--				: EIA708
--				: EIA608
--				:
-- Comments		:
--
---------------------------------------------------------------------------------------------------
-- Header		: INPUT_1_CLOSED_CAPTION_STATE
--
-- MIB ref		: swCardEventLogSlotXX       .28.73.78.80.85.84.95.49.95.67.76.79.83.69.68.95.67.65.80.84.73.79.78.95.83.84.65.84.69
-- absolute OID	: 1.3.6.1.4.1.7995.2.6.1.1.XX.28.73.78.80.85.84.95.49.95.67.76.79.83.69.68.95.67.65.80.84.73.79.78.95.83.84.65.84.69
-- Vary			: YES
--
-- Value(s)		: OK
--				: FAIL:No Closed Caption
--				: WARN:No Closed Caption
--				: Info:OK
--				: Info:No Closed Caption
--				: Info:No Closed Caption
--				: WARN:Checksum Error
--				:
-- Comments		:
--
---------------------------------------------------------------------------------------------------
-- Header		: INPUT_1_CLOSED_CAPTION_TITLE
--
-- MIB ref		: swCardEventLogSlotXX       .28.73.78.80.85.84.95.49.95.67.76.79.83.69.68.95.67.65.80.84.73.79.78.95.84.73.84.76.69
-- absolute OID	: 1.3.6.1.4.1.7995.2.6.1.1.XX.28.73.78.80.85.84.95.49.95.67.76.79.83.69.68.95.67.65.80.84.73.79.78.95.84.73.84.76.69
-- Vary			: YES
--
-- Value(s)		: -
--              : <CC608 Title>   Displays the decoded title
-- Comments		:
--
---------------------------------------------------------------------------------------------------
-- Header		: INPUT_1_EMBED_AUDIO_1_1_TYPE
--
-- MIB ref		: swCardEventLogSlotXX       .28.73.78.80.85.84.95.49.95.69.77.66.69.68.95.65.85.68.73.79.95.49.95.49.95.84.89.80.69
-- absolute OID	: 1.3.6.1.4.1.7995.2.6.1.1.XX.28.73.78.80.85.84.95.49.95.69.77.66.69.68.95.65.85.68.73.79.95.49.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_1_2_TYPE
--
-- MIB ref		: swCardEventLogSlotXX       .28.73.78.80.85.84.95.49.95.69.77.66.69.68.95.65.85.68.73.79.95.49.95.50.95.84.89.80.69
-- absolute OID	: 1.3.6.1.4.1.7995.2.6.1.1.XX.28.73.78.80.85.84.95.49.95.69.77.66.69.68.95.65.85.68.73.79.95.49.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_2_1_TYPE
--
-- MIB ref		: swCardEventLogSlotXX       .28.73.78.80.85.84.95.49.95.69.77.66.69.68.95.65.85.68.73.79.95.50.95.49.95.84.89.80.69
-- absolute OID	: 1.3.6.1.4.1.7995.2.6.1.1.XX.28.73.78.80.85.84.95.49.95.69.77.66.69.68.95.65.85.68.73.79.95.50.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_2_2_TYPE
--
-- MIB ref		: swCardEventLogSlotXX       .28.73.78.80.85.84.95.49.95.69.77.66.69.68.95.65.85.68.73.79.95.50.95.50.95.84.89.80.69
-- absolute OID	: 1.3.6.1.4.1.7995.2.6.1.1.XX.28.73.78.80.85.84.95.49.95.69.77.66.69.68.95.65.85.68.73.79.95.50.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_3_1_TYPE
--
-- MIB ref		: swCardEventLogSlotXX       .28.73.78.80.85.84.95.49.95.69.77.66.69.68.95.65.85.68.73.79.95.51.95.49.95.84.89.80.69
-- absolute OID	: 1.3.6.1.4.1.7995.2.6.1.1.XX.28.73.78.80.85.84.95.49.95.69.77.66.69.68.95.65.85.68.73.79.95.51.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_3_2_TYPE
--
-- MIB ref		: swCardEventLogSlotXX       .28.73.78.80.85.84.95.49.95.69.77.66.69.68.95.65.85.68.73.79.95.51.95.50.95.84.89.80.69
-- absolute OID	: 1.3.6.1.4.1.7995.2.6.1.1.XX.28.73.78.80.85.84.95.49.95.69.77.66.69.68.95.65.85.68.73.79.95.51.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_4_1_TYPE
--
-- MIB ref		: swCardEventLogSlotXX       .28.73.78.80.85.84.95.49.95.69.77.66.69.68.95.65.85.68.73.79.95.52.95.49.95.84.89.80.69
-- absolute OID	: 1.3.6.1.4.1.7995.2.6.1.1.XX.28.73.78.80.85.84.95.49.95.69.77.66.69.68.95.65.85.68.73.79.95.52.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_4_2_TYPE
--
-- MIB ref		: swCardEventLogSlotXX       .28.73.78.80.85.84.95.49.95.69.77.66.69.68.95.65.85.68.73.79.95.52.95.50.95.84.89.80.69
-- absolute OID	: 1.3.6.1.4.1.7995.2.6.1.1.XX.28.73.78.80.85.84.95.49.95.69.77.66.69.68.95.65.85.68.73.79.95.52.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_5_1_TYPE
--
-- MIB ref		: swCardEventLogSlotXX       .28.73.78.80.85.84.95.49.95.69.77.66.69.68.95.65.85.68.73.79.95.53.95.49.95.84.89.80.69
-- absolute OID	: 1.3.6.1.4.1.7995.2.6.1.1.XX.28.73.78.80.85.84.95.49.95.69.77.66.69.68.95.65.85.68.73.79.95.53.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_5_2_TYPE
--
-- MIB ref		: swCardEventLogSlotXX       .28.73.78.80.85.84.95.49.95.69.77.66.69.68.95.65.85.68.73.79.95.53.95.50.95.84.89.80.69
-- absolute OID	: 1.3.6.1.4.1.7995.2.6.1.1.XX.28.73.78.80.85.84.95.49.95.69.77.66.69.68.95.65.85.68.73.79.95.53.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_6_1_TYPE
--
-- MIB ref		: swCardEventLogSlotXX       .28.73.78.80.85.84.95.49.95.69.77.66.69.68.95.65.85.68.73.79.95.54.95.49.95.84.89.80.69
-- absolute OID	: 1.3.6.1.4.1.7995.2.6.1.1.XX.28.73.78.80.85.84.95.49.95.69.77.66.69.68.95.65.85.68.73.79.95.54.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_6_2_TYPE
--
-- MIB ref		: swCardEventLogSlotXX       .28.73.78.80.85.84.95.49.95.69.77.66.69.68.95.65.85.68.73.79.95.54.95.50.95.84.89.80.69
-- absolute OID	: 1.3.6.1.4.1.7995.2.6.1.1.XX.28.73.78.80.85.84.95.49.95.69.77.66.69.68.95.65.85.68.73.79.95.54.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_7_1_TYPE
--
-- MIB ref		: swCardEventLogSlotXX       .28.73.78.80.85.84.95.49.95.69.77.66.69.68.95.65.85.68.73.79.95.55.95.49.95.84.89.80.69
-- absolute OID	: 1.3.6.1.4.1.7995.2.6.1.1.XX.28.73.78.80.85.84.95.49.95.69.77.66.69.68.95.65.85.68.73.79.95.55.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_7_2_TYPE
--
-- MIB ref		: swCardEventLogSlotXX       .28.73.78.80.85.84.95.49.95.69.77.66.69.68.95.65.85.68.73.79.95.55.95.50.95.84.89.80.69
-- absolute OID	: 1.3.6.1.4.1.7995.2.6.1.1.XX.28.73.78.80.85.84.95.49.95.69.77.66.69.68.95.65.85.68.73.79.95.55.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_8_1_TYPE
--
-- MIB ref		: swCardEventLogSlotXX       .28.73.78.80.85.84.95.49.95.69.77.66.69.68.95.65.85.68.73.79.95.56.95.49.95.84.89.80.69
-- absolute OID	: 1.3.6.1.4.1.7995.2.6.1.1.XX.28.73.78.80.85.84.95.49.95.69.77.66.69.68.95.65.85.68.73.79.95.56.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------

-- Header		: INPUT_1_EMBED_AUDIO_8_2_TYPE
--
-- MIB ref		: swCardEventLogSlotXX       .28.73.78.80.85.84.95.49.95.69.77.66.69.68.95.65.85.68.73.79.95.56.95.50.95.84.89.80.69
-- absolute OID	: 1.3.6.1.4.1.7995.2.6.1.1.XX.28.73.78.80.85.84.95.49.95.69.77.66.69.68.95.65.85.68.73.79.95.56.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_PID_PREVIOUS_SEG_NUM
--
-- MIB ref		: swCardEventLogSlotXX       .28.73.78.80.85.84.95.49.95.80.73.68.95.80.82.69.86.73.79.85.83.95.83.69.71.95.78.85.77
-- absolute OID	: 1.3.6.1.4.1.7995.2.6.1.1.XX.28.73.78.80.85.84.95.49.95.80.73.68.95.80.82.69.86.73.79.85.83.95.83.69.71.95.78.85.77
-- Vary			: YES
--
-- Value(s)		: <0 to 65535>
--				: WARN:No PID
--				: Info:No PID
--				:
-- Comments		:
--
---------------------------------------------------------------------------------------------------
-- Header		: INPUT_1_EMBED_AUDIO_1_1_LEVEL
--
-- MIB ref		: swCardEventLogSlotXX       .29.73.78.80.85.84.95.49.95.69.77.66.69.68.95.65.85.68.73.79.95.49.95.49.95.76.69.86.69.76
-- absolute OID	: 1.3.6.1.4.1.7995.2.6.1.1.XX.29.73.78.80.85.84.95.49.95.69.77.66.69.68.95.65.85.68.73.79.95.49.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_1_1_STATE
--
-- MIB ref		: swCardEventLogSlotXX       .29.73.78.80.85.84.95.49.95.69.77.66.69.68.95.65.85.68.73.79.95.49.95.49.95.83.84.65.84.69
-- absolute OID	: 1.3.6.1.4.1.7995.2.6.1.1.XX.29.73.78.80.85.84.95.49.95.69.77.66.69.68.95.65.85.68.73.79.95.49.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_1_2_LEVEL
--
-- MIB ref		: swCardEventLogSlotXX       .29.73.78.80.85.84.95.49.95.69.77.66.69.68.95.65.85.68.73.79.95.49.95.50.95.76.69.86.69.76
-- absolute OID	: 1.3.6.1.4.1.7995.2.6.1.1.XX.29.73.78.80.85.84.95.49.95.69.77.66.69.68.95.65.85.68.73.79.95.49.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_1_2_STATE
--
-- MIB ref		: swCardEventLogSlotXX       .29.73.78.80.85.84.95.49.95.69.77.66.69.68.95.65.85.68.73.79.95.49.95.50.95.83.84.65.84.69
-- absolute OID	: 1.3.6.1.4.1.7995.2.6.1.1.XX.29.73.78.80.85.84.95.49.95.69.77.66.69.68.95.65.85.68.73.79.95.49.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_2_1_LEVEL
--
-- MIB ref		: swCardEventLogSlotXX       .29.73.78.80.85.84.95.49.95.69.77.66.69.68.95.65.85.68.73.79.95.50.95.49.95.76.69.86.69.76
-- absolute OID	: 1.3.6.1.4.1.7995.2.6.1.1.XX.29.73.78.80.85.84.95.49.95.69.77.66.69.68.95.65.85.68.73.79.95.50.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_2_1_STATE
--
-- MIB ref		: swCardEventLogSlotXX       .29.73.78.80.85.84.95.49.95.69.77.66.69.68.95.65.85.68.73.79.95.50.95.49.95.83.84.65.84.69
-- absolute OID	: 1.3.6.1.4.1.7995.2.6.1.1.XX.29.73.78.80.85.84.95.49.95.69.77.66.69.68.95.65.85.68.73.79.95.50.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_2_2_LEVEL
--
-- MIB ref		: swCardEventLogSlotXX       .29.73.78.80.85.84.95.49.95.69.77.66.69.68.95.65.85.68.73.79.95.50.95.50.95.76.69.86.69.76
-- absolute OID	: 1.3.6.1.4.1.7995.2.6.1.1.XX.29.73.78.80.85.84.95.49.95.69.77.66.69.68.95.65.85.68.73.79.95.50.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_2_2_STATE
--
-- MIB ref		: swCardEventLogSlotXX       .29.73.78.80.85.84.95.49.95.69.77.66.69.68.95.65.85.68.73.79.95.50.95.50.95.83.84.65.84.69
-- absolute OID	: 1.3.6.1.4.1.7995.2.6.1.1.XX.29.73.78.80.85.84.95.49.95.69.77.66.69.68.95.65.85.68.73.79.95.50.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_3_1_LEVEL
--
-- MIB ref		: swCardEventLogSlotXX       .29.73.78.80.85.84.95.49.95.69.77.66.69.68.95.65.85.68.73.79.95.51.95.49.95.76.69.86.69.76
-- absolute OID	: 1.3.6.1.4.1.7995.2.6.1.1.XX.29.73.78.80.85.84.95.49.95.69.77.66.69.68.95.65.85.68.73.79.95.51.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_3_1_STATE
--
-- MIB ref		: swCardEventLogSlotXX       .29.73.78.80.85.84.95.49.95.69.77.66.69.68.95.65.85.68.73.79.95.51.95.49.95.83.84.65.84.69
-- absolute OID	: 1.3.6.1.4.1.7995.2.6.1.1.XX.29.73.78.80.85.84.95.49.95.69.77.66.69.68.95.65.85.68.73.79.95.51.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_3_2_LEVEL
--
-- MIB ref		: swCardEventLogSlotXX       .29.73.78.80.85.84.95.49.95.69.77.66.69.68.95.65.85.68.73.79.95.51.95.50.95.76.69.86.69.76
-- absolute OID	: 1.3.6.1.4.1.7995.2.6.1.1.XX.29.73.78.80.85.84.95.49.95.69.77.66.69.68.95.65.85.68.73.79.95.51.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_3_2_STATE
--
-- MIB ref		: swCardEventLogSlotXX       .29.73.78.80.85.84.95.49.95.69.77.66.69.68.95.65.85.68.73.79.95.51.95.50.95.83.84.65.84.69
-- absolute OID	: 1.3.6.1.4.1.7995.2.6.1.1.XX.29.73.78.80.85.84.95.49.95.69.77.66.69.68.95.65.85.68.73.79.95.51.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_4_1_LEVEL
--
-- MIB ref		: swCardEventLogSlotXX       .29.73.78.80.85.84.95.49.95.69.77.66.69.68.95.65.85.68.73.79.95.52.95.49.95.76.69.86.69.76
-- absolute OID	: 1.3.6.1.4.1.7995.2.6.1.1.XX.29.73.78.80.85.84.95.49.95.69.77.66.69.68.95.65.85.68.73.79.95.52.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_4_1_STATE
--
-- MIB ref		: swCardEventLogSlotXX       .29.73.78.80.85.84.95.49.95.69.77.66.69.68.95.65.85.68.73.79.95.52.95.49.95.83.84.65.84.69
-- absolute OID	: 1.3.6.1.4.1.7995.2.6.1.1.XX.29.73.78.80.85.84.95.49.95.69.77.66.69.68.95.65.85.68.73.79.95.52.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_4_2_LEVEL
--
-- MIB ref		: swCardEventLogSlotXX       .29.73.78.80.85.84.95.49.95.69.77.66.69.68.95.65.85.68.73.79.95.52.95.50.95.76.69.86.69.76
-- absolute OID	: 1.3.6.1.4.1.7995.2.6.1.1.XX.29.73.78.80.85.84.95.49.95.69.77.66.69.68.95.65.85.68.73.79.95.52.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_4_2_STATE
--
-- MIB ref		: swCardEventLogSlotXX       .29.73.78.80.85.84.95.49.95.69.77.66.69.68.95.65.85.68.73.79.95.52.95.50.95.83.84.65.84.69
-- absolute OID	: 1.3.6.1.4.1.7995.2.6.1.1.XX.29.73.78.80.85.84.95.49.95.69.77.66.69.68.95.65.85.68.73.79.95.52.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_5_1_LEVEL
--
-- MIB ref		: swCardEventLogSlotXX       .29.73.78.80.85.84.95.49.95.69.77.66.69.68.95.65.85.68.73.79.95.53.95.49.95.76.69.86.69.76
-- absolute OID	: 1.3.6.1.4.1.7995.2.6.1.1.XX.29.73.78.80.85.84.95.49.95.69.77.66.69.68.95.65.85.68.73.79.95.53.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_5_1_STATE
--
-- MIB ref		: swCardEventLogSlotXX       .29.73.78.80.85.84.95.49.95.69.77.66.69.68.95.65.85.68.73.79.95.53.95.49.95.83.84.65.84.69
-- absolute OID	: 1.3.6.1.4.1.7995.2.6.1.1.XX.29.73.78.80.85.84.95.49.95.69.77.66.69.68.95.65.85.68.73.79.95.53.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_5_2_LEVEL
--
-- MIB ref		: swCardEventLogSlotXX       .29.73.78.80.85.84.95.49.95.69.77.66.69.68.95.65.85.68.73.79.95.53.95.50.95.76.69.86.69.76
-- absolute OID	: 1.3.6.1.4.1.7995.2.6.1.1.XX.29.73.78.80.85.84.95.49.95.69.77.66.69.68.95.65.85.68.73.79.95.53.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_5_2_STATE
--
-- MIB ref		: swCardEventLogSlotXX       .29.73.78.80.85.84.95.49.95.69.77.66.69.68.95.65.85.68.73.79.95.53.95.50.95.83.84.65.84.69
-- absolute OID	: 1.3.6.1.4.1.7995.2.6.1.1.XX.29.73.78.80.85.84.95.49.95.69.77.66.69.68.95.65.85.68.73.79.95.53.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_6_1_LEVEL
--
-- MIB ref		: swCardEventLogSlotXX       .29.73.78.80.85.84.95.49.95.69.77.66.69.68.95.65.85.68.73.79.95.54.95.49.95.76.69.86.69.76
-- absolute OID	: 1.3.6.1.4.1.7995.2.6.1.1.XX.29.73.78.80.85.84.95.49.95.69.77.66.69.68.95.65.85.68.73.79.95.54.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_6_1_STATE
--
-- MIB ref		: swCardEventLogSlotXX       .29.73.78.80.85.84.95.49.95.69.77.66.69.68.95.65.85.68.73.79.95.54.95.49.95.83.84.65.84.69
-- absolute OID	: 1.3.6.1.4.1.7995.2.6.1.1.XX.29.73.78.80.85.84.95.49.95.69.77.66.69.68.95.65.85.68.73.79.95.54.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_6_2_LEVEL
--
-- MIB ref		: swCardEventLogSlotXX       .29.73.78.80.85.84.95.49.95.69.77.66.69.68.95.65.85.68.73.79.95.54.95.50.95.76.69.86.69.76
-- absolute OID	: 1.3.6.1.4.1.7995.2.6.1.1.XX.29.73.78.80.85.84.95.49.95.69.77.66.69.68.95.65.85.68.73.79.95.54.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_6_2_STATE
--
-- MIB ref		: swCardEventLogSlotXX       .29.73.78.80.85.84.95.49.95.69.77.66.69.68.95.65.85.68.73.79.95.54.95.50.95.83.84.65.84.69
-- absolute OID	: 1.3.6.1.4.1.7995.2.6.1.1.XX.29.73.78.80.85.84.95.49.95.69.77.66.69.68.95.65.85.68.73.79.95.54.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_7_1_LEVEL
--
-- MIB ref		: swCardEventLogSlotXX       .29.73.78.80.85.84.95.49.95.69.77.66.69.68.95.65.85.68.73.79.95.55.95.49.95.76.69.86.69.76
-- absolute OID	: 1.3.6.1.4.1.7995.2.6.1.1.XX.29.73.78.80.85.84.95.49.95.69.77.66.69.68.95.65.85.68.73.79.95.55.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_7_1_STATE
--
-- MIB ref		: swCardEventLogSlotXX       .29.73.78.80.85.84.95.49.95.69.77.66.69.68.95.65.85.68.73.79.95.55.95.49.95.83.84.65.84.69
-- absolute OID	: 1.3.6.1.4.1.7995.2.6.1.1.XX.29.73.78.80.85.84.95.49.95.69.77.66.69.68.95.65.85.68.73.79.95.55.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_7_2_LEVEL
--
-- MIB ref		: swCardEventLogSlotXX       .29.73.78.80.85.84.95.49.95.69.77.66.69.68.95.65.85.68.73.79.95.55.95.50.95.76.69.86.69.76
-- absolute OID	: 1.3.6.1.4.1.7995.2.6.1.1.XX.29.73.78.80.85.84.95.49.95.69.77.66.69.68.95.65.85.68.73.79.95.55.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_7_2_STATE
--
-- MIB ref		: swCardEventLogSlotXX       .29.73.78.80.85.84.95.49.95.69.77.66.69.68.95.65.85.68.73.79.95.55.95.50.95.83.84.65.84.69
-- absolute OID	: 1.3.6.1.4.1.7995.2.6.1.1.XX.29.73.78.80.85.84.95.49.95.69.77.66.69.68.95.65.85.68.73.79.95.55.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_8_1_LEVEL
--
-- MIB ref		: swCardEventLogSlotXX       .29.73.78.80.85.84.95.49.95.69.77.66.69.68.95.65.85.68.73.79.95.56.95.49.95.76.69.86.69.76
-- absolute OID	: 1.3.6.1.4.1.7995.2.6.1.1.XX.29.73.78.80.85.84.95.49.95.69.77.66.69.68.95.65.85.68.73.79.95.56.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--

---------------------------------------------------------------------------------------------------
-- Header		: INPUT_1_EMBED_AUDIO_8_1_STATE
--
-- MIB ref		: swCardEventLogSlotXX       .29.73.78.80.85.84.95.49.95.69.77.66.69.68.95.65.85.68.73.79.95.56.95.49.95.83.84.65.84.69
-- absolute OID	: 1.3.6.1.4.1.7995.2.6.1.1.XX.29.73.78.80.85.84.95.49.95.69.77.66.69.68.95.65.85.68.73.79.95.56.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_8_2_LEVEL
--
-- MIB ref		: swCardEventLogSlotXX       .29.73.78.80.85.84.95.49.95.69.77.66.69.68.95.65.85.68.73.79.95.56.95.50.95.76.69.86.69.76
-- absolute OID	: 1.3.6.1.4.1.7995.2.6.1.1.XX.29.73.78.80.85.84.95.49.95.69.77.66.69.68.95.65.85.68.73.79.95.56.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_8_2_STATE
--
-- MIB ref		: swCardEventLogSlotXX       .29.73.78.80.85.84.95.49.95.69.77.66.69.68.95.65.85.68.73.79.95.56.95.50.95.83.84.65.84.69
-- absolute OID	: 1.3.6.1.4.1.7995.2.6.1.1.XX.29.73.78.80.85.84.95.49.95.69.77.66.69.68.95.65.85.68.73.79.95.56.95.50.95.83.84.65.84.69
-- Vary			: YES
--
-- Value(s)		: OK
--				: WARN:No Input
--				: Info:OK
--				: Info:No Input
--				:
-- Comments		:
--
---------------------------------------------------------------------------------------------------
-- Header		: INPUT_1_PID_PREVIOUS_DURATION
--
-- MIB ref		: swCardEventLogSlotXX       .29.73.78.80.85.84.95.49.95.80.73.68.95.80.82.69.86.73.79.85.83.95.68.85.82.65.84.73.79.78
-- absolute OID	: 1.3.6.1.4.1.7995.2.6.1.1.XX.29.73.78.80.85.84.95.49.95.80.73.68.95.80.82.69.86.73.79.85.83.95.68.85.82.65.84.73.79.78
-- Vary			: YES
--
-- Value(s)		: <0 to 9999999999999999999>
-- Value(s)		: WARN:No PID
-- Value(s)		: Info:No PID
--				:
-- Comments		:
--
---------------------------------------------------------------------------------------------------
-- Header		: INPUT_1_PID_PREVIOUS_HOUSE_ID
--
-- MIB ref		: swCardEventLogSlotXX       .29.73.78.80.85.84.95.49.95.80.73.68.95.80.82.69.86.73.79.85.83.95.72.79.85.83.69.95.73.68
-- absolute OID	: 1.3.6.1.4.1.7995.2.6.1.1.XX.29.73.78.80.85.84.95.49.95.80.73.68.95.80.82.69.86.73.79.85.83.95.72.79.85.83.69.95.73.68
-- Vary			: YES
--
-- Value(s)		: <19 Characters>
--				: WARN:No PID
--				: Info:No PID
--				:
-- Comments		:
--
---------------------------------------------------------------------------------------------------
-- Header		: INPUT_1_USER1_ANC_PACKET_NAME
--
-- MIB ref		: swCardEventLogSlotXX       .29.73.78.80.85.84.95.49.95.85.83.69.82.49.95.65.78.67.95.80.65.67.75.69.84.95.78.65.77.69
-- absolute OID	: 1.3.6.1.4.1.7995.2.6.1.1.XX.29.73.78.80.85.84.95.49.95.85.83.69.82.49.95.65.78.67.95.80.65.67.75.69.84.95.78.65.77.69
-- Vary			: YES
--
-- Value(s)		: <19 Characters>
--				:
-- Comments		: default: User Anc 1
--
---------------------------------------------------------------------------------------------------
-- Header		: INPUT_1_USER2_ANC_PACKET_NAME
--
-- MIB ref		: swCardEventLogSlotXX       .29.73.78.80.85.84.95.49.95.85.83.69.82.50.95.65.78.67.95.80.65.67.75.69.84.95.78.65.77.69
-- absolute OID	: 1.3.6.1.4.1.7995.2.6.1.1.XX.29.73.78.80.85.84.95.49.95.85.83.69.82.50.95.65.78.67.95.80.65.67.75.69.84.95.78.65.77.69
-- Vary			: YES
--
-- Value(s)		: <19 Characters>
--				:
-- Comments		: default: User Anc 2
--
---------------------------------------------------------------------------------------------------
-- Header		: INPUT_1_CONTENT_ADVISORY_STATE
--
-- MIB ref		: swCardEventLogSlotXX       .30.73.78.80.85.84.95.49.95.67.79.78.84.69.78.84.95.65.68.86.73.83.79.82.89.95.83.84.65.84.69
-- absolute OID	: 1.3.6.1.4.1.7995.2.6.1.1.XX.30.73.78.80.85.84.95.49.95.67.79.78.84.69.78.84.95.65.68.86.73.83.79.82.89.95.83.84.65.84.69
-- Vary			: YES
--
-- Value(s)		: OK
--				: FAIL:No CA
--				: Info:OK
--				: Info:No CA
--				:
-- Comments		:
--
---------------------------------------------------------------------------------------------------
-- Header		: INPUT_1_USER1_ANC_PACKET_STATE
--
-- MIB ref		: swCardEventLogSlotXX       .30.73.78.80.85.84.95.49.95.85.83.69.82.49.95.65.78.67.95.80.65.67.75.69.84.95.83.84.65.84.69
-- absolute OID	: 1.3.6.1.4.1.7995.2.6.1.1.XX.30.73.78.80.85.84.95.49.95.85.83.69.82.49.95.65.78.67.95.80.65.67.75.69.84.95.83.84.65.84.69
-- Vary			: YES
--
-- Value(s)		: OK
--				: FAIL:No User1 ANC
--				: Info:OK
--				: Info:No User1 ANC
-- Comments		:
--
---------------------------------------------------------------------------------------------------
-- Header		: INPUT_1_USER2_ANC_PACKET_STATE
--
-- MIB ref		: swCardEventLogSlotXX       .30.73.78.80.85.84.95.49.95.85.83.69.82.50.95.65.78.67.95.80.65.67.75.69.84.95.83.84.65.84.69
-- absolute OID	: 1.3.6.1.4.1.7995.2.6.1.1.XX.30.73.78.80.85.84.95.49.95.85.83.69.82.50.95.65.78.67.95.80.65.67.75.69.84.95.83.84.65.84.69
-- Vary			: YES
--
-- Value(s)		: OK
--				: FAIL:No User2 ANC
--				: Info:OK
--				: Info:No User2 ANC
-- Comments		:
--
---------------------------------------------------------------------------------------------------
-- Header		: INPUT_1_CONTENT_ADVISORY_SYSTEM
--
-- MIB ref		: swCardEventLogSlotXX       .31.73.78.80.85.84.95.49.95.67.79.78.84.69.78.84.95.65.68.86.73.83.79.82.89.95.83.89.83.84.69.77
-- absolute OID	: 1.3.6.1.4.1.7995.2.6.1.1.XX.31.73.78.80.85.84.95.49.95.67.79.78.84.69.78.84.95.65.68.86.73.83.79.82.89.95.83.89.83.84.69.77
-- Vary			: YES
--
-- Value(s)		: -
--				: 0-MPA
--				: 1-US TV PG
--				: 2-MPA
--				: 3-Canadian Eng
--				: 4-Canadian Fr
--				: 5-Reserved
--				: 6-Reserved
--				:
-- Comments		:
--
---------------------------------------------------------------------------------------------------
-- Header		: INPUT_1_EMBED_DOLBY_E_PR1_STATE
--
-- MIB ref		: swCardEventLogSlotXX       .31.73.78.80.85.84.95.49.95.69.77.66.69.68.95.68.79.76.66.89.95.69.95.80.82.49.95.83.84.65.84.69
-- absolute OID	: 1.3.6.1.4.1.7995.2.6.1.1.XX.31.73.78.80.85.84.95.49.95.69.77.66.69.68.95.68.79.76.66.89.95.69.95.80.82.49.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR2_STATE
--
-- MIB ref		: swCardEventLogSlotXX       .31.73.78.80.85.84.95.49.95.69.77.66.69.68.95.68.79.76.66.89.95.69.95.80.82.50.95.83.84.65.84.69
-- absolute OID	: 1.3.6.1.4.1.7995.2.6.1.1.XX.31.73.78.80.85.84.95.49.95.69.77.66.69.68.95.68.79.76.66.89.95.69.95.80.82.50.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR3_STATE
--
-- MIB ref		: swCardEventLogSlotXX       .31.73.78.80.85.84.95.49.95.69.77.66.69.68.95.68.79.76.66.89.95.69.95.80.82.51.95.83.84.65.84.69
-- absolute OID	: 1.3.6.1.4.1.7995.2.6.1.1.XX.31.73.78.80.85.84.95.49.95.69.77.66.69.68.95.68.79.76.66.89.95.69.95.80.82.51.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR4_STATE
--
-- MIB ref		: swCardEventLogSlotXX       .31.73.78.80.85.84.95.49.95.69.77.66.69.68.95.68.79.76.66.89.95.69.95.80.82.52.95.83.84.65.84.69
-- absolute OID	: 1.3.6.1.4.1.7995.2.6.1.1.XX.31.73.78.80.85.84.95.49.95.69.77.66.69.68.95.68.79.76.66.89.95.69.95.80.82.52.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR5_STATE
--
-- MIB ref		: swCardEventLogSlotXX       .31.73.78.80.85.84.95.49.95.69.77.66.69.68.95.68.79.76.66.89.95.69.95.80.82.53.95.83.84.65.84.69
-- absolute OID	: 1.3.6.1.4.1.7995.2.6.1.1.XX.31.73.78.80.85.84.95.49.95.69.77.66.69.68.95.68.79.76.66.89.95.69.95.80.82.53.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR6_STATE
--
-- MIB ref		: swCardEventLogSlotXX       .31.73.78.80.85.84.95.49.95.69.77.66.69.68.95.68.79.76.66.89.95.69.95.80.82.54.95.83.84.65.84.69
-- absolute OID	: 1.3.6.1.4.1.7995.2.6.1.1.XX.31.73.78.80.85.84.95.49.95.69.77.66.69.68.95.68.79.76.66.89.95.69.95.80.82.54.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR7_STATE
--
-- MIB ref		: swCardEventLogSlotXX       .31.73.78.80.85.84.95.49.95.69.77.66.69.68.95.68.79.76.66.89.95.69.95.80.82.55.95.83.84.65.84.69
-- absolute OID	: 1.3.6.1.4.1.7995.2.6.1.1.XX.31.73.78.80.85.84.95.49.95.69.77.66.69.68.95.68.79.76.66.89.95.69.95.80.82.55.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR8_STATE
--
-- MIB ref		: swCardEventLogSlotXX       .31.73.78.80.85.84.95.49.95.69.77.66.69.68.95.68.79.76.66.89.95.69.95.80.82.56.95.83.84.65.84.69
-- absolute OID	: 1.3.6.1.4.1.7995.2.6.1.1.XX.31.73.78.80.85.84.95.49.95.69.77.66.69.68.95.68.79.76.66.89.95.69.95.80.82.56.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_PID_PREVIOUS_FRAME_RATE
--
-- MIB ref		: swCardEventLogSlotXX       .31.73.78.80.85.84.95.49.95.80.73.68.95.80.82.69.86.73.79.85.83.95.70.82.65.77.69.95.82.65.84.69
-- absolute OID	: 1.3.6.1.4.1.7995.2.6.1.1.XX.31.73.78.80.85.84.95.49.95.80.73.68.95.80.82.69.86.73.79.85.83.95.70.82.65.77.69.95.82.65.84.69
-- Vary			: YES
--
-- Value(s)		: 23.976
--				: 24.000
--				: 25.000
--				: 29.970
--				: 30.000
--				: 50.000
--				: 59.940
--				: 60.000
--				: WARN:No PID
--				: Info:No PID
--				:
-- Comments		:
--
---------------------------------------------------------------------------------------------------
-- Header		: INPUT_1_ANCILLARY_TIMECODE_STATE
--
-- MIB ref		: swCardEventLogSlotXX       .32.73.78.80.85.84.95.49.95.65.78.67.73.76.76.65.82.89.95.84.73.77.69.67.79.68.69.95.83.84.65.84.69
-- absolute OID	: 1.3.6.1.4.1.7995.2.6.1.1.XX.32.73.78.80.85.84.95.49.95.65.78.67.73.76.76.65.82.89.95.84.73.77.69.67.79.68.69.95.83.84.65.84.69
-- Vary			: YES
--
-- Value(s)		: Info:No ANC TC
--          Detector not enabled
--              : Info:OK
--              : Info:Checksum Error
--              : Info:No ANC TC Field 1
--              : Info:No ANC TC Field 2
--              : Info:No ANC TC
--
--          Detector enabled
--              : OK
--              : WARN:Checksum Error
--              : WARN:No ANC TC Field 1
--              : WARN:No ANC TC Field 2
--              : FAIL:No ANC TC
-- Comments		:
--
---------------------------------------------------------------------------------------------------
-- Header		: INPUT_1_EMBED_AUDIO_1_1_CLIPPING
--
-- MIB ref		: swCardEventLogSlotXX       .32.73.78.80.85.84.95.49.95.69.77.66.69.68.95.65.85.68.73.79.95.49.95.49.95.67.76.73.80.80.73.78.71
-- absolute OID	: 1.3.6.1.4.1.7995.2.6.1.1.XX.32.73.78.80.85.84.95.49.95.69.77.66.69.68.95.65.85.68.73.79.95.49.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_1_2_CLIPPING
--
-- MIB ref		: swCardEventLogSlotXX       .32.73.78.80.85.84.95.49.95.69.77.66.69.68.95.65.85.68.73.79.95.49.95.50.95.67.76.73.80.80.73.78.71
-- absolute OID	: 1.3.6.1.4.1.7995.2.6.1.1.XX.32.73.78.80.85.84.95.49.95.69.77.66.69.68.95.65.85.68.73.79.95.49.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_2_1_CLIPPING
--
-- MIB ref		: swCardEventLogSlotXX       .32.73.78.80.85.84.95.49.95.69.77.66.69.68.95.65.85.68.73.79.95.50.95.49.95.67.76.73.80.80.73.78.71
-- absolute OID	: 1.3.6.1.4.1.7995.2.6.1.1.XX.32.73.78.80.85.84.95.49.95.69.77.66.69.68.95.65.85.68.73.79.95.50.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_2_2_CLIPPING
--
-- MIB ref		: swCardEventLogSlotXX       .32.73.78.80.85.84.95.49.95.69.77.66.69.68.95.65.85.68.73.79.95.50.95.50.95.67.76.73.80.80.73.78.71
-- absolute OID	: 1.3.6.1.4.1.7995.2.6.1.1.XX.32.73.78.80.85.84.95.49.95.69.77.66.69.68.95.65.85.68.73.79.95.50.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_3_1_CLIPPING
--
-- MIB ref		: swCardEventLogSlotXX       .32.73.78.80.85.84.95.49.95.69.77.66.69.68.95.65.85.68.73.79.95.51.95.49.95.67.76.73.80.80.73.78.71
-- absolute OID	: 1.3.6.1.4.1.7995.2.6.1.1.XX.32.73.78.80.85.84.95.49.95.69.77.66.69.68.95.65.85.68.73.79.95.51.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_3_2_CLIPPING
--
-- MIB ref		: swCardEventLogSlotXX       .32.73.78.80.85.84.95.49.95.69.77.66.69.68.95.65.85.68.73.79.95.51.95.50.95.67.76.73.80.80.73.78.71
-- absolute OID	: 1.3.6.1.4.1.7995.2.6.1.1.XX.32.73.78.80.85.84.95.49.95.69.77.66.69.68.95.65.85.68.73.79.95.51.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_4_1_CLIPPING
--
-- MIB ref		: swCardEventLogSlotXX       .32.73.78.80.85.84.95.49.95.69.77.66.69.68.95.65.85.68.73.79.95.52.95.49.95.67.76.73.80.80.73.78.71
-- absolute OID	: 1.3.6.1.4.1.7995.2.6.1.1.XX.32.73.78.80.85.84.95.49.95.69.77.66.69.68.95.65.85.68.73.79.95.52.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_4_2_CLIPPING
--
-- MIB ref		: swCardEventLogSlotXX       .32.73.78.80.85.84.95.49.95.69.77.66.69.68.95.65.85.68.73.79.95.52.95.50.95.67.76.73.80.80.73.78.71
-- absolute OID	: 1.3.6.1.4.1.7995.2.6.1.1.XX.32.73.78.80.85.84.95.49.95.69.77.66.69.68.95.65.85.68.73.79.95.52.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_5_1_CLIPPING
--
-- MIB ref		: swCardEventLogSlotXX       .32.73.78.80.85.84.95.49.95.69.77.66.69.68.95.65.85.68.73.79.95.53.95.49.95.67.76.73.80.80.73.78.71
-- absolute OID	: 1.3.6.1.4.1.7995.2.6.1.1.XX.32.73.78.80.85.84.95.49.95.69.77.66.69.68.95.65.85.68.73.79.95.53.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_5_2_CLIPPING
--
-- MIB ref		: swCardEventLogSlotXX       .32.73.78.80.85.84.95.49.95.69.77.66.69.68.95.65.85.68.73.79.95.53.95.50.95.67.76.73.80.80.73.78.71
-- absolute OID	: 1.3.6.1.4.1.7995.2.6.1.1.XX.32.73.78.80.85.84.95.49.95.69.77.66.69.68.95.65.85.68.73.79.95.53.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_6_1_CLIPPING
--
-- MIB ref		: swCardEventLogSlotXX       .32.73.78.80.85.84.95.49.95.69.77.66.69.68.95.65.85.68.73.79.95.54.95.49.95.67.76.73.80.80.73.78.71
-- absolute OID	: 1.3.6.1.4.1.7995.2.6.1.1.XX.32.73.78.80.85.84.95.49.95.69.77.66.69.68.95.65.85.68.73.79.95.54.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_6_2_CLIPPING
--
-- MIB ref		: swCardEventLogSlotXX       .32.73.78.80.85.84.95.49.95.69.77.66.69.68.95.65.85.68.73.79.95.54.95.50.95.67.76.73.80.80.73.78.71
-- absolute OID	: 1.3.6.1.4.1.7995.2.6.1.1.XX.32.73.78.80.85.84.95.49.95.69.77.66.69.68.95.65.85.68.73.79.95.54.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_7_1_CLIPPING
--
-- MIB ref		: swCardEventLogSlotXX       .32.73.78.80.85.84.95.49.95.69.77.66.69.68.95.65.85.68.73.79.95.55.95.49.95.67.76.73.80.80.73.78.71
-- absolute OID	: 1.3.6.1.4.1.7995.2.6.1.1.XX.32.73.78.80.85.84.95.49.95.69.77.66.69.68.95.65.85.68.73.79.95.55.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_7_2_CLIPPING
--
-- MIB ref		: swCardEventLogSlotXX       .32.73.78.80.85.84.95.49.95.69.77.66.69.68.95.65.85.68.73.79.95.55.95.50.95.67.76.73.80.80.73.78.71
-- absolute OID	: 1.3.6.1.4.1.7995.2.6.1.1.XX.32.73.78.80.85.84.95.49.95.69.77.66.69.68.95.65.85.68.73.79.95.55.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_8_1_CLIPPING
--
-- MIB ref		: swCardEventLogSlotXX       .32.73.78.80.85.84.95.49.95.69.77.66.69.68.95.65.85.68.73.79.95.56.95.49.95.67.76.73.80.80.73.78.71
-- absolute OID	: 1.3.6.1.4.1.7995.2.6.1.1.XX.32.73.78.80.85.84.95.49.95.69.77.66.69.68.95.65.85.68.73.79.95.56.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_8_2_CLIPPING
--
-- MIB ref		: swCardEventLogSlotXX       .32.73.78.80.85.84.95.49.95.69.77.66.69.68.95.65.85.68.73.79.95.56.95.50.95.67.76.73.80.80.73.78.71
-- absolute OID	: 1.3.6.1.4.1.7995.2.6.1.1.XX.32.73.78.80.85.84.95.49.95.69.77.66.69.68.95.65.85.68.73.79.95.56.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_1_1_BIT_DEPTH
--
-- MIB ref		: swCardEventLogSlotXX       .33.73.78.80.85.84.95.49.95.69.77.66.69.68.95.65.85.68.73.79.95.49.95.49.95.66.73.84.95.68.69.80.84.72
-- absolute OID	: 1.3.6.1.4.1.7995.2.6.1.1.XX.33.73.78.80.85.84.95.49.95.69.77.66.69.68.95.65.85.68.73.79.95.49.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_1_2_BIT_DEPTH
--
-- MIB ref		: swCardEventLogSlotXX       .33.73.78.80.85.84.95.49.95.69.77.66.69.68.95.65.85.68.73.79.95.49.95.50.95.66.73.84.95.68.69.80.84.72
-- absolute OID	: 1.3.6.1.4.1.7995.2.6.1.1.XX.33.73.78.80.85.84.95.49.95.69.77.66.69.68.95.65.85.68.73.79.95.49.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_2_1_BIT_DEPTH
--
-- MIB ref		: swCardEventLogSlotXX       .33.73.78.80.85.84.95.49.95.69.77.66.69.68.95.65.85.68.73.79.95.50.95.49.95.66.73.84.95.68.69.80.84.72
-- absolute OID	: 1.3.6.1.4.1.7995.2.6.1.1.XX.33.73.78.80.85.84.95.49.95.69.77.66.69.68.95.65.85.68.73.79.95.50.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_2_2_BIT_DEPTH
--
-- MIB ref		: swCardEventLogSlotXX       .33.73.78.80.85.84.95.49.95.69.77.66.69.68.95.65.85.68.73.79.95.50.95.50.95.66.73.84.95.68.69.80.84.72
-- absolute OID	: 1.3.6.1.4.1.7995.2.6.1.1.XX.33.73.78.80.85.84.95.49.95.69.77.66.69.68.95.65.85.68.73.79.95.50.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_3_1_BIT_DEPTH
--
-- MIB ref		: swCardEventLogSlotXX       .33.73.78.80.85.84.95.49.95.69.77.66.69.68.95.65.85.68.73.79.95.51.95.49.95.66.73.84.95.68.69.80.84.72
-- absolute OID	: 1.3.6.1.4.1.7995.2.6.1.1.XX.33.73.78.80.85.84.95.49.95.69.77.66.69.68.95.65.85.68.73.79.95.51.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_3_2_BIT_DEPTH
--
-- MIB ref		: swCardEventLogSlotXX       .33.73.78.80.85.84.95.49.95.69.77.66.69.68.95.65.85.68.73.79.95.51.95.50.95.66.73.84.95.68.69.80.84.72
-- absolute OID	: 1.3.6.1.4.1.7995.2.6.1.1.XX.33.73.78.80.85.84.95.49.95.69.77.66.69.68.95.65.85.68.73.79.95.51.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_4_1_BIT_DEPTH
--
-- MIB ref		: swCardEventLogSlotXX       .33.73.78.80.85.84.95.49.95.69.77.66.69.68.95.65.85.68.73.79.95.52.95.49.95.66.73.84.95.68.69.80.84.72
-- absolute OID	: 1.3.6.1.4.1.7995.2.6.1.1.XX.33.73.78.80.85.84.95.49.95.69.77.66.69.68.95.65.85.68.73.79.95.52.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_4_2_BIT_DEPTH
--
-- MIB ref		: swCardEventLogSlotXX       .33.73.78.80.85.84.95.49.95.69.77.66.69.68.95.65.85.68.73.79.95.52.95.50.95.66.73.84.95.68.69.80.84.72
-- absolute OID	: 1.3.6.1.4.1.7995.2.6.1.1.XX.33.73.78.80.85.84.95.49.95.69.77.66.69.68.95.65.85.68.73.79.95.52.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_5_1_BIT_DEPTH
--
-- MIB ref		: swCardEventLogSlotXX       .33.73.78.80.85.84.95.49.95.69.77.66.69.68.95.65.85.68.73.79.95.53.95.49.95.66.73.84.95.68.69.80.84.72
-- absolute OID	: 1.3.6.1.4.1.7995.2.6.1.1.XX.33.73.78.80.85.84.95.49.95.69.77.66.69.68.95.65.85.68.73.79.95.53.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_5_2_BIT_DEPTH
--
-- MIB ref		: swCardEventLogSlotXX       .33.73.78.80.85.84.95.49.95.69.77.66.69.68.95.65.85.68.73.79.95.53.95.50.95.66.73.84.95.68.69.80.84.72
-- absolute OID	: 1.3.6.1.4.1.7995.2.6.1.1.XX.33.73.78.80.85.84.95.49.95.69.77.66.69.68.95.65.85.68.73.79.95.53.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_6_1_BIT_DEPTH
--
-- MIB ref		: swCardEventLogSlotXX       .33.73.78.80.85.84.95.49.95.69.77.66.69.68.95.65.85.68.73.79.95.54.95.49.95.66.73.84.95.68.69.80.84.72
-- absolute OID	: 1.3.6.1.4.1.7995.2.6.1.1.XX.33.73.78.80.85.84.95.49.95.69.77.66.69.68.95.65.85.68.73.79.95.54.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_6_2_BIT_DEPTH
--
-- MIB ref		: swCardEventLogSlotXX       .33.73.78.80.85.84.95.49.95.69.77.66.69.68.95.65.85.68.73.79.95.54.95.50.95.66.73.84.95.68.69.80.84.72
-- absolute OID	: 1.3.6.1.4.1.7995.2.6.1.1.XX.33.73.78.80.85.84.95.49.95.69.77.66.69.68.95.65.85.68.73.79.95.54.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_7_1_BIT_DEPTH
--
-- MIB ref		: swCardEventLogSlotXX       .33.73.78.80.85.84.95.49.95.69.77.66.69.68.95.65.85.68.73.79.95.55.95.49.95.66.73.84.95.68.69.80.84.72
-- absolute OID	: 1.3.6.1.4.1.7995.2.6.1.1.XX.33.73.78.80.85.84.95.49.95.69.77.66.69.68.95.65.85.68.73.79.95.55.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_7_2_BIT_DEPTH
--
-- MIB ref		: swCardEventLogSlotXX       .33.73.78.80.85.84.95.49.95.69.77.66.69.68.95.65.85.68.73.79.95.55.95.50.95.66.73.84.95.68.69.80.84.72
-- absolute OID	: 1.3.6.1.4.1.7995.2.6.1.1.XX.33.73.78.80.85.84.95.49.95.69.77.66.69.68.95.65.85.68.73.79.95.55.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_8_1_BIT_DEPTH
--
-- MIB ref		: swCardEventLogSlotXX       .33.73.78.80.85.84.95.49.95.69.77.66.69.68.95.65.85.68.73.79.95.56.95.49.95.66.73.84.95.68.69.80.84.72
-- absolute OID	: 1.3.6.1.4.1.7995.2.6.1.1.XX.33.73.78.80.85.84.95.49.95.69.77.66.69.68.95.65.85.68.73.79.95.56.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_8_2_BIT_DEPTH
--
-- MIB ref		: swCardEventLogSlotXX       .33.73.78.80.85.84.95.49.95.69.77.66.69.68.95.65.85.68.73.79.95.56.95.50.95.66.73.84.95.68.69.80.84.72
-- absolute OID	: 1.3.6.1.4.1.7995.2.6.1.1.XX.33.73.78.80.85.84.95.49.95.69.77.66.69.68.95.65.85.68.73.79.95.56.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_UMID_PREVIOUS_FRAME_COUNT
--
-- MIB ref		: swCardEventLogSlotXX       .33.73.78.80.85.84.95.49.95.85.77.73.68.95.80.82.69.86.73.79.85.83.95.70.82.65.77.69.95.67.79.85.78.84
-- absolute OID	: 1.3.6.1.4.1.7995.2.6.1.1.XX.33.73.78.80.85.84.95.49.95.85.77.73.68.95.80.82.69.86.73.79.85.83.95.70.82.65.77.69.95.67.79.85.78.84
-- Vary			: YES
--
-- Value(s)		: -
--				: <100 to 4294967295>
--				:
-- Comments		:
--
---------------------------------------------------------------------------------------------------
-- Header		: INPUT_1_CONTENT_ADVISORY_AGE_RATING
--
-- MIB ref		: swCardEventLogSlotXX       .35.73.78.80.85.84.95.49.95.67.79.78.84.69.78.84.95.65.68.86.73.83.79.82.89.95.65.71.69.95.82.65.84.73.78.71
-- absolute OID	: 1.3.6.1.4.1.7995.2.6.1.1.XX.35.73.78.80.85.84.95.49.95.67.79.78.84.69.78.84.95.65.68.86.73.83.79.82.89.95.65.71.69.95.82.65.84.73.78.71
-- Vary			: YES
--
-- Value(s)		: -
-- Comments		:   For  INPUT_1_CONTENT_ADVISORY_SYSTEM=0-MP
--				:   or   INPUT_1_CONTENT_ADVISORY_SYSTEM=2-MP
--
--				: N/A
--				: G
--				: PG
--				: PG-13
--				: R
--				: NC-17
--				: X
--				: Not Rated
--
-- Comments		:   For INPUT_1_CONTENT_ADVISORY_SYSTEM=1-US TV PG
--				:   (If there is one or more Letters in brackets,
--				:         this shows addition Guidance.)
--
--				: None
--				: TV-Y
--				: TV-Y7 ( FV)
--				: TV-G
--				: TV-PG ( V S L D}
--				: TV-14 ( V S L D}
--				: TV-MA ( L S V}
--				: None
--
--				:   where:
--				:       FV = Fantasy Violence
--				:       V  = Violence
--				:       S  = Sexual Situations
--				:       L  = Adult Language
--				:       D  = Sexually Suggestive Dialog
--
-- Comments		:   For INPUT_1_CONTENT_ADVISORY_SYSTEM=3-Canadian Eng
--				: E
--				: C
--				: C8+
--				: G
--				: PG
--				: 14+
--				: 18+
--
-- Comments		:   For INPUT_1_CONTENT_ADVISORY_SYSTEM=4-Canadian Fr
--				: E
--				: G
--				: 8ans+
--				: 13ans+
--				: 16ans+
--				: 18ans+
--				:
--

---------------------------------------------------------------------------------------------------
-- Header		: INPUT_1_EMBEDDED_AUDIO_LIKE_1_CHANS
--
-- MIB ref		: swCardEventLogSlotXX       .35.73.78.80.85.84.95.49.95.69.77.66.69.68.68.69.68.95.65.85.68.73.79.95.76.73.75.69.95.49.95.67.72.65.78.83
-- absolute OID	: 1.3.6.1.4.1.7995.2.6.1.1.XX.35.73.78.80.85.84.95.49.95.69.77.66.69.68.68.69.68.95.65.85.68.73.79.95.76.73.75.69.95.49.95.67.72.65.78.83
-- Vary			: YES
--
-- Value(s)		: ChX+Y
--				:
-- Comments		: Where X and Y are the channel numbers being compared in the range 1 to 16
--              : Default- Ch1+2
---------------------------------------------------------------------------------------------------
-- Header		: INPUT_1_EMBEDDED_AUDIO_LIKE_1_STATE
--
-- MIB ref		: swCardEventLogSlotXX       .35.73.78.80.85.84.95.49.95.69.77.66.69.68.68.69.68.95.65.85.68.73.79.95.76.73.75.69.95.49.95.83.84.65.84.69
-- absolute OID	: 1.3.6.1.4.1.7995.2.6.1.1.XX.35.73.78.80.85.84.95.49.95.69.77.66.69.68.68.69.68.95.65.85.68.73.79.95.76.73.75.69.95.49.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
-- Header		: INPUT_1_EMBEDDED_AUDIO_LIKE_2_CHANS
--
-- MIB ref		: swCardEventLogSlotXX       .35.73.78.80.85.84.95.49.95.69.77.66.69.68.68.69.68.95.65.85.68.73.79.95.76.73.75.69.95.50.95.67.72.65.78.83
-- absolute OID	: 1.3.6.1.4.1.7995.2.6.1.1.XX.35.73.78.80.85.84.95.49.95.69.77.66.69.68.68.69.68.95.65.85.68.73.79.95.76.73.75.69.95.50.95.67.72.65.78.83
-- Vary			: YES
--
-- Value(s)		: ChX+Y
--				:
-- Comments		: Where X and Y are the channel numbers being compared in the range 1 to 16
--              : Default- Ch3+4
---------------------------------------------------------------------------------------------------
-- Header		: INPUT_1_EMBEDDED_AUDIO_LIKE_2_STATE
--
-- MIB ref		: swCardEventLogSlotXX       .35.73.78.80.85.84.95.49.95.69.77.66.69.68.68.69.68.95.65.85.68.73.79.95.76.73.75.69.95.50.95.83.84.65.84.69
-- absolute OID	: 1.3.6.1.4.1.7995.2.6.1.1.XX.35.73.78.80.85.84.95.49.95.69.77.66.69.68.68.69.68.95.65.85.68.73.79.95.76.73.75.69.95.50.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
-- Header		: INPUT_1_EMBEDDED_AUDIO_LIKE_3_CHANS
--
-- MIB ref		: swCardEventLogSlotXX       .35.73.78.80.85.84.95.49.95.69.77.66.69.68.68.69.68.95.65.85.68.73.79.95.76.73.75.69.95.51.95.67.72.65.78.83
-- absolute OID	: 1.3.6.1.4.1.7995.2.6.1.1.XX.35.73.78.80.85.84.95.49.95.69.77.66.69.68.68.69.68.95.65.85.68.73.79.95.76.73.75.69.95.51.95.67.72.65.78.83
-- Vary			: YES
--
-- Value(s)		: ChX+Y
--				:
-- Comments		: Where X and Y are the channel numbers being compared in the range 1 to 16
--              : Default- Ch5+6
---------------------------------------------------------------------------------------------------
-- Header		: INPUT_1_EMBEDDED_AUDIO_LIKE_3_STATE
--
-- MIB ref		: swCardEventLogSlotXX       .35.73.78.80.85.84.95.49.95.69.77.66.69.68.68.69.68.95.65.85.68.73.79.95.76.73.75.69.95.51.95.83.84.65.84.69
-- absolute OID	: 1.3.6.1.4.1.7995.2.6.1.1.XX.35.73.78.80.85.84.95.49.95.69.77.66.69.68.68.69.68.95.65.85.68.73.79.95.76.73.75.69.95.51.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
-- Header		: INPUT_1_EMBEDDED_AUDIO_LIKE_4_CHANS
--
-- MIB ref		: swCardEventLogSlotXX       .35.73.78.80.85.84.95.49.95.69.77.66.69.68.68.69.68.95.65.85.68.73.79.95.76.73.75.69.95.52.95.67.72.65.78.83
-- absolute OID	: 1.3.6.1.4.1.7995.2.6.1.1.XX.35.73.78.80.85.84.95.49.95.69.77.66.69.68.68.69.68.95.65.85.68.73.79.95.76.73.75.69.95.52.95.67.72.65.78.83
-- Vary			: YES
--
-- Value(s)		: ChX+Y
--				:
-- Comments		: Where X and Y are the channel numbers being compared in the range 1 to 16
--              : Default- Ch7+8

---------------------------------------------------------------------------------------------------
-- Header		: INPUT_1_EMBEDDED_AUDIO_LIKE_4_STATE
--
-- MIB ref		: swCardEventLogSlotXX       .35.73.78.80.85.84.95.49.95.69.77.66.69.68.68.69.68.95.65.85.68.73.79.95.76.73.75.69.95.52.95.83.84.65.84.69
-- absolute OID	: 1.3.6.1.4.1.7995.2.6.1.1.XX.35.73.78.80.85.84.95.49.95.69.77.66.69.68.68.69.68.95.65.85.68.73.79.95.76.73.75.69.95.52.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
