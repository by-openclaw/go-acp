-- ************************************************************************************
-- Snell&Wilcox Card:IQDRT8
--        Module Id#:158
--       Command Set:7
--          Filename:SNELL-IQDRT8-CMD-MIB.mib
--            Author:Jonathan Riches
--              Date:30/06/2005
--              Time:15:32
--
-- Copyright (c) 2005 Snell & Wilcox Ltd
-- All rights reserved.
--
-- ************************************************************************************

SNELL-IQDRT8-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDRT8,
    moduleIQDRT8MIB
        FROM SNELL-WILCOX-PRODUCT-REG;

 moduleIQDRT8CmdMi MODULE-IDENTITY
    LAST-UPDATED "0506301532Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDRT8MIB 1 }




--********************************************************************************
--*
--*  Snell Wilcox Card:
--*  command set:
--*  list commands/menus:
--*
--******************************************************************************
	iqdrt8CmdTable OBJECT-TYPE
		SYNTAX			SEQUENCE OF Iqdrt8CmdEntry
		MAX-ACCESS		not-accessible
		STATUS			current
		DESCRIPTION
				"Note the instance of this table is relected in the command set Version"
		::= { moduleIQDRT8 1 }

	iqdrt8CmdEntry OBJECT-TYPE
		SYNTAX		Iqdrt8CmdEntry
		MAX-ACCESS		not-accessible
		STATUS			current
		DESCRIPTION
				"Entry in command table."
		INDEX	{ iqdrt8SlotIndex }
		::= { iqdrt8CmdTable 1 }

	Iqdrt8CmdEntry ::=
		SEQUENCE {
			iqdrt8SlotIndex
				Unsigned32,
			iqdrt8CrosspointRouterDest1
				INTEGER,
			iqdrt8CrosspointRouterDest2
				INTEGER,
			iqdrt8CrosspointRouterDest3
				INTEGER,
			iqdrt8CrosspointRouterDest4
				INTEGER,
			iqdrt8CrosspointRouterDest5
				INTEGER,
			iqdrt8CrosspointRouterDest6
				INTEGER,
			iqdrt8CrosspointRouterDest7
				INTEGER,
			iqdrt8CrosspointRouterDest8
				INTEGER,
			iqdrt8CrosspointMonitor
				INTEGER,
			iqdrt8CrosspointTake
				INTEGER,
			iqdrt8CrosspointCancel
				INTEGER,
			iqdrt8CrosspointProtectDest1
				INTEGER,
			iqdrt8CrosspointProtectDest2
				INTEGER,
			iqdrt8CrosspointProtectDest3
				INTEGER,
			iqdrt8CrosspointProtectDest4
				INTEGER,
			iqdrt8CrosspointProtectDest5
				INTEGER,
			iqdrt8CrosspointProtectDest6
				INTEGER,
			iqdrt8CrosspointProtectDest7
				INTEGER,
			iqdrt8CrosspointProtectDest8
				INTEGER,
			iqdrt8CrosspointEnableTake
				INTEGER,
			iqdrt8DisplayPrev
				INTEGER,
			iqdrt8DisplayNext
				INTEGER,
			iqdrt8Display
				INTEGER,
			iqdrt8DisplayInputStatusInput1
				RollCallString,
			iqdrt8DisplayInputStatusInput2
				RollCallString,
			iqdrt8DisplayInputStatusInput3
				RollCallString,
			iqdrt8DisplayInputStatusInput4
				RollCallString,
			iqdrt8DisplayInputStatusInput5
				RollCallString,
			iqdrt8DisplayInputStatusInput6
				RollCallString,
			iqdrt8DisplayInputStatusInput7
				RollCallString,
			iqdrt8DisplayInputStatusInput8
				RollCallString,
			iqdrt8MemoriesRecall
				INTEGER,
			iqdrt8MemoriesNamesMemory1
				RollCallString,
			iqdrt8MemoriesNamesMemory2
				RollCallString,
			iqdrt8MemoriesNamesMemory3
				RollCallString,
			iqdrt8MemoriesNamesMemory4
				RollCallString,
			iqdrt8MemoriesNamesMemory5
				RollCallString,
			iqdrt8MemoriesNamesMemory6
				RollCallString,
			iqdrt8MemoriesNamesMemory7
				RollCallString,
			iqdrt8MemoriesNamesMemory8
				RollCallString,
			iqdrt8MemoriesNamesPreset
				INTEGER,
			iqdrt8MemoriesSave
				INTEGER,
			iqdrt8RollTrackDest1
				RollCallString,
			iqdrt8RollTrackDest2
				RollCallString,
			iqdrt8RollTrackDest3
				RollCallString,
			iqdrt8RollTrackDest4
				RollCallString,
			iqdrt8RollTrackDest5
				RollCallString,
			iqdrt8RollTrackDest6
				RollCallString,
			iqdrt8RollTrackDest7
				RollCallString,
			iqdrt8RollTrackDest8
				RollCallString,
			iqdrt8RollTrackRollTrackMessages
				INTEGER,
			iqdrt8NameAssocSourceSource1
				RollCallString,
			iqdrt8NameAssocSourceSource2
				RollCallString,
			iqdrt8NameAssocSourceSource3
				RollCallString,
			iqdrt8NameAssocSourceSource4
				RollCallString,
			iqdrt8NameAssocSourceSource5
				RollCallString,
			iqdrt8NameAssocSourceSource6
				RollCallString,
			iqdrt8NameAssocSourceSource7
				RollCallString,
			iqdrt8NameAssocSourceSource8
				RollCallString,
			iqdrt8NameAssocDestinationDest1
				RollCallString,
			iqdrt8NameAssocDestinationDest2
				RollCallString,
			iqdrt8NameAssocDestinationDest3
				RollCallString,
			iqdrt8NameAssocDestinationDest4
				RollCallString,
			iqdrt8NameAssocDestinationDest5
				RollCallString,
			iqdrt8NameAssocDestinationDest6
				RollCallString,
			iqdrt8NameAssocDestinationDest7
				RollCallString,
			iqdrt8NameAssocDestinationDest8
				RollCallString,
			iqdrt8SetupSwitchingPoint
				INTEGER,
			iqdrt8LoggingInputsInput1
				INTEGER,
			iqdrt8LoggingInputsInput2
				INTEGER,
			iqdrt8LoggingInputsInput3
				INTEGER,
			iqdrt8LoggingInputsInput4
				INTEGER,
			iqdrt8LoggingInputsInput5
				INTEGER,
			iqdrt8LoggingInputsInput6
				INTEGER,
			iqdrt8LoggingInputsInput7
				INTEGER,
			iqdrt8LoggingInputsInput8
				INTEGER,
			iqdrt8SetupLoggingOutputs
				INTEGER,
			iqdrt8SetupLoggingVideoRef
				INTEGER,
			iqdrt8SetupPresetUnit
				INTEGER,
			iqdrt8SetupSoftwareVersion
				RollCallString,
			iqdrt8SetupSerialNo
				RollCallString,
			iqdrt8SetupBuildNo
				RollCallString,
			iqdrt8SetupRestart
				INTEGER
		}

	iqdrt8SlotIndex OBJECT-TYPE
		SYNTAX		Unsigned32
		MAX-ACCESS		not-accessible
		STATUS			current
		DESCRIPTION
				"The unique Index value for each slot.  Its value
					ranges between 1 and the value of slotNumber."
		::= { iqdrt8CmdEntry 0 }


	iqdrt8CrosspointRouterDest1 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_1  cmdID= 8 
					Source_1*  value= 0  
					Source_2*  value= 1  
					Source_3*  value= 2  
					Source_4*  value= 3  
					Source_5*  value= 4  
					Source_6*  value= 5  
					Source_7*  value= 6  
					Source_8*  value= 7  "
		::= { iqdrt8CmdEntry 8 }


	iqdrt8CrosspointRouterDest2 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_2  cmdID= 9 
					Source_1*  value= 0  
					Source_2*  value= 1  
					Source_3*  value= 2  
					Source_4*  value= 3  
					Source_5*  value= 4  
					Source_6*  value= 5  
					Source_7*  value= 6  
					Source_8*  value= 7  "
		::= { iqdrt8CmdEntry 9 }


	iqdrt8CrosspointRouterDest3 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_3  cmdID= 10 
					Source_1*  value= 0  
					Source_2*  value= 1  
					Source_3*  value= 2  
					Source_4*  value= 3  
					Source_5*  value= 4  
					Source_6*  value= 5  
					Source_7*  value= 6  
					Source_8*  value= 7  "
		::= { iqdrt8CmdEntry 10 }


	iqdrt8CrosspointRouterDest4 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_4  cmdID= 11 
					Source_1*  value= 0  
					Source_2*  value= 1  
					Source_3*  value= 2  
					Source_4*  value= 3  
					Source_5*  value= 4  
					Source_6*  value= 5  
					Source_7*  value= 6  
					Source_8*  value= 7  "
		::= { iqdrt8CmdEntry 11 }


	iqdrt8CrosspointRouterDest5 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_5  cmdID= 12 
					Source_1*  value= 0  
					Source_2*  value= 1  
					Source_3*  value= 2  
					Source_4*  value= 3  
					Source_5*  value= 4  
					Source_6*  value= 5  
					Source_7*  value= 6  
					Source_8*  value= 7  "
		::= { iqdrt8CmdEntry 12 }


	iqdrt8CrosspointRouterDest6 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_6  cmdID= 13 
					Source_1*  value= 0  
					Source_2*  value= 1  
					Source_3*  value= 2  
					Source_4*  value= 3  
					Source_5*  value= 4  
					Source_6*  value= 5  
					Source_7*  value= 6  
					Source_8*  value= 7  "
		::= { iqdrt8CmdEntry 13 }


	iqdrt8CrosspointRouterDest7 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_7  cmdID= 14 
					Source_1*  value= 0  
					Source_2*  value= 1  
					Source_3*  value= 2  
					Source_4*  value= 3  
					Source_5*  value= 4  
					Source_6*  value= 5  
					Source_7*  value= 6  
					Source_8*  value= 7  "
		::= { iqdrt8CmdEntry 14 }


	iqdrt8CrosspointRouterDest8 OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Router
					Dest_8  cmdID= 15 
					Source_1*  value= 0  
					Source_2*  value= 1  
					Source_3*  value= 2  
					Source_4*  value= 3  
					Source_5*  value= 4  
					Source_6*  value= 5  
					Source_7*  value= 6  
					Source_8*  value= 7  "
		::= { iqdrt8CmdEntry 15 }


	iqdrt8CrosspointMonitor OBJECT-TYPE
		SYNTAX		INTEGER {
							val_Source_1(0),
							val_Source_2(1),
							val_Source_3(2),
							val_Source_4(3),
							val_Source_5(4),
							val_Source_6(5),
							val_Source_7(6),
							val_Source_8(7)
							}
		MAX-ACCESS		read-write
		STATUS			current
		DESCRIPTION
				"TYPE: - RadiobuttonList
				 PAGE: - Monitor
					Monitor  cmdID= 103 
					Source_1  value= 0  
					Source_2  value= 1  
					Source_3  value= 2  
					Source_4  value= 3  
					Source_5  value= 4  
					Source_6  value= 5  
					Source_7  value= 6  
					Source_8  value= 7  "
		::= { iqdrt8CmdEntry 103 }


	iqdrt8CrosspointTake OBJECT-TYPE
		SYNTAX		INTEGER { noAction(0),val_Take(1) }
		MAX-ACCESS		read-write
		STATUS			current
		DESCRIPTION
				"TYPE: - Button
					Take!  cmdID= 101  value= 1  "
		::= { iqdrt8CmdEntry 101 }


	iqdrt8CrosspointCancel OBJECT-TYPE
		SYNTAX		INTEGER { noAction(0),val_Cancel(1) }
		MAX-ACCESS		read-write
		STATUS			current
		DESCRIPTION
				"TYPE: - Button
					Cancel!  cmdID= 102  value= 1  "
		::= { iqdrt8CmdEntry 102 }


	iqdrt8CrosspointProtectDest1 OBJECT-TYPE
		SYNTAX		INTEGER { disable(0), enable(1) }
		MAX-ACCESS		read-write
		STATUS			current
		DESCRIPTION
				"TYPE: - Checkbox
				 PAGE: - Protect
					Dest_1  cmdID= 176 "
		::= { iqdrt8CmdEntry 176 }


	iqdrt8CrosspointProtectDest2 OBJECT-TYPE
		SYNTAX		INTEGER { disable(0), enable(1) }
		MAX-ACCESS		read-write
		STATUS			current
		DESCRIPTION
				"TYPE: - Checkbox
				 PAGE: - Protect
					Dest_2  cmdID= 177 "
		::= { iqdrt8CmdEntry 177 }


	iqdrt8CrosspointProtectDest3 OBJECT-TYPE
		SYNTAX		INTEGER { disable(0), enable(1) }
		MAX-ACCESS		read-write
		STATUS			current
		DESCRIPTION
				"TYPE: - Checkbox
				 PAGE: - Protect
					Dest_3  cmdID= 178 "
		::= { iqdrt8CmdEntry 178 }


	iqdrt8CrosspointProtectDest4 OBJECT-TYPE
		SYNTAX		INTEGER { disable(0), enable(1) }
		MAX-ACCESS		read-write
		STATUS			current
		DESCRIPTION
				"TYPE: - Checkbox
				 PAGE: - Protect
					Dest_4  cmdID= 179 "
		::= { iqdrt8CmdEntry 179 }


	iqdrt8CrosspointProtectDest5 OBJECT-TYPE
		SYNTAX		INTEGER { disable(0), enable(1) }
		MAX-ACCESS		read-write
		STATUS			current
		DESCRIPTION
				"TYPE: - Checkbox
				 PAGE: - Protect
					Dest_5  cmdID= 180 "
		::= { iqdrt8CmdEntry 180 }


	iqdrt8CrosspointProtectDest6 OBJECT-TYPE
		SYNTAX		INTEGER { disable(0), enable(1) }
		MAX-ACCESS		read-write
		STATUS			current
		DESCRIPTION
				"TYPE: - Checkbox
				 PAGE: - Protect
					Dest_6  cmdID= 181 "
		::= { iqdrt8CmdEntry 181 }


	iqdrt8CrosspointProtectDest7 OBJECT-TYPE
		SYNTAX		INTEGER { disable(0), enable(1) }
		MAX-ACCESS		read-write
		STATUS			current
		DESCRIPTION
				"TYPE: - Checkbox
				 PAGE: - Protect
					Dest_7  cmdID= 182 "
		::= { iqdrt8CmdEntry 182 }


	iqdrt8CrosspointProtectDest8 OBJECT-TYPE
		SYNTAX		INTEGER { disable(0), enable(1) }
		MAX-ACCESS		read-write
		STATUS			current
		DESCRIPTION
				"TYPE: - Checkbox
				 PAGE: - Protect
					Dest_8  cmdID= 183 "
		::= { iqdrt8CmdEntry 183 }


	iqdrt8CrosspointEnableTake OBJECT-TYPE
		SYNTAX		INTEGER { disable(0), enable(1) }
		MAX-ACCESS		read-write
		STATUS			current
		DESCRIPTION
				"TYPE: - Checkbox
					Enable_Take  cmdID= 104 "
		::= { iqdrt8CmdEntry 104 }


	iqdrt8DisplayPrev OBJECT-TYPE
		SYNTAX		INTEGER { noAction(0),val_Prev(1) }
		MAX-ACCESS		read-write
		STATUS			current
		DESCRIPTION
				"TYPE: - Button
				 PAGE: - Display
					Prev  cmdID= 124  value= 1  "
		::= { iqdrt8CmdEntry 124 }


	iqdrt8DisplayNext OBJECT-TYPE
		SYNTAX		INTEGER { noAction(0),val_Next(1) }
		MAX-ACCESS		read-write
		STATUS			current
		DESCRIPTION
				"TYPE: - Button
				 PAGE: - Display
					Next  cmdID= 125  value= 1  "
		::= { iqdrt8CmdEntry 125 }


	iqdrt8Display OBJECT-TYPE
		SYNTAX		INTEGER {
							val_Input_Status(0),
							val_Output_Status(1)
							}
		MAX-ACCESS		read-write
		STATUS			current
		DESCRIPTION
				"TYPE: - Button
				 PAGE: - Display
					Input_Status  cmdID= 7  value= 0  
					Output_Status  cmdID= 7  value= 1  "
		::= { iqdrt8CmdEntry 7 }


	iqdrt8DisplayInputStatusInput1 OBJECT-TYPE
		SYNTAX		RollCallString
		MAX-ACCESS		read-only
		STATUS			current
		DESCRIPTION
				"TYPE: - Display
				 PAGE: - Display- Input_Status
					Input_1  cmdID= 188  format=   "
		::= { iqdrt8CmdEntry 188 }


	iqdrt8DisplayInputStatusInput2 OBJECT-TYPE
		SYNTAX		RollCallString
		MAX-ACCESS		read-only
		STATUS			current
		DESCRIPTION
				"TYPE: - Display
				 PAGE: - Display- Input_Status
					Input_2  cmdID= 189  format=   "
		::= { iqdrt8CmdEntry 189 }


	iqdrt8DisplayInputStatusInput3 OBJECT-TYPE
		SYNTAX		RollCallString
		MAX-ACCESS		read-only
		STATUS			current
		DESCRIPTION
				"TYPE: - Display
				 PAGE: - Display- Input_Status
					Input_3  cmdID= 190  format=   "
		::= { iqdrt8CmdEntry 190 }


	iqdrt8DisplayInputStatusInput4 OBJECT-TYPE
		SYNTAX		RollCallString
		MAX-ACCESS		read-only
		STATUS			current
		DESCRIPTION
				"TYPE: - Display
				 PAGE: - Display- Input_Status
					Input_4  cmdID= 191  format=   "
		::= { iqdrt8CmdEntry 191 }


	iqdrt8DisplayInputStatusInput5 OBJECT-TYPE
		SYNTAX		RollCallString
		MAX-ACCESS		read-only
		STATUS			current
		DESCRIPTION
				"TYPE: - Display
				 PAGE: - Display- Input_Status
					Input_5  cmdID= 192  format=   "
		::= { iqdrt8CmdEntry 192 }


	iqdrt8DisplayInputStatusInput6 OBJECT-TYPE
		SYNTAX		RollCallString
		MAX-ACCESS		read-only
		STATUS			current
		DESCRIPTION
				"TYPE: - Display
				 PAGE: - Display- Input_Status
					Input_6  cmdID= 193  format=   "
		::= { iqdrt8CmdEntry 193 }


	iqdrt8DisplayInputStatusInput7 OBJECT-TYPE
		SYNTAX		RollCallString
		MAX-ACCESS		read-only
		STATUS			current
		DESCRIPTION
				"TYPE: - Display
				 PAGE: - Display- Input_Status
					Input_7  cmdID= 194  format=   "
		::= { iqdrt8CmdEntry 194 }


	iqdrt8DisplayInputStatusInput8 OBJECT-TYPE
		SYNTAX		RollCallString
		MAX-ACCESS		read-only
		STATUS			current
		DESCRIPTION
				"TYPE: - Display
				 PAGE: - Display- Input_Status
					Input_8  cmdID= 195  format=   "
		::= { iqdrt8CmdEntry 195 }


	iqdrt8MemoriesRecall OBJECT-TYPE
		SYNTAX		INTEGER {
							val_Memory_1(0),
							val_Memory_2(1),
							val_Memory_3(2),
							val_Memory_4(3),
							val_Memory_5(4),
							val_Memory_6(5),
							val_Memory_7(6),
							val_Memory_8(7)
							}
		MAX-ACCESS		read-write
		STATUS			current
		DESCRIPTION
				"TYPE: - RadiobuttonList
					Recall  cmdID= 67 
					Memory_1  value= 0  
					Memory_2  value= 1  
					Memory_3  value= 2  
					Memory_4  value= 3  
					Memory_5  value= 4  
					Memory_6  value= 5  
					Memory_7  value= 6  
					Memory_8  value= 7  "
		::= { iqdrt8CmdEntry 67 }


	iqdrt8MemoriesNamesMemory1 OBJECT-TYPE
		SYNTAX		RollCallString
		MAX-ACCESS		read-write
		STATUS			current
		DESCRIPTION
				"TYPE: - Editstring
					Memory_1  cmdID= 69  "
		::= { iqdrt8CmdEntry 69 }


	iqdrt8MemoriesNamesMemory2 OBJECT-TYPE
		SYNTAX		RollCallString
		MAX-ACCESS		read-write
		STATUS			current
		DESCRIPTION
				"TYPE: - Editstring
					Memory_2  cmdID= 70  "
		::= { iqdrt8CmdEntry 70 }


	iqdrt8MemoriesNamesMemory3 OBJECT-TYPE
		SYNTAX		RollCallString
		MAX-ACCESS		read-write
		STATUS			current
		DESCRIPTION
				"TYPE: - Editstring
					Memory_3  cmdID= 71  "
		::= { iqdrt8CmdEntry 71 }


	iqdrt8MemoriesNamesMemory4 OBJECT-TYPE
		SYNTAX		RollCallString
		MAX-ACCESS		read-write
		STATUS			current
		DESCRIPTION
				"TYPE: - Editstring
					Memory_4  cmdID= 72  "
		::= { iqdrt8CmdEntry 72 }


	iqdrt8MemoriesNamesMemory5 OBJECT-TYPE
		SYNTAX		RollCallString
		MAX-ACCESS		read-write
		STATUS			current
		DESCRIPTION
				"TYPE: - Editstring
					Memory_5  cmdID= 73  "
		::= { iqdrt8CmdEntry 73 }


	iqdrt8MemoriesNamesMemory6 OBJECT-TYPE
		SYNTAX		RollCallString
		MAX-ACCESS		read-write
		STATUS			current
		DESCRIPTION
				"TYPE: - Editstring
					Memory_6  cmdID= 74  "
		::= { iqdrt8CmdEntry 74 }


	iqdrt8MemoriesNamesMemory7 OBJECT-TYPE
		SYNTAX		RollCallString
		MAX-ACCESS		read-write
		STATUS			current
		DESCRIPTION
				"TYPE: - Editstring
					Memory_7  cmdID= 75  "
		::= { iqdrt8CmdEntry 75 }


	iqdrt8MemoriesNamesMemory8 OBJECT-TYPE
		SYNTAX		RollCallString
		MAX-ACCESS		read-write
		STATUS			current
		DESCRIPTION
				"TYPE: - Editstring
					Memory_8  cmdID= 76  "
		::= { iqdrt8CmdEntry 76 }


	iqdrt8MemoriesNamesPreset OBJECT-TYPE
		SYNTAX		INTEGER {
							val_Preset_All_Names(9),
							val_Memory_1(0),
							val_Memory_2(1),
							val_Memory_3(2),
							val_Memory_4(3),
							val_Memory_5(4),
							val_Memory_6(5),
							val_Memory_7(6),
							val_Memory_8(7),
							val_Preset_All_Memories(8)
							}
		MAX-ACCESS		read-write
		STATUS			current
		DESCRIPTION
				"TYPE: - Button
					Preset_All_Names  cmdID= 68  value= 9  
					Preset  cmdID= 68 
					Memory_1  value= 0  
					Memory_2  value= 1  
					Memory_3  value= 2  
					Memory_4  value= 3  
					Memory_5  value= 4  
					Memory_6  value= 5  
					Memory_7  value= 6  
					Memory_8  value= 7  
					Preset_All_Memories  value= 8  "
		::= { iqdrt8CmdEntry 68 }


	iqdrt8MemoriesSave OBJECT-TYPE
		SYNTAX		INTEGER {
							val_Memory_1(0),
							val_Memory_2(1),
							val_Memory_3(2),
							val_Memory_4(3),
							val_Memory_5(4),
							val_Memory_6(5),
							val_Memory_7(6),
							val_Memory_8(7)
							}
		MAX-ACCESS		read-write
		STATUS			current
		DESCRIPTION
				"TYPE: - RadiobuttonList
					Save  cmdID= 66 
					Memory_1  value= 0  
					Memory_2  value= 1  
					Memory_3  value= 2  
					Memory_4  value= 3  
					Memory_5  value= 4  
					Memory_6  value= 5  
					Memory_7  value= 6  
					Memory_8  value= 7  "
		::= { iqdrt8CmdEntry 66 }


	iqdrt8RollTrackDest1 OBJECT-TYPE
		SYNTAX		RollCallString
		MAX-ACCESS		read-write
		STATUS			current
		DESCRIPTION
				"TYPE: - Editstring
				 PAGE: - RollTrack
					Dest_1  cmdID= 48  "
		::= { iqdrt8CmdEntry 48 }


	iqdrt8RollTrackDest2 OBJECT-TYPE
		SYNTAX		RollCallString
		MAX-ACCESS		read-write
		STATUS			current
		DESCRIPTION
				"TYPE: - Editstring
				 PAGE: - RollTrack
					Dest_2  cmdID= 49  "
		::= { iqdrt8CmdEntry 49 }


	iqdrt8RollTrackDest3 OBJECT-TYPE
		SYNTAX		RollCallString
		MAX-ACCESS		read-write
		STATUS			current
		DESCRIPTION
				"TYPE: - Editstring
				 PAGE: - RollTrack
					Dest_3  cmdID= 50  "
		::= { iqdrt8CmdEntry 50 }


	iqdrt8RollTrackDest4 OBJECT-TYPE
		SYNTAX		RollCallString
		MAX-ACCESS		read-write
		STATUS			current
		DESCRIPTION
				"TYPE: - Editstring
				 PAGE: - RollTrack
					Dest_4  cmdID= 51  "
		::= { iqdrt8CmdEntry 51 }


	iqdrt8RollTrackDest5 OBJECT-TYPE
		SYNTAX		RollCallString
		MAX-ACCESS		read-write
		STATUS			current
		DESCRIPTION
				"TYPE: - Editstring
				 PAGE: - RollTrack
					Dest_5  cmdID= 52  "
		::= { iqdrt8CmdEntry 52 }


	iqdrt8RollTrackDest6 OBJECT-TYPE
		SYNTAX		RollCallString
		MAX-ACCESS		read-write
		STATUS			current
		DESCRIPTION
				"TYPE: - Editstring
				 PAGE: - RollTrack
					Dest_6  cmdID= 53  "
		::= { iqdrt8CmdEntry 53 }


	iqdrt8RollTrackDest7 OBJECT-TYPE
		SYNTAX		RollCallString
		MAX-ACCESS		read-write
		STATUS			current
		DESCRIPTION
				"TYPE: - Editstring
				 PAGE: - RollTrack
					Dest_7  cmdID= 54  "
		::= { iqdrt8CmdEntry 54 }


	iqdrt8RollTrackDest8 OBJECT-TYPE
		SYNTAX		RollCallString
		MAX-ACCESS		read-write
		STATUS			current
		DESCRIPTION
				"TYPE: - Editstring
				 PAGE: - RollTrack
					Dest_8  cmdID= 55  "
		::= { iqdrt8CmdEntry 55 }


	iqdrt8RollTrackRollTrackMessages OBJECT-TYPE
		SYNTAX		INTEGER { disable(0), enable(1) }
		MAX-ACCESS		read-write
		STATUS			current
		DESCRIPTION
				"TYPE: - Checkbox
				 PAGE: - RollTrack
					RollTrack_Messages  cmdID= 56 "
		::= { iqdrt8CmdEntry 56 }


	iqdrt8NameAssocSourceSource1 OBJECT-TYPE
		SYNTAX		RollCallString
		MAX-ACCESS		read-write
		STATUS			current
		DESCRIPTION
				"TYPE: - Editstring
				 PAGE: - Name_Assoc
					Source_1  cmdID= 16  "
		::= { iqdrt8CmdEntry 16 }


	iqdrt8NameAssocSourceSource2 OBJECT-TYPE
		SYNTAX		RollCallString
		MAX-ACCESS		read-write
		STATUS			current
		DESCRIPTION
				"TYPE: - Editstring
				 PAGE: - Name_Assoc
					Source_2  cmdID= 17  "
		::= { iqdrt8CmdEntry 17 }


	iqdrt8NameAssocSourceSource3 OBJECT-TYPE
		SYNTAX		RollCallString
		MAX-ACCESS		read-write
		STATUS			current
		DESCRIPTION
				"TYPE: - Editstring
				 PAGE: - Name_Assoc
					Source_3  cmdID= 18  "
		::= { iqdrt8CmdEntry 18 }


	iqdrt8NameAssocSourceSource4 OBJECT-TYPE
		SYNTAX		RollCallString
		MAX-ACCESS		read-write
		STATUS			current
		DESCRIPTION
				"TYPE: - Editstring
				 PAGE: - Name_Assoc
					Source_4  cmdID= 19  "
		::= { iqdrt8CmdEntry 19 }


	iqdrt8NameAssocSourceSource5 OBJECT-TYPE
		SYNTAX		RollCallString
		MAX-ACCESS		read-write
		STATUS			current
		DESCRIPTION
				"TYPE: - Editstring
				 PAGE: - Name_Assoc
					Source_5  cmdID= 20  "
		::= { iqdrt8CmdEntry 20 }


	iqdrt8NameAssocSourceSource6 OBJECT-TYPE
		SYNTAX		RollCallString
		MAX-ACCESS		read-write
		STATUS			current
		DESCRIPTION
				"TYPE: - Editstring
				 PAGE: - Name_Assoc
					Source_6  cmdID= 21  "
		::= { iqdrt8CmdEntry 21 }


	iqdrt8NameAssocSourceSource7 OBJECT-TYPE
		SYNTAX		RollCallString
		MAX-ACCESS		read-write
		STATUS			current
		DESCRIPTION
				"TYPE: - Editstring
				 PAGE: - Name_Assoc
					Source_7  cmdID= 22  "
		::= { iqdrt8CmdEntry 22 }


	iqdrt8NameAssocSourceSource8 OBJECT-TYPE
		SYNTAX		RollCallString
		MAX-ACCESS		read-write
		STATUS			current
		DESCRIPTION
				"TYPE: - Editstring
				 PAGE: - Name_Assoc
					Source_8  cmdID= 23  "
		::= { iqdrt8CmdEntry 23 }


	iqdrt8NameAssocDestinationDest1 OBJECT-TYPE
		SYNTAX		RollCallString
		MAX-ACCESS		read-write
		STATUS			current
		DESCRIPTION
				"TYPE: - Editstring
				 PAGE: - Name_Assoc
					Dest_1  cmdID= 24  "
		::= { iqdrt8CmdEntry 24 }


	iqdrt8NameAssocDestinationDest2 OBJECT-TYPE
		SYNTAX		RollCallString
		MAX-ACCESS		read-write
		STATUS			current
		DESCRIPTION
				"TYPE: - Editstring
				 PAGE: - Name_Assoc
					Dest_2  cmdID= 25  "
		::= { iqdrt8CmdEntry 25 }


	iqdrt8NameAssocDestinationDest3 OBJECT-TYPE
		SYNTAX		RollCallString
		MAX-ACCESS		read-write
		STATUS			current
		DESCRIPTION
				"TYPE: - Editstring
				 PAGE: - Name_Assoc
					Dest_3  cmdID= 26  "
		::= { iqdrt8CmdEntry 26 }


	iqdrt8NameAssocDestinationDest4 OBJECT-TYPE
		SYNTAX		RollCallString
		MAX-ACCESS		read-write
		STATUS			current
		DESCRIPTION
				"TYPE: - Editstring
				 PAGE: - Name_Assoc
					Dest_4  cmdID= 27  "
		::= { iqdrt8CmdEntry 27 }


	iqdrt8NameAssocDestinationDest5 OBJECT-TYPE
		SYNTAX		RollCallString
		MAX-ACCESS		read-write
		STATUS			current
		DESCRIPTION
				"TYPE: - Editstring
				 PAGE: - Name_Assoc
					Dest_5  cmdID= 28  "
		::= { iqdrt8CmdEntry 28 }


	iqdrt8NameAssocDestinationDest6 OBJECT-TYPE
		SYNTAX		RollCallString
		MAX-ACCESS		read-write
		STATUS			current
		DESCRIPTION
				"TYPE: - Editstring
				 PAGE: - Name_Assoc
					Dest_6  cmdID= 29  "
		::= { iqdrt8CmdEntry 29 }


	iqdrt8NameAssocDestinationDest7 OBJECT-TYPE
		SYNTAX		RollCallString
		MAX-ACCESS		read-write
		STATUS			current
		DESCRIPTION
				"TYPE: - Editstring
				 PAGE: - Name_Assoc
					Dest_7  cmdID= 30  "
		::= { iqdrt8CmdEntry 30 }


	iqdrt8NameAssocDestinationDest8 OBJECT-TYPE
		SYNTAX		RollCallString
		MAX-ACCESS		read-write
		STATUS			current
		DESCRIPTION
				"TYPE: - Editstring
				 PAGE: - Name_Assoc
					Dest_8  cmdID= 31  "
		::= { iqdrt8CmdEntry 31 }


	iqdrt8SetupSwitchingPoint OBJECT-TYPE
		SYNTAX		INTEGER {
							val_Field(1),
							val_Frame(0)
							}
		MAX-ACCESS		read-write
		STATUS			current
		DESCRIPTION
				"TYPE: - RadiobuttonList
					Switching_Point  cmdID= 5 
					Field  value= 1  
					Frame  value= 0  "
		::= { iqdrt8CmdEntry 5 }


	iqdrt8LoggingInputsInput1 OBJECT-TYPE
		SYNTAX		INTEGER { disable(0), enable(1) }
		MAX-ACCESS		read-write
		STATUS			current
		DESCRIPTION
				"TYPE: - Checkbox
				 PAGE: - Logging
					Input_1  cmdID= 114 "
		::= { iqdrt8CmdEntry 114 }


	iqdrt8LoggingInputsInput2 OBJECT-TYPE
		SYNTAX		INTEGER { disable(0), enable(1) }
		MAX-ACCESS		read-write
		STATUS			current
		DESCRIPTION
				"TYPE: - Checkbox
				 PAGE: - Logging
					Input_2  cmdID= 115 "
		::= { iqdrt8CmdEntry 115 }


	iqdrt8LoggingInputsInput3 OBJECT-TYPE
		SYNTAX		INTEGER { disable(0), enable(1) }
		MAX-ACCESS		read-write
		STATUS			current
		DESCRIPTION
				"TYPE: - Checkbox
				 PAGE: - Logging
					Input_3  cmdID= 116 "
		::= { iqdrt8CmdEntry 116 }


	iqdrt8LoggingInputsInput4 OBJECT-TYPE
		SYNTAX		INTEGER { disable(0), enable(1) }
		MAX-ACCESS		read-write
		STATUS			current
		DESCRIPTION
				"TYPE: - Checkbox
				 PAGE: - Logging
					Input_4  cmdID= 117 "
		::= { iqdrt8CmdEntry 117 }


	iqdrt8LoggingInputsInput5 OBJECT-TYPE
		SYNTAX		INTEGER { disable(0), enable(1) }
		MAX-ACCESS		read-write
		STATUS			current
		DESCRIPTION
				"TYPE: - Checkbox
				 PAGE: - Logging
					Input_5  cmdID= 118 "
		::= { iqdrt8CmdEntry 118 }


	iqdrt8LoggingInputsInput6 OBJECT-TYPE
		SYNTAX		INTEGER { disable(0), enable(1) }
		MAX-ACCESS		read-write
		STATUS			current
		DESCRIPTION
				"TYPE: - Checkbox
				 PAGE: - Logging
					Input_6  cmdID= 119 "
		::= { iqdrt8CmdEntry 119 }


	iqdrt8LoggingInputsInput7 OBJECT-TYPE
		SYNTAX		INTEGER { disable(0), enable(1) }
		MAX-ACCESS		read-write
		STATUS			current
		DESCRIPTION
				"TYPE: - Checkbox
				 PAGE: - Logging
					Input_7  cmdID= 120 "
		::= { iqdrt8CmdEntry 120 }


	iqdrt8LoggingInputsInput8 OBJECT-TYPE
		SYNTAX		INTEGER { disable(0), enable(1) }
		MAX-ACCESS		read-write
		STATUS			current
		DESCRIPTION
				"TYPE: - Checkbox
				 PAGE: - Logging
					Input_8  cmdID= 121 "
		::= { iqdrt8CmdEntry 121 }


	iqdrt8SetupLoggingOutputs OBJECT-TYPE
		SYNTAX		INTEGER { disable(0), enable(1) }
		MAX-ACCESS		read-write
		STATUS			current
		DESCRIPTION
				"TYPE: - Checkbox
				 PAGE: - Logging
					Outputs  cmdID= 184 "
		::= { iqdrt8CmdEntry 184 }


	iqdrt8SetupLoggingVideoRef OBJECT-TYPE
		SYNTAX		INTEGER { disable(0), enable(1) }
		MAX-ACCESS		read-write
		STATUS			current
		DESCRIPTION
				"TYPE: - Checkbox
				 PAGE: - Logging
					Video_Ref  cmdID= 123 "
		::= { iqdrt8CmdEntry 123 }


	iqdrt8SetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdrt8CmdEntry 3 }


	iqdrt8SetupSoftwareVersion OBJECT-TYPE
		SYNTAX		RollCallString
		MAX-ACCESS		read-only
		STATUS			current
		DESCRIPTION
				"TYPE: - Display
					Software_Version  cmdID= 2  format=   "
		::= { iqdrt8CmdEntry 2 }


	iqdrt8SetupSerialNo OBJECT-TYPE
		SYNTAX		RollCallString
		MAX-ACCESS		read-only
		STATUS			current
		DESCRIPTION
				"TYPE: - Display
					Serial_No  cmdID= 1  format=   "
		::= { iqdrt8CmdEntry 1 }


	iqdrt8SetupBuildNo OBJECT-TYPE
		SYNTAX		RollCallString
		MAX-ACCESS		read-only
		STATUS			current
		DESCRIPTION
				"TYPE: - Display
					Build_No  cmdID= 175  format=   "
		::= { iqdrt8CmdEntry 175 }


	iqdrt8SetupRestart OBJECT-TYPE
		SYNTAX		INTEGER { noAction(0),val_Restart(1) }
		MAX-ACCESS		read-write
		STATUS			current
		DESCRIPTION
				"TYPE: - Button
					Restart  cmdID= 4  value= 1  "
		::= { iqdrt8CmdEntry 4 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: LOST
--				: 625
--				: 525
-- Comments		: 
--
---------------------------------------------------------------------------------------------------
-- Header		: EDH_1
--
-- MIB ref		: swCardEventLogSlotXX       .5.69.68.72.95.49
-- absolute OID	: 1.3.6.1.4.1.7995.2.6.1.1.XX.5.83.84.68.95.49
-- Vary			: YES
--
-- Value(s)		: NONE
--				: RESET
--				: OK
--				: FAIL
-- Comments		: 
--
---------------------------------------------------------------------------------------------------
-- Header		: EDH_2
--
-- MIB ref		: swCardEventLogSlotXX       .5.69.68.72.95.50
-- absolute OID	: 1.3.6.1.4.1.7995.2.6.1.1.XX.5.69.68.72.95.50
-- Vary			: YES
--
-- Value(s)		: NONE
--				: RESET
--				: OK
--				: FAIL
-- Comments		: 
--
---------------------------------------------------------------------------------------------------
-- Header		: EDH_3
--
-- MIB ref		: swCardEventLogSlotXX       .5.69.68.72.95.51
-- absolute OID	: 1.3.6.1.4.1.7995.2.6.1.1.XX.5.69.68.72.95.51
-- Vary			: YES
--
-- Value(s)		: NONE
--				: RESET
--				: OK
--				: FAIL
-- Comments		: 
--
---------------------------------------------------------------------------------------------------
-- Header		: EDH_4
--
-- MIB ref		: swCardEventLogSlotXX       .5.69.68.72.95.52
-- absolute OID	: 1.3.6.1.4.1.7995.2.6.1.1.XX.5.69.68.72.95.52
-- Vary			: YES
--
-- Value(s)		: NONE
--				: RESET
--				: OK
--				: FAIL
-- Comments		: 
--
---------------------------------------------------------------------------------------------------
-- Header		: EDH_5
--
-- MIB ref		: swCardEventLogSlotXX       .5.69.68.72.95.53
-- absolute OID	: 1.3.6.1.4.1.7995.2.6.1.1.XX.5.69.68.72.95.53
-- Vary			: YES
--
-- Value(s)		: NONE
--				: RESET
--				: OK
--				: FAIL
-- Comments		: 
--
---------------------------------------------------------------------------------------------------
-- Header		: EDH_6
--
-- MIB ref		: swCardEventLogSlotXX       .5.69.68.72.95.54
-- absolute OID	: 1.3.6.1.4.1.7995.2.6.1.1.XX.5.69.68.72.95.54
-- Vary			: YES
--
-- Value(s)		: NONE
--				: RESET
--				: OK
--				: FAIL
-- Comments		: 
--
---------------------------------------------------------------------------------------------------
-- Header		: EDH_7
--
-- MIB ref		: swCardEventLogSlotXX       .5.69.68.72.95.55
-- absolute OID	: 1.3.6.1.4.1.7995.2.6.1.1.XX.5.69.68.72.95.55
-- Vary			: YES
--
-- Value(s)		: NONE
--				: RESET
--				: OK
--				: FAIL
-- Comments		: 
--
---------------------------------------------------------------------------------------------------
-- Header		: EDH_8
--
-- MIB ref		: swCardEventLogSlotXX       .5.69.68.72.95.56
-- absolute OID	: 1.3.6.1.4.1.7995.2.6.1.1.XX.5.69.68.72.95.56
-- Vary			: YES
--
-- Value(s)		: NONE
--				: RESET
--				: OK
--				: FAIL
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL_MODE
--				: 
-- Comments		: 
--
---------------------------------------------------------------------------------------------------
-- Header		: STD_1
--
-- MIB ref		: swCardEventLogSlotXX       .5.83.84.68.95.49
-- absolute OID	: 1.3.6.1.4.1.7995.2.6.1.1.XX.5.83.84.68.95.49
-- Vary			: YES
--
-- Value(s)		: UNKNOWN
--				: 143
--				: 177
--				: 270
--				: 360
--				: ***
-- Comments		: 
--
---------------------------------------------------------------------------------------------------
-- Header		: STD_2
--
-- MIB ref		: swCardEventLogSlotXX       .5.83.84.68.95.50
-- absolute OID	: 1.3.6.1.4.1.7995.2.6.1.1.XX.5.83.84.68.95.50
-- Vary			: YES
--
-- Value(s)		: UNKNOWN
--				: 143
--				: 177
--				: 270
--				: 360
--				: ***
-- Comments		: 
--
---------------------------------------------------------------------------------------------------
-- Header		: STD_3
--
-- MIB ref		: swCardEventLogSlotXX       .5.83.84.68.95.51
-- absolute OID	: 1.3.6.1.4.1.7995.2.6.1.1.XX.5.83.84.68.95.51
-- Vary			: YES
--
-- Value(s)		: UNKNOWN
--				: 143
--				: 177
--				: 270
--				: 360
--				: ***
-- Comments		: 
--
---------------------------------------------------------------------------------------------------
-- Header		: STD_4
--
-- MIB ref		: swCardEventLogSlotXX       .5.83.84.68.95.52
-- absolute OID	: 1.3.6.1.4.1.7995.2.6.1.1.XX.5.83.84.68.95.52
-- Vary			: YES
--
-- Value(s)		: UNKNOWN
--				: 143
--				: 177
--				: 270
--				: 360
--				: ***
-- Comments		: 
--
---------------------------------------------------------------------------------------------------
-- Header		: STD_5
--
-- MIB ref		: swCardEventLogSlotXX       .5.83.84.68.95.53
-- absolute OID	: 1.3.6.1.4.1.7995.2.6.1.1.XX.5.83.84.68.95.53
-- Vary			: YES
--
-- Value(s)		: UNKNOWN
--				: 143
--				: 177
--				: 270
--				: 360
--				: ***
-- Comments		: 
--
---------------------------------------------------------------------------------------------------
-- Header		: STD_6
--
-- MIB ref		: swCardEventLogSlotXX       .5.83.84.68.95.54
-- absolute OID	: 1.3.6.1.4.1.7995.2.6.1.1.XX.5.83.84.68.95.54
-- Vary			: YES
--
-- Value(s)		: UNKNOWN
--				: 143
--				: 177
--				: 270
--				: 360
--				: ***
-- Comments		: 
--
---------------------------------------------------------------------------------------------------
-- Header		: STD_7
--
-- MIB ref		: swCardEventLogSlotXX       .5.83.84.68.95.55
-- absolute OID	: 1.3.6.1.4.1.7995.2.6.1.1.XX.5.83.84.68.95.55
-- Vary			: YES
--
-- Value(s)		: UNKNOWN
--				: 143
--				: 177
--				: 270
--				: 360
--				: ***
-- Comments		: 
--
---------------------------------------------------------------------------------------------------
-- Header		: STD_8
--
-- MIB ref		: swCardEventLogSlotXX       .5.83.84.68.95.56
-- absolute OID	: 1.3.6.1.4.1.7995.2.6.1.1.XX.5.83.84.68.95.56
-- Vary			: YES
--
-- Value(s)		: UNKNOWN
--				: 143
--				: 177
--				: 270
--				: 360
--				: ***
-- Comments		: 
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: LOST
--				: OK
-- Comments		: 
--
---------------------------------------------------------------------------------------------------
-- Header		: INPUT_1
--
-- MIB ref		: swCardEventLogSlotXX       .7.73.78.80.85.84.95.49
-- absolute OID	: 1.3.6.1.4.1.7995.2.6.1.1.XX.7.73.78.80.85.84.95.49
-- Vary			: YES
--
-- Value(s)		: LOST
--				: OK
-- Comments		: 
--
---------------------------------------------------------------------------------------------------
-- Header		: INPUT_2
--
-- MIB ref		: swCardEventLogSlotXX       .7.73.78.80.85.84.95.50
-- absolute OID	: 1.3.6.1.4.1.7995.2.6.1.1.XX.7.73.78.80.85.84.95.50
-- Vary			: YES
--
-- Value(s)		: LOST
--				: OK
-- Comments		: 
--
---------------------------------------------------------------------------------------------------
-- Header		: INPUT_3
--
-- MIB ref		: swCardEventLogSlotXX       .7.73.78.80.85.84.95.51
-- absolute OID	: 1.3.6.1.4.1.7995.2.6.1.1.XX.7.73.78.80.85.84.95.51
-- Vary			: YES
--
-- Value(s)		: LOST
--				: OK
-- Comments		: 
--
---------------------------------------------------------------------------------------------------
-- Header		: INPUT_4
--
-- MIB ref		: swCardEventLogSlotXX       .7.73.78.80.85.84.95.52
-- absolute OID	: 1.3.6.1.4.1.7995.2.6.1.1.XX.7.73.78.80.85.84.95.52
-- Vary			: YES
--
-- Value(s)		: LOST
--				: OK
-- Comments		: 
--
---------------------------------------------------------------------------------------------------
-- Header		: INPUT_5
--
-- MIB ref		: swCardEventLogSlotXX       .7.73.78.80.85.84.95.53
-- absolute OID	: 1.3.6.1.4.1.7995.2.6.1.1.XX.7.73.78.80.85.84.95.53
-- Vary			: YES
--
-- Value(s)		: LOST
--				: OK
-- Comments		: 
--
---------------------------------------------------------------------------------------------------
-- Header		: INPUT_6
--
-- MIB ref		: swCardEventLogSlotXX       .7.73.78.80.85.84.95.54
-- absolute OID	: 1.3.6.1.4.1.7995.2.6.1.1.XX.7.73.78.80.85.84.95.54
-- Vary			: YES
--
-- Value(s)		: LOST
--				: OK
-- Comments		: 
--
---------------------------------------------------------------------------------------------------
-- Header		: INPUT_7
--
-- MIB ref		: swCardEventLogSlotXX       .7.73.78.80.85.84.95.55
-- absolute OID	: 1.3.6.1.4.1.7995.2.6.1.1.XX.7.73.78.80.85.84.95.55
-- Vary			: YES
--
-- Value(s)		: LOST
--				: OK
-- Comments		: 
--
---------------------------------------------------------------------------------------------------
-- Header		: INPUT_8
--
-- MIB ref		: swCardEventLogSlotXX       .7.73.78.80.85.84.95.56
-- absolute OID	: 1.3.6.1.4.1.7995.2.6.1.1.XX.7.73.78.80.85.84.95.56
-- Vary			: YES
--
-- Value(s)		: LOST
--				: OK
-- Comments		: 
--
---------------------------------------------------------------------------------------------------
-- Header		: ERRSEC_1
--
-- MIB ref		: swCardEventLogSlotXX       .8.69.82.82.83.69.67.95.49
-- absolute OID	: 1.3.6.1.4.1.7995.2.6.1.1.XX.8.69.82.82.83.69.67.95.49
-- Vary			: YES
-- Vary Number  : YES
-- Value(s)		: 
--				: 
-- Comments		: 
--
---------------------------------------------------------------------------------------------------
-- Header		: ERRSEC_2
--
-- MIB ref		: swCardEventLogSlotXX       .8.69.82.82.83.69.67.95.50
-- absolute OID	: 1.3.6.1.4.1.7995.2.6.1.1.XX.8.69.82.82.83.69.67.95.50
-- Vary			: YES
-- Vary Number  : YES
-- Value(s)		: 
--				: 
-- Comments		: 
--
---------------------------------------------------------------------------------------------------
-- Header		: ERRSEC_3
--
-- MIB ref		: swCardEventLogSlotXX       .8.69.82.82.83.69.67.95.51
-- absolute OID	: 1.3.6.1.4.1.7995.2.6.1.1.XX.8.69.82.82.83.69.67.95.51
-- Vary			: YES
-- Vary Number  : YES
-- Value(s)		: 
--				: 
-- Comments		: 
--
---------------------------------------------------------------------------------------------------
-- Header		: ERRSEC_4
--
-- MIB ref		: swCardEventLogSlotXX       .8.69.82.82.83.69.67.95.52
-- absolute OID	: 1.3.6.1.4.1.7995.2.6.1.1.XX.8.69.82.82.83.69.67.95.52
-- Vary			: YES
-- Vary Number  : YES
-- Value(s)		: 
--				: 
-- Comments		: 
--
---------------------------------------------------------------------------------------------------
-- Header		: ERRSEC_5
--
-- MIB ref		: swCardEventLogSlotXX       .8.69.82.82.83.69.67.95.53
-- absolute OID	: 1.3.6.1.4.1.7995.2.6.1.1.XX.8.69.82.82.83.69.67.95.53
-- Vary			: YES
-- Vary Number  : YES
-- Value(s)		: 
--				: 
-- Comments		: 
--
---------------------------------------------------------------------------------------------------
-- Header		: ERRSEC_6
--
-- MIB ref		: swCardEventLogSlotXX       .8.69.82.82.83.69.67.95.54
-- absolute OID	: 1.3.6.1.4.1.7995.2.6.1.1.XX.8.69.82.82.83.69.67.95.54
-- Vary			: YES
-- Vary Number  : YES
-- Value(s)		: 
--				: 
-- Comments		: 
--
---------------------------------------------------------------------------------------------------
-- Header		: ERRSEC_7
--
-- MIB ref		: swCardEventLogSlotXX       .8.69.82.82.83.69.67.95.55
-- absolute OID	: 1.3.6.1.4.1.7995.2.6.1.1.XX.8.69.82.82.83.69.67.95.55
-- Vary			: YES
-- Vary Number  : YES
-- Value(s)		: 
--				: 
-- Comments		: 
--
---------------------------------------------------------------------------------------------------
-- Header		: ERRSEC_8
--
-- MIB ref		: swCardEventLogSlotXX       .8.69.82.82.83.69.67.95.56
-- absolute OID	: 1.3.6.1.4.1.7995.2.6.1.1.XX.8.69.82.82.83.69.67.95.56
-- Vary			: YES
-- Vary Number  : YES
-- Value(s)		: 
--				: 
-- Comments		: 
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_2
--
-- MIB ref		: swCardEventLogSlotXX       .8.79.85.84.80.85.84.95.50
-- absolute OID	: 1.3.6.1.4.1.7995.2.6.1.1.XX.8.79.85.84.80.85.84.95.50
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_3
--
-- MIB ref		: swCardEventLogSlotXX       .8.79.85.84.80.85.84.95.51
-- absolute OID	: 1.3.6.1.4.1.7995.2.6.1.1.XX.8.79.85.84.80.85.84.95.51
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_4
--
-- MIB ref		: swCardEventLogSlotXX       .8.79.85.84.80.85.84.95.52
-- absolute OID	: 1.3.6.1.4.1.7995.2.6.1.1.XX.8.79.85.84.80.85.84.95.52
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_5
--
-- MIB ref		: swCardEventLogSlotXX       .8.79.85.84.80.85.84.95.53
-- absolute OID	: 1.3.6.1.4.1.7995.2.6.1.1.XX.8.79.85.84.80.85.84.95.53
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_6
--
-- MIB ref		: swCardEventLogSlotXX       .8.79.85.84.80.85.84.95.54
-- absolute OID	: 1.3.6.1.4.1.7995.2.6.1.1.XX.8.79.85.84.80.85.84.95.54
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_7
--
-- MIB ref		: swCardEventLogSlotXX       .8.79.85.84.80.85.84.95.55
-- absolute OID	: 1.3.6.1.4.1.7995.2.6.1.1.XX.8.79.85.84.80.85.84.95.55
-- Vary			: YES
--
-- Value(s)		: Source_1
--				: Source_2
--				: Source_3
--				: Source_4
--				: Source_5
--				: Source_6
--				: Source_7
--				: Source_8
-- Comments		: 
--
---------------------------------------------------------------------------------------------------
-- Header		: OUTPUT_8
--
-- MIB ref		: swCardEventLogSlotXX       .8.79.85.84.80.85.84.95.56
-- absolute OID	: 1.3.6.1.4.1.7995.2.6.1.1.XX.8.79.85.84.80.85.84.95.56
-- Vary			: YES
--
-- Value(s)		: Source_1
--				: Source_2
--				: Source_3
--				: Source_4
--				: Source_5
--				: Source_6
--				: Source_7
--				: Source_8
-- Comments		: 
--
---------------------------------------------------------------------------------------------------
