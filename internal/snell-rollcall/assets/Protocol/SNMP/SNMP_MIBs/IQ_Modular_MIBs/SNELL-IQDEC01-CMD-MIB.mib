-- ************************************************************************************
-- Snell&Wilcox Card:IQDEC01
--        Module Id#:413
--       Command Set:16
--          Filename:SNELL-IQDEC01-CMD-MIB.mib
--            Author:Jonathan Riches
--              Date:10/01/2008
--              Time:10:01
--
-- Copyright (c) 2005 Snell & Wilcox Ltd
-- All rights reserved.
--
-- ************************************************************************************

SNELL-IQDEC01-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDEC01,
    moduleIQDEC01MIB
        FROM SNELL-WILCOX-PRODUCT-REG;

 moduleIQDEC01CmdMi MODULE-IDENTITY
    LAST-UPDATED "0801101001Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDEC01MIB 1 }




--********************************************************************************
--*
--*  Snell Wilcox Card:
--*  command set:
--*  list commands/menus:
--*
--******************************************************************************
	iqdec01CmdTable OBJECT-TYPE
		SYNTAX			SEQUENCE OF Iqdec01CmdEntry
		MAX-ACCESS		not-accessible
		STATUS			current
		DESCRIPTION
				"Note the instance of this table is relected in the command set Version"
		::= { moduleIQDEC01 1 }

	iqdec01CmdEntry OBJECT-TYPE
		SYNTAX		Iqdec01CmdEntry
		MAX-ACCESS		not-accessible
		STATUS			current
		DESCRIPTION
				"Entry in command table."
		INDEX	{ iqdec01SlotIndex }
		::= { iqdec01CmdTable 1 }

	Iqdec01CmdEntry ::=
		SEQUENCE {
			iqdec01SlotIndex
				Unsigned32,
			iqdec01VideoInputSelect
				INTEGER,
			iqdec01InputCompositeStdPAL
				INTEGER,
			iqdec01InputCompositeStdNTSC
				INTEGER,
			iqdec01InputCompositeStdNTSCJ
				INTEGER,
			iqdec01InputCompositeStdPALM
				INTEGER,
			iqdec01InputCompositeStdPALN
				INTEGER,
			iqdec01InputCompositeStdSECAM
				INTEGER,
			iqdec01InputCompositeStdN44360
				INTEGER,
			iqdec01InputCompositeStdPAL44360
				INTEGER,
			iqdec01InputSDIStd525
				INTEGER,
			iqdec01InputSDIStd625
				INTEGER,
			iqdec01VideoProcampLumaGain
				INTEGER,
			iqdec01VideoProcampBlackLevel
				INTEGER,
			iqdec01VideoProcampChromaGain
				INTEGER,
			iqdec01VideoProcampNTSCHue
				INTEGER,
			iqdec01VideoProcampVEnhance
				INTEGER,
			iqdec01VideoProcampHEnhance
				INTEGER,
			iqdec01VideoProcampHEnhanceFreq
				INTEGER,
			iqdec01VideoProcampPicturePosition
				INTEGER,
			iqdec01VideoProcampYCTiming
				INTEGER,
			iqdec01ProcampBordersLeft
				INTEGER,
			iqdec01ProcampBordersRed
				INTEGER,
			iqdec01ProcampBordersRight
				INTEGER,
			iqdec01ProcampBordersGreen
				INTEGER,
			iqdec01ProcampBordersTop
				INTEGER,
			iqdec01ProcampBordersBlue
				INTEGER,
			iqdec01ProcampBordersBottom
				INTEGER,
			iqdec01VideoNoiseReducerLumaStrength
				INTEGER,
			iqdec01VideoNoiseReducerChromaStrength
				INTEGER,
			iqdec01VideoNoiseReducerThresholdMode
				INTEGER,
			iqdec01VideoNoiseReducerManualThreshold
				INTEGER,
			iqdec01VideoNoiseReducerAutoBias
				INTEGER,
			iqdec01VideoNoiseReducerDelayMode
				INTEGER,
			iqdec01VideoNoiseReducerNoiseMeasured
				RollCallString,


			iqdec01DeembedPair14DeembedPair1LGain
				INTEGER,
			iqdec01DeembedPair14DeembedPair1GainR
				INTEGER,
			iqdec01DeembedPair14DeembedPair1LInvert
				INTEGER,
			iqdec01DeembedPair14DeembedPair1InvertR
				INTEGER,
			iqdec01DeembedPair14DeembedPair1LMute
				INTEGER,
			iqdec01DeembedPair14DeembedPair1MuteR
				INTEGER,
			iqdec01DeembedPair14DeembedPair1Stereo
				INTEGER,
			iqdec01DeembedPair14DeembedPair1Delay
				INTEGER,
			iqdec01DeembedPair14DeembedPair2LGain
				INTEGER,
			iqdec01DeembedPair14DeembedPair2GainR
				INTEGER,
			iqdec01DeembedPair14DeembedPair2LInvert
				INTEGER,
			iqdec01DeembedPair14DeembedPair2InvertR
				INTEGER,
			iqdec01DeembedPair14DeembedPair2LMute
				INTEGER,
			iqdec01DeembedPair14DeembedPair2MuteR
				INTEGER,
			iqdec01DeembedPair14DeembedPair2Stereo
				INTEGER,
			iqdec01DeembedPair14DeembedPair2Delay
				INTEGER,
			iqdec01DeembedPair14DeembedPair3LGain
				INTEGER,
			iqdec01DeembedPair14DeembedPair3GainR
				INTEGER,
			iqdec01DeembedPair14DeembedPair3LInvert
				INTEGER,
			iqdec01DeembedPair14DeembedPair3InvertR
				INTEGER,
			iqdec01DeembedPair14DeembedPair3LMute
				INTEGER,
			iqdec01DeembedPair14DeembedPair3MuteR
				INTEGER,
			iqdec01DeembedPair14DeembedPair3Stereo
				INTEGER,
			iqdec01DeembedPair14DeembedPair3Delay
				INTEGER,
			iqdec01DeembedPair14DeembedPair4LGain
				INTEGER,
			iqdec01DeembedPair14DeembedPair4GainR
				INTEGER,
			iqdec01DeembedPair14DeembedPair4LInvert
				INTEGER,
			iqdec01DeembedPair14DeembedPair4InvertR
				INTEGER,
			iqdec01DeembedPair14DeembedPair4LMute
				INTEGER,
			iqdec01DeembedPair14DeembedPair4MuteR
				INTEGER,
			iqdec01DeembedPair14DeembedPair4Stereo
				INTEGER,
			iqdec01DeembedPair14DeembedPair4Delay
				INTEGER,
			iqdec01DeembedPair58DeembedPair5LGain
				INTEGER,
			iqdec01DeembedPair58DeembedPair5GainR
				INTEGER,
			iqdec01DeembedPair58DeembedPair5LInvert
				INTEGER,
			iqdec01DeembedPair58DeembedPair5InvertR
				INTEGER,
			iqdec01DeembedPair58DeembedPair5LMute
				INTEGER,
			iqdec01DeembedPair58DeembedPair5MuteR
				INTEGER,
			iqdec01DeembedPair58DeembedPair5Stereo
				INTEGER,
			iqdec01DeembedPair58DeembedPair5Delay
				INTEGER,
			iqdec01DeembedPair58DeembedPair6LGain
				INTEGER,
			iqdec01DeembedPair58DeembedPair6GainR
				INTEGER,
			iqdec01DeembedPair58DeembedPair6LInvert
				INTEGER,
			iqdec01DeembedPair58DeembedPair6InvertR
				INTEGER,
			iqdec01DeembedPair58DeembedPair6LMute
				INTEGER,
			iqdec01DeembedPair58DeembedPair6MuteR
				INTEGER,
			iqdec01DeembedPair58DeembedPair6Stereo
				INTEGER,
			iqdec01DeembedPair58DeembedPair6Delay
				INTEGER,
			iqdec01DeembedPair58DeembedPair7LGain
				INTEGER,
			iqdec01DeembedPair58DeembedPair7GainR
				INTEGER,
			iqdec01DeembedPair58DeembedPair7LInvert
				INTEGER,
			iqdec01DeembedPair58DeembedPair7InvertR
				INTEGER,
			iqdec01DeembedPair58DeembedPair7LMute
				INTEGER,
			iqdec01DeembedPair58DeembedPair7MuteR
				INTEGER,
			iqdec01DeembedPair58DeembedPair7Stereo
				INTEGER,
			iqdec01DeembedPair58DeembedPair7Delay
				INTEGER,
			iqdec01DeembedPair58DeembedPair8LGain
				INTEGER,
			iqdec01DeembedPair58DeembedPair8GainR
				INTEGER,
			iqdec01DeembedPair58DeembedPair8LInvert
				INTEGER,
			iqdec01DeembedPair58DeembedPair8InvertR
				INTEGER,
			iqdec01DeembedPair58DeembedPair8LMute
				INTEGER,
			iqdec01DeembedPair58DeembedPair8MuteR
				INTEGER,
			iqdec01DeembedPair58DeembedPair8Stereo
				INTEGER,
			iqdec01DeembedPair58DeembedPair8Delay
				INTEGER,
			iqdec01AnalogAudioPair1AnalogPair1LGain
				INTEGER,
			iqdec01AnalogAudioPair1AnalogPair1GainR
				INTEGER,
			iqdec01AnalogAudioPair1AnalogPair1LInvert
				INTEGER,
			iqdec01AnalogAudioPair1AnalogPair1InvertR
				INTEGER,
			iqdec01AnalogAudioPair1AnalogPair1LMute
				INTEGER,
			iqdec01AnalogAudioPair1AnalogPair1MuteR
				INTEGER,
			iqdec01AnalogAudioPair1AnalogPair1Stereo
				INTEGER,
			iqdec01AnalogAudioPair1AnalogPair1Delay
				INTEGER,
			iqdec01AnalogAudioPair1AnalogPair2LGain
				INTEGER,
			iqdec01AnalogAudioPair1AnalogPair2GainR
				INTEGER,
			iqdec01AnalogAudioPair1AnalogPair2LInvert
				INTEGER,
			iqdec01AnalogAudioPair1AnalogPair2InvertR
				INTEGER,
			iqdec01AnalogAudioPair1AnalogPair2LMute
				INTEGER,
			iqdec01AnalogAudioPair1AnalogPair2MuteR
				INTEGER,
			iqdec01AnalogAudioPair1AnalogPair2Stereo
				INTEGER,
			iqdec01AnalogAudioPair1AnalogPair2Delay
				INTEGER,
			iqdec01AudioMix1Source1
				INTEGER,
			iqdec01AudioMix1Source2
				INTEGER,
			iqdec01AudioMix1Source3
				INTEGER,
			iqdec01AudioMix1Source4
				INTEGER,
			iqdec01AudioMix1Source5
				INTEGER,
			iqdec01AudioMix1Source6
				INTEGER,
			iqdec01AudioMix1Source7
				INTEGER,
			iqdec01AudioMix1Source8
				INTEGER,
			iqdec01AudioMix1GainGain1
				INTEGER,
			iqdec01AudioMix1GainGain2
				INTEGER,
			iqdec01AudioMix1GainGain3
				INTEGER,
			iqdec01AudioMix1GainGain4
				INTEGER,
			iqdec01AudioMix1GainGain5
				INTEGER,
			iqdec01AudioMix1GainGain6
				INTEGER,
			iqdec01AudioMix1GainGain7
				INTEGER,
			iqdec01AudioMix1GainGain8
				INTEGER,
			iqdec01AudioMix2Source1
				INTEGER,
			iqdec01AudioMix2Source2
				INTEGER,
			iqdec01AudioMix2Source3
				INTEGER,
			iqdec01AudioMix2Source4
				INTEGER,
			iqdec01AudioMix2Source5
				INTEGER,
			iqdec01AudioMix2Source6
				INTEGER,
			iqdec01AudioMix2Source7
				INTEGER,
			iqdec01AudioMix2Source8
				INTEGER,
			iqdec01AudioMix2GainGain1
				INTEGER,
			iqdec01AudioMix2GainGain2
				INTEGER,
			iqdec01AudioMix2GainGain3
				INTEGER,
			iqdec01AudioMix2GainGain4
				INTEGER,
			iqdec01AudioMix2GainGain5
				INTEGER,
			iqdec01AudioMix2GainGain6
				INTEGER,
			iqdec01AudioMix2GainGain7
				INTEGER,
			iqdec01AudioMix2GainGain8
				INTEGER,
			iqdec01AudioMix3Source1
				INTEGER,
			iqdec01AudioMix3Source2
				INTEGER,
			iqdec01AudioMix3Source3
				INTEGER,
			iqdec01AudioMix3Source4
				INTEGER,
			iqdec01AudioMix3Source5
				INTEGER,
			iqdec01AudioMix3Source6
				INTEGER,
			iqdec01AudioMix3Source7
				INTEGER,
			iqdec01AudioMix3Source8
				INTEGER,
			iqdec01AudioMix3GainGain1
				INTEGER,
			iqdec01AudioMix3GainGain2
				INTEGER,
			iqdec01AudioMix3GainGain3
				INTEGER,
			iqdec01AudioMix3GainGain4
				INTEGER,
			iqdec01AudioMix3GainGain5
				INTEGER,
			iqdec01AudioMix3GainGain6
				INTEGER,
			iqdec01AudioMix3GainGain7
				INTEGER,
			iqdec01AudioMix3GainGain8
				INTEGER,
			iqdec01AudioMix4Source1
				INTEGER,
			iqdec01AudioMix4Source2
				INTEGER,
			iqdec01AudioMix4Source3
				INTEGER,
			iqdec01AudioMix4Source4
				INTEGER,
			iqdec01AudioMix4Source5
				INTEGER,
			iqdec01AudioMix4Source6
				INTEGER,
			iqdec01AudioMix4Source7
				INTEGER,
			iqdec01AudioMix4Source8
				INTEGER,
			iqdec01AudioMix4GainGain1
				INTEGER,
			iqdec01AudioMix4GainGain2
				INTEGER,
			iqdec01AudioMix4GainGain3
				INTEGER,
			iqdec01AudioMix4GainGain4
				INTEGER,
			iqdec01AudioMix4GainGain5
				INTEGER,
			iqdec01AudioMix4GainGain6
				INTEGER,
			iqdec01AudioMix4GainGain7
				INTEGER,
			iqdec01AudioMix4GainGain8
				INTEGER,
			iqdec01AudioMixerGainDisplaysMix1Gain1Disp
				RollCallString,
			iqdec01AudioMixerGainDisplaysMix1Gain2Disp
				RollCallString,
			iqdec01AudioMixerGainDisplaysMix1Gain3Disp
				RollCallString,
			iqdec01AudioMixerGainDisplaysMix1Gain4Disp
				RollCallString,
			iqdec01AudioMixerGainDisplaysMix1Gain5Disp
				RollCallString,
			iqdec01AudioMixerGainDisplaysMix1Gain6Disp
				RollCallString,
			iqdec01AudioMixerGainDisplaysMix1Gain7Disp
				RollCallString,
			iqdec01AudioMixerGainDisplaysMix1Gain8Disp
				RollCallString,
			iqdec01AudioMixerGainDisplaysMix2Gain1Disp
				RollCallString,
			iqdec01AudioMixerGainDisplaysMix2Gain2Disp
				RollCallString,
			iqdec01AudioMixerGainDisplaysMix2Gain3Disp
				RollCallString,
			iqdec01AudioMixerGainDisplaysMix2Gain4Disp
				RollCallString,
			iqdec01AudioMixerGainDisplaysMix2Gain5Disp
				RollCallString,
			iqdec01AudioMixerGainDisplaysMix2Gain6Disp
				RollCallString,
			iqdec01AudioMixerGainDisplaysMix2Gain7Disp
				RollCallString,
			iqdec01AudioMixerGainDisplaysMix2Gain8Disp
				RollCallString,
			iqdec01AudioMixerGainDisplaysMix3Gain1Disp
				RollCallString,
			iqdec01AudioMixerGainDisplaysMix3Gain2Disp
				RollCallString,
			iqdec01AudioMixerGainDisplaysMix3Gain3Disp
				RollCallString,
			iqdec01AudioMixerGainDisplaysMix3Gain4Disp
				RollCallString,
			iqdec01AudioMixerGainDisplaysMix3Gain5Disp
				RollCallString,
			iqdec01AudioMixerGainDisplaysMix3Gain6Disp
				RollCallString,
			iqdec01AudioMixerGainDisplaysMix3Gain7Disp
				RollCallString,
			iqdec01AudioMixerGainDisplaysMix3Gain8Disp
				RollCallString,
			iqdec01AudioMixerGainDisplaysMix4Gain1Disp
				RollCallString,
			iqdec01AudioMixerGainDisplaysMix4Gain2Disp
				RollCallString,
			iqdec01AudioMixerGainDisplaysMix4Gain3Disp
				RollCallString,
			iqdec01AudioMixerGainDisplaysMix4Gain4Disp
				RollCallString,
			iqdec01AudioMixerGainDisplaysMix4Gain5Disp
				RollCallString,
			iqdec01AudioMixerGainDisplaysMix4Gain6Disp
				RollCallString,
			iqdec01AudioMixerGainDisplaysMix4Gain7Disp
				RollCallString,
			iqdec01AudioMixerGainDisplaysMix4Gain8Disp
				RollCallString,
			iqdec01AudioBusAandBBusALSrc
				INTEGER,
			iqdec01AudioBusAandBBusASrcR
				INTEGER,
			iqdec01AudioBusAandBBusALGain
				INTEGER,
			iqdec01AudioBusAandBBusAGainR
				INTEGER,
			iqdec01AudioBusAandBBusALInvert
				INTEGER,
			iqdec01AudioBusAandBBusAInvertR
				INTEGER,
			iqdec01AudioBusAandBBusALMute
				INTEGER,
			iqdec01AudioBusAandBBusAMuteR
				INTEGER,
			iqdec01AudioBusAandBBusAStereo
				INTEGER,
			iqdec01AudioBusAandBBusBLSrc
				INTEGER,
			iqdec01AudioBusAandBBusBSrcR
				INTEGER,
			iqdec01AudioBusAandBBusBLGain
				INTEGER,
			iqdec01AudioBusAandBBusBGainR
				INTEGER,
			iqdec01AudioBusAandBBusBLInvert
				INTEGER,
			iqdec01AudioBusAandBBusBInvertR
				INTEGER,
			iqdec01AudioBusAandBBusBLMute
				INTEGER,
			iqdec01AudioBusAandBBusBMuteR
				INTEGER,
			iqdec01AudioBusAandBBusBStereo
				INTEGER,
			iqdec01AudioOutputsEmbedder1Source
				INTEGER,
			iqdec01AudioOutputsEmbedder1Destination
				INTEGER,
			iqdec01AudioOutputsEmbedder1Disable
				INTEGER,
			iqdec01AudioOutputsEmbedder2Source
				INTEGER,
			iqdec01AudioOutputsEmbedder2Destination
				INTEGER,
			iqdec01AudioOutputsEmbedder2Disable
				INTEGER,
			iqdec01AudioOutputsAES1Source
				INTEGER,
			iqdec01AudioOutputsAES2Source
				INTEGER,
			iqdec01AudioDelaySetupSetManual
				INTEGER,
			iqdec01AudioDelaySetupIncludeManual
				INTEGER,
			iqdec01AudioDelaySetupIncludeInternal
				INTEGER,
			iqdec01AudioDelaySetupIncludeGPI
				INTEGER,
			iqdec01AudioDelaySetupIncludeRTrack14
				INTEGER,
			iqdec01AudioDelaySetupIncludeRTrack15
				INTEGER,
			iqdec01AudioDelaySetupIncludeRTrack16
				INTEGER,
			iqdec01AudioDelaySetupIncludeRTrack17
				INTEGER,
			iqdec01AudioDelaySetupTotalDelay
				RollCallString,
			iqdec01AudioDelaySetupManual
				RollCallString,
			iqdec01AudioDelaySetupInternal
				RollCallString,
			iqdec01AudioDelaySetupGPI
				RollCallString,
			iqdec01AudioDelaySetupRTrack14
				RollCallString,
			iqdec01AudioDelaySetupRTrack15
				RollCallString,
			iqdec01AudioDelaySetupRTrack16
				RollCallString,
			iqdec01AudioDelaySetupRTrack17
				RollCallString,
			iqdec01AudioSetupHeadroom
				INTEGER,
			iqdec01AudioSetupLineUp
				INTEGER,
			iqdec01AudioSetupAudioSlewSelect
				INTEGER,
			iqdec01AudioSetupAudioToneFrequencyLeft
				INTEGER,
			iqdec01AudioSetupAudioToneFrequencyRight
				INTEGER,
			iqdec01AudioSetupAudioToneIdentifyTone
				INTEGER,
			iqdec01AudioSetupAudioMonitoringSilence
				INTEGER,
			iqdec01AudioSetupAudioMonitoringLowLevel
				INTEGER,
			iqdec01AudioSetupAudioMonitoringHighLevel
				INTEGER,
			iqdec01AudioSetupAudioMonitoringOverload
				INTEGER,
			iqdec01AudioSetupAudioMonitoringWarningTimer
				INTEGER,
			iqdec01AudioSetupChannelStatusChannelStatusDest
				RollCallString,
			iqdec01AudioSetupChannelStatusAESValidityBit
				INTEGER,
			iqdec01AudioSetupCalibrateAudio
				INTEGER,
			iqdec01AudioSetupCalonVideoIPSel
				INTEGER,
			iqdec01Decoder
				INTEGER,
			iqdec01DecoderColorKiller
				INTEGER,
			iqdec01DecoderMinimumDelay
				INTEGER,
			iqdec01DecoderSECAMStudioNotch
				INTEGER,
			iqdec01DecoderSECAMStudioLumaBandwidth
				INTEGER,
			iqdec01DecoderSECAMVHSLumaBandwidth
				INTEGER,
			iqdec01GenlockReferenceSrc
				INTEGER,
			iqdec01GenlockReferenceTimeHPhase625
				INTEGER,
			iqdec01GenlockReferenceTimeVPhase625
				INTEGER,
			iqdec01GenlockReferenceTimeHPhase525
				INTEGER,
			iqdec01GenlockReferenceTimeVPhase525
				INTEGER,
			iqdec01GenlockReferenceTimeHDelay625
				INTEGER,
			iqdec01GenlockReferenceTimeVDelay625
				INTEGER,
			iqdec01GenlockReferenceTimeHDelay525
				INTEGER,
			iqdec01GenlockReferenceTimeVDelay525
				INTEGER,
			iqdec01GenlockFreerunFrequency
				INTEGER,
			iqdec01GenlockFrameDelay
				INTEGER,
			iqdec01SetupPatternPatternType
				INTEGER,
			iqdec01SetupPatternPatternEnable
				INTEGER,
			iqdec01SetupPatternAnimatedPattern
				INTEGER,
			iqdec01SetupCaptionEditCaption
				RollCallString,
			iqdec01SetupCaptionCaptionSelect
				INTEGER,
			iqdec01525Pass525Lines1122Line11
				INTEGER,
			iqdec01525Pass525Lines1122Line12
				INTEGER,
			iqdec01525Pass525Lines1122Line13
				INTEGER,
			iqdec01525Pass525Lines1122Line14
				INTEGER,
			iqdec01525Pass525Lines1122Line15
				INTEGER,
			iqdec01525Pass525Lines1122Line16
				INTEGER,
			iqdec01525Pass525Lines1122Line17
				INTEGER,
			iqdec01525Pass525Lines1122Line18
				INTEGER,
			iqdec01525Pass525Lines1122Line19
				INTEGER,
			iqdec01525Pass525Lines1122Line20
				INTEGER,
			iqdec01525Pass525Lines1122Line21
				INTEGER,
			iqdec01525Pass525Lines1122Line22
				INTEGER,
			iqdec01525Pass525Lines274285Line274
				INTEGER,
			iqdec01525Pass525Lines274285Line275
				INTEGER,
			iqdec01525Pass525Lines274285Line276
				INTEGER,
			iqdec01525Pass525Lines274285Line277
				INTEGER,
			iqdec01525Pass525Lines274285Line278
				INTEGER,
			iqdec01525Pass525Lines274285Line279
				INTEGER,
			iqdec01525Pass525Lines274285Line280
				INTEGER,
			iqdec01525Pass525Lines274285Line281
				INTEGER,
			iqdec01525Pass525Lines274285Line282
				INTEGER,
			iqdec01525Pass525Lines274285Line283
				INTEGER,
			iqdec01525Pass525Lines274285Line284
				INTEGER,
			iqdec01525Pass525Lines274285Line285
				INTEGER,
			iqdec01625Pass625Lines723Line7
				INTEGER,
			iqdec01625Pass625Lines723Line8
				INTEGER,
			iqdec01625Pass625Lines723Line9
				INTEGER,
			iqdec01625Pass625Lines723Line10
				INTEGER,
			iqdec01625Pass625Lines723Line11
				INTEGER,
			iqdec01625Pass625Lines723Line12
				INTEGER,
			iqdec01625Pass625Lines723Line13
				INTEGER,
			iqdec01625Pass625Lines723Line14
				INTEGER,
			iqdec01625Pass625Lines723Line15
				INTEGER,
			iqdec01625Pass625Lines723Line16
				INTEGER,
			iqdec01625Pass625Lines723Line17
				INTEGER,
			iqdec01625Pass625Lines723Line18
				INTEGER,
			iqdec01625Pass625Lines723Line19
				INTEGER,
			iqdec01625Pass625Lines723Line20
				INTEGER,
			iqdec01625Pass625Lines723Line21
				INTEGER,
			iqdec01625Pass625Lines723Line22
				INTEGER,
			iqdec01625Pass625Lines723Line23
				INTEGER,
			iqdec01625Pass625Lines320335Line320
				INTEGER,
			iqdec01625Pass625Lines320335Line321
				INTEGER,
			iqdec01625Pass625Lines320335Line322
				INTEGER,
			iqdec01625Pass625Lines320335Line323
				INTEGER,
			iqdec01625Pass625Lines320335Line324
				INTEGER,
			iqdec01625Pass625Lines320335Line325
				INTEGER,
			iqdec01625Pass625Lines320335Line326
				INTEGER,
			iqdec01625Pass625Lines320335Line327
				INTEGER,
			iqdec01625Pass625Lines320335Line328
				INTEGER,
			iqdec01625Pass625Lines320335Line329
				INTEGER,
			iqdec01625Pass625Lines320335Line330
				INTEGER,
			iqdec01625Pass625Lines320335Line331
				INTEGER,
			iqdec01625Pass625Lines320335Line332
				INTEGER,
			iqdec01625Pass625Lines320335Line333
				INTEGER,
			iqdec01625Pass625Lines320335Line334
				INTEGER,
			iqdec01625Pass625Lines320335Line335
				INTEGER,
			iqdec01SetupVBIHANCBlankHANCBlank
				INTEGER,
			iqdec01SetupVBIHANCBlankSECAMBottles
				INTEGER,
			iqdec01SetupGPIIOGPIMode
				INTEGER,
			iqdec01SetupGPIIOGPIipSelect
				INTEGER,
			iqdec01SetupGPIIOGPIopSelect
				INTEGER,
			iqdec01SetupGPIIOOutActiveHigh
				INTEGER,
			iqdec01SetupGPIIOTimerActiveHigh
				INTEGER,
			iqdec01SetupGPIIOAudioDelay
				INTEGER,
			iqdec01SetupGPIIOGPIInDelay
				RollCallString,
			iqdec01SetupGPIIOGPIOutDelay
				RollCallString,
			iqdec01SetupRollTrackDisableAll
				INTEGER,
			iqdec01SetupRollTrackIndex
				INTEGER,
			iqdec01SetupRollTrackSource
				INTEGER,
			iqdec01SetupRollTrackAddress
				RollCallString,
			iqdec01SetupRollTrackCommand
				RollCallString,
			iqdec01SetupRollTrackStatus
				RollCallString,
			iqdec01SetupRollTrackSending
				RollCallString,
			iqdec01SetupEnableLoggingInput
				INTEGER,
			iqdec01SetupLoggingInput
				RollCallString,
			iqdec01SetupEnableLoggingStd
				INTEGER,
			iqdec01SetupLoggingStd
				RollCallString,
			iqdec01SetupEnableLoggingReference
				INTEGER,
			iqdec01SetupLoggingReference
				RollCallString,
			iqdec01SetupEnableLoggingEDH
				INTEGER,
			iqdec01SetupLoggingEDH
				RollCallString,
			iqdec01SetupEnableLoggingEDHErr
				INTEGER,
			iqdec01SetupLoggingEDHErr
				RollCallString,
			iqdec01SetupEnableLoggingRollTrack
				INTEGER,
			iqdec01SetupLoggingRollTrack
				RollCallString,
			iqdec01SetupEnableLoggingDeemb1
				INTEGER,
			iqdec01SetupLoggingDeemb1
				RollCallString,
			iqdec01SetupEnableLoggingDeemb2
				INTEGER,
			iqdec01SetupLoggingDeemb2
				RollCallString,
			iqdec01SetupEnableLoggingDeemb3
				INTEGER,
			iqdec01SetupLoggingDeemb3
				RollCallString,
			iqdec01SetupEnableLoggingDeemb4
				INTEGER,
			iqdec01SetupLoggingDeemb4
				RollCallString,
			iqdec01SetupEnableLoggingDeemb5
				INTEGER,
			iqdec01SetupLoggingDeemb5
				RollCallString,
			iqdec01SetupEnableLoggingDeemb6
				INTEGER,
			iqdec01SetupLoggingDeemb6
				RollCallString,
			iqdec01SetupEnableLoggingDeemb7
				INTEGER,
			iqdec01SetupLoggingDeemb7
				RollCallString,
			iqdec01SetupEnableLoggingDeemb8
				INTEGER,
			iqdec01SetupLoggingDeemb8
				RollCallString,
			iqdec01SetupEnableLoggingnPCM1
				INTEGER,
			iqdec01SetupLoggingnPCM1
				RollCallString,
			iqdec01SetupEnableLoggingnPCM2
				INTEGER,
			iqdec01SetupLoggingnPCM2
				RollCallString,
			iqdec01SetupEnableLoggingnPCM3
				INTEGER,
			iqdec01SetupLoggingnPCM3
				RollCallString,
			iqdec01SetupEnableLoggingnPCM4
				INTEGER,
			iqdec01SetupLoggingnPCM4
				RollCallString,
			iqdec01SetupEnableLoggingnPCM5
				INTEGER,
			iqdec01SetupLoggingnPCM5
				RollCallString,
			iqdec01SetupEnableLoggingnPCM6
				INTEGER,
			iqdec01SetupLoggingnPCM6
				RollCallString,
			iqdec01SetupEnableLoggingnPCM7
				INTEGER,
			iqdec01SetupLoggingnPCM7
				RollCallString,
			iqdec01SetupEnableLoggingnPCM8
				INTEGER,
			iqdec01SetupLoggingnPCM8
				RollCallString,
			iqdec01SetupEnableLoggingANALOG1L
				INTEGER,
			iqdec01SetupLoggingANALOG1L
				RollCallString,
			iqdec01SetupEnableLoggingANALOG1R
				INTEGER,
			iqdec01SetupLoggingANALOG1R
				RollCallString,
			iqdec01SetupEnableLoggingANALOG2L
				INTEGER,
			iqdec01SetupLoggingANALOG2L
				RollCallString,
			iqdec01SetupEnableLoggingANALOG2R
				INTEGER,
			iqdec01SetupLoggingANALOG2R
				RollCallString,
			iqdec01SetupEnableLoggingBUSAL
				INTEGER,
			iqdec01SetupLoggingBUSAL
				RollCallString,
			iqdec01SetupEnableLoggingBUSAR
				INTEGER,
			iqdec01SetupLoggingBUSAR
				RollCallString,
			iqdec01SetupEnableLoggingBUSBL
				INTEGER,
			iqdec01SetupLoggingBUSBL
				RollCallString,
			iqdec01SetupEnableLoggingBUSBR
				INTEGER,
			iqdec01SetupLoggingBUSBR
				RollCallString,
			iqdec01SetupDefaultOutput
				INTEGER,
			iqdec01SetupDefaultOutputDefaultPattern
				INTEGER,
			iqdec01SetupDefaultOutputDefaultCaption
				RollCallString,
			iqdec01SetupInformationWindow
				INTEGER,
			iqdec01SetupSoftwareVersion
				RollCallString,
			iqdec01SetupSerialNumber
				RollCallString,
			iqdec01SetupBuildNumber
				RollCallString,
			iqdec01SetupFPGASyncVersion
				RollCallString,
			iqdec01SetupFPGADecVersion
				RollCallString,
			iqdec01SetupRestart
				INTEGER,
			iqdec01SetupErrorSecondsReset
				INTEGER,
			iqdec01SetupFactoryDefault
				INTEGER,
			iqdec01SetupRollTrack14
				INTEGER,
			iqdec01SetupRollTrack15
				INTEGER,
			iqdec01SetupRollTrack16
				INTEGER,
			iqdec01SetupRollTrack17
				INTEGER,
			iqdec01UserMemoryRecall
				INTEGER,
			iqdec01UserMemoryClear
				INTEGER,
			iqdec01UserMemory1Name
				RollCallString,
			iqdec01UserMemorySave
				INTEGER,
			iqdec01UserMemory2Name
				RollCallString,
			iqdec01UserMemory3Name
				RollCallString,
			iqdec01UserMemory4Name
				RollCallString,
			iqdec01UserMemory5Name
				RollCallString,
			iqdec01UserMemory6Name
				RollCallString,
			iqdec01UserMemory7Name
				RollCallString,
			iqdec01UserMemory8Name
				RollCallString,
			iqdec01UserMem
				INTEGER,
			iqdec01Freeze
				INTEGER
		}

	iqdec01SlotIndex OBJECT-TYPE
		SYNTAX		Unsigned32
		MAX-ACCESS		not-accessible
		STATUS			current
		DESCRIPTION
				"The unique Index value for each slot.  Its value
					ranges between 1 and the value of slotNumber."
		::= { iqdec01CmdEntry 0 }


	iqdec01VideoInputSelect OBJECT-TYPE
		SYNTAX		INTEGER {
							val_Composite_A(0),
							val_Composite_B(1),
							val_YC(2),
							val_SDI(3)
							}
		MAX-ACCESS		read-write
		STATUS			current
		DESCRIPTION
				"TYPE: - RadiobuttonList
				 PAGE: - Video
					Select  cmdID= 1002
					Composite A  value= 0
					Composite B  value= 1
					YC  value= 2
					SDI  value= 3  "
		::= { iqdec01CmdEntry 1002 }


	iqdec01InputCompositeStdPAL OBJECT-TYPE
		SYNTAX		INTEGER { disable(0), enable(1) }
		MAX-ACCESS		read-write
		STATUS			current
		DESCRIPTION
				"TYPE: - Checkbox
				 PAGE: - Video
					PAL  cmdID= 4912 "
		::= { iqdec01CmdEntry 4912 }


	iqdec01InputCompositeStdNTSC OBJECT-TYPE
		SYNTAX		INTEGER { disable(0), enable(1) }
		MAX-ACCESS		read-write
		STATUS			current
		DESCRIPTION
				"TYPE: - Checkbox
				 PAGE: - Video
					NTSC  cmdID= 4913 "
		::= { iqdec01CmdEntry 4913 }


	iqdec01InputCompositeStdNTSCJ OBJECT-TYPE
		SYNTAX		INTEGER { disable(0), enable(1) }
		MAX-ACCESS		read-write
		STATUS			current
		DESCRIPTION
				"TYPE: - Checkbox
				 PAGE: - Video
					NTSC J  cmdID= 4914 "
		::= { iqdec01CmdEntry 4914 }


	iqdec01InputCompositeStdPALM OBJECT-TYPE
		SYNTAX		INTEGER { disable(0), enable(1) }
		MAX-ACCESS		read-write
		STATUS			current
		DESCRIPTION
				"TYPE: - Checkbox
				 PAGE: - Video
					PAL M  cmdID= 4915 "
		::= { iqdec01CmdEntry 4915 }


	iqdec01InputCompositeStdPALN OBJECT-TYPE
		SYNTAX		INTEGER { disable(0), enable(1) }
		MAX-ACCESS		read-write
		STATUS			current
		DESCRIPTION
				"TYPE: - Checkbox
				 PAGE: - Video
					PAL N  cmdID= 4916 "
		::= { iqdec01CmdEntry 4916 }


	iqdec01InputCompositeStdSECAM OBJECT-TYPE
		SYNTAX		INTEGER { disable(0), enable(1) }
		MAX-ACCESS		read-write
		STATUS			current
		DESCRIPTION
				"TYPE: - Checkbox
				 PAGE: - Video
					SECAM  cmdID= 4917 "
		::= { iqdec01CmdEntry 4917 }


	iqdec01InputCompositeStdN44360 OBJECT-TYPE
		SYNTAX		INTEGER { disable(0), enable(1) }
		MAX-ACCESS		read-write
		STATUS			current
		DESCRIPTION
				"TYPE: - Checkbox
				 PAGE: - Video
					N4.43 60  cmdID= 4918 "
		::= { iqdec01CmdEntry 4918 }


	iqdec01InputCompositeStdPAL44360 OBJECT-TYPE
		SYNTAX		INTEGER { disable(0), enable(1) }
		MAX-ACCESS		read-write
		STATUS			current
		DESCRIPTION
				"TYPE: - Checkbox
				 PAGE: - Video
					PAL4.43 60  cmdID= 4919 "
		::= { iqdec01CmdEntry 4919 }


	iqdec01InputSDIStd525 OBJECT-TYPE
		SYNTAX		INTEGER { disable(0), enable(1) }
		MAX-ACCESS		read-write
		STATUS			current
		DESCRIPTION
				"TYPE: - Checkbox
				 PAGE: - Video
					525  cmdID= 1100 "
		::= { iqdec01CmdEntry 1100 }


	iqdec01InputSDIStd625 OBJECT-TYPE
		SYNTAX		INTEGER { disable(0), enable(1) }
		MAX-ACCESS		read-write
		STATUS			current
		DESCRIPTION
				"TYPE: - Checkbox
				 PAGE: - Video
					625  cmdID= 1101 "
		::= { iqdec01CmdEntry 1101 }


	iqdec01VideoProcampLumaGain OBJECT-TYPE
		SYNTAX		INTEGER
		MAX-ACCESS		read-write
		STATUS			current
		DESCRIPTION
				"TYPE: - Number
				 PAGE: - Video
					Luma Gain  cmdID= 1600  min= -60  max= 60  step= 1  format= %0.1fdB  div_scale= 10
					Min = -6.0dB  Max = 6.0dB  Step = 0.1dB "
		::= { iqdec01CmdEntry 1600 }


	iqdec01VideoProcampBlackLevel OBJECT-TYPE
		SYNTAX		INTEGER
		MAX-ACCESS		read-write
		STATUS			current
		DESCRIPTION
				"TYPE: - Number
				 PAGE: - Video
					Black Level  cmdID= 1601  min= -1200  max= 1200  step= 5  format= %0.1fmV  div_scale= 10
					Min = -120.0mV  Max = 120.0mV  Step = 0.5mV "
		::= { iqdec01CmdEntry 1601 }


	iqdec01VideoProcampChromaGain OBJECT-TYPE
		SYNTAX		INTEGER
		MAX-ACCESS		read-write
		STATUS			current
		DESCRIPTION
				"TYPE: - Number
				 PAGE: - Video
					Chroma Gain  cmdID= 1602  min= -60  max= 60  step= 1  format= %0.1fdB  div_scale= 10
					Min = -6.0dB  Max = 6.0dB  Step = 0.1dB "
		::= { iqdec01CmdEntry 1602 }


	iqdec01VideoProcampNTSCHue OBJECT-TYPE
		SYNTAX		INTEGER
		MAX-ACCESS		read-write
		STATUS			current
		DESCRIPTION
				"TYPE: - Number
				 PAGE: - Video
					NTSC Hue  cmdID= 4908  min= -45  max= 45  step= 1  format= %0.0fdegs  div_scale= 1
					Min = -45degs  Max = 45degs  Step = 1degs "
		::= { iqdec01CmdEntry 4908 }


	iqdec01VideoProcampVEnhance OBJECT-TYPE
		SYNTAX		INTEGER
		MAX-ACCESS		read-write
		STATUS			current
		DESCRIPTION
				"TYPE: - Number
				 PAGE: - Video
					V Enhance  cmdID= 1603  min= 0  max= 3  step= 1  format= %0.0f  div_scale= 1
					Min = 0  Max = 3  Step = 1 "
		::= { iqdec01CmdEntry 1603 }


	iqdec01VideoProcampHEnhance OBJECT-TYPE
		SYNTAX		INTEGER
		MAX-ACCESS		read-write
		STATUS			current
		DESCRIPTION
				"TYPE: - Number
				 PAGE: - Video
					H Enhance  cmdID= 1604  min= 0  max= 3  step= 1  format= %0.0f  div_scale= 1
					Min = 0  Max = 3  Step = 1 "
		::= { iqdec01CmdEntry 1604 }


	iqdec01VideoProcampHEnhanceFreq OBJECT-TYPE
		SYNTAX		INTEGER {
							val_3_375_MHz(0),
							val_2_250_MHz(1)
							}
		MAX-ACCESS		read-write
		STATUS			current
		DESCRIPTION
				"TYPE: - RadiobuttonList
				 PAGE: - Video
					H Enhance Freq  cmdID= 1605
					3.375 MHz  value= 0
					2.250 MHz  value= 1  "
		::= { iqdec01CmdEntry 1605 }


	iqdec01VideoProcampPicturePosition OBJECT-TYPE
		SYNTAX		INTEGER
		MAX-ACCESS		read-write
		STATUS			current
		DESCRIPTION
				"TYPE: - Number
				 PAGE: - Video
					Picture Position  cmdID= 1606  min= -592  max= 592  step= 148  format= %0.1fns  div_scale= 1
					Min = -592.0ns  Max = 592.0ns  Step = 148.0ns "
		::= { iqdec01CmdEntry 1606 }


	iqdec01VideoProcampYCTiming OBJECT-TYPE
		SYNTAX		INTEGER
		MAX-ACCESS		read-write
		STATUS			current
		DESCRIPTION
				"TYPE: - Number
				 PAGE: - Video
					Y/C Timing  cmdID= 1607  min= -592  max= 592  step= 148  format= %0.1fns  div_scale= 1
					Min = -592.0ns  Max = 592.0ns  Step = 148.0ns "
		::= { iqdec01CmdEntry 1607 }


	iqdec01ProcampBordersLeft OBJECT-TYPE
		SYNTAX		INTEGER
		MAX-ACCESS		read-write
		STATUS			current
		DESCRIPTION
				"TYPE: - Number
				 PAGE: - Video
					Left  cmdID= 1400  min= 0  max= 200  step= 2  format= %0.0fpx  div_scale= 1
					Min = 0px  Max = 200px  Step = 2px "
		::= { iqdec01CmdEntry 1400 }


	iqdec01ProcampBordersRed OBJECT-TYPE
		SYNTAX		INTEGER
		MAX-ACCESS		read-write
		STATUS			current
		DESCRIPTION
				"TYPE: - Number
				 PAGE: - Video
					Red  cmdID= 1404  min= 0  max= 255  step= 1  format= %0.0f  div_scale= 1
					Min = 0  Max = 255  Step = 1 "
		::= { iqdec01CmdEntry 1404 }


	iqdec01ProcampBordersRight OBJECT-TYPE
		SYNTAX		INTEGER
		MAX-ACCESS		read-write
		STATUS			current
		DESCRIPTION
				"TYPE: - Number
				 PAGE: - Video
					Right  cmdID= 1401  min= 0  max= 200  step= 2  format= %0.0fpx  div_scale= 1
					Min = 0px  Max = 200px  Step = 2px "
		::= { iqdec01CmdEntry 1401 }


	iqdec01ProcampBordersGreen OBJECT-TYPE
		SYNTAX		INTEGER
		MAX-ACCESS		read-write
		STATUS			current
		DESCRIPTION
				"TYPE: - Number
				 PAGE: - Video
					Green  cmdID= 1405  min= 0  max= 255  step= 1  format= %0.0f  div_scale= 1
					Min = 0  Max = 255  Step = 1 "
		::= { iqdec01CmdEntry 1405 }


	iqdec01ProcampBordersTop OBJECT-TYPE
		SYNTAX		INTEGER
		MAX-ACCESS		read-write
		STATUS			current
		DESCRIPTION
				"TYPE: - Number
				 PAGE: - Video
					Top  cmdID= 1402  min= 0  max= 200  step= 1  format= %0.0fln  div_scale= 1
					Min = 0ln  Max = 200ln  Step = 1ln "
		::= { iqdec01CmdEntry 1402 }


	iqdec01ProcampBordersBlue OBJECT-TYPE
		SYNTAX		INTEGER
		MAX-ACCESS		read-write
		STATUS			current
		DESCRIPTION
				"TYPE: - Number
				 PAGE: - Video
					Blue  cmdID= 1406  min= 0  max= 255  step= 1  format= %0.0f  div_scale= 1
					Min = 0  Max = 255  Step = 1 "
		::= { iqdec01CmdEntry 1406 }


	iqdec01ProcampBordersBottom OBJECT-TYPE
		SYNTAX		INTEGER
		MAX-ACCESS		read-write
		STATUS			current
		DESCRIPTION
				"TYPE: - Number
				 PAGE: - Video
					Bottom  cmdID= 1403  min= 0  max= 200  step= 1  format= %0.0fln  div_scale= 1
					Min = 0ln  Max = 200ln  Step = 1ln "
		::= { iqdec01CmdEntry 1403 }


	iqdec01VideoNoiseReducerLumaStrength OBJECT-TYPE
		SYNTAX		INTEGER
		MAX-ACCESS		read-write
		STATUS			current
		DESCRIPTION
				"TYPE: - Number
				 PAGE: - Video
					Luma Strength  cmdID= 7600  min= 0  max= 31  step= 1  format= %0.0f  div_scale= 1
					Min = 0  Max = 31  Step = 1 "
		::= { iqdec01CmdEntry 7600 }


	iqdec01VideoNoiseReducerChromaStrength OBJECT-TYPE
		SYNTAX		INTEGER
		MAX-ACCESS		read-write
		STATUS			current
		DESCRIPTION
				"TYPE: - Number
				 PAGE: - Video
					Chroma Strength  cmdID= 7601  min= 0  max= 31  step= 1  format= %0.0f  div_scale= 1
					Min = 0  Max = 31  Step = 1 "
		::= { iqdec01CmdEntry 7601 }


	iqdec01VideoNoiseReducerThresholdMode OBJECT-TYPE
		SYNTAX		INTEGER {
							val_Auto(0),
							val_Manual(1)
							}
		MAX-ACCESS		read-write
		STATUS			current
		DESCRIPTION
				"TYPE: - RadiobuttonList
				 PAGE: - Video
					Threshold Mode  cmdID= 7602
					Auto  value= 0
					Manual  value= 1  "
		::= { iqdec01CmdEntry 7602 }


	iqdec01VideoNoiseReducerManualThreshold OBJECT-TYPE
		SYNTAX		INTEGER
		MAX-ACCESS		read-write
		STATUS			current
		DESCRIPTION
				"TYPE: - Number
				 PAGE: - Video
					Manual Threshold  cmdID= 7603  min= 0  max= 15  step= 1  format= %0.0f  div_scale= 1
					Min = 0  Max = 15  Step = 1 "
		::= { iqdec01CmdEntry 7603 }


	iqdec01VideoNoiseReducerAutoBias OBJECT-TYPE
		SYNTAX		INTEGER
		MAX-ACCESS		read-write
		STATUS			current
		DESCRIPTION
				"TYPE: - Number
				 PAGE: - Video
					Auto Bias  cmdID= 7604  min= -7  max= 7  step= 1  format= %0.0f  div_scale= 1
					Min = -7  Max = 7  Step = 1 "
		::= { iqdec01CmdEntry 7604 }


	iqdec01VideoNoiseReducerDelayMode OBJECT-TYPE
		SYNTAX		INTEGER {
							val_Normal_Delay(0),
							val_Minimum_Delay(1)
							}
		MAX-ACCESS		read-write
		STATUS			current
		DESCRIPTION
				"TYPE: - RadiobuttonList
				 PAGE: - Video
					Delay Mode  cmdID= 7605
					Normal Delay   value= 0
					Minimum Delay  value= 1  "
		::= { iqdec01CmdEntry 7605 }


	iqdec01VideoNoiseReducerNoiseMeasured OBJECT-TYPE
		SYNTAX		RollCallString
		MAX-ACCESS		read-only
		STATUS			current
		DESCRIPTION
				"TYPE: - Display
				 PAGE: - Video
					Noise Measured  cmdID= 7606  format=   "
		::= { iqdec01CmdEntry 7606 }

	iqdec01DeembedPair14DeembedPair1LGain OBJECT-TYPE
		SYNTAX		INTEGER
		MAX-ACCESS		read-write
		STATUS			current
		DESCRIPTION
				"TYPE: - Number
				 PAGE: - Audio- De-embed Pair 1-4
					L-Gain  cmdID= 4000  min= -180  max= 180  step= 1  format= %0.1fdB  div_scale= 10
					Min = -18.0dB  Max = 18.0dB  Step = 0.1dB "
		::= { iqdec01CmdEntry 4000 }


	iqdec01DeembedPair14DeembedPair1GainR OBJECT-TYPE
		SYNTAX		INTEGER
		MAX-ACCESS		read-write
		STATUS			current
		DESCRIPTION
				"TYPE: - Number
				 PAGE: - Audio- De-embed Pair 1-4
					Gain-R  cmdID= 4001  min= -180  max= 180  step= 1  format= %0.1fdB  div_scale= 10
					Min = -18.0dB  Max = 18.0dB  Step = 0.1dB "
		::= { iqdec01CmdEntry 4001 }


	iqdec01DeembedPair14DeembedPair1LInvert OBJECT-TYPE
		SYNTAX		INTEGER { disable(0), enable(1) }
		MAX-ACCESS		read-write
		STATUS			current
		DESCRIPTION
				"TYPE: - Checkbox
				 PAGE: - Audio- De-embed Pair 1-4
					L-Invert  cmdID= 4002 "
		::= { iqdec01CmdEntry 4002 }


	iqdec01DeembedPair14DeembedPair1InvertR OBJECT-TYPE
		SYNTAX		INTEGER { disable(0), enable(1) }
		MAX-ACCESS		read-write
		STATUS			current
		DESCRIPTION
				"TYPE: - Checkbox
				 PAGE: - Audio- De-embed Pair 1-4
					Invert-R  cmdID= 4003 "
		::= { iqdec01CmdEntry 4003 }


	iqdec01DeembedPair14DeembedPair1LMute OBJECT-TYPE
		SYNTAX		INTEGER { disable(0), enable(1) }
		MAX-ACCESS		read-write
		STATUS			current
		DESCRIPTION
				"TYPE: - Checkbox
				 PAGE: - Audio- De-embed Pair 1-4
					L-Mute  cmdID= 4004 "
		::= { iqdec01CmdEntry 4004 }


	iqdec01DeembedPair14DeembedPair1MuteR OBJECT-TYPE
		SYNTAX		INTEGER { disable(0), enable(1) }
		MAX-ACCESS		read-write
		STATUS			current
		DESCRIPTION
				"TYPE: - Checkbox
				 PAGE: - Audio- De-embed Pair 1-4
					Mute-R  cmdID= 4005 "
		::= { iqdec01CmdEntry 4005 }


	iqdec01DeembedPair14DeembedPair1Stereo OBJECT-TYPE
		SYNTAX		INTEGER { disable(0), enable(1) }
		MAX-ACCESS		read-write
		STATUS			current
		DESCRIPTION
				"TYPE: - Checkbox
				 PAGE: - Audio- De-embed Pair 1-4
					Stereo  cmdID= 4006 "
		::= { iqdec01CmdEntry 4006 }


	iqdec01DeembedPair14DeembedPair1Delay OBJECT-TYPE
		SYNTAX		INTEGER
		MAX-ACCESS		read-write
		STATUS			current
		DESCRIPTION
				"TYPE: - Number
				 PAGE: - Audio- De-embed Pair 1-4
					Delay  cmdID= 4007  min= 0  max= 1500  step= 1  format= %0.0fms  div_scale= 1
					Min = 0ms  Max = 1500ms  Step = 1ms "
		::= { iqdec01CmdEntry 4007 }


	iqdec01DeembedPair14DeembedPair2LGain OBJECT-TYPE
		SYNTAX		INTEGER
		MAX-ACCESS		read-write
		STATUS			current
		DESCRIPTION
				"TYPE: - Number
				 PAGE: - Audio- De-embed Pair 1-4
					L-Gain  cmdID= 4010  min= -180  max= 180  step= 1  format= %0.1fdB  div_scale= 10
					Min = -18.0dB  Max = 18.0dB  Step = 0.1dB "
		::= { iqdec01CmdEntry 4010 }


	iqdec01DeembedPair14DeembedPair2GainR OBJECT-TYPE
		SYNTAX		INTEGER
		MAX-ACCESS		read-write
		STATUS			current
		DESCRIPTION
				"TYPE: - Number
				 PAGE: - Audio- De-embed Pair 1-4
					Gain-R  cmdID= 4011  min= -180  max= 180  step= 1  format= %0.1fdB  div_scale= 10
					Min = -18.0dB  Max = 18.0dB  Step = 0.1dB "
		::= { iqdec01CmdEntry 4011 }


	iqdec01DeembedPair14DeembedPair2LInvert OBJECT-TYPE
		SYNTAX		INTEGER { disable(0), enable(1) }
		MAX-ACCESS		read-write
		STATUS			current
		DESCRIPTION
				"TYPE: - Checkbox
				 PAGE: - Audio- De-embed Pair 1-4
					L-Invert  cmdID= 4012 "
		::= { iqdec01CmdEntry 4012 }


	iqdec01DeembedPair14DeembedPair2InvertR OBJECT-TYPE
		SYNTAX		INTEGER { disable(0), enable(1) }
		MAX-ACCESS		read-write
		STATUS			current
		DESCRIPTION
				"TYPE: - Checkbox
				 PAGE: - Audio- De-embed Pair 1-4
					Invert-R  cmdID= 4013 "
		::= { iqdec01CmdEntry 4013 }


	iqdec01DeembedPair14DeembedPair2LMute OBJECT-TYPE
		SYNTAX		INTEGER { disable(0), enable(1) }
		MAX-ACCESS		read-write
		STATUS			current
		DESCRIPTION
				"TYPE: - Checkbox
				 PAGE: - Audio- De-embed Pair 1-4
					L-Mute  cmdID= 4014 "
		::= { iqdec01CmdEntry 4014 }


	iqdec01DeembedPair14DeembedPair2MuteR OBJECT-TYPE
		SYNTAX		INTEGER { disable(0), enable(1) }
		MAX-ACCESS		read-write
		STATUS			current
		DESCRIPTION
				"TYPE: - Checkbox
				 PAGE: - Audio- De-embed Pair 1-4
					Mute-R  cmdID= 4015 "
		::= { iqdec01CmdEntry 4015 }


	iqdec01DeembedPair14DeembedPair2Stereo OBJECT-TYPE
		SYNTAX		INTEGER { disable(0), enable(1) }
		MAX-ACCESS		read-write
		STATUS			current
		DESCRIPTION
				"TYPE: - Checkbox
				 PAGE: - Audio- De-embed Pair 1-4
					Stereo  cmdID= 4016 "
		::= { iqdec01CmdEntry 4016 }


	iqdec01DeembedPair14DeembedPair2Delay OBJECT-TYPE
		SYNTAX		INTEGER
		MAX-ACCESS		read-write
		STATUS			current
		DESCRIPTION
				"TYPE: - Number
				 PAGE: - Audio- De-embed Pair 1-4
					Delay  cmdID= 4017  min= 0  max= 1500  step= 1  format= %0.0fms  div_scale= 1
					Min = 0ms  Max = 1500ms  Step = 1ms "
		::= { iqdec01CmdEntry 4017 }


	iqdec01DeembedPair14DeembedPair3LGain OBJECT-TYPE
		SYNTAX		INTEGER
		MAX-ACCESS		read-write
		STATUS			current
		DESCRIPTION
				"TYPE: - Number
				 PAGE: - Audio- De-embed Pair 1-4
					L-Gain  cmdID= 4020  min= -180  max= 180  step= 1  format= %0.1fdB  div_scale= 10
					Min = -18.0dB  Max = 18.0dB  Step = 0.1dB "
		::= { iqdec01CmdEntry 4020 }


	iqdec01DeembedPair14DeembedPair3GainR OBJECT-TYPE
		SYNTAX		INTEGER
		MAX-ACCESS		read-write
		STATUS			current
		DESCRIPTION
				"TYPE: - Number
				 PAGE: - Audio- De-embed Pair 1-4
					Gain-R  cmdID= 4021  min= -180  max= 180  step= 1  format= %0.1fdB  div_scale= 10
					Min = -18.0dB  Max = 18.0dB  Step = 0.1dB "
		::= { iqdec01CmdEntry 4021 }


	iqdec01DeembedPair14DeembedPair3LInvert OBJECT-TYPE
		SYNTAX		INTEGER { disable(0), enable(1) }
		MAX-ACCESS		read-write
		STATUS			current
		DESCRIPTION
				"TYPE: - Checkbox
				 PAGE: - Audio- De-embed Pair 1-4
					L-Invert  cmdID= 4022 "
		::= { iqdec01CmdEntry 4022 }


	iqdec01DeembedPair14DeembedPair3InvertR OBJECT-TYPE
		SYNTAX		INTEGER { disable(0), enable(1) }
		MAX-ACCESS		read-write
		STATUS			current
		DESCRIPTION
				"TYPE: - Checkbox
				 PAGE: - Audio- De-embed Pair 1-4
					Invert-R  cmdID= 4023 "
		::= { iqdec01CmdEntry 4023 }


	iqdec01DeembedPair14DeembedPair3LMute OBJECT-TYPE
		SYNTAX		INTEGER { disable(0), enable(1) }
		MAX-ACCESS		read-write
		STATUS			current
		DESCRIPTION
				"TYPE: - Checkbox
				 PAGE: - Audio- De-embed Pair 1-4
					L-Mute  cmdID= 4024 "
		::= { iqdec01CmdEntry 4024 }


	iqdec01DeembedPair14DeembedPair3MuteR OBJECT-TYPE
		SYNTAX		INTEGER { disable(0), enable(1) }
		MAX-ACCESS		read-write
		STATUS			current
		DESCRIPTION
				"TYPE: - Checkbox
				 PAGE: - Audio- De-embed Pair 1-4
					Mute-R  cmdID= 4025 "
		::= { iqdec01CmdEntry 4025 }


	iqdec01DeembedPair14DeembedPair3Stereo OBJECT-TYPE
		SYNTAX		INTEGER { disable(0), enable(1) }
		MAX-ACCESS		read-write
		STATUS			current
		DESCRIPTION
				"TYPE: - Checkbox
				 PAGE: - Audio- De-embed Pair 1-4
					Stereo  cmdID= 4026 "
		::= { iqdec01CmdEntry 4026 }


	iqdec01DeembedPair14DeembedPair3Delay OBJECT-TYPE
		SYNTAX		INTEGER
		MAX-ACCESS		read-write
		STATUS			current
		DESCRIPTION
				"TYPE: - Number
				 PAGE: - Audio- De-embed Pair 1-4
					Delay  cmdID= 4027  min= 0  max= 1500  step= 1  format= %0.0fms  div_scale= 1
					Min = 0ms  Max = 1500ms  Step = 1ms "
		::= { iqdec01CmdEntry 4027 }


	iqdec01DeembedPair14DeembedPair4LGain OBJECT-TYPE
		SYNTAX		INTEGER
		MAX-ACCESS		read-write
		STATUS			current
		DESCRIPTION
				"TYPE: - Number
				 PAGE: - Audio- De-embed Pair 1-4
					L-Gain  cmdID= 4030  min= -180  max= 180  step= 1  format= %0.1fdB  div_scale= 10
					Min = -18.0dB  Max = 18.0dB  Step = 0.1dB "
		::= { iqdec01CmdEntry 4030 }


	iqdec01DeembedPair14DeembedPair4GainR OBJECT-TYPE
		SYNTAX		INTEGER
		MAX-ACCESS		read-write
		STATUS			current
		DESCRIPTION
				"TYPE: - Number
				 PAGE: - Audio- De-embed Pair 1-4
					Gain-R  cmdID= 4031  min= -180  max= 180  step= 1  format= %0.1fdB  div_scale= 10
					Min = -18.0dB  Max = 18.0dB  Step = 0.1dB "
		::= { iqdec01CmdEntry 4031 }


	iqdec01DeembedPair14DeembedPair4LInvert OBJECT-TYPE
		SYNTAX		INTEGER { disable(0), enable(1) }
		MAX-ACCESS		read-write
		STATUS			current
		DESCRIPTION
				"TYPE: - Checkbox
				 PAGE: - Audio- De-embed Pair 1-4
					L-Invert  cmdID= 4032 "
		::= { iqdec01CmdEntry 4032 }


	iqdec01DeembedPair14DeembedPair4InvertR OBJECT-TYPE
		SYNTAX		INTEGER { disable(0), enable(1) }
		MAX-ACCESS		read-write
		STATUS			current
		DESCRIPTION
				"TYPE: - Checkbox
				 PAGE: - Audio- De-embed Pair 1-4
					Invert-R  cmdID= 4033 "
		::= { iqdec01CmdEntry 4033 }


	iqdec01DeembedPair14DeembedPair4LMute OBJECT-TYPE
		SYNTAX		INTEGER { disable(0), enable(1) }
		MAX-ACCESS		read-write
		STATUS			current
		DESCRIPTION
				"TYPE: - Checkbox
				 PAGE: - Audio- De-embed Pair 1-4
					L-Mute  cmdID= 4034 "
		::= { iqdec01CmdEntry 4034 }


	iqdec01DeembedPair14DeembedPair4MuteR OBJECT-TYPE
		SYNTAX		INTEGER { disable(0), enable(1) }
		MAX-ACCESS		read-write
		STATUS			current
		DESCRIPTION
				"TYPE: - Checkbox
				 PAGE: - Audio- De-embed Pair 1-4
					Mute-R  cmdID= 4035 "
		::= { iqdec01CmdEntry 4035 }


	iqdec01DeembedPair14DeembedPair4Stereo OBJECT-TYPE
		SYNTAX		INTEGER { disable(0), enable(1) }
		MAX-ACCESS		read-write
		STATUS			current
		DESCRIPTION
				"TYPE: - Checkbox
				 PAGE: - Audio- De-embed Pair 1-4
					Stereo  cmdID= 4036 "
		::= { iqdec01CmdEntry 4036 }


	iqdec01DeembedPair14DeembedPair4Delay OBJECT-TYPE
		SYNTAX		INTEGER
		MAX-ACCESS		read-write
		STATUS			current
		DESCRIPTION
				"TYPE: - Number
				 PAGE: - Audio- De-embed Pair 1-4
					Delay  cmdID= 4037  min= 0  max= 1500  step= 1  format= %0.0fms  div_scale= 1
					Min = 0ms  Max = 1500ms  Step = 1ms "
		::= { iqdec01CmdEntry 4037 }


	iqdec01DeembedPair58DeembedPair5LGain OBJECT-TYPE
		SYNTAX		INTEGER
		MAX-ACCESS		read-write
		STATUS			current
		DESCRIPTION
				"TYPE: - Number
				 PAGE: - Audio- De-embed Pair 5-8
					L-Gain  cmdID= 4040  min= -180  max= 180  step= 1  format= %0.1fdB  div_scale= 10
					Min = -18.0dB  Max = 18.0dB  Step = 0.1dB "
		::= { iqdec01CmdEntry 4040 }


	iqdec01DeembedPair58DeembedPair5GainR OBJECT-TYPE
		SYNTAX		INTEGER
		MAX-ACCESS		read-write
		STATUS			current
		DESCRIPTION
				"TYPE: - Number
				 PAGE: - Audio- De-embed Pair 5-8
					Gain-R  cmdID= 4041  min= -180  max= 180  step= 1  format= %0.1fdB  div_scale= 10
					Min = -18.0dB  Max = 18.0dB  Step = 0.1dB "
		::= { iqdec01CmdEntry 4041 }


	iqdec01DeembedPair58DeembedPair5LInvert OBJECT-TYPE
		SYNTAX		INTEGER { disable(0), enable(1) }
		MAX-ACCESS		read-write
		STATUS			current
		DESCRIPTION
				"TYPE: - Checkbox
				 PAGE: - Audio- De-embed Pair 5-8
					L-Invert  cmdID= 4042 "
		::= { iqdec01CmdEntry 4042 }


	iqdec01DeembedPair58DeembedPair5InvertR OBJECT-TYPE
		SYNTAX		INTEGER { disable(0), enable(1) }
		MAX-ACCESS		read-write
		STATUS			current
		DESCRIPTION
				"TYPE: - Checkbox
				 PAGE: - Audio- De-embed Pair 5-8
					Invert-R  cmdID= 4043 "
		::= { iqdec01CmdEntry 4043 }


	iqdec01DeembedPair58DeembedPair5LMute OBJECT-TYPE
		SYNTAX		INTEGER { disable(0), enable(1) }
		MAX-ACCESS		read-write
		STATUS			current
		DESCRIPTION
				"TYPE: - Checkbox
				 PAGE: - Audio- De-embed Pair 5-8
					L-Mute  cmdID= 4044 "
		::= { iqdec01CmdEntry 4044 }


	iqdec01DeembedPair58DeembedPair5MuteR OBJECT-TYPE
		SYNTAX		INTEGER { disable(0), enable(1) }
		MAX-ACCESS		read-write
		STATUS			current
		DESCRIPTION
				"TYPE: - Checkbox
				 PAGE: - Audio- De-embed Pair 5-8
					Mute-R  cmdID= 4045 "
		::= { iqdec01CmdEntry 4045 }


	iqdec01DeembedPair58DeembedPair5Stereo OBJECT-TYPE
		SYNTAX		INTEGER { disable(0), enable(1) }
		MAX-ACCESS		read-write
		STATUS			current
		DESCRIPTION
				"TYPE: - Checkbox
				 PAGE: - Audio- De-embed Pair 5-8
					Stereo  cmdID= 4046 "
		::= { iqdec01CmdEntry 4046 }


	iqdec01DeembedPair58DeembedPair5Delay OBJECT-TYPE
		SYNTAX		INTEGER
		MAX-ACCESS		read-write
		STATUS			current
		DESCRIPTION
				"TYPE: - Number
				 PAGE: - Audio- De-embed Pair 5-8
					Delay  cmdID= 4047  min= 0  max= 1500  step= 1  format= %0.0fms  div_scale= 1
					Min = 0ms  Max = 1500ms  Step = 1ms "
		::= { iqdec01CmdEntry 4047 }


	iqdec01DeembedPair58DeembedPair6LGain OBJECT-TYPE
		SYNTAX		INTEGER
		MAX-ACCESS		read-write
		STATUS			current
		DESCRIPTION
				"TYPE: - Number
				 PAGE: - Audio- De-embed Pair 5-8
					L-Gain  cmdID= 4050  min= -180  max= 180  step= 1  format= %0.1fdB  div_scale= 10
					Min = -18.0dB  Max = 18.0dB  Step = 0.1dB "
		::= { iqdec01CmdEntry 4050 }


	iqdec01DeembedPair58DeembedPair6GainR OBJECT-TYPE
		SYNTAX		INTEGER
		MAX-ACCESS		read-write
		STATUS			current
		DESCRIPTION
				"TYPE: - Number
				 PAGE: - Audio- De-embed Pair 5-8
					Gain-R  cmdID= 4051  min= -180  max= 180  step= 1  format= %0.1fdB  div_scale= 10
					Min = -18.0dB  Max = 18.0dB  Step = 0.1dB "
		::= { iqdec01CmdEntry 4051 }


	iqdec01DeembedPair58DeembedPair6LInvert OBJECT-TYPE
		SYNTAX		INTEGER { disable(0), enable(1) }
		MAX-ACCESS		read-write
		STATUS			current
		DESCRIPTION
				"TYPE: - Checkbox
				 PAGE: - Audio- De-embed Pair 5-8
					L-Invert  cmdID= 4052 "
		::= { iqdec01CmdEntry 4052 }


	iqdec01DeembedPair58DeembedPair6InvertR OBJECT-TYPE
		SYNTAX		INTEGER { disable(0), enable(1) }
		MAX-ACCESS		read-write
		STATUS			current
		DESCRIPTION
				"TYPE: - Checkbox
				 PAGE: - Audio- De-embed Pair 5-8
					Invert-R  cmdID= 4053 "
		::= { iqdec01CmdEntry 4053 }


	iqdec01DeembedPair58DeembedPair6LMute OBJECT-TYPE
		SYNTAX		INTEGER { disable(0), enable(1) }
		MAX-ACCESS		read-write
		STATUS			current
		DESCRIPTION
				"TYPE: - Checkbox
				 PAGE: - Audio- De-embed Pair 5-8
					L-Mute   cmdID= 4054 "
		::= { iqdec01CmdEntry 4054 }


	iqdec01DeembedPair58DeembedPair6MuteR OBJECT-TYPE
		SYNTAX		INTEGER { disable(0), enable(1) }
		MAX-ACCESS		read-write
		STATUS			current
		DESCRIPTION
				"TYPE: - Checkbox
				 PAGE: - Audio- De-embed Pair 5-8
					Mute-R  cmdID= 4055 "
		::= { iqdec01CmdEntry 4055 }


	iqdec01DeembedPair58DeembedPair6Stereo OBJECT-TYPE
		SYNTAX		INTEGER { disable(0), enable(1) }
		MAX-ACCESS		read-write
		STATUS			current
		DESCRIPTION
				"TYPE: - Checkbox
				 PAGE: - Audio- De-embed Pair 5-8
					Stereo  cmdID= 4056 "
		::= { iqdec01CmdEntry 4056 }


	iqdec01DeembedPair58DeembedPair6Delay OBJECT-TYPE
		SYNTAX		INTEGER
		MAX-ACCESS		read-write
		STATUS			current
		DESCRIPTION
				"TYPE: - Number
				 PAGE: - Audio- De-embed Pair 5-8
					Delay  cmdID= 4057  min= 0  max= 1500  step= 1  format= %0.0fms  div_scale= 1
					Min = 0ms  Max = 1500ms  Step = 1ms "
		::= { iqdec01CmdEntry 4057 }


	iqdec01DeembedPair58DeembedPair7LGain OBJECT-TYPE
		SYNTAX		INTEGER
		MAX-ACCESS		read-write
		STATUS			current
		DESCRIPTION
				"TYPE: - Number
				 PAGE: - Audio- De-embed Pair 5-8
					L-Gain  cmdID= 4060  min= -180  max= 180  step= 1  format= %0.1fdB  div_scale= 10
					Min = -18.0dB  Max = 18.0dB  Step = 0.1dB "
		::= { iqdec01CmdEntry 4060 }


	iqdec01DeembedPair58DeembedPair7GainR OBJECT-TYPE
		SYNTAX		INTEGER
		MAX-ACCESS		read-write
		STATUS			current
		DESCRIPTION
				"TYPE: - Number
				 PAGE: - Audio- De-embed Pair 5-8
					Gain-R  cmdID= 4061  min= -180  max= 180  step= 1  format= %0.1fdB  div_scale= 10
					Min = -18.0dB  Max = 18.0dB  Step = 0.1dB "
		::= { iqdec01CmdEntry 4061 }


	iqdec01DeembedPair58DeembedPair7LInvert OBJECT-TYPE
		SYNTAX		INTEGER { disable(0), enable(1) }
		MAX-ACCESS		read-write
		STATUS			current
		DESCRIPTION
				"TYPE: - Checkbox
				 PAGE: - Audio- De-embed Pair 5-8
					L-Invert  cmdID= 4062 "
		::= { iqdec01CmdEntry 4062 }


	iqdec01DeembedPair58DeembedPair7InvertR OBJECT-TYPE
		SYNTAX		INTEGER { disable(0), enable(1) }
		MAX-ACCESS		read-write
		STATUS			current
		DESCRIPTION
				"TYPE: - Checkbox
				 PAGE: - Audio- De-embed Pair 5-8
					Invert-R  cmdID= 4063 "
		::= { iqdec01CmdEntry 4063 }


	iqdec01DeembedPair58DeembedPair7LMute OBJECT-TYPE
		SYNTAX		INTEGER { disable(0), enable(1) }
		MAX-ACCESS		read-write
		STATUS			current
		DESCRIPTION
				"TYPE: - Checkbox
				 PAGE: - Audio- De-embed Pair 5-8
					L-Mute  cmdID= 4064 "
		::= { iqdec01CmdEntry 4064 }


	iqdec01DeembedPair58DeembedPair7MuteR OBJECT-TYPE
		SYNTAX		INTEGER { disable(0), enable(1) }
		MAX-ACCESS		read-write
		STATUS			current
		DESCRIPTION
				"TYPE: - Checkbox
				 PAGE: - Audio- De-embed Pair 5-8
					Mute-R  cmdID= 4065 "
		::= { iqdec01CmdEntry 4065 }


	iqdec01DeembedPair58DeembedPair7Stereo OBJECT-TYPE
		SYNTAX		INTEGER { disable(0), enable(1) }
		MAX-ACCESS		read-write
		STATUS			current
		DESCRIPTION
				"TYPE: - Checkbox
				 PAGE: - Audio- De-embed Pair 5-8
					Stereo  cmdID= 4066 "
		::= { iqdec01CmdEntry 4066 }


	iqdec01DeembedPair58DeembedPair7Delay OBJECT-TYPE
		SYNTAX		INTEGER
		MAX-ACCESS		read-write
		STATUS			current
		DESCRIPTION
				"TYPE: - Number
				 PAGE: - Audio- De-embed Pair 5-8
					Delay  cmdID= 4067  min= 0  max= 1500  step= 1  format= %0.0fms  div_scale= 1
					Min = 0ms  Max = 1500ms  Step = 1ms "
		::= { iqdec01CmdEntry 4067 }


	iqdec01DeembedPair58DeembedPair8LGain OBJECT-TYPE
		SYNTAX		INTEGER
		MAX-ACCESS		read-write
		STATUS			current
		DESCRIPTION
				"TYPE: - Number
				 PAGE: - Audio- De-embed Pair 5-8
					L-Gain  cmdID= 4070  min= -180  max= 180  step= 1  format= %0.1fdB  div_scale= 10
					Min = -18.0dB  Max = 18.0dB  Step = 0.1dB "
		::= { iqdec01CmdEntry 4070 }


	iqdec01DeembedPair58DeembedPair8GainR OBJECT-TYPE
		SYNTAX		INTEGER
		MAX-ACCESS		read-write
		STATUS			current
		DESCRIPTION
				"TYPE: - Number
				 PAGE: - Audio- De-embed Pair 5-8
					Gain-R  cmdID= 4071  min= -180  max= 180  step= 1  format= %0.1fdB  div_scale= 10
					Min = -18.0dB  Max = 18.0dB  Step = 0.1dB "
		::= { iqdec01CmdEntry 4071 }


	iqdec01DeembedPair58DeembedPair8LInvert OBJECT-TYPE
		SYNTAX		INTEGER { disable(0), enable(1) }
		MAX-ACCESS		read-write
		STATUS			current
		DESCRIPTION
				"TYPE: - Checkbox
				 PAGE: - Audio- De-embed Pair 5-8
					L-Invert  cmdID= 4072 "
		::= { iqdec01CmdEntry 4072 }


	iqdec01DeembedPair58DeembedPair8InvertR OBJECT-TYPE
		SYNTAX		INTEGER { disable(0), enable(1) }
		MAX-ACCESS		read-write
		STATUS			current
		DESCRIPTION
				"TYPE: - Checkbox
				 PAGE: - Audio- De-embed Pair 5-8
					Invert-R  cmdID= 4073 "
		::= { iqdec01CmdEntry 4073 }


	iqdec01DeembedPair58DeembedPair8LMute OBJECT-TYPE
		SYNTAX		INTEGER { disable(0), enable(1) }
		MAX-ACCESS		read-write
		STATUS			current
		DESCRIPTION
				"TYPE: - Checkbox
				 PAGE: - Audio- De-embed Pair 5-8
					L-Mute  cmdID= 4074 "
		::= { iqdec01CmdEntry 4074 }


	iqdec01DeembedPair58DeembedPair8MuteR OBJECT-TYPE
		SYNTAX		INTEGER { disable(0), enable(1) }
		MAX-ACCESS		read-write
		STATUS			current
		DESCRIPTION
				"TYPE: - Checkbox
				 PAGE: - Audio- De-embed Pair 5-8
					Mute-R  cmdID= 4075 "
		::= { iqdec01CmdEntry 4075 }


	iqdec01DeembedPair58DeembedPair8Stereo OBJECT-TYPE
		SYNTAX		INTEGER { disable(0), enable(1) }
		MAX-ACCESS		read-write
		STATUS			current
		DESCRIPTION
				"TYPE: - Checkbox
				 PAGE: - Audio- De-embed Pair 5-8
					Stereo  cmdID= 4076 "
		::= { iqdec01CmdEntry 4076 }


	iqdec01DeembedPair58DeembedPair8Delay OBJECT-TYPE
		SYNTAX		INTEGER
		MAX-ACCESS		read-write
		STATUS			current
		DESCRIPTION
				"TYPE: - Number
				 PAGE: - Audio- De-embed Pair 5-8
					Delay  cmdID= 4077  min= 0  max= 1500  step= 1  format= %0.0fms  div_scale= 1
					Min = 0ms  Max = 1500ms  Step = 1ms "
		::= { iqdec01CmdEntry 4077 }


	iqdec01AnalogAudioPair1AnalogPair1LGain OBJECT-TYPE
		SYNTAX		INTEGER
		MAX-ACCESS		read-write
		STATUS			current
		DESCRIPTION
				"TYPE: - Number
				 PAGE: - Audio- Analog Audio Pair 1
					L-Gain  cmdID= 4100  min= -68  max= 68  step= 1  format= %0.1fdB  div_scale= 2
					Min = -34.0dB  Max = 34.0dB  Step = 0.5dB "
		::= { iqdec01CmdEntry 4100 }


	iqdec01AnalogAudioPair1AnalogPair1GainR OBJECT-TYPE
		SYNTAX		INTEGER
		MAX-ACCESS		read-write
		STATUS			current
		DESCRIPTION
				"TYPE: - Number
				 PAGE: - Audio- Analog Audio Pair 1
					Gain-R  cmdID= 4101  min= -68  max= 68  step= 1  format= %0.1fdB  div_scale= 2
					Min = -34.0dB  Max = 34.0dB  Step = 0.5dB "
		::= { iqdec01CmdEntry 4101 }


	iqdec01AnalogAudioPair1AnalogPair1LInvert OBJECT-TYPE
		SYNTAX		INTEGER { disable(0), enable(1) }
		MAX-ACCESS		read-write
		STATUS			current
		DESCRIPTION
				"TYPE: - Checkbox
				 PAGE: - Audio- Analog Audio Pair 1
					L-Invert  cmdID= 4102 "
		::= { iqdec01CmdEntry 4102 }


	iqdec01AnalogAudioPair1AnalogPair1InvertR OBJECT-TYPE
		SYNTAX		INTEGER { disable(0), enable(1) }
		MAX-ACCESS		read-write
		STATUS			current
		DESCRIPTION
				"TYPE: - Checkbox
				 PAGE: - Audio- Analog Audio Pair 1
					Invert-R  cmdID= 4103 "
		::= { iqdec01CmdEntry 4103 }


	iqdec01AnalogAudioPair1AnalogPair1LMute OBJECT-TYPE
		SYNTAX		INTEGER { disable(0), enable(1) }
		MAX-ACCESS		read-write
		STATUS			current
		DESCRIPTION
				"TYPE: - Checkbox
				 PAGE: - Audio- Analog Audio Pair 1
					L-Mute  cmdID= 4104 "
		::= { iqdec01CmdEntry 4104 }


	iqdec01AnalogAudioPair1AnalogPair1MuteR OBJECT-TYPE
		SYNTAX		INTEGER { disable(0), enable(1) }
		MAX-ACCESS		read-write
		STATUS			current
		DESCRIPTION
				"TYPE: - Checkbox
				 PAGE: - Audio- Analog Audio Pair 1
					Mute-R  cmdID= 4105 "
		::= { iqdec01CmdEntry 4105 }


	iqdec01AnalogAudioPair1AnalogPair1Stereo OBJECT-TYPE
		SYNTAX		INTEGER { disable(0), enable(1) }
		MAX-ACCESS		read-write
		STATUS			current
		DESCRIPTION
				"TYPE: - Checkbox
				 PAGE: - Audio- Analog Audio Pair 1
					Stereo  cmdID= 4106 "
		::= { iqdec01CmdEntry 4106 }


	iqdec01AnalogAudioPair1AnalogPair1Delay OBJECT-TYPE
		SYNTAX		INTEGER
		MAX-ACCESS		read-write
		STATUS			current
		DESCRIPTION
				"TYPE: - Number
				 PAGE: - Audio- Analog Audio Pair 1
					Delay  cmdID= 4107  min= 0  max= 1500  step= 1  format= %0.0fms  div_scale= 1
					Min = 0ms  Max = 1500ms  Step = 1ms "
		::= { iqdec01CmdEntry 4107 }


	iqdec01AnalogAudioPair1AnalogPair2LGain OBJECT-TYPE
		SYNTAX		INTEGER
		MAX-ACCESS		read-write
		STATUS			current
		DESCRIPTION
				"TYPE: - Number
				 PAGE: - Audio- Analog Audio Pair 1
					L-Gain  cmdID= 4110  min= -68  max= 68  step= 1  format= %0.1fdB  div_scale= 2
					Min = -34.0dB  Max = 34.0dB  Step = 0.5dB "
		::= { iqdec01CmdEntry 4110 }


	iqdec01AnalogAudioPair1AnalogPair2GainR OBJECT-TYPE
		SYNTAX		INTEGER
		MAX-ACCESS		read-write
		STATUS			current
		DESCRIPTION
				"TYPE: - Number
				 PAGE: - Audio- Analog Audio Pair 1
					Gain-R  cmdID= 4111  min= -68  max= 68  step= 1  format= %0.1fdB  div_scale= 2
					Min = -34.0dB  Max = 34.0dB  Step = 0.5dB "
		::= { iqdec01CmdEntry 4111 }


	iqdec01AnalogAudioPair1AnalogPair2LInvert OBJECT-TYPE
		SYNTAX		INTEGER { disable(0), enable(1) }
		MAX-ACCESS		read-write
		STATUS			current
		DESCRIPTION
				"TYPE: - Checkbox
				 PAGE: - Audio- Analog Audio Pair 1
					L-Invert  cmdID= 4112 "
		::= { iqdec01CmdEntry 4112 }


	iqdec01AnalogAudioPair1AnalogPair2InvertR OBJECT-TYPE
		SYNTAX		INTEGER { disable(0), enable(1) }
		MAX-ACCESS		read-write
		STATUS			current
		DESCRIPTION
				"TYPE: - Checkbox
				 PAGE: - Audio- Analog Audio Pair 1
					Invert-R  cmdID= 4113 "
		::= { iqdec01CmdEntry 4113 }


	iqdec01AnalogAudioPair1AnalogPair2LMute OBJECT-TYPE
		SYNTAX		INTEGER { disable(0), enable(1) }
		MAX-ACCESS		read-write
		STATUS			current
		DESCRIPTION
				"TYPE: - Checkbox
				 PAGE: - Audio- Analog Audio Pair 1
					L-Mute  cmdID= 4114 "
		::= { iqdec01CmdEntry 4114 }


	iqdec01AnalogAudioPair1AnalogPair2MuteR OBJECT-TYPE
		SYNTAX		INTEGER { disable(0), enable(1) }
		MAX-ACCESS		read-write
		STATUS			current
		DESCRIPTION
				"TYPE: - Checkbox
				 PAGE: - Audio- Analog Audio Pair 1
					Mute-R  cmdID= 4115 "
		::= { iqdec01CmdEntry 4115 }


	iqdec01AnalogAudioPair1AnalogPair2Stereo OBJECT-TYPE
		SYNTAX		INTEGER { disable(0), enable(1) }
		MAX-ACCESS		read-write
		STATUS			current
		DESCRIPTION
				"TYPE: - Checkbox
				 PAGE: - Audio- Analog Audio Pair 1
					Stereo  cmdID= 4116 "
		::= { iqdec01CmdEntry 4116 }


	iqdec01AnalogAudioPair1AnalogPair2Delay OBJECT-TYPE
		SYNTAX		INTEGER
		MAX-ACCESS		read-write
		STATUS			current
		DESCRIPTION
				"TYPE: - Number
				 PAGE: - Audio- Analog Audio Pair 1
					Delay  cmdID= 4117  min= 0  max= 1500  step= 1  format= %0.0fms  div_scale= 1
					Min = 0ms  Max = 1500ms  Step = 1ms "
		::= { iqdec01CmdEntry 4117 }


	iqdec01AudioMix1Source1 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 1  cmdID= 4700
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4700 }


	iqdec01AudioMix1Source2 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 2  cmdID= 4701
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4701 }


	iqdec01AudioMix1Source3 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 3  cmdID= 4702
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4702 }


	iqdec01AudioMix1Source4 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 4  cmdID= 4703
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4703 }


	iqdec01AudioMix1Source5 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 5  cmdID= 4704
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4704 }


	iqdec01AudioMix1Source6 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 6  cmdID= 4705
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4705 }


	iqdec01AudioMix1Source7 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 7  cmdID= 4706
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4706 }


	iqdec01AudioMix1Source8 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 1
					Source 8  cmdID= 4707
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4707 }


	iqdec01AudioMix1GainGain1 OBJECT-TYPE
		SYNTAX		INTEGER
		MAX-ACCESS		read-write
		STATUS			current
		DESCRIPTION
				"TYPE: - Number
				 PAGE: - Audio- Audio Mix 1- Gain
					Gain 1  cmdID= 4710  min= -85  max= 0  step= 1  format= %0.0fdB  div_scale= 1
					Min = -85dB  Max = 0dB  Step = 1dB "
		::= { iqdec01CmdEntry 4710 }


	iqdec01AudioMix1GainGain2 OBJECT-TYPE
		SYNTAX		INTEGER
		MAX-ACCESS		read-write
		STATUS			current
		DESCRIPTION
				"TYPE: - Number
				 PAGE: - Audio- Audio Mix 1- Gain
					Gain 2  cmdID= 4711  min= -85  max= 0  step= 1  format= %0.0fdB  div_scale= 1
					Min = -85dB  Max = 0dB  Step = 1dB "
		::= { iqdec01CmdEntry 4711 }


	iqdec01AudioMix1GainGain3 OBJECT-TYPE
		SYNTAX		INTEGER
		MAX-ACCESS		read-write
		STATUS			current
		DESCRIPTION
				"TYPE: - Number
				 PAGE: - Audio- Audio Mix 1- Gain
					Gain 3  cmdID= 4712  min= -85  max= 0  step= 1  format= %0.0fdB  div_scale= 1
					Min = -85dB  Max = 0dB  Step = 1dB "
		::= { iqdec01CmdEntry 4712 }


	iqdec01AudioMix1GainGain4 OBJECT-TYPE
		SYNTAX		INTEGER
		MAX-ACCESS		read-write
		STATUS			current
		DESCRIPTION
				"TYPE: - Number
				 PAGE: - Audio- Audio Mix 1- Gain
					Gain 4  cmdID= 4713  min= -85  max= 0  step= 1  format= %0.0fdB  div_scale= 1
					Min = -85dB  Max = 0dB  Step = 1dB "
		::= { iqdec01CmdEntry 4713 }


	iqdec01AudioMix1GainGain5 OBJECT-TYPE
		SYNTAX		INTEGER
		MAX-ACCESS		read-write
		STATUS			current
		DESCRIPTION
				"TYPE: - Number
				 PAGE: - Audio- Audio Mix 1- Gain
					Gain 5  cmdID= 4714  min= -85  max= 0  step= 1  format= %0.0fdB  div_scale= 1
					Min = -85dB  Max = 0dB  Step = 1dB "
		::= { iqdec01CmdEntry 4714 }


	iqdec01AudioMix1GainGain6 OBJECT-TYPE
		SYNTAX		INTEGER
		MAX-ACCESS		read-write
		STATUS			current
		DESCRIPTION
				"TYPE: - Number
				 PAGE: - Audio- Audio Mix 1- Gain
					Gain 6  cmdID= 4715  min= -85  max= 0  step= 1  format= %0.0fdB  div_scale= 1
					Min = -85dB  Max = 0dB  Step = 1dB "
		::= { iqdec01CmdEntry 4715 }


	iqdec01AudioMix1GainGain7 OBJECT-TYPE
		SYNTAX		INTEGER
		MAX-ACCESS		read-write
		STATUS			current
		DESCRIPTION
				"TYPE: - Number
				 PAGE: - Audio- Audio Mix 1- Gain
					Gain 7  cmdID= 4716  min= -85  max= 0  step= 1  format= %0.0fdB  div_scale= 1
					Min = -85dB  Max = 0dB  Step = 1dB "
		::= { iqdec01CmdEntry 4716 }


	iqdec01AudioMix1GainGain8 OBJECT-TYPE
		SYNTAX		INTEGER
		MAX-ACCESS		read-write
		STATUS			current
		DESCRIPTION
				"TYPE: - Number
				 PAGE: - Audio- Audio Mix 1- Gain
					Gain 8  cmdID= 4717  min= -85  max= 0  step= 1  format= %0.0fdB  div_scale= 1
					Min = -85dB  Max = 0dB  Step = 1dB "
		::= { iqdec01CmdEntry 4717 }


	iqdec01AudioMix2Source1 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 1  cmdID= 4730
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4730 }


	iqdec01AudioMix2Source2 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 2  cmdID= 4731
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4731 }


	iqdec01AudioMix2Source3 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 3  cmdID= 4732
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4732 }


	iqdec01AudioMix2Source4 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 4  cmdID= 4733
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4733 }


	iqdec01AudioMix2Source5 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 5  cmdID= 4734
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4734 }


	iqdec01AudioMix2Source6 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 6  cmdID= 4735
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4735 }


	iqdec01AudioMix2Source7 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 7  cmdID= 4736
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4736 }


	iqdec01AudioMix2Source8 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 2
					Source 8  cmdID= 4737
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4737 }


	iqdec01AudioMix2GainGain1 OBJECT-TYPE
		SYNTAX		INTEGER
		MAX-ACCESS		read-write
		STATUS			current
		DESCRIPTION
				"TYPE: - Number
				 PAGE: - Audio- Audio Mix 2- Gain
					Gain 1  cmdID= 4740  min= -85  max= 0  step= 1  format= %0.0fdB  div_scale= 1
					Min = -85dB  Max = 0dB  Step = 1dB "
		::= { iqdec01CmdEntry 4740 }


	iqdec01AudioMix2GainGain2 OBJECT-TYPE
		SYNTAX		INTEGER
		MAX-ACCESS		read-write
		STATUS			current
		DESCRIPTION
				"TYPE: - Number
				 PAGE: - Audio- Audio Mix 2- Gain
					Gain 2  cmdID= 4741  min= -85  max= 0  step= 1  format= %0.0fdB  div_scale= 1
					Min = -85dB  Max = 0dB  Step = 1dB "
		::= { iqdec01CmdEntry 4741 }


	iqdec01AudioMix2GainGain3 OBJECT-TYPE
		SYNTAX		INTEGER
		MAX-ACCESS		read-write
		STATUS			current
		DESCRIPTION
				"TYPE: - Number
				 PAGE: - Audio- Audio Mix 2- Gain
					Gain 3  cmdID= 4742  min= -85  max= 0  step= 1  format= %0.0fdB  div_scale= 1
					Min = -85dB  Max = 0dB  Step = 1dB "
		::= { iqdec01CmdEntry 4742 }


	iqdec01AudioMix2GainGain4 OBJECT-TYPE
		SYNTAX		INTEGER
		MAX-ACCESS		read-write
		STATUS			current
		DESCRIPTION
				"TYPE: - Number
				 PAGE: - Audio- Audio Mix 2- Gain
					Gain 4  cmdID= 4743  min= -85  max= 0  step= 1  format= %0.0fdB  div_scale= 1
					Min = -85dB  Max = 0dB  Step = 1dB "
		::= { iqdec01CmdEntry 4743 }


	iqdec01AudioMix2GainGain5 OBJECT-TYPE
		SYNTAX		INTEGER
		MAX-ACCESS		read-write
		STATUS			current
		DESCRIPTION
				"TYPE: - Number
				 PAGE: - Audio- Audio Mix 2- Gain
					Gain 5  cmdID= 4744  min= -85  max= 0  step= 1  format= %0.0fdB  div_scale= 1
					Min = -85dB  Max = 0dB  Step = 1dB "
		::= { iqdec01CmdEntry 4744 }


	iqdec01AudioMix2GainGain6 OBJECT-TYPE
		SYNTAX		INTEGER
		MAX-ACCESS		read-write
		STATUS			current
		DESCRIPTION
				"TYPE: - Number
				 PAGE: - Audio- Audio Mix 2- Gain
					Gain 6  cmdID= 4745  min= -85  max= 0  step= 1  format= %0.0fdB  div_scale= 1
					Min = -85dB  Max = 0dB  Step = 1dB "
		::= { iqdec01CmdEntry 4745 }


	iqdec01AudioMix2GainGain7 OBJECT-TYPE
		SYNTAX		INTEGER
		MAX-ACCESS		read-write
		STATUS			current
		DESCRIPTION
				"TYPE: - Number
				 PAGE: - Audio- Audio Mix 2- Gain
					Gain 7  cmdID= 4746  min= -85  max= 0  step= 1  format= %0.0fdB  div_scale= 1
					Min = -85dB  Max = 0dB  Step = 1dB "
		::= { iqdec01CmdEntry 4746 }


	iqdec01AudioMix2GainGain8 OBJECT-TYPE
		SYNTAX		INTEGER
		MAX-ACCESS		read-write
		STATUS			current
		DESCRIPTION
				"TYPE: - Number
				 PAGE: - Audio- Audio Mix 2- Gain
					Gain 8  cmdID= 4747  min= -85  max= 0  step= 1  format= %0.0fdB  div_scale= 1
					Min = -85dB  Max = 0dB  Step = 1dB "
		::= { iqdec01CmdEntry 4747 }


	iqdec01AudioMix3Source1 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 1  cmdID= 4760
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4760 }


	iqdec01AudioMix3Source2 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 2  cmdID= 4761
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4761 }


	iqdec01AudioMix3Source3 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 3  cmdID= 4762
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4762 }


	iqdec01AudioMix3Source4 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 4  cmdID= 4763
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4763 }


	iqdec01AudioMix3Source5 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 5  cmdID= 4764
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4764 }


	iqdec01AudioMix3Source6 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 6  cmdID= 4765
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4765 }


	iqdec01AudioMix3Source7 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 7  cmdID= 4766
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4766 }


	iqdec01AudioMix3Source8 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 3
					Source 8  cmdID= 4767
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4767 }


	iqdec01AudioMix3GainGain1 OBJECT-TYPE
		SYNTAX		INTEGER
		MAX-ACCESS		read-write
		STATUS			current
		DESCRIPTION
				"TYPE: - Number
				 PAGE: - Audio- Audio Mix 3- Gain
					Gain 1  cmdID= 4770  min= -85  max= 0  step= 1  format= %0.0fdB  div_scale= 1
					Min = -85dB  Max = 0dB  Step = 1dB "
		::= { iqdec01CmdEntry 4770 }


	iqdec01AudioMix3GainGain2 OBJECT-TYPE
		SYNTAX		INTEGER
		MAX-ACCESS		read-write
		STATUS			current
		DESCRIPTION
				"TYPE: - Number
				 PAGE: - Audio- Audio Mix 3- Gain
					Gain 2  cmdID= 4771  min= -85  max= 0  step= 1  format= %0.0fdB  div_scale= 1
					Min = -85dB  Max = 0dB  Step = 1dB "
		::= { iqdec01CmdEntry 4771 }


	iqdec01AudioMix3GainGain3 OBJECT-TYPE
		SYNTAX		INTEGER
		MAX-ACCESS		read-write
		STATUS			current
		DESCRIPTION
				"TYPE: - Number
				 PAGE: - Audio- Audio Mix 3- Gain
					Gain 3  cmdID= 4772  min= -85  max= 0  step= 1  format= %0.0fdB  div_scale= 1
					Min = -85dB  Max = 0dB  Step = 1dB "
		::= { iqdec01CmdEntry 4772 }


	iqdec01AudioMix3GainGain4 OBJECT-TYPE
		SYNTAX		INTEGER
		MAX-ACCESS		read-write
		STATUS			current
		DESCRIPTION
				"TYPE: - Number
				 PAGE: - Audio- Audio Mix 3- Gain
					Gain 4  cmdID= 4773  min= -85  max= 0  step= 1  format= %0.0fdB  div_scale= 1
					Min = -85dB  Max = 0dB  Step = 1dB "
		::= { iqdec01CmdEntry 4773 }


	iqdec01AudioMix3GainGain5 OBJECT-TYPE
		SYNTAX		INTEGER
		MAX-ACCESS		read-write
		STATUS			current
		DESCRIPTION
				"TYPE: - Number
				 PAGE: - Audio- Audio Mix 3- Gain
					Gain 5  cmdID= 4774  min= -85  max= 0  step= 1  format= %0.0fdB  div_scale= 1
					Min = -85dB  Max = 0dB  Step = 1dB "
		::= { iqdec01CmdEntry 4774 }


	iqdec01AudioMix3GainGain6 OBJECT-TYPE
		SYNTAX		INTEGER
		MAX-ACCESS		read-write
		STATUS			current
		DESCRIPTION
				"TYPE: - Number
				 PAGE: - Audio- Audio Mix 3- Gain
					Gain 6  cmdID= 4775  min= -85  max= 0  step= 1  format= %0.0fdB  div_scale= 1
					Min = -85dB  Max = 0dB  Step = 1dB "
		::= { iqdec01CmdEntry 4775 }


	iqdec01AudioMix3GainGain7 OBJECT-TYPE
		SYNTAX		INTEGER
		MAX-ACCESS		read-write
		STATUS			current
		DESCRIPTION
				"TYPE: - Number
				 PAGE: - Audio- Audio Mix 3- Gain
					Gain 7  cmdID= 4776  min= -85  max= 0  step= 1  format= %0.0fdB  div_scale= 1
					Min = -85dB  Max = 0dB  Step = 1dB "
		::= { iqdec01CmdEntry 4776 }


	iqdec01AudioMix3GainGain8 OBJECT-TYPE
		SYNTAX		INTEGER
		MAX-ACCESS		read-write
		STATUS			current
		DESCRIPTION
				"TYPE: - Number
				 PAGE: - Audio- Audio Mix 3- Gain
					Gain 8  cmdID= 4777  min= -85  max= 0  step= 1  format= %0.0fdB  div_scale= 1
					Min = -85dB  Max = 0dB  Step = 1dB "
		::= { iqdec01CmdEntry 4777 }


	iqdec01AudioMix4Source1 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 1  cmdID= 4790
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4790 }


	iqdec01AudioMix4Source2 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 2  cmdID= 4791
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4791 }


	iqdec01AudioMix4Source3 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 3  cmdID= 4792
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4792 }


	iqdec01AudioMix4Source4 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 4  cmdID= 4793
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4793 }


	iqdec01AudioMix4Source5 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 5  cmdID= 4794
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4794 }


	iqdec01AudioMix4Source6 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 6  cmdID= 4795
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4795 }


	iqdec01AudioMix4Source7 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 7  cmdID= 4796
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4796 }


	iqdec01AudioMix4Source8 OBJECT-TYPE
		SYNTAX		INTEGER {
							val_None(0),
							val_Analog_1L(1),
							val_Analog_1R(2),
							val_Analog_2L(3),
							val_Analog_2R(4),
							val_SDI_DeEmbed_1L(5),
							val_SDI_DeEmbed_1R(6),
							val_SDI_DeEmbed_2L(7),
							val_SDI_DeEmbed_2R(8),
							val_SDI_DeEmbed_3L(9),
							val_SDI_DeEmbed_3R(10),
							val_SDI_DeEmbed_4L(11),
							val_SDI_DeEmbed_4R(12),
							val_SDI_DeEmbed_5L(13),
							val_SDI_DeEmbed_5R(14),
							val_SDI_DeEmbed_6L(15),
							val_SDI_DeEmbed_6R(16),
							val_SDI_DeEmbed_7L(17),
							val_SDI_DeEmbed_7R(18),
							val_SDI_DeEmbed_8L(19),
							val_SDI_DeEmbed_8R(20),
							val_Tone_L(21),
							val_Tone_R(22)
							}
		MAX-ACCESS		read-write
		STATUS			current
		DESCRIPTION
				"TYPE: - RadiobuttonList
				 PAGE: - Audio- Audio Mix 4
					Source 8  cmdID= 4797
					None  value= 0
					Analog 1L  value= 1
					Analog 1R  value= 2
					Analog 2L  value= 3
					Analog 2R  value= 4
					SDI DeEmbed 1L  value= 5
					SDI DeEmbed 1R  value= 6
					SDI DeEmbed 2L  value= 7
					SDI DeEmbed 2R  value= 8
					SDI DeEmbed 3L  value= 9
					SDI DeEmbed 3R  value= 10
					SDI DeEmbed 4L  value= 11
					SDI DeEmbed 4R  value= 12
					SDI DeEmbed 5L  value= 13
					SDI DeEmbed 5R  value= 14
					SDI DeEmbed 6L  value= 15
					SDI DeEmbed 6R  value= 16
					SDI DeEmbed 7L  value= 17
					SDI DeEmbed 7R  value= 18
					SDI DeEmbed 8L  value= 19
					SDI DeEmbed 8R  value= 20
					Tone L  value= 21
					Tone R  value= 22  "
		::= { iqdec01CmdEntry 4797 }


	iqdec01AudioMix4GainGain1 OBJECT-TYPE
		SYNTAX		INTEGER
		MAX-ACCESS		read-write
		STATUS			current
		DESCRIPTION
				"TYPE: - Number
				 PAGE: - Audio- Audio Mix 4- Gain
					Gain 1  cmdID= 4800  min= -85  max= 0  step= 1  format= %0.0fdB  div_scale= 1
					Min = -85dB  Max = 0dB  Step = 1dB "
		::= { iqdec01CmdEntry 4800 }


	iqdec01AudioMix4GainGain2 OBJECT-TYPE
		SYNTAX		INTEGER
		MAX-ACCESS		read-write
		STATUS			current
		DESCRIPTION
				"TYPE: - Number
				 PAGE: - Audio- Audio Mix 4- Gain
					Gain 2  cmdID= 4801  min= -85  max= 0  step= 1  format= %0.0fdB  div_scale= 1
					Min = -85dB  Max = 0dB  Step = 1dB "
		::= { iqdec01CmdEntry 4801 }


	iqdec01AudioMix4GainGain3 OBJECT-TYPE
		SYNTAX		INTEGER
		MAX-ACCESS		read-write
		STATUS			current
		DESCRIPTION
				"TYPE: - Number
				 PAGE: - Audio- Audio Mix 4- Gain
					Gain 3  cmdID= 4802  min= -85  max= 0  step= 1  format= %0.0fdB  div_scale= 1
					Min = -85dB  Max = 0dB  Step = 1dB "
		::= { iqdec01CmdEntry 4802 }


	iqdec01AudioMix4GainGain4 OBJECT-TYPE
		SYNTAX		INTEGER
		MAX-ACCESS		read-write
		STATUS			current
		DESCRIPTION
				"TYPE: - Number
				 PAGE: - Audio- Audio Mix 4- Gain
					Gain 4  cmdID= 4803  min= -85  max= 0  step= 1  format= %0.0fdB  div_scale= 1
					Min = -85dB  Max = 0dB  Step = 1dB "
		::= { iqdec01CmdEntry 4803 }


	iqdec01AudioMix4GainGain5 OBJECT-TYPE
		SYNTAX		INTEGER
		MAX-ACCESS		read-write
		STATUS			current
		DESCRIPTION
				"TYPE: - Number
				 PAGE: - Audio- Audio Mix 4- Gain
					Gain 5  cmdID= 4804  min= -85  max= 0  step= 1  format= %0.0fdB  div_scale= 1
					Min = -85dB  Max = 0dB  Step = 1dB "
		::= { iqdec01CmdEntry 4804 }


	iqdec01AudioMix4GainGain6 OBJECT-TYPE
		SYNTAX		INTEGER
		MAX-ACCESS		read-write
		STATUS			current
		DESCRIPTION
				"TYPE: - Number
				 PAGE: - Audio- Audio Mix 4- Gain
					Gain 6  cmdID= 4805  min= -85  max= 0  step= 1  format= %0.0fdB  div_scale= 1
					Min = -85dB  Max = 0dB  Step = 1dB "
		::= { iqdec01CmdEntry 4805 }


	iqdec01AudioMix4GainGain7 OBJECT-TYPE
		SYNTAX		INTEGER
		MAX-ACCESS		read-write
		STATUS			current
		DESCRIPTION
				"TYPE: - Number
				 PAGE: - Audio- Audio Mix 4- Gain
					Gain 7  cmdID= 4806  min= -85  max= 0  step= 1  format= %0.0fdB  div_scale= 1
					Min = -85dB  Max = 0dB  Step = 1dB "
		::= { iqdec01CmdEntry 4806 }


	iqdec01AudioMix4GainGain8 OBJECT-TYPE
		SYNTAX		INTEGER
		MAX-ACCESS		read-write
		STATUS			current
		DESCRIPTION
				"TYPE: - Number
				 PAGE: - Audio- Audio Mix 4- Gain
					Gain 8  cmdID= 4807  min= -85  max= 0  step= 1  format= %0.0fdB  div_scale= 1
					Min = -85dB  Max = 0dB  Step = 1dB "
		::= { iqdec01CmdEntry 4807 }


	iqdec01AudioMixerGainDisplaysMix1Gain1Disp OBJECT-TYPE
		SYNTAX		RollCallString
		MAX-ACCESS		read-only
		STATUS			current
		DESCRIPTION
				"TYPE: - Display
				 PAGE: - Audio
					Mix-1 Gain-1 Disp  cmdID= 4720  format=   "
		::= { iqdec01CmdEntry 4720 }


	iqdec01AudioMixerGainDisplaysMix1Gain2Disp OBJECT-TYPE
		SYNTAX		RollCallString
		MAX-ACCESS		read-only
		STATUS			current
		DESCRIPTION
				"TYPE: - Display
				 PAGE: - Audio
					Mix-1 Gain-2 Disp  cmdID= 4721  format=   "
		::= { iqdec01CmdEntry 4721 }


	iqdec01AudioMixerGainDisplaysMix1Gain3Disp OBJECT-TYPE
		SYNTAX		RollCallString
		MAX-ACCESS		read-only
		STATUS			current
		DESCRIPTION
				"TYPE: - Display
				 PAGE: - Audio
					Mix-1 Gain-3 Disp  cmdID= 4722  format=   "
		::= { iqdec01CmdEntry 4722 }


	iqdec01AudioMixerGainDisplaysMix1Gain4Disp OBJECT-TYPE
		SYNTAX		RollCallString
		MAX-ACCESS		read-only
		STATUS			current
		DESCRIPTION
				"TYPE: - Display
				 PAGE: - Audio
					Mix-1 Gain-4 Disp  cmdID= 4723  format=   "
		::= { iqdec01CmdEntry 4723 }


	iqdec01AudioMixerGainDisplaysMix1Gain5Disp OBJECT-TYPE
		SYNTAX		RollCallString
		MAX-ACCESS		read-only
		STATUS			current
		DESCRIPTION
				"TYPE: - Display
				 PAGE: - Audio
					Mix-1 Gain-5 Disp  cmdID= 4724  format=   "
		::= { iqdec01CmdEntry 4724 }


	iqdec01AudioMixerGainDisplaysMix1Gain6Disp OBJECT-TYPE
		SYNTAX		RollCallString
		MAX-ACCESS		read-only
		STATUS			current
		DESCRIPTION
				"TYPE: - Display
				 PAGE: - Audio
					Mix-1 Gain-6 Disp  cmdID= 4725  format=   "
		::= { iqdec01CmdEntry 4725 }


	iqdec01AudioMixerGainDisplaysMix1Gain7Disp OBJECT-TYPE
		SYNTAX		RollCallString
		MAX-ACCESS		read-only
		STATUS			current
		DESCRIPTION
				"TYPE: - Display
				 PAGE: - Audio
					Mix-1 Gain-7 Disp  cmdID= 4726  format=   "
		::= { iqdec01CmdEntry 4726 }


	iqdec01AudioMixerGainDisplaysMix1Gain8Disp OBJECT-TYPE
		SYNTAX		RollCallString
		MAX-ACCESS		read-only
		STATUS			current
		DESCRIPTION
				"TYPE: - Display
				 PAGE: - Audio
					Mix-1 Gain-8 Disp  cmdID= 4727  format=   "
		::= { iqdec01CmdEntry 4727 }


	iqdec01AudioMixerGainDisplaysMix2Gain1Disp OBJECT-TYPE
		SYNTAX		RollCallString
		MAX-ACCESS		read-only
		STATUS			current
		DESCRIPTION
				"TYPE: - Display
				 PAGE: - Audio
					Mix-2 Gain-1 Disp  cmdID= 4750  format=   "
		::= { iqdec01CmdEntry 4750 }


	iqdec01AudioMixerGainDisplaysMix2Gain2Disp OBJECT-TYPE
		SYNTAX		RollCallString
		MAX-ACCESS		read-only
		STATUS			current
		DESCRIPTION
				"TYPE: - Display
				 PAGE: - Audio
					Mix-2 Gain-2 Disp  cmdID= 4751  format=   "
		::= { iqdec01CmdEntry 4751 }


	iqdec01AudioMixerGainDisplaysMix2Gain3Disp OBJECT-TYPE
		SYNTAX		RollCallString
		MAX-ACCESS		read-only
		STATUS			current
		DESCRIPTION
				"TYPE: - Display
				 PAGE: - Audio
					Mix-2 Gain-3 Disp  cmdID= 4752  format=   "
		::= { iqdec01CmdEntry 4752 }


	iqdec01AudioMixerGainDisplaysMix2Gain4Disp OBJECT-TYPE
		SYNTAX		RollCallString
		MAX-ACCESS		read-only
		STATUS			current
		DESCRIPTION
				"TYPE: - Display
				 PAGE: - Audio
					Mix-2 Gain-4 Disp  cmdID= 4753  format=   "
		::= { iqdec01CmdEntry 4753 }


	iqdec01AudioMixerGainDisplaysMix2Gain5Disp OBJECT-TYPE
		SYNTAX		RollCallString
		MAX-ACCESS		read-only
		STATUS			current
		DESCRIPTION
				"TYPE: - Display
				 PAGE: - Audio
					Mix-2 Gain-5 Disp  cmdID= 4754  format=   "
		::= { iqdec01CmdEntry 4754 }


	iqdec01AudioMixerGainDisplaysMix2Gain6Disp OBJECT-TYPE
		SYNTAX		RollCallString
		MAX-ACCESS		read-only
		STATUS			current
		DESCRIPTION
				"TYPE: - Display
				 PAGE: - Audio
					Mix-2 Gain-6 Disp  cmdID= 4755  format=   "
		::= { iqdec01CmdEntry 4755 }


	iqdec01AudioMixerGainDisplaysMix2Gain7Disp OBJECT-TYPE
		SYNTAX		RollCallString
		MAX-ACCESS		read-only
		STATUS			current
		DESCRIPTION
				"TYPE: - Display
				 PAGE: - Audio
					Mix-2 Gain-7 Disp  cmdID= 4756  format=   "
		::= { iqdec01CmdEntry 4756 }


	iqdec01AudioMixerGainDisplaysMix2Gain8Disp OBJECT-TYPE
		SYNTAX		RollCallString
		MAX-ACCESS		read-only
		STATUS			current
		DESCRIPTION
				"TYPE: - Display
				 PAGE: - Audio
					Mix-2 Gain-8 Disp  cmdID= 4757  format=   "
		::= { iqdec01CmdEntry 4757 }


	iqdec01AudioMixerGainDisplaysMix3Gain1Disp OBJECT-TYPE
		SYNTAX		RollCallString
		MAX-ACCESS		read-only
		STATUS			current
		DESCRIPTION
				"TYPE: - Display
				 PAGE: - Audio
					Mix-3 Gain-1 Disp  cmdID= 4780  format=   "
		::= { iqdec01CmdEntry 4780 }


	iqdec01AudioMixerGainDisplaysMix3Gain2Disp OBJECT-TYPE
		SYNTAX		RollCallString
		MAX-ACCESS		read-only
		STATUS			current
		DESCRIPTION
				"TYPE: - Display
				 PAGE: - Audio
					Mix-3 Gain-2 Disp  cmdID= 4781  format=   "
		::= { iqdec01CmdEntry 4781 }


	iqdec01AudioMixerGainDisplaysMix3Gain3Disp OBJECT-TYPE
		SYNTAX		RollCallString
		MAX-ACCESS		read-only
		STATUS			current
		DESCRIPTION
				"TYPE: - Display
				 PAGE: - Audio
					Mix-3 Gain-3 Disp  cmdID= 4782  format=   "
		::= { iqdec01CmdEntry 4782 }


	iqdec01AudioMixerGainDisplaysMix3Gain4Disp OBJECT-TYPE
		SYNTAX		RollCallString
		MAX-ACCESS		read-only
		STATUS			current
		DESCRIPTION
				"TYPE: - Display
				 PAGE: - Audio
					Mix-3 Gain-4 Disp  cmdID= 4783  format=   "
		::= { iqdec01CmdEntry 4783 }


	iqdec01AudioMixerGainDisplaysMix3Gain5Disp OBJECT-TYPE
		SYNTAX		RollCallString
		MAX-ACCESS		read-only
		STATUS			current
		DESCRIPTION
				"TYPE: - Display
				 PAGE: - Audio
					Mix-3 Gain-5 Disp  cmdID= 4784  format=   "
		::= { iqdec01CmdEntry 4784 }


	iqdec01AudioMixerGainDisplaysMix3Gain6Disp OBJECT-TYPE
		SYNTAX		RollCallString
		MAX-ACCESS		read-only
		STATUS			current
		DESCRIPTION
				"TYPE: - Display
				 PAGE: - Audio
					Mix-3 Gain-6 Disp  cmdID= 4785  format=   "
		::= { iqdec01CmdEntry 4785 }


	iqdec01AudioMixerGainDisplaysMix3Gain7Disp OBJECT-TYPE
		SYNTAX		RollCallString
		MAX-ACCESS		read-only
		STATUS			current
		DESCRIPTION
				"TYPE: - Display
				 PAGE: - Audio
					Mix-3 Gain-7 Disp  cmdID= 4786  format=   "
		::= { iqdec01CmdEntry 4786 }


	iqdec01AudioMixerGainDisplaysMix3Gain8Disp OBJECT-TYPE
		SYNTAX		RollCallString
		MAX-ACCESS		read-only
		STATUS			current
		DESCRIPTION
				"TYPE: - Display
				 PAGE: - Audio
					Mix-3 Gain-8 Disp  cmdID= 4787  format=   "
		::= { iqdec01CmdEntry 4787 }


	iqdec01AudioMixerGainDisplaysMix4Gain1Disp OBJECT-TYPE
		SYNTAX		RollCallString
		MAX-ACCESS		read-only
		STATUS			current
		DESCRIPTION
				"TYPE: - Display
				 PAGE: - Audio
					Mix-4 Gain-1 Disp  cmdID= 4810  format=   "
		::= { iqdec01CmdEntry 4810 }


	iqdec01AudioMixerGainDisplaysMix4Gain2Disp OBJECT-TYPE
		SYNTAX		RollCallString
		MAX-ACCESS		read-only
		STATUS			current
		DESCRIPTION
				"TYPE: - Display
				 PAGE: - Audio
					Mix-4 Gain-2 Disp  cmdID= 4811  format=   "
		::= { iqdec01CmdEntry 4811 }


	iqdec01AudioMixerGainDisplaysMix4Gain3Disp OBJECT-TYPE
		SYNTAX		RollCallString
		MAX-ACCESS		read-only
		STATUS			current
		DESCRIPTION
				"TYPE: - Display
				 PAGE: - Audio
					Mix-4 Gain-3 Disp  cmdID= 4812  format=   "
		::= { iqdec01CmdEntry 4812 }


	iqdec01AudioMixerGainDisplaysMix4Gain4Disp OBJECT-TYPE
		SYNTAX		RollCallString
		MAX-ACCESS		read-only
		STATUS			current
		DESCRIPTION
				"TYPE: - Display
				 PAGE: - Audio
					Mix-4 Gain-4 Disp  cmdID= 4813  format=   "
		::= { iqdec01CmdEntry 4813 }


	iqdec01AudioMixerGainDisplaysMix4Gain5Disp OBJECT-TYPE
		SYNTAX		RollCallString
		MAX-ACCESS		read-only
		STATUS			current
		DESCRIPTION
				"TYPE: - Display
				 PAGE: - Audio
					Mix-4 Gain-5 Disp  cmdID= 4814  format=   "
		::= { iqdec01CmdEntry 4814 }


	iqdec01AudioMixerGainDisplaysMix4Gain6Disp OBJECT-TYPE
		SYNTAX		RollCallString
		MAX-ACCESS		read-only
		STATUS			current
		DESCRIPTION
				"TYPE: - Display
				 PAGE: - Audio
					Mix-4 Gain-6 Disp  cmdID= 4815  format=   "
		::= { iqdec01CmdEntry 4815 }


	iqdec01AudioMixerGainDisplaysMix4Gain7Disp OBJECT-TYPE
		SYNTAX		RollCallString
		MAX-ACCESS		read-only
		STATUS			current
		DESCRIPTION
				"TYPE: - Display
				 PAGE: - Audio
					Mix-4 Gain-7 Disp  cmdID= 4816  format=   "
		::= { iqdec01CmdEntry 4816 }


	iqdec01AudioMixerGainDisplaysMix4Gain8Disp OBJECT-TYPE
		SYNTAX		RollCallString
		MAX-ACCESS		read-only
		STATUS			current
		DESCRIPTION
				"TYPE: - Display
				 PAGE: - Audio
					Mix-4 Gain-8 Disp  cmdID= 4817  format=   "
		::= { iqdec01CmdEntry 4817 }


	iqdec01AudioBusAandBBusALSrc OBJECT-TYPE
		SYNTAX		INTEGER {
							val_Analog_1L(0),
							val_Analog_1R(1),
							val_Analog_2L(2),
							val_Analog_2R(3),
							val_SDI_DeEmbed_1L(4),
							val_SDI_DeEmbed_1R(5),
							val_SDI_DeEmbed_2L(6),
							val_SDI_DeEmbed_2R(7),
							val_SDI_DeEmbed_3L(8),
							val_SDI_DeEmbed_3R(9),
							val_SDI_DeEmbed_4L(10),
							val_SDI_DeEmbed_4R(11),
							val_SDI_DeEmbed_5L(12),
							val_SDI_DeEmbed_5R(13),
							val_SDI_DeEmbed_6L(14),
							val_SDI_DeEmbed_6R(15),
							val_SDI_DeEmbed_7L(16),
							val_SDI_DeEmbed_7R(17),
							val_SDI_DeEmbed_8L(18),
							val_SDI_DeEmbed_8R(19),
							val_Tone_L(20),
							val_Tone_R(21),
							val_Mixer_1(22),
							val_Mixer_2(23),
							val_Mixer_3(24),
							val_Mixer_4(25)
							}
		MAX-ACCESS		read-write
		STATUS			current
		DESCRIPTION
				"TYPE: - RadiobuttonList
				 PAGE: - Audio- Audio Bus A and B
					L-Src   cmdID= 4200
					Analog 1L  value= 0
					Analog 1R  value= 1
					Analog 2L  value= 2
					Analog 2R  value= 3
					SDI DeEmbed 1L  value= 4
					SDI DeEmbed 1R  value= 5
					SDI DeEmbed 2L  value= 6
					SDI DeEmbed 2R  value= 7
					SDI DeEmbed 3L  value= 8
					SDI DeEmbed 3R  value= 9
					SDI DeEmbed 4L  value= 10
					SDI DeEmbed 4R  value= 11
					SDI DeEmbed 5L  value= 12
					SDI DeEmbed 5R  value= 13
					SDI DeEmbed 6L  value= 14
					SDI DeEmbed 6R  value= 15
					SDI DeEmbed 7L  value= 16
					SDI DeEmbed 7R  value= 17
					SDI DeEmbed 8L  value= 18
					SDI DeEmbed 8R  value= 19
					Tone L  value= 20
					Tone R  value= 21
					Mixer 1  value= 22
					Mixer 2  value= 23
					Mixer 3  value= 24
					Mixer 4  value= 25  "
		::= { iqdec01CmdEntry 4200 }


	iqdec01AudioBusAandBBusASrcR OBJECT-TYPE
		SYNTAX		INTEGER {
							val_Analog_1L(0),
							val_Analog_1R(1),
							val_Analog_2L(2),
							val_Analog_2R(3),
							val_SDI_DeEmbed_1L(4),
							val_SDI_DeEmbed_1R(5),
							val_SDI_DeEmbed_2L(6),
							val_SDI_DeEmbed_2R(7),
							val_SDI_DeEmbed_3L(8),
							val_SDI_DeEmbed_3R(9),
							val_SDI_DeEmbed_4L(10),
							val_SDI_DeEmbed_4R(11),
							val_SDI_DeEmbed_5L(12),
							val_SDI_DeEmbed_5R(13),
							val_SDI_DeEmbed_6L(14),
							val_SDI_DeEmbed_6R(15),
							val_SDI_DeEmbed_7L(16),
							val_SDI_DeEmbed_7R(17),
							val_SDI_DeEmbed_8L(18),
							val_SDI_DeEmbed_8R(19),
							val_Tone_L(20),
							val_Tone_R(21),
							val_Mixer_1(22),
							val_Mixer_2(23),
							val_Mixer_3(24),
							val_Mixer_4(25)
							}
		MAX-ACCESS		read-write
		STATUS			current
		DESCRIPTION
				"TYPE: - RadiobuttonList
				 PAGE: - Audio- Audio Bus A and B
					Src-R  cmdID= 4201
					Analog 1L  value= 0
					Analog 1R  value= 1
					Analog 2L  value= 2
					Analog 2R  value= 3
					SDI DeEmbed 1L  value= 4
					SDI DeEmbed 1R  value= 5
					SDI DeEmbed 2L  value= 6
					SDI DeEmbed 2R  value= 7
					SDI DeEmbed 3L  value= 8
					SDI DeEmbed 3R  value= 9
					SDI DeEmbed 4L  value= 10
					SDI DeEmbed 4R  value= 11
					SDI DeEmbed 5L  value= 12
					SDI DeEmbed 5R  value= 13
					SDI DeEmbed 6L  value= 14
					SDI DeEmbed 6R  value= 15
					SDI DeEmbed 7L  value= 16
					SDI DeEmbed 7R  value= 17
					SDI DeEmbed 8L  value= 18
					SDI DeEmbed 8R  value= 19
					Tone L  value= 20
					Tone R  value= 21
					Mixer 1  value= 22
					Mixer 2  value= 23
					Mixer 3  value= 24
					Mixer 4  value= 25  "
		::= { iqdec01CmdEntry 4201 }


	iqdec01AudioBusAandBBusALGain OBJECT-TYPE
		SYNTAX		INTEGER
		MAX-ACCESS		read-write
		STATUS			current
		DESCRIPTION
				"TYPE: - Number
				 PAGE: - Audio- Audio Bus A and B
					L-Gain   cmdID= 4202  min= -180  max= 180  step= 1  format= %0.1fdB  div_scale= 10
					Min = -18.0dB  Max = 18.0dB  Step = 0.1dB "
		::= { iqdec01CmdEntry 4202 }


	iqdec01AudioBusAandBBusAGainR OBJECT-TYPE
		SYNTAX		INTEGER
		MAX-ACCESS		read-write
		STATUS			current
		DESCRIPTION
				"TYPE: - Number
				 PAGE: - Audio- Audio Bus A and B
					Gain-R  cmdID= 4203  min= -180  max= 180  step= 1  format= %0.1fdB  div_scale= 10
					Min = -18.0dB  Max = 18.0dB  Step = 0.1dB "
		::= { iqdec01CmdEntry 4203 }


	iqdec01AudioBusAandBBusALInvert OBJECT-TYPE
		SYNTAX		INTEGER { disable(0), enable(1) }
		MAX-ACCESS		read-write
		STATUS			current
		DESCRIPTION
				"TYPE: - Checkbox
				 PAGE: - Audio- Audio Bus A and B
					L-Invert  cmdID= 4204 "
		::= { iqdec01CmdEntry 4204 }


	iqdec01AudioBusAandBBusAInvertR OBJECT-TYPE
		SYNTAX		INTEGER { disable(0), enable(1) }
		MAX-ACCESS		read-write
		STATUS			current
		DESCRIPTION
				"TYPE: - Checkbox
				 PAGE: - Audio- Audio Bus A and B
					Invert-R  cmdID= 4205 "
		::= { iqdec01CmdEntry 4205 }


	iqdec01AudioBusAandBBusALMute OBJECT-TYPE
		SYNTAX		INTEGER { disable(0), enable(1) }
		MAX-ACCESS		read-write
		STATUS			current
		DESCRIPTION
				"TYPE: - Checkbox
				 PAGE: - Audio- Audio Bus A and B
					L-Mute   cmdID= 4206 "
		::= { iqdec01CmdEntry 4206 }


	iqdec01AudioBusAandBBusAMuteR OBJECT-TYPE
		SYNTAX		INTEGER { disable(0), enable(1) }
		MAX-ACCESS		read-write
		STATUS			current
		DESCRIPTION
				"TYPE: - Checkbox
				 PAGE: - Audio- Audio Bus A and B
					Mute-R  cmdID= 4207 "
		::= { iqdec01CmdEntry 4207 }


	iqdec01AudioBusAandBBusAStereo OBJECT-TYPE
		SYNTAX		INTEGER { disable(0), enable(1) }
		MAX-ACCESS		read-write
		STATUS			current
		DESCRIPTION
				"TYPE: - Checkbox
				 PAGE: - Audio- Audio Bus A and B
					Stereo  cmdID= 4208 "
		::= { iqdec01CmdEntry 4208 }


	iqdec01AudioBusAandBBusBLSrc OBJECT-TYPE
		SYNTAX		INTEGER {
							val_Analog_1L(0),
							val_Analog_1R(1),
							val_Analog_2L(2),
							val_Analog_2R(3),
							val_SDI_DeEmbed_1L(4),
							val_SDI_DeEmbed_1R(5),
							val_SDI_DeEmbed_2L(6),
							val_SDI_DeEmbed_2R(7),
							val_SDI_DeEmbed_3L(8),
							val_SDI_DeEmbed_3R(9),
							val_SDI_DeEmbed_4L(10),
							val_SDI_DeEmbed_4R(11),
							val_SDI_DeEmbed_5L(12),
							val_SDI_DeEmbed_5R(13),
							val_SDI_DeEmbed_6L(14),
							val_SDI_DeEmbed_6R(15),
							val_SDI_DeEmbed_7L(16),
							val_SDI_DeEmbed_7R(17),
							val_SDI_DeEmbed_8L(18),
							val_SDI_DeEmbed_8R(19),
							val_Tone_L(20),
							val_Tone_R(21),
							val_Mixer_1(22),
							val_Mixer_2(23),
							val_Mixer_3(24),
							val_Mixer_4(25)
							}
		MAX-ACCESS		read-write
		STATUS			current
		DESCRIPTION
				"TYPE: - RadiobuttonList
				 PAGE: - Audio- Audio Bus A and B
					L-Src  cmdID= 4209
					Analog 1L  value= 0
					Analog 1R  value= 1
					Analog 2L  value= 2
					Analog 2R  value= 3
					SDI DeEmbed 1L  value= 4
					SDI DeEmbed 1R  value= 5
					SDI DeEmbed 2L  value= 6
					SDI DeEmbed 2R  value= 7
					SDI DeEmbed 3L  value= 8
					SDI DeEmbed 3R  value= 9
					SDI DeEmbed 4L  value= 10
					SDI DeEmbed 4R  value= 11
					SDI DeEmbed 5L  value= 12
					SDI DeEmbed 5R  value= 13
					SDI DeEmbed 6L  value= 14
					SDI DeEmbed 6R  value= 15
					SDI DeEmbed 7L  value= 16
					SDI DeEmbed 7R  value= 17
					SDI DeEmbed 8L  value= 18
					SDI DeEmbed 8R  value= 19
					Tone L  value= 20
					Tone R  value= 21
					Mixer 1  value= 22
					Mixer 2  value= 23
					Mixer 3  value= 24
					Mixer 4  value= 25  "
		::= { iqdec01CmdEntry 4209 }


	iqdec01AudioBusAandBBusBSrcR OBJECT-TYPE
		SYNTAX		INTEGER {
							val_Analog_1L(0),
							val_Analog_1R(1),
							val_Analog_2L(2),
							val_Analog_2R(3),
							val_SDI_DeEmbed_1L(4),
							val_SDI_DeEmbed_1R(5),
							val_SDI_DeEmbed_2L(6),
							val_SDI_DeEmbed_2R(7),
							val_SDI_DeEmbed_3L(8),
							val_SDI_DeEmbed_3R(9),
							val_SDI_DeEmbed_4L(10),
							val_SDI_DeEmbed_4R(11),
							val_SDI_DeEmbed_5L(12),
							val_SDI_DeEmbed_5R(13),
							val_SDI_DeEmbed_6L(14),
							val_SDI_DeEmbed_6R(15),
							val_SDI_DeEmbed_7L(16),
							val_SDI_DeEmbed_7R(17),
							val_SDI_DeEmbed_8L(18),
							val_SDI_DeEmbed_8R(19),
							val_Tone_L(20),
							val_Tone_R(21),
							val_Mixer_1(22),
							val_Mixer_2(23),
							val_Mixer_3(24),
							val_Mixer_4(25)
							}
		MAX-ACCESS		read-write
		STATUS			current
		DESCRIPTION
				"TYPE: - RadiobuttonList
				 PAGE: - Audio- Audio Bus A and B
					Src-R  cmdID= 4210
					Analog 1L  value= 0
					Analog 1R  value= 1
					Analog 2L  value= 2
					Analog 2R  value= 3
					SDI DeEmbed 1L  value= 4
					SDI DeEmbed 1R  value= 5
					SDI DeEmbed 2L  value= 6
					SDI DeEmbed 2R  value= 7
					SDI DeEmbed 3L  value= 8
					SDI DeEmbed 3R  value= 9
					SDI DeEmbed 4L  value= 10
					SDI DeEmbed 4R  value= 11
					SDI DeEmbed 5L  value= 12
					SDI DeEmbed 5R  value= 13
					SDI DeEmbed 6L  value= 14
					SDI DeEmbed 6R  value= 15
					SDI DeEmbed 7L  value= 16
					SDI DeEmbed 7R  value= 17
					SDI DeEmbed 8L  value= 18
					SDI DeEmbed 8R  value= 19
					Tone L  value= 20
					Tone R  value= 21
					Mixer 1  value= 22
					Mixer 2  value= 23
					Mixer 3  value= 24
					Mixer 4  value= 25  "
		::= { iqdec01CmdEntry 4210 }


	iqdec01AudioBusAandBBusBLGain OBJECT-TYPE
		SYNTAX		INTEGER
		MAX-ACCESS		read-write
		STATUS			current
		DESCRIPTION
				"TYPE: - Number
				 PAGE: - Audio- Audio Bus A and B
					L-Gain  cmdID= 4211  min= -180  max= 180  step= 1  format= %0.1fdB  div_scale= 10
					Min = -18.0dB  Max = 18.0dB  Step = 0.1dB "
		::= { iqdec01CmdEntry 4211 }


	iqdec01AudioBusAandBBusBGainR OBJECT-TYPE
		SYNTAX		INTEGER
		MAX-ACCESS		read-write
		STATUS			current
		DESCRIPTION
				"TYPE: - Number
				 PAGE: - Audio- Audio Bus A and B
					Gain-R  cmdID= 4212  min= -180  max= 180  step= 1  format= %0.1fdB  div_scale= 10
					Min = -18.0dB  Max = 18.0dB  Step = 0.1dB "
		::= { iqdec01CmdEntry 4212 }


	iqdec01AudioBusAandBBusBLInvert OBJECT-TYPE
		SYNTAX		INTEGER { disable(0), enable(1) }
		MAX-ACCESS		read-write
		STATUS			current
		DESCRIPTION
				"TYPE: - Checkbox
				 PAGE: - Audio- Audio Bus A and B
					L-Invert  cmdID= 4213 "
		::= { iqdec01CmdEntry 4213 }


	iqdec01AudioBusAandBBusBInvertR OBJECT-TYPE
		SYNTAX		INTEGER { disable(0), enable(1) }
		MAX-ACCESS		read-write
		STATUS			current
		DESCRIPTION
				"TYPE: - Checkbox
				 PAGE: - Audio- Audio Bus A and B
					Invert-R  cmdID= 4214 "
		::= { iqdec01CmdEntry 4214 }


	iqdec01AudioBusAandBBusBLMute OBJECT-TYPE
		SYNTAX		INTEGER { disable(0), enable(1) }
		MAX-ACCESS		read-write
		STATUS			current
		DESCRIPTION
				"TYPE: - Checkbox
				 PAGE: - Audio- Audio Bus A and B
					L-Mute  cmdID= 4215 "
		::= { iqdec01CmdEntry 4215 }


	iqdec01AudioBusAandBBusBMuteR OBJECT-TYPE
		SYNTAX		INTEGER { disable(0), enable(1) }
		MAX-ACCESS		read-write
		STATUS			current
		DESCRIPTION
				"TYPE: - Checkbox
				 PAGE: - Audio- Audio Bus A and B
					Mute-R  cmdID= 4216 "
		::= { iqdec01CmdEntry 4216 }


	iqdec01AudioBusAandBBusBStereo OBJECT-TYPE
		SYNTAX		INTEGER { disable(0), enable(1) }
		MAX-ACCESS		read-write
		STATUS			current
		DESCRIPTION
				"TYPE: - Checkbox
				 PAGE: - Audio- Audio Bus A and B
					Stereo  cmdID= 4217 "
		::= { iqdec01CmdEntry 4217 }


	iqdec01AudioOutputsEmbedder1Source OBJECT-TYPE
		SYNTAX		INTEGER {
							val_BUS_A(0),
							val_BUS_B(1)
							}
		MAX-ACCESS		read-write
		STATUS			current
		DESCRIPTION
				"TYPE: - RadiobuttonList
				 PAGE: - Audio- Audio Outputs
					Source  cmdID= 4301
					BUS A  value= 0
					BUS B  value= 1  "
		::= { iqdec01CmdEntry 4301 }


	iqdec01AudioOutputsEmbedder1Destination OBJECT-TYPE
		SYNTAX		INTEGER {
							val_Pair_1(0),
							val_Pair_2(1),
							val_Pair_3(2),
							val_Pair_4(3),
							val_Pair_5(4),
							val_Pair_6(5),
							val_Pair_7(6),
							val_Pair_8(7)
							}
		MAX-ACCESS		read-write
		STATUS			current
		DESCRIPTION
				"TYPE: - RadiobuttonList
				 PAGE: - Audio- Audio Outputs
					Destination  cmdID= 4302
					Pair 1  value= 0
					Pair 2  value= 1
					Pair 3  value= 2
					Pair 4  value= 3
					Pair 5  value= 4
					Pair 6  value= 5
					Pair 7  value= 6
					Pair 8  value= 7  "
		::= { iqdec01CmdEntry 4302 }


	iqdec01AudioOutputsEmbedder1Disable OBJECT-TYPE
		SYNTAX		INTEGER { disable(0), enable(1) }
		MAX-ACCESS		read-write
		STATUS			current
		DESCRIPTION
				"TYPE: - Checkbox
				 PAGE: - Audio- Audio Outputs
					Disable  cmdID= 4303 "
		::= { iqdec01CmdEntry 4303 }


	iqdec01AudioOutputsEmbedder2Source OBJECT-TYPE
		SYNTAX		INTEGER {
							val_BUS_A(0),
							val_BUS_B(1)
							}
		MAX-ACCESS		read-write
		STATUS			current
		DESCRIPTION
				"TYPE: - RadiobuttonList
				 PAGE: - Audio- Audio Outputs
					Source  cmdID= 4304
					BUS A  value= 0
					BUS B  value= 1  "
		::= { iqdec01CmdEntry 4304 }


	iqdec01AudioOutputsEmbedder2Destination OBJECT-TYPE
		SYNTAX		INTEGER {
							val_Pair_1(0),
							val_Pair_2(1),
							val_Pair_3(2),
							val_Pair_4(3),
							val_Pair_5(4),
							val_Pair_6(5),
							val_Pair_7(6),
							val_Pair_8(7)
							}
		MAX-ACCESS		read-write
		STATUS			current
		DESCRIPTION
				"TYPE: - RadiobuttonList
				 PAGE: - Audio- Audio Outputs
					Destination  cmdID= 4305
					Pair 1  value= 0
					Pair 2  value= 1
					Pair 3  value= 2
					Pair 4  value= 3
					Pair 5  value= 4
					Pair 6  value= 5
					Pair 7  value= 6
					Pair 8  value= 7  "
		::= { iqdec01CmdEntry 4305 }


	iqdec01AudioOutputsEmbedder2Disable OBJECT-TYPE
		SYNTAX		INTEGER { disable(0), enable(1) }
		MAX-ACCESS		read-write
		STATUS			current
		DESCRIPTION
				"TYPE: - Checkbox
				 PAGE: - Audio- Audio Outputs
					Disable  cmdID= 4306 "
		::= { iqdec01CmdEntry 4306 }


	iqdec01AudioOutputsAES1Source OBJECT-TYPE
		SYNTAX		INTEGER {
							val_BUS_A(0),
							val_BUS_B(1)
							}
		MAX-ACCESS		read-write
		STATUS			current
		DESCRIPTION
				"TYPE: - RadiobuttonList
				 PAGE: - Audio- Audio Outputs
					Source  cmdID= 4307
					BUS A  value= 0
					BUS B  value= 1  "
		::= { iqdec01CmdEntry 4307 }


	iqdec01AudioOutputsAES2Source OBJECT-TYPE
		SYNTAX		INTEGER {
							val_BUS_A(0),
							val_BUS_B(1)
							}
		MAX-ACCESS		read-write
		STATUS			current
		DESCRIPTION
				"TYPE: - RadiobuttonList
				 PAGE: - Audio- Audio Outputs
					Source  cmdID= 4309
					BUS A  value= 0
					BUS B  value= 1  "
		::= { iqdec01CmdEntry 4309 }


	iqdec01AudioDelaySetupSetManual OBJECT-TYPE
		SYNTAX		INTEGER
		MAX-ACCESS		read-write
		STATUS			current
		DESCRIPTION
				"TYPE: - Number
				 PAGE: - Audio- Audio Delay Setup
					Set Manual  cmdID= 4400  min= -40  max= 1500  step= 1  format= %0.0fms  div_scale= 1
					Min = -40ms  Max = 1500ms  Step = 1ms "
		::= { iqdec01CmdEntry 4400 }


	iqdec01AudioDelaySetupIncludeManual OBJECT-TYPE
		SYNTAX		INTEGER { disable(0), enable(1) }
		MAX-ACCESS		read-write
		STATUS			current
		DESCRIPTION
				"TYPE: - Checkbox
				 PAGE: - Audio- Audio Delay Setup
					Include Manual  cmdID= 4402 "
		::= { iqdec01CmdEntry 4402 }


	iqdec01AudioDelaySetupIncludeInternal OBJECT-TYPE
		SYNTAX		INTEGER { disable(0), enable(1) }
		MAX-ACCESS		read-write
		STATUS			current
		DESCRIPTION
				"TYPE: - Checkbox
				 PAGE: - Audio- Audio Delay Setup
					Include Internal  cmdID= 4401 "
		::= { iqdec01CmdEntry 4401 }


	iqdec01AudioDelaySetupIncludeGPI OBJECT-TYPE
		SYNTAX		INTEGER { disable(0), enable(1) }
		MAX-ACCESS		read-write
		STATUS			current
		DESCRIPTION
				"TYPE: - Checkbox
				 PAGE: - Audio- Audio Delay Setup
					Include GPI  cmdID= 4403 "
		::= { iqdec01CmdEntry 4403 }


	iqdec01AudioDelaySetupIncludeRTrack14 OBJECT-TYPE
		SYNTAX		INTEGER { disable(0), enable(1) }
		MAX-ACCESS		read-write
		STATUS			current
		DESCRIPTION
				"TYPE: - Checkbox
				 PAGE: - Audio- Audio Delay Setup
					Include RTrack14  cmdID= 4404 "
		::= { iqdec01CmdEntry 4404 }


	iqdec01AudioDelaySetupIncludeRTrack15 OBJECT-TYPE
		SYNTAX		INTEGER { disable(0), enable(1) }
		MAX-ACCESS		read-write
		STATUS			current
		DESCRIPTION
				"TYPE: - Checkbox
				 PAGE: - Audio- Audio Delay Setup
					Include RTrack15  cmdID= 4405 "
		::= { iqdec01CmdEntry 4405 }


	iqdec01AudioDelaySetupIncludeRTrack16 OBJECT-TYPE
		SYNTAX		INTEGER { disable(0), enable(1) }
		MAX-ACCESS		read-write
		STATUS			current
		DESCRIPTION
				"TYPE: - Checkbox
				 PAGE: - Audio- Audio Delay Setup
					Include RTrack16  cmdID= 4406 "
		::= { iqdec01CmdEntry 4406 }


	iqdec01AudioDelaySetupIncludeRTrack17 OBJECT-TYPE
		SYNTAX		INTEGER { disable(0), enable(1) }
		MAX-ACCESS		read-write
		STATUS			current
		DESCRIPTION
				"TYPE: - Checkbox
				 PAGE: - Audio- Audio Delay Setup
					Include RTrack17  cmdID= 4407 "
		::= { iqdec01CmdEntry 4407 }


	iqdec01AudioDelaySetupTotalDelay OBJECT-TYPE
		SYNTAX		RollCallString
		MAX-ACCESS		read-only
		STATUS			current
		DESCRIPTION
				"TYPE: - Display
				 PAGE: - Audio- Audio Delay Setup
					Total Delay  cmdID= 4417  format=   "
		::= { iqdec01CmdEntry 4417 }


	iqdec01AudioDelaySetupManual OBJECT-TYPE
		SYNTAX		RollCallString
		MAX-ACCESS		read-only
		STATUS			current
		DESCRIPTION
				"TYPE: - Display
				 PAGE: - Audio- Audio Delay Setup
					Manual  cmdID= 4419  format=   "
		::= { iqdec01CmdEntry 4419 }


	iqdec01AudioDelaySetupInternal OBJECT-TYPE
		SYNTAX		RollCallString
		MAX-ACCESS		read-only
		STATUS			current
		DESCRIPTION
				"TYPE: - Display
				 PAGE: - Audio- Audio Delay Setup
					Internal  cmdID= 4418  format=   "
		::= { iqdec01CmdEntry 4418 }


	iqdec01AudioDelaySetupGPI OBJECT-TYPE
		SYNTAX		RollCallString
		MAX-ACCESS		read-only
		STATUS			current
		DESCRIPTION
				"TYPE: - Display
				 PAGE: - Audio- Audio Delay Setup
					GPI  cmdID= 4420  format=   "
		::= { iqdec01CmdEntry 4420 }


	iqdec01AudioDelaySetupRTrack14 OBJECT-TYPE
		SYNTAX		RollCallString
		MAX-ACCESS		read-only
		STATUS			current
		DESCRIPTION
				"TYPE: - Display
				 PAGE: - Audio- Audio Delay Setup
					RTrack14  cmdID= 4421  format=   "
		::= { iqdec01CmdEntry 4421 }


	iqdec01AudioDelaySetupRTrack15 OBJECT-TYPE
		SYNTAX		RollCallString
		MAX-ACCESS		read-only
		STATUS			current
		DESCRIPTION
				"TYPE: - Display
				 PAGE: - Audio- Audio Delay Setup
					RTrack15  cmdID= 4422  format=   "
		::= { iqdec01CmdEntry 4422 }


	iqdec01AudioDelaySetupRTrack16 OBJECT-TYPE
		SYNTAX		RollCallString
		MAX-ACCESS		read-only
		STATUS			current
		DESCRIPTION
				"TYPE: - Display
				 PAGE: - Audio- Audio Delay Setup
					RTrack16  cmdID= 4423  format=   "
		::= { iqdec01CmdEntry 4423 }


	iqdec01AudioDelaySetupRTrack17 OBJECT-TYPE
		SYNTAX		RollCallString
		MAX-ACCESS		read-only
		STATUS			current
		DESCRIPTION
				"TYPE: - Display
				 PAGE: - Audio- Audio Delay Setup
					RTrack17  cmdID= 4424  format=   "
		::= { iqdec01CmdEntry 4424 }


	iqdec01AudioSetupHeadroom OBJECT-TYPE
		SYNTAX		INTEGER
		MAX-ACCESS		read-write
		STATUS			current
		DESCRIPTION
				"TYPE: - Number
				 PAGE: - Audio- Audio Setup
					Headroom  cmdID= 4130  min= 8  max= 48  step= 1  format= %0.1fdB  div_scale= 2
					Min = 4.0dB  Max = 24.0dB  Step = 0.5dB "
		::= { iqdec01CmdEntry 4130 }


	iqdec01AudioSetupLineUp OBJECT-TYPE
		SYNTAX		INTEGER
		MAX-ACCESS		read-write
		STATUS			current
		DESCRIPTION
				"TYPE: - Number
				 PAGE: - Audio- Audio Setup
					Line Up  cmdID= 4131  min= -48  max= 20  step= 1  format= %0.1fdBu  div_scale= 2
					Min = -24.0dBu  Max = 10.0dBu  Step = 0.5dBu "
		::= { iqdec01CmdEntry 4131 }


	iqdec01AudioSetupAudioSlewSelect OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Audio- Audio Setup
					Audio Slew Select  cmdID= 4605
					Instant  value= 0
					Fast  value= 1
					Medium  value= 2
					Slow  value= 3
					Slowest  value= 4  "
		::= { iqdec01CmdEntry 4605 }


	iqdec01AudioSetupAudioToneFrequencyLeft OBJECT-TYPE
		SYNTAX		INTEGER
		MAX-ACCESS		read-write
		STATUS			current
		DESCRIPTION
				"TYPE: - Number
				 PAGE: - Audio- Audio Setup
					Frequency Left  cmdID= 4601  min= 100  max= 15000  step= 100  format= %0.1fkHz  div_scale= 1000
					Min = 0.1kHz  Max = 15.0kHz  Step = 0.1kHz "
		::= { iqdec01CmdEntry 4601 }


	iqdec01AudioSetupAudioToneFrequencyRight OBJECT-TYPE
		SYNTAX		INTEGER
		MAX-ACCESS		read-write
		STATUS			current
		DESCRIPTION
				"TYPE: - Number
				 PAGE: - Audio- Audio Setup
					Frequency Right  cmdID= 4602  min= 100  max= 15000  step= 100  format= %0.1fkHz  div_scale= 1000
					Min = 0.1kHz  Max = 15.0kHz  Step = 0.1kHz "
		::= { iqdec01CmdEntry 4602 }


	iqdec01AudioSetupAudioToneIdentifyTone OBJECT-TYPE
		SYNTAX		INTEGER {
							val_Off(0),
							val_Left(1),
							val_Right(2)
							}
		MAX-ACCESS		read-write
		STATUS			current
		DESCRIPTION
				"TYPE: - RadiobuttonList
				 PAGE: - Audio- Audio Setup
					Identify Tone  cmdID= 4603
					Off  value= 0
					Left  value= 1
					Right  value= 2  "
		::= { iqdec01CmdEntry 4603 }


	iqdec01AudioSetupAudioMonitoringSilence OBJECT-TYPE
		SYNTAX		INTEGER
		MAX-ACCESS		read-write
		STATUS			current
		DESCRIPTION
				"TYPE: - Number
				 PAGE: - Audio- Audio Setup
					Silence  cmdID= 4500  min= -80  max= 0  step= 1  format= %0.0fdB  div_scale= 1
					Min = -80dB  Max = 0dB  Step = 1dB "
		::= { iqdec01CmdEntry 4500 }


	iqdec01AudioSetupAudioMonitoringLowLevel OBJECT-TYPE
		SYNTAX		INTEGER
		MAX-ACCESS		read-write
		STATUS			current
		DESCRIPTION
				"TYPE: - Number
				 PAGE: - Audio- Audio Setup
					Low Level  cmdID= 4501  min= -80  max= 0  step= 1  format= %0.0fdB  div_scale= 1
					Min = -80dB  Max = 0dB  Step = 1dB "
		::= { iqdec01CmdEntry 4501 }


	iqdec01AudioSetupAudioMonitoringHighLevel OBJECT-TYPE
		SYNTAX		INTEGER
		MAX-ACCESS		read-write
		STATUS			current
		DESCRIPTION
				"TYPE: - Number
				 PAGE: - Audio- Audio Setup
					High Level  cmdID= 4502  min= -80  max= 0  step= 1  format= %0.0fdB  div_scale= 1
					Min = -80dB  Max = 0dB  Step = 1dB "
		::= { iqdec01CmdEntry 4502 }


	iqdec01AudioSetupAudioMonitoringOverload OBJECT-TYPE
		SYNTAX		INTEGER
		MAX-ACCESS		read-write
		STATUS			current
		DESCRIPTION
				"TYPE: - Number
				 PAGE: - Audio- Audio Setup
					Overload  cmdID= 4503  min= -80  max= 0  step= 1  format= %0.0fdB  div_scale= 1
					Min = -80dB  Max = 0dB  Step = 1dB "
		::= { iqdec01CmdEntry 4503 }


	iqdec01AudioSetupAudioMonitoringWarningTimer OBJECT-TYPE
		SYNTAX		INTEGER
		MAX-ACCESS		read-write
		STATUS			current
		DESCRIPTION
				"TYPE: - Number
				 PAGE: - Audio- Audio Setup
					Warning Timer  cmdID= 4504  min= 1  max= 20  step= 1  format= %0.0fsec  div_scale= 1
					Min = 1sec  Max = 20sec  Step = 1sec "
		::= { iqdec01CmdEntry 4504 }


	iqdec01AudioSetupChannelStatusChannelStatusDest OBJECT-TYPE
		SYNTAX		RollCallString
		MAX-ACCESS		read-write
		STATUS			current
		DESCRIPTION
				"TYPE: - Editstring
				 PAGE: - Audio- Audio Setup
					Channel Status Dest  cmdID= 4606  "
		::= { iqdec01CmdEntry 4606 }


	iqdec01AudioSetupChannelStatusAESValidityBit OBJECT-TYPE
		SYNTAX		INTEGER { disable(0), enable(1) }
		MAX-ACCESS		read-write
		STATUS			current
		DESCRIPTION
				"TYPE: - Checkbox
				 PAGE: - Audio- Audio Setup
					AES Validity Bit  cmdID= 4607 "
		::= { iqdec01CmdEntry 4607 }


	iqdec01AudioSetupCalibrateAudio OBJECT-TYPE
		SYNTAX		INTEGER { noAction(0),val_Calibrate_Audio(1) }
		MAX-ACCESS		read-write
		STATUS			current
		DESCRIPTION
				"TYPE: - Button
				 PAGE: - Audio- Audio Setup
					Calibrate Audio  cmdID= 4610  value= 1  "
		::= { iqdec01CmdEntry 4610 }


	iqdec01AudioSetupCalonVideoIPSel OBJECT-TYPE
		SYNTAX		INTEGER { disable(0), enable(1) }
		MAX-ACCESS		read-write
		STATUS			current
		DESCRIPTION
				"TYPE: - Checkbox
				 PAGE: - Audio- Audio Setup
					Cal on Video IP Sel  cmdID= 4611 "
		::= { iqdec01CmdEntry 4611 }


	iqdec01Decoder OBJECT-TYPE
		SYNTAX		INTEGER {
							val_Studio(0),
							val_Simple(1),
							val_VHS_Unstable(6)
							}
		MAX-ACCESS		read-write
		STATUS			current
		DESCRIPTION
				"TYPE: - RadiobuttonList
				 PAGE: - Decoder
					Decoder  cmdID= 4904
					Studio  value= 0
					Simple  value= 1
					VHS/Unstable  value= 6  "
		::= { iqdec01CmdEntry 4904 }


	iqdec01DecoderColorKiller OBJECT-TYPE
		SYNTAX		INTEGER {
							val_Chroma_Off(0),
							val_Chroma_On(1),
							val_Auto(2)
							}
		MAX-ACCESS		read-write
		STATUS			current
		DESCRIPTION
				"TYPE: - RadiobuttonList
				 PAGE: - Decoder
					Color Killer  cmdID= 4903
					Chroma Off  value= 0
					Chroma On  value= 1
					Auto  value= 2  "
		::= { iqdec01CmdEntry 4903 }


	iqdec01DecoderMinimumDelay OBJECT-TYPE
		SYNTAX		INTEGER { disable(0), enable(1) }
		MAX-ACCESS		read-write
		STATUS			current
		DESCRIPTION
				"TYPE: - Checkbox
				 PAGE: - Decoder
					Minimum Delay  cmdID= 4902 "
		::= { iqdec01CmdEntry 4902 }


	iqdec01DecoderSECAMStudioNotch OBJECT-TYPE
		SYNTAX		INTEGER {
							val_Adaptive(0),
							val_Controllable(1)
							}
		MAX-ACCESS		read-write
		STATUS			current
		DESCRIPTION
				"TYPE: - RadiobuttonList
				 PAGE: - Decoder
					Notch  cmdID= 4906
					Adaptive  value= 0
					Controllable  value= 1  "
		::= { iqdec01CmdEntry 4906 }


	iqdec01DecoderSECAMStudioLumaBandwidth OBJECT-TYPE
		SYNTAX		INTEGER {
							val_Wide(0),
							val_Medium(1),
							val_Narrow(2)
							}
		MAX-ACCESS		read-write
		STATUS			current
		DESCRIPTION
				"TYPE: - RadiobuttonList
				 PAGE: - Decoder
					Luma Bandwidth  cmdID= 4905
					Wide  value= 0
					Medium  value= 1
					Narrow  value= 2  "
		::= { iqdec01CmdEntry 4905 }


	iqdec01DecoderSECAMVHSLumaBandwidth OBJECT-TYPE
		SYNTAX		INTEGER {
							val_Wide(0),
							val_Medium(1),
							val_Narrow(2)
							}
		MAX-ACCESS		read-write
		STATUS			current
		DESCRIPTION
				"TYPE: - RadiobuttonList
				 PAGE: - Decoder
					Luma Bandwidth  cmdID= 4907
					Wide  value= 0
					Medium  value= 1
					Narrow  value= 2  "
		::= { iqdec01CmdEntry 4907 }


	iqdec01GenlockReferenceSrc OBJECT-TYPE
		SYNTAX		INTEGER {
							val_Free_Run(0),
							val_External_Reference(1),
							val_Input_Video(2)
							}
		MAX-ACCESS		read-write
		STATUS			current
		DESCRIPTION
				"TYPE: - RadiobuttonList
				 PAGE: - Genlock
					Reference Src  cmdID= 2000
					Free Run  value= 0
					External Reference  value= 1
					Input Video  value= 2  "
		::= { iqdec01CmdEntry 2000 }


	iqdec01GenlockReferenceTimeHPhase625 OBJECT-TYPE
		SYNTAX		INTEGER
		MAX-ACCESS		read-write
		STATUS			current
		DESCRIPTION
				"TYPE: - Number
				 PAGE: - Genlock
					H Phase 625  cmdID= 2001  min= -864  max= 864  step= 1  format= %0.0fpx  div_scale= 1
					Min = -864px  Max = 864px  Step = 1px "
		::= { iqdec01CmdEntry 2001 }


	iqdec01GenlockReferenceTimeVPhase625 OBJECT-TYPE
		SYNTAX		INTEGER
		MAX-ACCESS		read-write
		STATUS			current
		DESCRIPTION
				"TYPE: - Number
				 PAGE: - Genlock
					V Phase 625  cmdID= 2002  min= -312  max= 312  step= 1  format= %0.0fln  div_scale= 1
					Min = -312ln  Max = 312ln  Step = 1ln "
		::= { iqdec01CmdEntry 2002 }


	iqdec01GenlockReferenceTimeHPhase525 OBJECT-TYPE
		SYNTAX		INTEGER
		MAX-ACCESS		read-write
		STATUS			current
		DESCRIPTION
				"TYPE: - Number
				 PAGE: - Genlock
					H Phase 525  cmdID= 2003  min= -858  max= 858  step= 1  format= %0.0fpx  div_scale= 1
					Min = -858px  Max = 858px  Step = 1px "
		::= { iqdec01CmdEntry 2003 }


	iqdec01GenlockReferenceTimeVPhase525 OBJECT-TYPE
		SYNTAX		INTEGER
		MAX-ACCESS		read-write
		STATUS			current
		DESCRIPTION
				"TYPE: - Number
				 PAGE: - Genlock
					V Phase 525  cmdID= 2004  min= -262  max= 262  step= 1  format= %0.0fln  div_scale= 1
					Min = -262ln  Max = 262ln  Step = 1ln "
		::= { iqdec01CmdEntry 2004 }


	iqdec01GenlockReferenceTimeHDelay625 OBJECT-TYPE
		SYNTAX		INTEGER
		MAX-ACCESS		read-write
		STATUS			current
		DESCRIPTION
				"TYPE: - Number
				 PAGE: - Genlock
					H Delay 625  cmdID= 2005  min= 0  max= 1727  step= 1  format= %0.0fpx  div_scale= 1
					Min = 0px  Max = 1727px  Step = 1px "
		::= { iqdec01CmdEntry 2005 }


	iqdec01GenlockReferenceTimeVDelay625 OBJECT-TYPE
		SYNTAX		INTEGER
		MAX-ACCESS		read-write
		STATUS			current
		DESCRIPTION
				"TYPE: - Number
				 PAGE: - Genlock
					V Delay 625  cmdID= 2006  min= 0  max= 624  step= 1  format= %0.0fln  div_scale= 1
					Min = 0ln  Max = 624ln  Step = 1ln "
		::= { iqdec01CmdEntry 2006 }


	iqdec01GenlockReferenceTimeHDelay525 OBJECT-TYPE
		SYNTAX		INTEGER
		MAX-ACCESS		read-write
		STATUS			current
		DESCRIPTION
				"TYPE: - Number
				 PAGE: - Genlock
					H Delay 525  cmdID= 2007  min= 0  max= 1715  step= 1  format= %0.0fpx  div_scale= 1
					Min = 0px  Max = 1715px  Step = 1px "
		::= { iqdec01CmdEntry 2007 }


	iqdec01GenlockReferenceTimeVDelay525 OBJECT-TYPE
		SYNTAX		INTEGER
		MAX-ACCESS		read-write
		STATUS			current
		DESCRIPTION
				"TYPE: - Number
				 PAGE: - Genlock
					V Delay 525  cmdID= 2008  min= 0  max= 524  step= 1  format= %0.0fln  div_scale= 1
					Min = 0ln  Max = 524ln  Step = 1ln "
		::= { iqdec01CmdEntry 2008 }


	iqdec01GenlockFreerunFrequency OBJECT-TYPE
		SYNTAX		INTEGER
		MAX-ACCESS		read-write
		STATUS			current
		DESCRIPTION
				"TYPE: - Number
				 PAGE: - Genlock
					Freerun Frequency  cmdID= 2104  min= -60  max= 60  step= 1  format= %0.0f  div_scale= 1
					Min = -60  Max = 60  Step = 1 "
		::= { iqdec01CmdEntry 2104 }


	iqdec01GenlockFrameDelay OBJECT-TYPE
		SYNTAX		INTEGER {
							val_0_Frame_Delay(0),
							val_1_Frame_Delay(1),
							val_2_Frame_Delay(2)
							}
		MAX-ACCESS		read-write
		STATUS			current
		DESCRIPTION
				"TYPE: - RadiobuttonList
				 PAGE: - Genlock
					Frame Delay  cmdID= 2106
					0 Frame Delay  value= 0
					1 Frame Delay  value= 1
					2 Frame Delay  value= 2  "
		::= { iqdec01CmdEntry 2106 }


	iqdec01SetupPatternPatternType OBJECT-TYPE
		SYNTAX		INTEGER {
							val_Black(0),
							val_EBU_Color_Bars(1),
							val_100_Color_Bars(2),
							val_Ramp(3),
							val_Multi_Burst(4),
							val_Pulse_Bar(5)
							}
		MAX-ACCESS		read-write
		STATUS			current
		DESCRIPTION
				"TYPE: - RadiobuttonList
				 PAGE: - Setup
					Pattern Type  cmdID= 2401
					Black  value= 0
					EBU Color Bars  value= 1
					100% Color Bars  value= 2
					Ramp  value= 3
					Multi-Burst  value= 4
					Pulse & Bar  value= 5  "
		::= { iqdec01CmdEntry 2401 }


	iqdec01SetupPatternPatternEnable OBJECT-TYPE
		SYNTAX		INTEGER { disable(0), enable(1) }
		MAX-ACCESS		read-write
		STATUS			current
		DESCRIPTION
				"TYPE: - Checkbox
				 PAGE: - Setup
					Pattern Enable  cmdID= 2402 "
		::= { iqdec01CmdEntry 2402 }


	iqdec01SetupPatternAnimatedPattern OBJECT-TYPE
		SYNTAX		INTEGER { disable(0), enable(1) }
		MAX-ACCESS		read-write
		STATUS			current
		DESCRIPTION
				"TYPE: - Checkbox
				 PAGE: - Setup
					Animated Pattern  cmdID= 12802 "
		::= { iqdec01CmdEntry 12802 }


	iqdec01SetupCaptionEditCaption OBJECT-TYPE
		SYNTAX		RollCallString
		MAX-ACCESS		read-write
		STATUS			current
		DESCRIPTION
				"TYPE: - Editstring
				 PAGE: - Setup
					Edit Caption  cmdID= 2901  "
		::= { iqdec01CmdEntry 2901 }


	iqdec01SetupCaptionCaptionSelect OBJECT-TYPE
		SYNTAX		INTEGER { disable(0), enable(1) }
		MAX-ACCESS		read-write
		STATUS			current
		DESCRIPTION
				"TYPE: - Checkbox
				 PAGE: - Setup
					Caption Select  cmdID= 2900 "
		::= { iqdec01CmdEntry 2900 }


	iqdec01525Pass525Lines1122Line11 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 11  cmdID= 2201
					Blank  value= 0
					Pass VBI  value= 1
					Decode VBI  value= 2  "
		::= { iqdec01CmdEntry 2201 }


	iqdec01525Pass525Lines1122Line12 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 12  cmdID= 2202
					Blank  value= 0
					Pass VBI  value= 1
					Decode VBI  value= 2  "
		::= { iqdec01CmdEntry 2202 }


	iqdec01525Pass525Lines1122Line13 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 13  cmdID= 2203
					Blank  value= 0
					Pass VBI  value= 1
					Decode VBI  value= 2  "
		::= { iqdec01CmdEntry 2203 }


	iqdec01525Pass525Lines1122Line14 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 14  cmdID= 2204
					Blank  value= 0
					Pass VBI  value= 1
					Decode VBI  value= 2  "
		::= { iqdec01CmdEntry 2204 }


	iqdec01525Pass525Lines1122Line15 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 15  cmdID= 2205
					Blank  value= 0
					Pass VBI  value= 1
					Decode VBI  value= 2  "
		::= { iqdec01CmdEntry 2205 }


	iqdec01525Pass525Lines1122Line16 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 16  cmdID= 2206
					Blank  value= 0
					Pass VBI  value= 1
					Decode VBI  value= 2  "
		::= { iqdec01CmdEntry 2206 }


	iqdec01525Pass525Lines1122Line17 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 17  cmdID= 2207
					Blank  value= 0
					Pass VBI  value= 1
					Decode VBI  value= 2  "
		::= { iqdec01CmdEntry 2207 }


	iqdec01525Pass525Lines1122Line18 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 18  cmdID= 2208
					Blank  value= 0
					Pass VBI  value= 1
					Decode VBI  value= 2  "
		::= { iqdec01CmdEntry 2208 }


	iqdec01525Pass525Lines1122Line19 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 19  cmdID= 2209
					Blank  value= 0
					Pass VBI  value= 1
					Decode VBI  value= 2  "
		::= { iqdec01CmdEntry 2209 }


	iqdec01525Pass525Lines1122Line20 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 11-22
					Line 20  cmdID= 2210
					Blank  value= 0
					Pass VBI  value= 1
					Decode VBI  value= 2  "
		::= { iqdec01CmdEntry 2210 }


	iqdec01525Pass525Lines1122Line21 OBJECT-TYPE
		SYNTAX		INTEGER {
							val_Blank(0),
							val_Data(1),
							val_Picture(2),
							val_Closed_Captions(3)
							}
		MAX-ACCESS		read-write
		STATUS			current
		DESCRIPTION
				"TYPE: - RadiobuttonList
				 PAGE: - Setup- VBI & HANC Blank- 525 Lines 11-22
					Line 21  cmdID= 2211
					Blank  value= 0
					Data  value= 1
					Picture  value= 2
					Closed Captions  value= 3  "
		::= { iqdec01CmdEntry 2211 }


	iqdec01525Pass525Lines1122Line22 OBJECT-TYPE
		SYNTAX		INTEGER {
							val_Blank(0),
							val_Data(1),
							val_Picture(2)
							}
		MAX-ACCESS		read-write
		STATUS			current
		DESCRIPTION
				"TYPE: - RadiobuttonList
				 PAGE: - Setup- VBI & HANC Blank- 525 Lines 11-22
					Line 22  cmdID= 2212
					Blank  value= 0
					Data  value= 1
					Picture  value= 2  "
		::= { iqdec01CmdEntry 2212 }


	iqdec01525Pass525Lines274285Line274 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 274  cmdID= 2213
					Blank  value= 0
					Pass VBI  value= 1
					Decode VBI  value= 2  "
		::= { iqdec01CmdEntry 2213 }


	iqdec01525Pass525Lines274285Line275 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 275  cmdID= 2214
					Blank  value= 0
					Pass VBI  value= 1
					Decode VBI  value= 2  "
		::= { iqdec01CmdEntry 2214 }


	iqdec01525Pass525Lines274285Line276 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 276  cmdID= 2215
					Blank  value= 0
					Pass VBI  value= 1
					Decode VBI  value= 2  "
		::= { iqdec01CmdEntry 2215 }


	iqdec01525Pass525Lines274285Line277 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 277  cmdID= 2216
					Blank  value= 0
					Pass VBI  value= 1
					Decode VBI  value= 2  "
		::= { iqdec01CmdEntry 2216 }


	iqdec01525Pass525Lines274285Line278 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 278  cmdID= 2217
					Blank  value= 0
					Pass VBI  value= 1
					Decode VBI  value= 2  "
		::= { iqdec01CmdEntry 2217 }


	iqdec01525Pass525Lines274285Line279 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 279  cmdID= 2218
					Blank  value= 0
					Pass VBI  value= 1
					Decode VBI  value= 2  "
		::= { iqdec01CmdEntry 2218 }


	iqdec01525Pass525Lines274285Line280 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 280  cmdID= 2219
					Blank  value= 0
					Pass VBI  value= 1
					Decode VBI  value= 2  "
		::= { iqdec01CmdEntry 2219 }


	iqdec01525Pass525Lines274285Line281 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 281  cmdID= 2220
					Blank  value= 0
					Pass VBI  value= 1
					Decode VBI  value= 2  "
		::= { iqdec01CmdEntry 2220 }


	iqdec01525Pass525Lines274285Line282 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 525 Lines 274-285
					Line 282  cmdID= 2221
					Blank  value= 0
					Pass VBI  value= 1
					Decode VBI  value= 2  "
		::= { iqdec01CmdEntry 2221 }


	iqdec01525Pass525Lines274285Line283 OBJECT-TYPE
		SYNTAX		INTEGER {
							val_Blank(0),
							val_Data(1),
							val_Picture(2)
							}
		MAX-ACCESS		read-write
		STATUS			current
		DESCRIPTION
				"TYPE: - RadiobuttonList
				 PAGE: - Setup- VBI & HANC Blank- 525 Lines 274-285
					Line 283  cmdID= 2222
					Blank  value= 0
					Data  value= 1
					Picture  value= 2  "
		::= { iqdec01CmdEntry 2222 }


	iqdec01525Pass525Lines274285Line284 OBJECT-TYPE
		SYNTAX		INTEGER {
							val_Blank(0),
							val_Data(1),
							val_Picture(2),
							val_Closed_Captions(3)
							}
		MAX-ACCESS		read-write
		STATUS			current
		DESCRIPTION
				"TYPE: - RadiobuttonList
				 PAGE: - Setup- VBI & HANC Blank- 525 Lines 274-285
					Line 284  cmdID= 2223
					Blank  value= 0
					Data  value= 1
					Picture  value= 2
					Closed Captions  value= 3  "
		::= { iqdec01CmdEntry 2223 }


	iqdec01525Pass525Lines274285Line285 OBJECT-TYPE
		SYNTAX		INTEGER {
							val_Blank(0),
							val_Data(1),
							val_Picture(2)
							}
		MAX-ACCESS		read-write
		STATUS			current
		DESCRIPTION
				"TYPE: - RadiobuttonList
				 PAGE: - Setup- VBI & HANC Blank- 525 Lines 274-285
					Line 285  cmdID= 2224
					Blank  value= 0
					Data  value= 1
					Picture  value= 2  "
		::= { iqdec01CmdEntry 2224 }


	iqdec01625Pass625Lines723Line7 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 7  cmdID= 2230
					Blank  value= 0
					Pass VBI  value= 1
					Decode VBI  value= 2  "
		::= { iqdec01CmdEntry 2230 }


	iqdec01625Pass625Lines723Line8 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 8  cmdID= 2231
					Blank  value= 0
					Pass VBI  value= 1
					Decode VBI  value= 2  "
		::= { iqdec01CmdEntry 2231 }


	iqdec01625Pass625Lines723Line9 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 9  cmdID= 2232
					Blank  value= 0
					Pass VBI  value= 1
					Decode VBI  value= 2  "
		::= { iqdec01CmdEntry 2232 }


	iqdec01625Pass625Lines723Line10 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 10  cmdID= 2233
					Blank  value= 0
					Pass VBI  value= 1
					Decode VBI  value= 2  "
		::= { iqdec01CmdEntry 2233 }


	iqdec01625Pass625Lines723Line11 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 11  cmdID= 2234
					Blank  value= 0
					Pass VBI  value= 1
					Decode VBI  value= 2  "
		::= { iqdec01CmdEntry 2234 }


	iqdec01625Pass625Lines723Line12 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 12  cmdID= 2235
					Blank  value= 0
					Pass VBI  value= 1
					Decode VBI  value= 2  "
		::= { iqdec01CmdEntry 2235 }


	iqdec01625Pass625Lines723Line13 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 13  cmdID= 2236
					Blank  value= 0
					Pass VBI  value= 1
					Decode VBI  value= 2  "
		::= { iqdec01CmdEntry 2236 }


	iqdec01625Pass625Lines723Line14 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 14  cmdID= 2237
					Blank  value= 0
					Pass VBI  value= 1
					Decode VBI  value= 2  "
		::= { iqdec01CmdEntry 2237 }


	iqdec01625Pass625Lines723Line15 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 15  cmdID= 2238
					Blank  value= 0
					Pass VBI  value= 1
					Decode VBI  value= 2  "
		::= { iqdec01CmdEntry 2238 }


	iqdec01625Pass625Lines723Line16 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 16  cmdID= 2239
					Blank  value= 0
					Pass VBI  value= 1
					Decode VBI  value= 2  "
		::= { iqdec01CmdEntry 2239 }


	iqdec01625Pass625Lines723Line17 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 17  cmdID= 2240
					Blank  value= 0
					Pass VBI  value= 1
					Decode VBI  value= 2  "
		::= { iqdec01CmdEntry 2240 }


	iqdec01625Pass625Lines723Line18 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 18  cmdID= 2241
					Blank  value= 0
					Pass VBI  value= 1
					Decode VBI  value= 2  "
		::= { iqdec01CmdEntry 2241 }


	iqdec01625Pass625Lines723Line19 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 19  cmdID= 2242
					Blank  value= 0
					Pass VBI  value= 1
					Decode VBI  value= 2  "
		::= { iqdec01CmdEntry 2242 }


	iqdec01625Pass625Lines723Line20 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 20  cmdID= 2243
					Blank  value= 0
					Pass VBI  value= 1
					Decode VBI  value= 2  "
		::= { iqdec01CmdEntry 2243 }


	iqdec01625Pass625Lines723Line21 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 21  cmdID= 2244
					Blank  value= 0
					Pass VBI  value= 1
					Decode VBI  value= 2  "
		::= { iqdec01CmdEntry 2244 }


	iqdec01625Pass625Lines723Line22 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 7-23
					Line 22  cmdID= 2245
					Blank  value= 0
					Pass VBI  value= 1
					Decode VBI  value= 2  "
		::= { iqdec01CmdEntry 2245 }


	iqdec01625Pass625Lines723Line23 OBJECT-TYPE
		SYNTAX		INTEGER {
							val_Blank(0),
							val_WSS(1),
							val_Picture(2)
							}
		MAX-ACCESS		read-write
		STATUS			current
		DESCRIPTION
				"TYPE: - RadiobuttonList
				 PAGE: - Setup- VBI & HANC Blank- 625 Lines 7-23
					Line 23  cmdID= 2246
					Blank  value= 0
					WSS  value= 1
					Picture  value= 2  "
		::= { iqdec01CmdEntry 2246 }


	iqdec01625Pass625Lines320335Line320 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 320  cmdID= 2247
					Blank  value= 0
					Pass VBI  value= 1
					Decode VBI  value= 2  "
		::= { iqdec01CmdEntry 2247 }


	iqdec01625Pass625Lines320335Line321 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 321  cmdID= 2248
					Blank  value= 0
					Pass VBI  value= 1
					Decode VBI  value= 2  "
		::= { iqdec01CmdEntry 2248 }


	iqdec01625Pass625Lines320335Line322 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 322  cmdID= 2249
					Blank  value= 0
					Pass VBI  value= 1
					Decode VBI  value= 2  "
		::= { iqdec01CmdEntry 2249 }


	iqdec01625Pass625Lines320335Line323 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 323  cmdID= 2250
					Blank  value= 0
					Pass VBI  value= 1
					Decode VBI  value= 2  "
		::= { iqdec01CmdEntry 2250 }


	iqdec01625Pass625Lines320335Line324 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 324  cmdID= 2251
					Blank  value= 0
					Pass VBI  value= 1
					Decode VBI  value= 2  "
		::= { iqdec01CmdEntry 2251 }


	iqdec01625Pass625Lines320335Line325 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 325  cmdID= 2252
					Blank  value= 0
					Pass VBI  value= 1
					Decode VBI  value= 2  "
		::= { iqdec01CmdEntry 2252 }


	iqdec01625Pass625Lines320335Line326 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 326  cmdID= 2253
					Blank  value= 0
					Pass VBI  value= 1
					Decode VBI  value= 2  "
		::= { iqdec01CmdEntry 2253 }


	iqdec01625Pass625Lines320335Line327 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 327  cmdID= 2254
					Blank  value= 0
					Pass VBI  value= 1
					Decode VBI  value= 2  "
		::= { iqdec01CmdEntry 2254 }


	iqdec01625Pass625Lines320335Line328 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 328  cmdID= 2255
					Blank  value= 0
					Pass VBI  value= 1
					Decode VBI  value= 2  "
		::= { iqdec01CmdEntry 2255 }


	iqdec01625Pass625Lines320335Line329 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 329  cmdID= 2256
					Blank  value= 0
					Pass VBI  value= 1
					Decode VBI  value= 2  "
		::= { iqdec01CmdEntry 2256 }


	iqdec01625Pass625Lines320335Line330 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 330  cmdID= 2257
					Blank  value= 0
					Pass VBI  value= 1
					Decode VBI  value= 2  "
		::= { iqdec01CmdEntry 2257 }


	iqdec01625Pass625Lines320335Line331 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 331  cmdID= 2258
					Blank  value= 0
					Pass VBI  value= 1
					Decode VBI  value= 2  "
		::= { iqdec01CmdEntry 2258 }


	iqdec01625Pass625Lines320335Line332 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 332  cmdID= 2259
					Blank  value= 0
					Pass VBI  value= 1
					Decode VBI  value= 2  "
		::= { iqdec01CmdEntry 2259 }


	iqdec01625Pass625Lines320335Line333 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 333  cmdID= 2260
					Blank  value= 0
					Pass VBI  value= 1
					Decode VBI  value= 2  "
		::= { iqdec01CmdEntry 2260 }


	iqdec01625Pass625Lines320335Line334 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 334  cmdID= 2261
					Blank  value= 0
					Pass VBI  value= 1
					Decode VBI  value= 2  "
		::= { iqdec01CmdEntry 2261 }


	iqdec01625Pass625Lines320335Line335 OBJECT-TYPE
		SYNTAX		INTEGER {
							val_Blank(0),
							val_Pass_VBI(1),
							val_Decode_VBI(2)
							}
		MAX-ACCESS		read-write
		STATUS			current
		DESCRIPTION
				"TYPE: - RadiobuttonList
				 PAGE: - Setup- VBI & HANC Blank- 625 Lines 320-335
					Line 335  cmdID= 2262
					Blank  value= 0
					Pass VBI  value= 1
					Decode VBI  value= 2  "
		::= { iqdec01CmdEntry 2262 }


	iqdec01SetupVBIHANCBlankHANCBlank OBJECT-TYPE
		SYNTAX		INTEGER { disable(0), enable(1) }
		MAX-ACCESS		read-write
		STATUS			current
		DESCRIPTION
				"TYPE: - Checkbox
				 PAGE: - Setup- VBI & HANC Blank
					HANC Blank  cmdID= 2200 "
		::= { iqdec01CmdEntry 2200 }


	iqdec01SetupVBIHANCBlankSECAMBottles OBJECT-TYPE
		SYNTAX		INTEGER {
							val_Auto(0),
							val_Off(1),
							val_On(2)
							}
		MAX-ACCESS		read-write
		STATUS			current
		DESCRIPTION
				"TYPE: - RadiobuttonList
				 PAGE: - Setup- VBI & HANC Blank
					SECAM Bottles  cmdID= 2267
					Auto  value= 0
					Off  value= 1
					On  value= 2  "
		::= { iqdec01CmdEntry 2267 }


	iqdec01SetupGPIIOGPIMode OBJECT-TYPE
		SYNTAX		INTEGER {
							val_Unused(0),
							val_Input(1),
							val_Output(2)
							}
		MAX-ACCESS		read-write
		STATUS			current
		DESCRIPTION
				"TYPE: - RadiobuttonList
				 PAGE: - Setup- GPI I/O
					GPI Mode  cmdID= 3200
					Unused  value= 0
					Input  value= 1
					Output  value= 2  "
		::= { iqdec01CmdEntry 3200 }


	iqdec01SetupGPIIOGPIipSelect OBJECT-TYPE
		SYNTAX		INTEGER {
							val_Pattern(0),
							val_Freeze(1),
							val_Memory1(2),
							val_Memory2(3),
							val_Memory3(4),
							val_Memory4(5),
							val_Memory5(6),
							val_Memory6(7),
							val_Memory7(8),
							val_Memory8(9),
							val_Memory_1_2(10),
							val_Memory_3_4(11),
							val_Memory_5_6(12),
							val_Memory_7_8(13)
							}
		MAX-ACCESS		read-write
		STATUS			current
		DESCRIPTION
				"TYPE: - RadiobuttonList
				 PAGE: - Setup- GPI I/O
					GPI i/p Select  cmdID= 3202
					Pattern  value= 0
					Freeze  value= 1
					Memory1  value= 2
					Memory2  value= 3
					Memory3  value= 4
					Memory4  value= 5
					Memory5  value= 6
					Memory6  value= 7
					Memory7  value= 8
					Memory8  value= 9
					Memory 1-2  value= 10
					Memory 3-4  value= 11
					Memory 5-6  value= 12
					Memory 7-8  value= 13  "
		::= { iqdec01CmdEntry 3202 }


	iqdec01SetupGPIIOGPIopSelect OBJECT-TYPE
		SYNTAX		INTEGER {
							val_Input_Present(0),
							val_Standard_625(1),
							val_Video_Delay(2)
							}
		MAX-ACCESS		read-write
		STATUS			current
		DESCRIPTION
				"TYPE: - RadiobuttonList
				 PAGE: - Setup- GPI I/O
					GPI o/p Select  cmdID= 3204
					Input Present  value= 0
					Standard 625  value= 1
					Video Delay  value= 2  "
		::= { iqdec01CmdEntry 3204 }


	iqdec01SetupGPIIOOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3206 "
		::= { iqdec01CmdEntry 3206 }


	iqdec01SetupGPIIOTimerActiveHigh OBJECT-TYPE
		SYNTAX		INTEGER { disable(0), enable(1) }
		MAX-ACCESS		read-write
		STATUS			current
		DESCRIPTION
				"TYPE: - Checkbox
				 PAGE: - Setup- GPI I/O
					Timer Active High  cmdID= 3207 "
		::= { iqdec01CmdEntry 3207 }


	iqdec01SetupGPIIOAudioDelay OBJECT-TYPE
		SYNTAX		INTEGER { disable(0), enable(1) }
		MAX-ACCESS		read-write
		STATUS			current
		DESCRIPTION
				"TYPE: - Checkbox
				 PAGE: - Setup- GPI I/O
					Audio Delay  cmdID= 3209 "
		::= { iqdec01CmdEntry 3209 }


	iqdec01SetupGPIIOGPIInDelay OBJECT-TYPE
		SYNTAX		RollCallString
		MAX-ACCESS		read-only
		STATUS			current
		DESCRIPTION
				"TYPE: - Display
				 PAGE: - Setup- GPI I/O
					GPI In Delay  cmdID= 3208  format=   "
		::= { iqdec01CmdEntry 3208 }


	iqdec01SetupGPIIOGPIOutDelay OBJECT-TYPE
		SYNTAX		RollCallString
		MAX-ACCESS		read-only
		STATUS			current
		DESCRIPTION
				"TYPE: - Display
				 PAGE: - Setup- GPI I/O
					GPI Out Delay  cmdID= 3205  format=   "
		::= { iqdec01CmdEntry 3205 }


	iqdec01SetupRollTrackDisableAll OBJECT-TYPE
		SYNTAX		INTEGER { disable(0), enable(1) }
		MAX-ACCESS		read-write
		STATUS			current
		DESCRIPTION
				"TYPE: - Checkbox
				 PAGE: - Setup- RollTrack
					Disable All  cmdID= 3004 "
		::= { iqdec01CmdEntry 3004 }


	iqdec01SetupRollTrackIndex OBJECT-TYPE
		SYNTAX		INTEGER
		MAX-ACCESS		read-write
		STATUS			current
		DESCRIPTION
				"TYPE: - Number
				 PAGE: - Setup- RollTrack
					RollTrack Index  cmdID= 3000  min= 1  max= 16  step= 1  format= %0.0f  div_scale= 1
					Min = 1  Max = 16  Step = 1 "
		::= { iqdec01CmdEntry 3000 }


	iqdec01SetupRollTrackSource OBJECT-TYPE
		SYNTAX		INTEGER {
							val_Unused(-1),
							val_Input_Present(0),
							val_Input_Missing(1),
							val_Standard_525(2),
							val_Standard_625(3),
							val_Audio_Delay(4),
							val_Video_Delay(5),
							val_Ref_Lost(6),
							val_Ref_Present(7),
							val_Ref_Error(8),
							val_De_embed_1_Lost(9),
							val_De_embed_1_Present(10),
							val_De_embed_2_Lost(11),
							val_De_embed_2_Present(12),
							val_De_embed_3_Lost(13),
							val_De_embed_3_Present(14),
							val_De_embed_4_Lost(15),
							val_De_embed_4_Present(16),
							val_De_embed_5_Lost(17),
							val_De_embed_5_Present(18),
							val_De_embed_6_Lost(19),
							val_De_embed_6_Present(20),
							val_De_embed_7_Lost(21),
							val_De_embed_7_Present(22),
							val_De_embed_8_Lost(23),
							val_De_embed_8_Present(24)
							}
		MAX-ACCESS		read-write
		STATUS			current
		DESCRIPTION
				"TYPE: - RadiobuttonList
				 PAGE: - Setup- RollTrack
					RollTrack Source  cmdID= 3001
					Unused  value= -1
					Input Present  value= 0
					Input Missing  value= 1
					Standard 525  value= 2
					Standard 625  value= 3
					Audio Delay  value= 4
					Video Delay  value= 5
					Ref. Lost  value= 6
					Ref. Present  value= 7
					Ref. Error  value= 8
					De-embed 1 Lost  value= 9
					De-embed 1 Present  value= 10
					De-embed 2 Lost  value= 11
					De-embed 2 Present  value= 12
					De-embed 3 Lost  value= 13
					De-embed 3 Present  value= 14
					De-embed 4 Lost  value= 15
					De-embed 4 Present  value= 16
					De-embed 5 Lost  value= 17
					De-embed 5 Present  value= 18
					De-embed 6 Lost  value= 19
					De-embed 6 Present  value= 20
					De-embed 7 Lost  value= 21
					De-embed 7 Present  value= 22
					De-embed 8 Lost  value= 23
					De-embed 8 Present  value= 24  "
		::= { iqdec01CmdEntry 3001 }


	iqdec01SetupRollTrackAddress OBJECT-TYPE
		SYNTAX		RollCallString
		MAX-ACCESS		read-write
		STATUS			current
		DESCRIPTION
				"TYPE: - Editstring
				 PAGE: - Setup- RollTrack
					RollTrack Address  cmdID= 3002  "
		::= { iqdec01CmdEntry 3002 }


	iqdec01SetupRollTrackCommand OBJECT-TYPE
		SYNTAX		RollCallString
		MAX-ACCESS		read-write
		STATUS			current
		DESCRIPTION
				"TYPE: - Editstring
				 PAGE: - Setup- RollTrack
					RollTrack Command  cmdID= 3003  "
		::= { iqdec01CmdEntry 3003 }


	iqdec01SetupRollTrackStatus OBJECT-TYPE
		SYNTAX		RollCallString
		MAX-ACCESS		read-only
		STATUS			current
		DESCRIPTION
				"TYPE: - Display
				 PAGE: - Setup- RollTrack
					RollTrack Status  cmdID= 3005  format=   "
		::= { iqdec01CmdEntry 3005 }


	iqdec01SetupRollTrackSending OBJECT-TYPE
		SYNTAX		RollCallString
		MAX-ACCESS		read-only
		STATUS			current
		DESCRIPTION
				"TYPE: - Display
				 PAGE: - Setup- RollTrack
					RollTrack Sending  cmdID= 3006  format=   "
		::= { iqdec01CmdEntry 3006 }


	iqdec01SetupEnableLoggingInput OBJECT-TYPE
		SYNTAX		INTEGER { disable(0), enable(1) }
		MAX-ACCESS		read-write
		STATUS			current
		DESCRIPTION
				"TYPE: - Checkbox
				 PAGE: - Setup- Logging
					Input  cmdID= 6000 "
		::= { iqdec01CmdEntry 6000 }


	iqdec01SetupLoggingInput OBJECT-TYPE
		SYNTAX		RollCallString
		MAX-ACCESS		read-only
		STATUS			current
		DESCRIPTION
				"TYPE: - Display
				 PAGE: - Setup- Logging
					Input  cmdID= 6200  format=   "
		::= { iqdec01CmdEntry 6200 }


	iqdec01SetupEnableLoggingStd OBJECT-TYPE
		SYNTAX		INTEGER { disable(0), enable(1) }
		MAX-ACCESS		read-write
		STATUS			current
		DESCRIPTION
				"TYPE: - Checkbox
				 PAGE: - Setup- Logging
					Std  cmdID= 6001 "
		::= { iqdec01CmdEntry 6001 }


	iqdec01SetupLoggingStd OBJECT-TYPE
		SYNTAX		RollCallString
		MAX-ACCESS		read-only
		STATUS			current
		DESCRIPTION
				"TYPE: - Display
				 PAGE: - Setup- Logging
					Std  cmdID= 6201  format=   "
		::= { iqdec01CmdEntry 6201 }


	iqdec01SetupEnableLoggingReference OBJECT-TYPE
		SYNTAX		INTEGER { disable(0), enable(1) }
		MAX-ACCESS		read-write
		STATUS			current
		DESCRIPTION
				"TYPE: - Checkbox
				 PAGE: - Setup- Logging
					Reference  cmdID= 6002 "
		::= { iqdec01CmdEntry 6002 }


	iqdec01SetupLoggingReference OBJECT-TYPE
		SYNTAX		RollCallString
		MAX-ACCESS		read-only
		STATUS			current
		DESCRIPTION
				"TYPE: - Display
				 PAGE: - Setup- Logging
					Reference  cmdID= 6202  format=   "
		::= { iqdec01CmdEntry 6202 }


	iqdec01SetupEnableLoggingRollTrack OBJECT-TYPE
		SYNTAX		INTEGER { disable(0), enable(1) }
		MAX-ACCESS		read-write
		STATUS			current
		DESCRIPTION
				"TYPE: - Checkbox
				 PAGE: - Setup- Logging
					RollTrack  cmdID= 6005 "
		::= { iqdec01CmdEntry 6005 }


	iqdec01SetupLoggingRollTrack OBJECT-TYPE
		SYNTAX		RollCallString
		MAX-ACCESS		read-only
		STATUS			current
		DESCRIPTION
				"TYPE: - Display
				 PAGE: - Setup- Logging
					RollTrack  cmdID= 6205  format=   "
		::= { iqdec01CmdEntry 6205 }


	iqdec01SetupEnableLoggingDeemb1 OBJECT-TYPE
		SYNTAX		INTEGER { disable(0), enable(1) }
		MAX-ACCESS		read-write
		STATUS			current
		DESCRIPTION
				"TYPE: - Checkbox
				 PAGE: - Setup- Logging
					De-emb 1  cmdID= 6006 "
		::= { iqdec01CmdEntry 6006 }


	iqdec01SetupLoggingDeemb1 OBJECT-TYPE
		SYNTAX		RollCallString
		MAX-ACCESS		read-only
		STATUS			current
		DESCRIPTION
				"TYPE: - Display
				 PAGE: - Setup- Logging
					De-emb 1  cmdID= 6206  format=   "
		::= { iqdec01CmdEntry 6206 }


	iqdec01SetupEnableLoggingDeemb2 OBJECT-TYPE
		SYNTAX		INTEGER { disable(0), enable(1) }
		MAX-ACCESS		read-write
		STATUS			current
		DESCRIPTION
				"TYPE: - Checkbox
				 PAGE: - Setup- Logging
					De-emb 2  cmdID= 6007 "
		::= { iqdec01CmdEntry 6007 }


	iqdec01SetupLoggingDeemb2 OBJECT-TYPE
		SYNTAX		RollCallString
		MAX-ACCESS		read-only
		STATUS			current
		DESCRIPTION
				"TYPE: - Display
				 PAGE: - Setup- Logging
					De-emb 2  cmdID= 6207  format=   "
		::= { iqdec01CmdEntry 6207 }


	iqdec01SetupEnableLoggingDeemb3 OBJECT-TYPE
		SYNTAX		INTEGER { disable(0), enable(1) }
		MAX-ACCESS		read-write
		STATUS			current
		DESCRIPTION
				"TYPE: - Checkbox
				 PAGE: - Setup- Logging
					De-emb 3  cmdID= 6008 "
		::= { iqdec01CmdEntry 6008 }


	iqdec01SetupLoggingDeemb3 OBJECT-TYPE
		SYNTAX		RollCallString
		MAX-ACCESS		read-only
		STATUS			current
		DESCRIPTION
				"TYPE: - Display
				 PAGE: - Setup- Logging
					De-emb 3  cmdID= 6208  format=   "
		::= { iqdec01CmdEntry 6208 }


	iqdec01SetupEnableLoggingDeemb4 OBJECT-TYPE
		SYNTAX		INTEGER { disable(0), enable(1) }
		MAX-ACCESS		read-write
		STATUS			current
		DESCRIPTION
				"TYPE: - Checkbox
				 PAGE: - Setup- Logging
					De-emb 4  cmdID= 6009 "
		::= { iqdec01CmdEntry 6009 }


	iqdec01SetupLoggingDeemb4 OBJECT-TYPE
		SYNTAX		RollCallString
		MAX-ACCESS		read-only
		STATUS			current
		DESCRIPTION
				"TYPE: - Display
				 PAGE: - Setup- Logging
					De-emb 4  cmdID= 6209  format=   "
		::= { iqdec01CmdEntry 6209 }


	iqdec01SetupEnableLoggingDeemb5 OBJECT-TYPE
		SYNTAX		INTEGER { disable(0), enable(1) }
		MAX-ACCESS		read-write
		STATUS			current
		DESCRIPTION
				"TYPE: - Checkbox
				 PAGE: - Setup- Logging
					De-emb 5  cmdID= 6010 "
		::= { iqdec01CmdEntry 6010 }


	iqdec01SetupLoggingDeemb5 OBJECT-TYPE
		SYNTAX		RollCallString
		MAX-ACCESS		read-only
		STATUS			current
		DESCRIPTION
				"TYPE: - Display
				 PAGE: - Setup- Logging
					De-emb 5  cmdID= 6210  format=   "
		::= { iqdec01CmdEntry 6210 }


	iqdec01SetupEnableLoggingDeemb6 OBJECT-TYPE
		SYNTAX		INTEGER { disable(0), enable(1) }
		MAX-ACCESS		read-write
		STATUS			current
		DESCRIPTION
				"TYPE: - Checkbox
				 PAGE: - Setup- Logging
					De-emb 6  cmdID= 6011 "
		::= { iqdec01CmdEntry 6011 }


	iqdec01SetupLoggingDeemb6 OBJECT-TYPE
		SYNTAX		RollCallString
		MAX-ACCESS		read-only
		STATUS			current
		DESCRIPTION
				"TYPE: - Display
				 PAGE: - Setup- Logging
					De-emb 6  cmdID= 6211  format=   "
		::= { iqdec01CmdEntry 6211 }


	iqdec01SetupEnableLoggingDeemb7 OBJECT-TYPE
		SYNTAX		INTEGER { disable(0), enable(1) }
		MAX-ACCESS		read-write
		STATUS			current
		DESCRIPTION
				"TYPE: - Checkbox
				 PAGE: - Setup- Logging
					De-emb 7  cmdID= 6012 "
		::= { iqdec01CmdEntry 6012 }


	iqdec01SetupLoggingDeemb7 OBJECT-TYPE
		SYNTAX		RollCallString
		MAX-ACCESS		read-only
		STATUS			current
		DESCRIPTION
				"TYPE: - Display
				 PAGE: - Setup- Logging
					De-emb 7  cmdID= 6212  format=   "
		::= { iqdec01CmdEntry 6212 }


	iqdec01SetupEnableLoggingDeemb8 OBJECT-TYPE
		SYNTAX		INTEGER { disable(0), enable(1) }
		MAX-ACCESS		read-write
		STATUS			current
		DESCRIPTION
				"TYPE: - Checkbox
				 PAGE: - Setup- Logging
					De-emb 8  cmdID= 6013 "
		::= { iqdec01CmdEntry 6013 }


	iqdec01SetupLoggingDeemb8 OBJECT-TYPE
		SYNTAX		RollCallString
		MAX-ACCESS		read-only
		STATUS			current
		DESCRIPTION
				"TYPE: - Display
				 PAGE: - Setup- Logging
					De-emb 8  cmdID= 6213  format=   "
		::= { iqdec01CmdEntry 6213 }


	iqdec01SetupEnableLoggingnPCM1 OBJECT-TYPE
		SYNTAX		INTEGER { disable(0), enable(1) }
		MAX-ACCESS		read-write
		STATUS			current
		DESCRIPTION
				"TYPE: - Checkbox
				 PAGE: - Setup- Logging
					nPCM 1  cmdID= 6014 "
		::= { iqdec01CmdEntry 6014 }


	iqdec01SetupLoggingnPCM1 OBJECT-TYPE
		SYNTAX		RollCallString
		MAX-ACCESS		read-only
		STATUS			current
		DESCRIPTION
				"TYPE: - Display
				 PAGE: - Setup- Logging
					nPCM 1  cmdID= 6214  format=   "
		::= { iqdec01CmdEntry 6214 }


	iqdec01SetupEnableLoggingnPCM2 OBJECT-TYPE
		SYNTAX		INTEGER { disable(0), enable(1) }
		MAX-ACCESS		read-write
		STATUS			current
		DESCRIPTION
				"TYPE: - Checkbox
				 PAGE: - Setup- Logging
					nPCM 2  cmdID= 6015 "
		::= { iqdec01CmdEntry 6015 }


	iqdec01SetupLoggingnPCM2 OBJECT-TYPE
		SYNTAX		RollCallString
		MAX-ACCESS		read-only
		STATUS			current
		DESCRIPTION
				"TYPE: - Display
				 PAGE: - Setup- Logging
					nPCM 2  cmdID= 6215  format=   "
		::= { iqdec01CmdEntry 6215 }


	iqdec01SetupEnableLoggingnPCM3 OBJECT-TYPE
		SYNTAX		INTEGER { disable(0), enable(1) }
		MAX-ACCESS		read-write
		STATUS			current
		DESCRIPTION
				"TYPE: - Checkbox
				 PAGE: - Setup- Logging
					nPCM 3  cmdID= 6016 "
		::= { iqdec01CmdEntry 6016 }


	iqdec01SetupLoggingnPCM3 OBJECT-TYPE
		SYNTAX		RollCallString
		MAX-ACCESS		read-only
		STATUS			current
		DESCRIPTION
				"TYPE: - Display
				 PAGE: - Setup- Logging
					nPCM 3  cmdID= 6216  format=   "
		::= { iqdec01CmdEntry 6216 }


	iqdec01SetupEnableLoggingnPCM4 OBJECT-TYPE
		SYNTAX		INTEGER { disable(0), enable(1) }
		MAX-ACCESS		read-write
		STATUS			current
		DESCRIPTION
				"TYPE: - Checkbox
				 PAGE: - Setup- Logging
					nPCM 4  cmdID= 6017 "
		::= { iqdec01CmdEntry 6017 }


	iqdec01SetupLoggingnPCM4 OBJECT-TYPE
		SYNTAX		RollCallString
		MAX-ACCESS		read-only
		STATUS			current
		DESCRIPTION
				"TYPE: - Display
				 PAGE: - Setup- Logging
					nPCM 4  cmdID= 6217  format=   "
		::= { iqdec01CmdEntry 6217 }


	iqdec01SetupEnableLoggingnPCM5 OBJECT-TYPE
		SYNTAX		INTEGER { disable(0), enable(1) }
		MAX-ACCESS		read-write
		STATUS			current
		DESCRIPTION
				"TYPE: - Checkbox
				 PAGE: - Setup- Logging
					nPCM 5  cmdID= 6018 "
		::= { iqdec01CmdEntry 6018 }


	iqdec01SetupLoggingnPCM5 OBJECT-TYPE
		SYNTAX		RollCallString
		MAX-ACCESS		read-only
		STATUS			current
		DESCRIPTION
				"TYPE: - Display
				 PAGE: - Setup- Logging
					nPCM 5  cmdID= 6218  format=   "
		::= { iqdec01CmdEntry 6218 }


	iqdec01SetupEnableLoggingnPCM6 OBJECT-TYPE
		SYNTAX		INTEGER { disable(0), enable(1) }
		MAX-ACCESS		read-write
		STATUS			current
		DESCRIPTION
				"TYPE: - Checkbox
				 PAGE: - Setup- Logging
					nPCM 6  cmdID= 6019 "
		::= { iqdec01CmdEntry 6019 }


	iqdec01SetupLoggingnPCM6 OBJECT-TYPE
		SYNTAX		RollCallString
		MAX-ACCESS		read-only
		STATUS			current
		DESCRIPTION
				"TYPE: - Display
				 PAGE: - Setup- Logging
					nPCM 6  cmdID= 6219  format=   "
		::= { iqdec01CmdEntry 6219 }


	iqdec01SetupEnableLoggingnPCM7 OBJECT-TYPE
		SYNTAX		INTEGER { disable(0), enable(1) }
		MAX-ACCESS		read-write
		STATUS			current
		DESCRIPTION
				"TYPE: - Checkbox
				 PAGE: - Setup- Logging
					nPCM 7  cmdID= 6020 "
		::= { iqdec01CmdEntry 6020 }


	iqdec01SetupLoggingnPCM7 OBJECT-TYPE
		SYNTAX		RollCallString
		MAX-ACCESS		read-only
		STATUS			current
		DESCRIPTION
				"TYPE: - Display
				 PAGE: - Setup- Logging
					nPCM 7  cmdID= 6220  format=   "
		::= { iqdec01CmdEntry 6220 }


	iqdec01SetupEnableLoggingnPCM8 OBJECT-TYPE
		SYNTAX		INTEGER { disable(0), enable(1) }
		MAX-ACCESS		read-write
		STATUS			current
		DESCRIPTION
				"TYPE: - Checkbox
				 PAGE: - Setup- Logging
					nPCM 8  cmdID= 6021 "
		::= { iqdec01CmdEntry 6021 }


	iqdec01SetupLoggingnPCM8 OBJECT-TYPE
		SYNTAX		RollCallString
		MAX-ACCESS		read-only
		STATUS			current
		DESCRIPTION
				"TYPE: - Display
				 PAGE: - Setup- Logging
					nPCM 8  cmdID= 6221  format=   "
		::= { iqdec01CmdEntry 6221 }


	iqdec01SetupEnableLoggingANALOG1L OBJECT-TYPE
		SYNTAX		INTEGER { disable(0), enable(1) }
		MAX-ACCESS		read-write
		STATUS			current
		DESCRIPTION
				"TYPE: - Checkbox
				 PAGE: - Setup- Logging
					ANALOG 1L  cmdID= 6022 "
		::= { iqdec01CmdEntry 6022 }


	iqdec01SetupLoggingANALOG1L OBJECT-TYPE
		SYNTAX		RollCallString
		MAX-ACCESS		read-only
		STATUS			current
		DESCRIPTION
				"TYPE: - Display
				 PAGE: - Setup- Logging
					ANALOG 1L  cmdID= 6222  format=   "
		::= { iqdec01CmdEntry 6222 }


	iqdec01SetupEnableLoggingANALOG1R OBJECT-TYPE
		SYNTAX		INTEGER { disable(0), enable(1) }
		MAX-ACCESS		read-write
		STATUS			current
		DESCRIPTION
				"TYPE: - Checkbox
				 PAGE: - Setup- Logging
					ANALOG 1R  cmdID= 6023 "
		::= { iqdec01CmdEntry 6023 }


	iqdec01SetupLoggingANALOG1R OBJECT-TYPE
		SYNTAX		RollCallString
		MAX-ACCESS		read-only
		STATUS			current
		DESCRIPTION
				"TYPE: - Display
				 PAGE: - Setup- Logging
					ANALOG 1R  cmdID= 6223  format=   "
		::= { iqdec01CmdEntry 6223 }


	iqdec01SetupEnableLoggingANALOG2L OBJECT-TYPE
		SYNTAX		INTEGER { disable(0), enable(1) }
		MAX-ACCESS		read-write
		STATUS			current
		DESCRIPTION
				"TYPE: - Checkbox
				 PAGE: - Setup- Logging
					ANALOG 2L  cmdID= 6024 "
		::= { iqdec01CmdEntry 6024 }


	iqdec01SetupLoggingANALOG2L OBJECT-TYPE
		SYNTAX		RollCallString
		MAX-ACCESS		read-only
		STATUS			current
		DESCRIPTION
				"TYPE: - Display
				 PAGE: - Setup- Logging
					ANALOG 2L  cmdID= 6224  format=   "
		::= { iqdec01CmdEntry 6224 }


	iqdec01SetupEnableLoggingANALOG2R OBJECT-TYPE
		SYNTAX		INTEGER { disable(0), enable(1) }
		MAX-ACCESS		read-write
		STATUS			current
		DESCRIPTION
				"TYPE: - Checkbox
				 PAGE: - Setup- Logging
					ANALOG 2R  cmdID= 6025 "
		::= { iqdec01CmdEntry 6025 }


	iqdec01SetupLoggingANALOG2R OBJECT-TYPE
		SYNTAX		RollCallString
		MAX-ACCESS		read-only
		STATUS			current
		DESCRIPTION
				"TYPE: - Display
				 PAGE: - Setup- Logging
					ANALOG 2R  cmdID= 6225  format=   "
		::= { iqdec01CmdEntry 6225 }


	iqdec01SetupEnableLoggingBUSAL OBJECT-TYPE
		SYNTAX		INTEGER { disable(0), enable(1) }
		MAX-ACCESS		read-write
		STATUS			current
		DESCRIPTION
				"TYPE: - Checkbox
				 PAGE: - Setup- Logging
					BUS AL  cmdID= 6026 "
		::= { iqdec01CmdEntry 6026 }


	iqdec01SetupLoggingBUSAL OBJECT-TYPE
		SYNTAX		RollCallString
		MAX-ACCESS		read-only
		STATUS			current
		DESCRIPTION
				"TYPE: - Display
				 PAGE: - Setup- Logging
					BUS AL  cmdID= 6226  format=   "
		::= { iqdec01CmdEntry 6226 }


	iqdec01SetupEnableLoggingBUSAR OBJECT-TYPE
		SYNTAX		INTEGER { disable(0), enable(1) }
		MAX-ACCESS		read-write
		STATUS			current
		DESCRIPTION
				"TYPE: - Checkbox
				 PAGE: - Setup- Logging
					BUS AR  cmdID= 6027 "
		::= { iqdec01CmdEntry 6027 }


	iqdec01SetupLoggingBUSAR OBJECT-TYPE
		SYNTAX		RollCallString
		MAX-ACCESS		read-only
		STATUS			current
		DESCRIPTION
				"TYPE: - Display
				 PAGE: - Setup- Logging
					BUS AR  cmdID= 6227  format=   "
		::= { iqdec01CmdEntry 6227 }


	iqdec01SetupEnableLoggingBUSBL OBJECT-TYPE
		SYNTAX		INTEGER { disable(0), enable(1) }
		MAX-ACCESS		read-write
		STATUS			current
		DESCRIPTION
				"TYPE: - Checkbox
				 PAGE: - Setup- Logging
					BUS BL  cmdID= 6028 "
		::= { iqdec01CmdEntry 6028 }


	iqdec01SetupLoggingBUSBL OBJECT-TYPE
		SYNTAX		RollCallString
		MAX-ACCESS		read-only
		STATUS			current
		DESCRIPTION
				"TYPE: - Display
				 PAGE: - Setup- Logging
					BUS BL  cmdID= 6228  format=   "
		::= { iqdec01CmdEntry 6228 }


	iqdec01SetupEnableLoggingBUSBR OBJECT-TYPE
		SYNTAX		INTEGER { disable(0), enable(1) }
		MAX-ACCESS		read-write
		STATUS			current
		DESCRIPTION
				"TYPE: - Checkbox
				 PAGE: - Setup- Logging
					BUS BR  cmdID= 6029 "
		::= { iqdec01CmdEntry 6029 }


	iqdec01SetupLoggingBUSBR OBJECT-TYPE
		SYNTAX		RollCallString
		MAX-ACCESS		read-only
		STATUS			current
		DESCRIPTION
				"TYPE: - Display
				 PAGE: - Setup- Logging
					BUS BR  cmdID= 6229  format=   "
		::= { iqdec01CmdEntry 6229 }


	iqdec01SetupDefaultOutput OBJECT-TYPE
		SYNTAX		INTEGER {
							val_Pass_Video(0),
							val_Freeze(1),
							val_Pattern(2),
							val_Pattern_Caption(3)
							}
		MAX-ACCESS		read-write
		STATUS			current
		DESCRIPTION
				"TYPE: - RadiobuttonList
				 PAGE: - Setup
					Default Output  cmdID= 8100
					Pass Video  value= 0
					Freeze  value= 1
					Pattern  value= 2
					Pattern&Caption  value= 3  "
		::= { iqdec01CmdEntry 8100 }


	iqdec01SetupDefaultOutputDefaultPattern OBJECT-TYPE
		SYNTAX		INTEGER {
							val_Black(0),
							val_EBU_Color_Bars(1),
							val_100_Color_Bars(2),
							val_Ramp(3),
							val_Multi_Burst(4),
							val_Pulse_Bar(5)
							}
		MAX-ACCESS		read-write
		STATUS			current
		DESCRIPTION
				"TYPE: - RadiobuttonList
				 PAGE: - Setup
					Default Pattern  cmdID= 8200
					Black  value= 0
					EBU Color Bars  value= 1
					100% Color Bars  value= 2
					Ramp  value= 3
					Multi-Burst  value= 4
					Pulse & Bar  value= 5  "
		::= { iqdec01CmdEntry 8200 }


	iqdec01SetupDefaultOutputDefaultCaption OBJECT-TYPE
		SYNTAX		RollCallString
		MAX-ACCESS		read-write
		STATUS			current
		DESCRIPTION
				"TYPE: - Editstring
				 PAGE: - Setup
					Default Caption  cmdID= 8201  "
		::= { iqdec01CmdEntry 8201 }


	iqdec01SetupInformationWindow OBJECT-TYPE
		SYNTAX		INTEGER {
							val_Input_Status(0),
							val_EDH_ANC_Status(1),
							val_Audio_Input_Status(2)
							}
		MAX-ACCESS		read-write
		STATUS			current
		DESCRIPTION
				"TYPE: - RadiobuttonList
				 PAGE: - Setup
					Information Window  cmdID= 8010
					Input Status  value= 0
					EDH & ANC Status  value= 1
					Audio Input Status  value= 2  "
		::= { iqdec01CmdEntry 8010 }


	iqdec01SetupSoftwareVersion OBJECT-TYPE
		SYNTAX		RollCallString
		MAX-ACCESS		read-only
		STATUS			current
		DESCRIPTION
				"TYPE: - Display
				 PAGE: - Setup
					Software Version  cmdID= 7001  format=   "
		::= { iqdec01CmdEntry 7001 }


	iqdec01SetupSerialNumber OBJECT-TYPE
		SYNTAX		RollCallString
		MAX-ACCESS		read-only
		STATUS			current
		DESCRIPTION
				"TYPE: - Display
				 PAGE: - Setup
					Serial Number  cmdID= 7005  format=   "
		::= { iqdec01CmdEntry 7005 }


	iqdec01SetupBuildNumber OBJECT-TYPE
		SYNTAX		RollCallString
		MAX-ACCESS		read-only
		STATUS			current
		DESCRIPTION
				"TYPE: - Display
				 PAGE: - Setup
					Build Number  cmdID= 7009  format=   "
		::= { iqdec01CmdEntry 7009 }


	iqdec01SetupFPGASyncVersion OBJECT-TYPE
		SYNTAX		RollCallString
		MAX-ACCESS		read-only
		STATUS			current
		DESCRIPTION
				"TYPE: - Display
				 PAGE: - Setup
					FPGA Sync Version  cmdID= 7002  format=   "
		::= { iqdec01CmdEntry 7002 }


	iqdec01SetupFPGADecVersion OBJECT-TYPE
		SYNTAX		RollCallString
		MAX-ACCESS		read-only
		STATUS			current
		DESCRIPTION
				"TYPE: - Display
				 PAGE: - Setup
					FPGA Dec Version  cmdID= 7003  format=   "
		::= { iqdec01CmdEntry 7003 }


	iqdec01SetupRestart OBJECT-TYPE
		SYNTAX		INTEGER { noAction(0),val_Restart(1) }
		MAX-ACCESS		read-write
		STATUS			current
		DESCRIPTION
				"TYPE: - Button
				 PAGE: - Setup
					Restart  cmdID= 8001  value= 1  "
		::= { iqdec01CmdEntry 8001 }


	iqdec01SetupErrorSecondsReset OBJECT-TYPE
		SYNTAX		INTEGER { noAction(0),val_Error_Seconds_Reset(1) }
		MAX-ACCESS		read-write
		STATUS			current
		DESCRIPTION
				"TYPE: - Button
				 PAGE: - Setup
					Error Seconds Reset  cmdID= 8000  value= 1  "
		::= { iqdec01CmdEntry 8000 }


	iqdec01SetupFactoryDefault OBJECT-TYPE
		SYNTAX		INTEGER { noAction(0),val_Factory_Default(1) }
		MAX-ACCESS		read-write
		STATUS			current
		DESCRIPTION
				"TYPE: - Button
				 PAGE: - Setup
					Factory Default  cmdID= 7008  value= 1  "
		::= { iqdec01CmdEntry 7008 }


	iqdec01SetupRollTrack14 OBJECT-TYPE
		SYNTAX		INTEGER
		MAX-ACCESS		read-write
		STATUS			current
		DESCRIPTION
				"TYPE: - Number
				 PAGE: - Setup
					RollTrack14  cmdID= 14  min= -2147483648  max= 2147483647  step= 1  format=   div_scale= 1
					Min =   Max =   Step =  "
		::= { iqdec01CmdEntry 14 }


	iqdec01SetupRollTrack15 OBJECT-TYPE
		SYNTAX		INTEGER
		MAX-ACCESS		read-write
		STATUS			current
		DESCRIPTION
				"TYPE: - Number
				 PAGE: - Setup
					RollTrack15  cmdID= 15  min= -2147483648  max= 2147483647  step= 1  format=   div_scale= 1
					Min =   Max =   Step =  "
		::= { iqdec01CmdEntry 15 }


	iqdec01SetupRollTrack16 OBJECT-TYPE
		SYNTAX		INTEGER
		MAX-ACCESS		read-write
		STATUS			current
		DESCRIPTION
				"TYPE: - Number
				 PAGE: - Setup
					RollTrack16  cmdID= 16  min= -2147483648  max= 2147483647  step= 1  format=   div_scale= 1
					Min =   Max =   Step =  "
		::= { iqdec01CmdEntry 16 }


	iqdec01SetupRollTrack17 OBJECT-TYPE
		SYNTAX		INTEGER
		MAX-ACCESS		read-write
		STATUS			current
		DESCRIPTION
				"TYPE: - Number
				 PAGE: - Setup
					RollTrack17  cmdID= 17  min= -2147483648  max= 2147483647  step= 1  format=   div_scale= 1
					Min =   Max =   Step =  "
		::= { iqdec01CmdEntry 17 }


	iqdec01UserMemoryRecall OBJECT-TYPE
		SYNTAX		INTEGER {
							val_Recall1(0),
							val_Recall2(1),
							val_Recall3(2),
							val_Recall4(3),
							val_Recall5(4),
							val_Recall6(5),
							val_Recall7(6),
							val_Recall8(7),
							val_unspecified(8)
							}
		MAX-ACCESS		read-write
		STATUS			current
		DESCRIPTION
				"TYPE: - Button
				 PAGE: - User Mem
					Recall  cmdID= 5000  value= 0
					Recall  cmdID= 5000  value= 1
					Recall  cmdID= 5000  value= 2
					Recall  cmdID= 5000  value= 3
					Recall  cmdID= 5000  value= 4
					Recall  cmdID= 5000  value= 5
					Recall  cmdID= 5000  value= 6
					Recall  cmdID= 5000  value= 7
					   cmdID= 5000  value= 8  "
		::= { iqdec01CmdEntry 5000 }


	iqdec01UserMemoryClear OBJECT-TYPE
		SYNTAX		INTEGER {
							val_Clear1(0),
							val_Clear2(1),
							val_Clear3(2),
							val_Clear4(3),
							val_Clear5(4),
							val_Clear6(5),
							val_Clear7(6),
							val_Clear8(7),
							val_unspecified(8)
							}
		MAX-ACCESS		read-write
		STATUS			current
		DESCRIPTION
				"TYPE: - Button
				 PAGE: - User Mem
					Clear  cmdID= 5010  value= 0
					Clear  cmdID= 5010  value= 1
					Clear  cmdID= 5010  value= 2
					Clear  cmdID= 5010  value= 3
					Clear  cmdID= 5010  value= 4
					Clear  cmdID= 5010  value= 5
					Clear  cmdID= 5010  value= 6
					Clear  cmdID= 5010  value= 7
					   cmdID= 5010  value= 8  "
		::= { iqdec01CmdEntry 5010 }


	iqdec01UserMemory1Name OBJECT-TYPE
		SYNTAX		RollCallString
		MAX-ACCESS		read-write
		STATUS			current
		DESCRIPTION
				"TYPE: - Editstring
				 PAGE: - User Mem
					Name  cmdID= 5002  "
		::= { iqdec01CmdEntry 5002 }


	iqdec01UserMemorySave OBJECT-TYPE
		SYNTAX		INTEGER {
							val_Save1(0),
							val_Save2(1),
							val_Save3(2),
							val_Save4(3),
							val_Save5(4),
							val_Save6(5),
							val_Save7(6),
							val_Save8(7),
							val_unspecified(8)
							}
		MAX-ACCESS		read-write
		STATUS			current
		DESCRIPTION
				"TYPE: - Button
				 PAGE: - User Mem
					Save  cmdID= 5001  value= 0
					Save  cmdID= 5001  value= 1
					Save  cmdID= 5001  value= 2
					Save  cmdID= 5001  value= 3
					Save  cmdID= 5001  value= 4
					Save  cmdID= 5001  value= 5
					Save  cmdID= 5001  value= 6
					Save  cmdID= 5001  value= 7
					   cmdID= 5001  value= 8  "
		::= { iqdec01CmdEntry 5001 }


	iqdec01UserMemory2Name OBJECT-TYPE
		SYNTAX		RollCallString
		MAX-ACCESS		read-write
		STATUS			current
		DESCRIPTION
				"TYPE: - Editstring
				 PAGE: - User Mem
					Name  cmdID= 5003  "
		::= { iqdec01CmdEntry 5003 }


	iqdec01UserMemory3Name OBJECT-TYPE
		SYNTAX		RollCallString
		MAX-ACCESS		read-write
		STATUS			current
		DESCRIPTION
				"TYPE: - Editstring
				 PAGE: - User Mem
					Name  cmdID= 5004  "
		::= { iqdec01CmdEntry 5004 }


	iqdec01UserMemory4Name OBJECT-TYPE
		SYNTAX		RollCallString
		MAX-ACCESS		read-write
		STATUS			current
		DESCRIPTION
				"TYPE: - Editstring
				 PAGE: - User Mem
					Name  cmdID= 5005  "
		::= { iqdec01CmdEntry 5005 }


	iqdec01UserMemory5Name OBJECT-TYPE
		SYNTAX		RollCallString
		MAX-ACCESS		read-write
		STATUS			current
		DESCRIPTION
				"TYPE: - Editstring
				 PAGE: - User Mem
					Name  cmdID= 5006  "
		::= { iqdec01CmdEntry 5006 }


	iqdec01UserMemory6Name OBJECT-TYPE
		SYNTAX		RollCallString
		MAX-ACCESS		read-write
		STATUS			current
		DESCRIPTION
				"TYPE: - Editstring
				 PAGE: - User Mem
					Name  cmdID= 5007  "
		::= { iqdec01CmdEntry 5007 }


	iqdec01UserMemory7Name OBJECT-TYPE
		SYNTAX		RollCallString
		MAX-ACCESS		read-write
		STATUS			current
		DESCRIPTION
				"TYPE: - Editstring
				 PAGE: - User Mem
					Name  cmdID= 5008  "
		::= { iqdec01CmdEntry 5008 }


	iqdec01UserMemory8Name OBJECT-TYPE
		SYNTAX		RollCallString
		MAX-ACCESS		read-write
		STATUS			current
		DESCRIPTION
				"TYPE: - Editstring
				 PAGE: - User Mem
					Name  cmdID= 5009  "
		::= { iqdec01CmdEntry 5009 }


	iqdec01UserMem OBJECT-TYPE
		SYNTAX		INTEGER
		MAX-ACCESS		read-write
		STATUS			current
		DESCRIPTION
				"TYPE: - Number
				 PAGE: - User Mem
					   cmdID= 5011  min= 0  max= 65535  step= 1  format= %d  div_scale= 1
					Min = 0  Max = -1  Step = 1 "
		::= { iqdec01CmdEntry 5011 }


	iqdec01Freeze OBJECT-TYPE
		SYNTAX		INTEGER { disable(0), enable(1) }
		MAX-ACCESS		read-write
		STATUS			current
		DESCRIPTION
				"TYPE: - Checkbox
					Freeze  cmdID= 2400 "
		::= { iqdec01CmdEntry 2400 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S3425654
--				:
-- Comments		: Serial Number of module
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: OK        (EDH present on SDI input and no error detected)
--				: FAIL      (EDH present on SDI input and error detected)
--              : NONE      (EDH not present on SDI input)
-- Comments		:
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: 525
--				: 625
--				: ERROR:525
--				: ERROR:625
--				: PAL
--				: NTSC
--				: NTSC_J
--				: PAL_M
--				: PAL_N
--				: SECAM
--				: N443_60
--				: PAL443_60
--				: ERROR:PAL
--				: ERROR:NTSC
--				: ERROR:NTSC_J
--				: ERROR:PAL_M
--				: ERROR:PAL_N
--				: ERROR:SECAM
--				: ERROR:N443_60
--				: ERROR:PAL443_60
--				: UNKNOWN
--				: STDERR
-- Comments		:
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
--				: ERR
-- Comments		:
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: WARNING:SILENT
--				: WARNING:QUIET
--              : OK
--              : WARNING:HIGH
--              : WARNING:OVERLOAD
-- Comments		:
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: WARNING:SILENT
--				: WARNING:QUIET
--              : OK
--              : WARNING:HIGH
--              : WARNING:OVERLOAD
-- Comments		:
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: WARNING:SILENT
--				: WARNING:QUIET
--              : OK
--              : WARNING:HIGH
--              : WARNING:OVERLOAD
-- Comments		:
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: WARNING:SILENT
--				: WARNING:QUIET
--              : OK
--              : WARNING:HIGH
--              : WARNING:OVERLOAD
-- Comments		:
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
--
-- Value(s)		: 0
--				: n Number of errored seconds since EDH statistics reset
-- Comments		:
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: 525
--				: 625
--				: AES
--				: WARNING:LOSS
--				: ERROR:525
--				: ERROR:625
--				: ERROR:AES
--				: WARNING:525_N/A
--				: WARNING:625_N/A
--				: WARNING:AES_N/A
--				: NONE
-- Comments		:
--
---------------------------------------------------------------------------------------------------
-- Header		: NPCM_1
--
-- MIB ref		: swCardEventLogSlotXX       .6.78.80.67.77.95.49
-- absolute OID	: 1.3.6.1.4.1.7995.2.6.1.1.XX.6.78.80.67.77.95.49
-- Vary			: YES
--
-- Value(s)		: OK  (non PCM audio detected on input pair)
--				: NONE - Either nothing present on embedded audio input pair or PCM audio detected
-- Comments		:
--
---------------------------------------------------------------------------------------------------
-- Header		: NPCM_2
--
-- MIB ref		: swCardEventLogSlotXX       .6.78.80.67.77.95.50
-- absolute OID	: 1.3.6.1.4.1.7995.2.6.1.1.XX.6.78.80.67.77.95.50
-- Vary			: YES
--
-- Value(s)		: OK  (non PCM audio detected on input pair)
--				: NONE - Either nothing present on embedded audio input pair or PCM audio detected
-- Comments		:
--
---------------------------------------------------------------------------------------------------
-- Header		: NPCM_3
--
-- MIB ref		: swCardEventLogSlotXX       .6.78.80.67.77.95.51
-- absolute OID	: 1.3.6.1.4.1.7995.2.6.1.1.XX.6.78.80.67.77.95.51
-- Vary			: YES
--
-- Value(s)		: OK  (non PCM audio detected on input pair)
--				: NONE - Either nothing present on embedded audio input pair or PCM audio detected
-- Comments		:
--
---------------------------------------------------------------------------------------------------
-- Header		: NPCM_4
--
-- MIB ref		: swCardEventLogSlotXX       .6.78.80.67.77.95.52
-- absolute OID	: 1.3.6.1.4.1.7995.2.6.1.1.XX.6.78.80.67.77.95.52
-- Vary			: YES
--
-- Value(s)		: OK  (non PCM audio detected on input pair)
--				: NONE - Either nothing present on embedded audio input pair or PCM audio detected
-- Comments		:
--
---------------------------------------------------------------------------------------------------
-- Header		: NPCM_5
--
-- MIB ref		: swCardEventLogSlotXX       .6.78.80.67.77.95.53
-- absolute OID	: 1.3.6.1.4.1.7995.2.6.1.1.XX.6.78.80.67.77.95.53
-- Vary			: YES
--
-- Value(s)		: OK  (non PCM audio detected on input pair)
--				: NONE - Either nothing present on embedded audio input pair or PCM audio detected
-- Comments		:
--
---------------------------------------------------------------------------------------------------
-- Header		: NPCM_6
--
-- MIB ref		: swCardEventLogSlotXX       .6.78.80.67.77.95.54
-- absolute OID	: 1.3.6.1.4.1.7995.2.6.1.1.XX.6.78.80.67.77.95.54
-- Vary			: YES
--
-- Value(s)		: OK  (non PCM audio detected on input pair)
--				: NONE - Either nothing present on embedded audio input pair or PCM audio detected
-- Comments		:
--
---------------------------------------------------------------------------------------------------
-- Header		: NPCM_7
--
-- MIB ref		: swCardEventLogSlotXX       .6.78.80.67.77.95.55
-- absolute OID	: 1.3.6.1.4.1.7995.2.6.1.1.XX.6.78.80.67.77.95.55
-- Vary			: YES
--
-- Value(s)		: OK  (non PCM audio detected on input pair)
--				: NONE - Either nothing present on embedded audio input pair or PCM audio detected
-- Comments		:
--
---------------------------------------------------------------------------------------------------
-- Header		: NPCM_8
--
-- MIB ref		: swCardEventLogSlotXX       .6.78.80.67.77.95.56
-- absolute OID	: 1.3.6.1.4.1.7995.2.6.1.1.XX.6.78.80.67.77.95.56
-- Vary			: YES
--
-- Value(s)		: OK  (non PCM audio detected on input pair)
--				: NONE - Either nothing present on embedded audio input pair or PCM audio detected
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 1
--				:
-- Comments		: Number of current control sessions
--
---------------------------------------------------------------------------------------------------
-- Header		: ANALOG_1L
--
-- MIB ref		: swCardEventLogSlotXX       .9.65.78.65.76.79.71.95.49.76
-- absolute OID	: 1.3.6.1.4.1.7995.2.6.1.1.XX.9.65.78.65.76.79.71.95.49.76
-- Vary			: YES
--
-- Value(s)		: WARNING:SILENT
--				: WARNING:QUIET
--              : OK
--              : WARNING:HIGH
--              : WARNING:OVERLOAD
-- Comments		:
--
---------------------------------------------------------------------------------------------------
-- Header		: ANALOG_1R
--
-- MIB ref		: swCardEventLogSlotXX       .9.65.78.65.76.79.71.95.49.82
-- absolute OID	: 1.3.6.1.4.1.7995.2.6.1.1.XX.9.65.78.65.76.79.71.95.49.82
-- Vary			: YES
--
-- Value(s)		: WARNING:SILENT
--				: WARNING:QUIET
--              : OK
--              : WARNING:HIGH
--              : WARNING:OVERLOAD
-- Comments		:
--
---------------------------------------------------------------------------------------------------
-- Header		: ANALOG_2L
--
-- MIB ref		: swCardEventLogSlotXX       .9.65.78.65.76.79.71.95.50.76
-- absolute OID	: 1.3.6.1.4.1.7995.2.6.1.1.XX.9.65.78.65.76.79.71.95.50.76
-- Vary			: YES
--
-- Value(s)		: WARNING:SILENT
--				: WARNING:QUIET
--              : OK
--              : WARNING:HIGH
--              : WARNING:OVERLOAD
-- Comments		:
--
---------------------------------------------------------------------------------------------------
-- Header		: ANALOG_2R
--
-- MIB ref		: swCardEventLogSlotXX       .9.65.78.65.76.79.71.95.50.82
-- absolute OID	: 1.3.6.1.4.1.7995.2.6.1.1.XX.9.65.78.65.76.79.71.95.50.82
-- Vary			: YES
--
-- Value(s)		: WARNING:SILENT
--				: WARNING:QUIET
--              : OK
--              : WARNING:HIGH
--              : WARNING:OVERLOAD
-- Comments		:
--
---------------------------------------------------------------------------------------------------
-- Header		: DEEMBED_1
--
-- MIB ref		: swCardEventLogSlotXX       .9.68.69.69.77.66.69.68.95.49
-- absolute OID	: 1.3.6.1.4.1.7995.2.6.1.1.XX.9.68.69.69.77.66.69.68.95.49
-- Vary			: YES
--
-- Value(s)		: OK  (embedded audio detected on input pair)
--				: NONE  (Nothing present on embedded audio input pair)
-- Comments		:
--
---------------------------------------------------------------------------------------------------
-- Header		: DEEMBED_2
--
-- MIB ref		: swCardEventLogSlotXX       .9.68.69.69.77.66.69.68.95.50
-- absolute OID	: 1.3.6.1.4.1.7995.2.6.1.1.XX.9.68.69.69.77.66.69.68.95.50
-- Vary			: YES
--
-- Value(s)		: OK  (embedded audio detected on input pair)
--				: NONE  (Nothing present on embedded audio input pair)
-- Comments		:
--
---------------------------------------------------------------------------------------------------
-- Header		: DEEMBED_3
--
-- MIB ref		: swCardEventLogSlotXX       .9.68.69.69.77.66.69.68.95.51
-- absolute OID	: 1.3.6.1.4.1.7995.2.6.1.1.XX.9.68.69.69.77.66.69.68.95.51
-- Vary			: YES
--
-- Value(s)		: OK  (embedded audio detected on input pair)
--				: NONE  (Nothing present on embedded audio input pair)
-- Comments		:
--
---------------------------------------------------------------------------------------------------
-- Header		: DEEMBED_4
--
-- MIB ref		: swCardEventLogSlotXX       .9.68.69.69.77.66.69.68.95.52
-- absolute OID	: 1.3.6.1.4.1.7995.2.6.1.1.XX.9.68.69.69.77.66.69.68.95.52
-- Vary			: YES
--
-- Value(s)		: OK  (embedded audio detected on input pair)
--				: NONE  (Nothing present on embedded audio input pair)
-- Comments		:
--
---------------------------------------------------------------------------------------------------
-- Header		: DEEMBED_5
--
-- MIB ref		: swCardEventLogSlotXX       .9.68.69.69.77.66.69.68.95.53
-- absolute OID	: 1.3.6.1.4.1.7995.2.6.1.1.XX.9.68.69.69.77.66.69.68.95.53
-- Vary			: YES
--
-- Value(s)		: OK  (embedded audio detected on input pair)
--				: NONE  (Nothing present on embedded audio input pair)
-- Comments		:
--
---------------------------------------------------------------------------------------------------
-- Header		: DEEMBED_6
--
-- MIB ref		: swCardEventLogSlotXX       .9.68.69.69.77.66.69.68.95.54
-- absolute OID	: 1.3.6.1.4.1.7995.2.6.1.1.XX.9.68.69.69.77.66.69.68.95.54
-- Vary			: YES
--
-- Value(s)		: OK  (embedded audio detected on input pair)
--				: NONE  (Nothing present on embedded audio input pair)
-- Comments		:
--
---------------------------------------------------------------------------------------------------
-- Header		: DEEMBED_7
--
-- MIB ref		: swCardEventLogSlotXX       .9.68.69.69.77.66.69.68.95.55
-- absolute OID	: 1.3.6.1.4.1.7995.2.6.1.1.XX.9.68.69.69.77.66.69.68.95.55
-- Vary			: YES
--
-- Value(s)		: OK  (embedded audio detected on input pair)
--				: NONE  (Nothing present on embedded audio input pair)
-- Comments		:
--
---------------------------------------------------------------------------------------------------
-- Header		: DEEMBED_8
--
-- MIB ref		: swCardEventLogSlotXX       .9.68.69.69.77.66.69.68.95.56
-- absolute OID	: 1.3.6.1.4.1.7995.2.6.1.1.XX.9.68.69.69.77.66.69.68.95.56
-- Vary			: YES
--
-- Value(s)		: OK  (embedded audio detected on input pair)
--				: NONE  (Nothing present on embedded audio input pair)
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: FAIL
--				: OK
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2008-01-10T09:54:22Z
--				:
-- Comments		: Time of last restart
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: 2008-01-10T09:59:19Z
--				:
-- Comments		: Time of last control modify command
--
---------------------------------------------------------------------------------------------------
