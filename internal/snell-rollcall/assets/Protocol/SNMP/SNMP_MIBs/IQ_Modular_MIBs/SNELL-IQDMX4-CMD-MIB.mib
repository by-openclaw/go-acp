-- ************************************************************************************
-- Snell&Wilcox Card:IQDMX4
--        Module Id#:39
--       Command Set:6
--          Filename:SNELL-IQDMX4-CMD-MIB.mib
--            Author:Jonathan Riches
--              Date:30/06/2005
--              Time:13:55
--
-- Copyright (c) 2005 Snell & Wilcox Ltd
-- All rights reserved.
--
-- ************************************************************************************

SNELL-IQDMX4-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMX4,
    moduleIQDMX4MIB
        FROM SNELL-WILCOX-PRODUCT-REG;

 moduleIQDMX4CmdMi MODULE-IDENTITY
    LAST-UPDATED "0506301355Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMX4MIB 1 }




--********************************************************************************
--*
--*  Snell Wilcox Card:
--*  command set:
--*  list commands/menus:
--*
--******************************************************************************
	iqdmx4CmdTable OBJECT-TYPE
		SYNTAX			SEQUENCE OF Iqdmx4CmdEntry
		MAX-ACCESS		not-accessible
		STATUS			current
		DESCRIPTION
				"Note the instance of this table is relected in the command set Version"
		::= { moduleIQDMX4 1 }

	iqdmx4CmdEntry OBJECT-TYPE
		SYNTAX		Iqdmx4CmdEntry
		MAX-ACCESS		not-accessible
		STATUS			current
		DESCRIPTION
				"Entry in command table."
		INDEX	{ iqdmx4SlotIndex }
		::= { iqdmx4CmdTable 1 }

	Iqdmx4CmdEntry ::=
		SEQUENCE {
			iqdmx4SlotIndex
				Unsigned32,
			iqdmx4Inputs
				INTEGER,
			iqdmx4EDHShowStats
				INTEGER,
			iqdmx4EDHResetStats
				INTEGER,
			iqdmx4AutoCycleCycleListItem1
				INTEGER,
			iqdmx4AutoCycleCycleListItem2
				INTEGER,
			iqdmx4AutoCycleCycleListItem3
				INTEGER,
			iqdmx4AutoCycleCycleListItem4
				INTEGER,
			iqdmx4AutoCycleCycleTime
				INTEGER,
			iqdmx4SetupNamesInput1
				RollCallString,
			iqdmx4SetupNamesInput2
				RollCallString,
			iqdmx4SetupNamesInput3
				RollCallString,
			iqdmx4SetupNamesInput4
				RollCallString,
			iqdmx4SetupPresetUnit
				INTEGER,
			iqdmx4SetupLoggingInputStatus
				INTEGER,
			iqdmx4SetupLoggingEDHErrors
				INTEGER,
			iqdmx4SetupSoftwareVersion
				RollCallString,
			iqdmx4SetupSerialNo
				RollCallString
		}

	iqdmx4SlotIndex OBJECT-TYPE
		SYNTAX		Unsigned32
		MAX-ACCESS		not-accessible
		STATUS			current
		DESCRIPTION
				"The unique Index value for each slot.  Its value
					ranges between 1 and the value of slotNumber."
		::= { iqdmx4CmdEntry 0 }


	iqdmx4Inputs OBJECT-TYPE
		SYNTAX		INTEGER {
							val_1(0),
							val_2(1),
							val_3(2),
							val_4(3)
							}
		MAX-ACCESS		read-write
		STATUS			current
		DESCRIPTION
				"TYPE: - RadiobuttonList
					Inputs  cmdID= 4 
					1  value= 0  
					2  value= 1  
					3  value= 2  
					4  value= 3  "
		::= { iqdmx4CmdEntry 4 }


	iqdmx4EDHShowStats OBJECT-TYPE
		SYNTAX		INTEGER { disable(0), enable(1) }
		MAX-ACCESS		read-write
		STATUS			current
		DESCRIPTION
				"TYPE: - Checkbox
					Show_Stats  cmdID= 5 "
		::= { iqdmx4CmdEntry 5 }


	iqdmx4EDHResetStats OBJECT-TYPE
		SYNTAX		INTEGER { noAction(0),val_Reset_Stats(1) }
		MAX-ACCESS		read-write
		STATUS			current
		DESCRIPTION
				"TYPE: - Button
					Reset_Stats  cmdID= 6  value= 1  "
		::= { iqdmx4CmdEntry 6 }


	iqdmx4AutoCycleCycleListItem1 OBJECT-TYPE
		SYNTAX		INTEGER
		MAX-ACCESS		read-write
		STATUS			current
		DESCRIPTION
				"TYPE: - Number
					Item_1  cmdID= 7  min= 0  max= 8  step= 1  format= %.0f  div_scale= 1 
					Min = 0  Max = 8  Step = 1 "
		::= { iqdmx4CmdEntry 7 }


	iqdmx4AutoCycleCycleListItem2 OBJECT-TYPE
		SYNTAX		INTEGER
		MAX-ACCESS		read-write
		STATUS			current
		DESCRIPTION
				"TYPE: - Number
					Item_2  cmdID= 8  min= 0  max= 8  step= 1  format= %.0f  div_scale= 1 
					Min = 0  Max = 8  Step = 1 "
		::= { iqdmx4CmdEntry 8 }


	iqdmx4AutoCycleCycleListItem3 OBJECT-TYPE
		SYNTAX		INTEGER
		MAX-ACCESS		read-write
		STATUS			current
		DESCRIPTION
				"TYPE: - Number
					Item_3  cmdID= 9  min= 0  max= 8  step= 1  format= %.0f  div_scale= 1 
					Min = 0  Max = 8  Step = 1 "
		::= { iqdmx4CmdEntry 9 }


	iqdmx4AutoCycleCycleListItem4 OBJECT-TYPE
		SYNTAX		INTEGER
		MAX-ACCESS		read-write
		STATUS			current
		DESCRIPTION
				"TYPE: - Number
					Item_4  cmdID= 10  min= 0  max= 8  step= 1  format= %.0f  div_scale= 1 
					Min = 0  Max = 8  Step = 1 "
		::= { iqdmx4CmdEntry 10 }


	iqdmx4AutoCycleCycleTime OBJECT-TYPE
		SYNTAX		INTEGER
		MAX-ACCESS		read-write
		STATUS			current
		DESCRIPTION
				"TYPE: - Number
					CycleTime  cmdID= 15  min= 0  max= 32000  step= 1  format= %.0f Frames  div_scale= 1 
					Min = 0 Frames  Max = 32000 Frames  Step = 1 Frames "
		::= { iqdmx4CmdEntry 15 }


	iqdmx4SetupNamesInput1 OBJECT-TYPE
		SYNTAX		RollCallString
		MAX-ACCESS		read-write
		STATUS			current
		DESCRIPTION
				"TYPE: - Editstring
					Input_1  cmdID= 16  "
		::= { iqdmx4CmdEntry 16 }


	iqdmx4SetupNamesInput2 OBJECT-TYPE
		SYNTAX		RollCallString
		MAX-ACCESS		read-write
		STATUS			current
		DESCRIPTION
				"TYPE: - Editstring
					Input_2  cmdID= 17  "
		::= { iqdmx4CmdEntry 17 }


	iqdmx4SetupNamesInput3 OBJECT-TYPE
		SYNTAX		RollCallString
		MAX-ACCESS		read-write
		STATUS			current
		DESCRIPTION
				"TYPE: - Editstring
					Input_3  cmdID= 18  "
		::= { iqdmx4CmdEntry 18 }


	iqdmx4SetupNamesInput4 OBJECT-TYPE
		SYNTAX		RollCallString
		MAX-ACCESS		read-write
		STATUS			current
		DESCRIPTION
				"TYPE: - Editstring
					Input_4  cmdID= 19  "
		::= { iqdmx4CmdEntry 19 }


	iqdmx4SetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdmx4CmdEntry 3 }


	iqdmx4SetupLoggingInputStatus OBJECT-TYPE
		SYNTAX		INTEGER { disable(0), enable(1) }
		MAX-ACCESS		read-write
		STATUS			current
		DESCRIPTION
				"TYPE: - Checkbox
					Input_Status  cmdID= 24 "
		::= { iqdmx4CmdEntry 24 }


	iqdmx4SetupLoggingEDHErrors OBJECT-TYPE
		SYNTAX		INTEGER { disable(0), enable(1) }
		MAX-ACCESS		read-write
		STATUS			current
		DESCRIPTION
				"TYPE: - Checkbox
					EDH_Errors  cmdID= 25 "
		::= { iqdmx4CmdEntry 25 }


	iqdmx4SetupSoftwareVersion OBJECT-TYPE
		SYNTAX		RollCallString
		MAX-ACCESS		read-only
		STATUS			current
		DESCRIPTION
				"TYPE: - Display
					Software_Version  cmdID= 2  format=   "
		::= { iqdmx4CmdEntry 2 }


	iqdmx4SetupSerialNo OBJECT-TYPE
		SYNTAX		RollCallString
		MAX-ACCESS		read-only
		STATUS			current
		DESCRIPTION
				"TYPE: - Display
					Serial_No  cmdID= 1  format=   "
		::= { iqdmx4CmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: CH
--
-- MIB ref		: swCardEventLogSlotXX       .2.67.72
-- absolute OID	: 1.3.6.1.4.1.7995.2.6.1.1.XX.2.67.72
-- Vary			: YES
--
-- Value(s)		: 1
--				: 2
--				: 3
--				: 4
-- Comments		: 
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: 525
--				: 625
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
-- Vary Numeber : YES
-- Value(s)		: 0
--				: 
-- Comments		: 
--
---------------------------------------------------------------------------------------------------
-- Header		: CH_NAME
--
-- MIB ref		: swCardEventLogSlotXX       .7.67.72.95.78.65.77.69
-- absolute OID	: 1.3.6.1.4.1.7995.2.6.1.1.XX.7.67.72.95.78.65.77.69
-- Vary			: YES
--
-- Value(s)		: INPUT_1
--				: INPUT_2
--				: INPUT_3
--				: INPUT_4
-- Comments		: 
--
---------------------------------------------------------------------------------------------------
