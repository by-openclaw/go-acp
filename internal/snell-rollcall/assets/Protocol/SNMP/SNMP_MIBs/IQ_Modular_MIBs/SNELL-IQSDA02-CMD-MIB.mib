-- ************************************************************************************
-- Snell&Wilcox Card:IQSDA02
--        Module Id#:464
--       Command Set:9
--          Filename:SNELL-IQSDA02-CMD-MIB.mib
--            Author:Jonathan Riches
--              Date:15/09/2008
--              Time:12:30
--
-- Copyright (c) 2008 Snell & Wilcox Ltd
-- All rights reserved.
--
-- ************************************************************************************

SNELL-IQSDA02-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQSDA02,
    moduleIQSDA02MIB
        FROM SNELL-WILCOX-PRODUCT-REG;

 moduleIQSDA02CmdMi MODULE-IDENTITY
    LAST-UPDATED "0809151130Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQSDA02MIB 1 }




--********************************************************************************
--*
--*  Snell Wilcox Card:
--*  command set:
--*  list commands/menus:
--*
--******************************************************************************
	iqsda02CmdTable OBJECT-TYPE
		SYNTAX			SEQUENCE OF Iqsda02CmdEntry
		MAX-ACCESS		not-accessible
		STATUS			current
		DESCRIPTION
				"Note the instance of this table is relected in the command set Version"
		::= { moduleIQSDA02 1 }

	iqsda02CmdEntry OBJECT-TYPE
		SYNTAX		Iqsda02CmdEntry
		MAX-ACCESS		not-accessible
		STATUS			current
		DESCRIPTION
				"Entry in command table."
		INDEX	{ iqsda02SlotIndex }
		::= { iqsda02CmdTable 1 }

	Iqsda02CmdEntry ::=
		SEQUENCE {
			iqsda02SlotIndex
				Unsigned32,
			iqsda02HyperionBlackishBlackBlackishLevel
				RollCallString,
			iqsda02HyperionBlackishBlackMinLevelThres
				INTEGER,
			iqsda02TemporalControlBlackishEnableAlarm
				INTEGER,
			iqsda02TemporalControlBlackishAlarm
				RollCallString,
			iqsda02TemporalControlBlackishFailCount
				INTEGER,
			iqsda02TemporalControlBlackishWarningCount
				INTEGER,
			iqsda02TemporalControlBlackishFailHoldCount
				INTEGER,
			iqsda02TemporalControlBlackishResetAlarm
				INTEGER,
			iqsda02TemporalControlBlackEnableAlarm
				INTEGER,
			iqsda02TemporalControlBlackAlarm
				RollCallString,
			iqsda02TemporalControlBlackFailCount
				INTEGER,
			iqsda02TemporalControlBlackWarningCount
				INTEGER,
			iqsda02TemporalControlBlackFailHoldCount
				INTEGER,
			iqsda02TemporalControlBlackResetAlarm
				INTEGER,
			iqsda02VideoMonitorAveragePictureLvlDisplayTimeout
				RollCallString,
			iqsda02VideoMonitorAveragePictureLvlHyperionDisplayEn
				INTEGER,
			iqsda02HyperionFreezeStillishStillishLevel
				RollCallString,
			iqsda02HyperionFreezeStillishMaxLevelThres
				INTEGER,
			iqsda02TemporalControlStillishEnableAlarm
				INTEGER,
			iqsda02TemporalControlStillishAlarm
				RollCallString,
			iqsda02TemporalControlStillishFailCount
				INTEGER,
			iqsda02TemporalControlStillishWarningCount
				INTEGER,
			iqsda02TemporalControlStillishFailHoldCount
				INTEGER,
			iqsda02TemporalControlStillishResetAlarm
				INTEGER,
			iqsda02TemporalControlFreezeEnableAlarm
				INTEGER,
            iqsda02TemporalControlFreezeTolerance
                INTEGER,
			iqsda02TemporalControlFreezeAlarm
				RollCallString,
			iqsda02TemporalControlFreezeFailCount
				INTEGER,
			iqsda02TemporalControlFreezeWarningCount
				INTEGER,
			iqsda02TemporalControlFreezeFailHoldCount
				INTEGER,
			iqsda02TemporalControlFreezeResetAlarm
				INTEGER,
			iqsda02VideoMonitorAveragePictureLvlEnableAlarm
				INTEGER,
			iqsda02VideoMonitorAveragePictureLvl
				RollCallString,
			iqsda02VideoMonitorAveragePictureLvlMaxLoggingThres
				INTEGER,
			iqsda02VideoMonitorAveragePictureLvlMinLoggingThres
				INTEGER,
			iqsda02LumaVideoLevelOverloadStatus
				RollCallString,
			iqsda02LumaVideoLevelOverloadMaximumReading
				RollCallString,
			iqsda02LumaVideoLevelOverloadEnableAlarm
				INTEGER,
			iqsda02LumaVideoLevelOverloadOverloadThreshold
				INTEGER,
			iqsda02LumaVideoLevelOverloadAvePicAboveThres
				INTEGER,
			iqsda02LumaVideoLevelUnderloadStatus
				RollCallString,
			iqsda02LumaVideoLevelUnderloadMinimumReading
				RollCallString,
			iqsda02LumaVideoLevelUnderloadEnableAlarm
				INTEGER,
			iqsda02LumaVideoLevelUnderloadUnderloadThreshold
				INTEGER,
			iqsda02LumaVideoLevelUnderloadAvePicBelowThres
				INTEGER,
			iqsda02ChromaVideoLevelOverloadStatus
				RollCallString,
			iqsda02ChromaVideoLevelOverloadMaximumReading
				RollCallString,
			iqsda02ChromaVideoLevelOverloadEnableAlarm
				INTEGER,
			iqsda02ChromaVideoLevelOverloadOverloadThreshold
				INTEGER,
			iqsda02ChromaVideoLevelOverloadAvePicAboveThres
				INTEGER,
			iqsda02ChromaVideoLevelUnderloadStatus
				RollCallString,
			iqsda02ChromaVideoLevelUnderloadMinimumReading
				RollCallString,
			iqsda02ChromaVideoLevelUnderloadEnableAlarm
				INTEGER,
			iqsda02ChromaVideoLevelUnderloadUnderloadThreshold
				INTEGER,
			iqsda02ChromaVideoLevelUnderloadAvePicBelowThres
				INTEGER,
			iqsda02HyperionVideoMonitorChromaBitDepth
				RollCallString,
			iqsda02HyperionVideoMonitorLumaBitDepth
				RollCallString,
			iqsda02ClosedCaptionsCCCEA608BState
				RollCallString,
			iqsda02ClosedCaptionsCCCEA608BTitle1
				RollCallString,
			iqsda02ClosedCaptionsCCCEA608BTitle2
				RollCallString,
			iqsda02ClosedCaptionsCCCEA708BField1
				RollCallString,
			iqsda02ClosedCaptionsCCCEA708BField2
				RollCallString,
			iqsda02ClosedCaptionsTemporalControlEnableAlarm
				INTEGER,
			iqsda02ClosedCaptionsTemporalControlAlarm
				RollCallString,
			iqsda02ClosedCaptionsTemporalControlFailCount
				INTEGER,
			iqsda02ClosedCaptionsTemporalControlWarningCount
				INTEGER,
			iqsda02ClosedCaptionsTemporalControlFailHoldCount
				INTEGER,
			iqsda02ClosedCaptionsTemporalControlResetAlarm
				INTEGER,
			iqsda02AncillaryDataContentAdvisoryEnableAlarm
				INTEGER,
			iqsda02AncillaryDataContentAdvisorySystem
				RollCallString,
			iqsda02AncillaryDataContentAdvisoryRating
				RollCallString,
			iqsda02TimeCodeAncTimeCodeEnableAlarm
				INTEGER,
			iqsda02TimeCodeAncTimeCodeField1
				RollCallString,
			iqsda02TimeCodeAncTimeCodeField2
				RollCallString,
			iqsda02TimeCodeVITCEnableAlarm
				INTEGER,
			iqsda02TimeCodeVITCField1
				RollCallString,
			iqsda02TimeCodeVITCField2
				RollCallString,
			iqsda02AncillaryDataTimeCodeCurrentTimeCode
				RollCallString,
			iqsda02AncillaryDataTimeCodeSDTimeCodeSel
				INTEGER,
			iqsda02AncillaryDataUserAncDet1EnableAlarm
				INTEGER,
			iqsda02AncillaryDataUserAncDet1DIDType
				INTEGER,
			iqsda02AncillaryDataUserAncDet1DIDselect
				INTEGER,
			iqsda02AncillaryDataUserAncDet1SDIDselect
				INTEGER,
			iqsda02AncillaryDataUserAncDet1Field1
				RollCallString,
			iqsda02AncillaryDataUserAncDet1Field2
				RollCallString,
			iqsda02AncillaryDataUserAncDet1Name
				RollCallString,
			iqsda02AncillaryDataUserAncDet2EnableAlarm
				INTEGER,
			iqsda02AncillaryDataUserAncDet2DIDType
				INTEGER,
			iqsda02AncillaryDataUserAncDet2DIDselect
				INTEGER,
			iqsda02AncillaryDataUserAncDet2SDIDselect
				INTEGER,
			iqsda02AncillaryDataUserAncDet2Field1
				RollCallString,
			iqsda02AncillaryDataUserAncDet2Field2
				RollCallString,
			iqsda02AncillaryDataUserAncDet2Name
				RollCallString,
			iqsda02AncillaryDataWSSVIInputWSSPresence
				RollCallString,
			iqsda02AncillaryDataWSSVIInputWSSEnableAlarm
				INTEGER,
			iqsda02AncillaryDataWSSVIInputWSSData
				RollCallString,
			iqsda02AncillaryDataWSSVIInputWSSScanSys
				RollCallString,
			iqsda02AncillaryDataWSSVIInputWSSType
				INTEGER,
			iqsda02AncillaryDataWSSVIInputVIPresence
				RollCallString,
			iqsda02AncillaryDataWSSVIInputVIEnableAlarm
				INTEGER,
			iqsda02AncillaryDataWSSVIInputVIType
				INTEGER,
			iqsda02AncillaryDataWSSVIInputVIData
				RollCallString,
			iqsda02AncillaryDataWSSVIInputVIScanSys
				RollCallString,
			iqsda02HyperionAudioDataActiveAudioCh
				RollCallString,
			iqsda02AudioDataGroup1EnableAlarmCh1
				INTEGER,
			iqsda02AudioDataGroup1TypeCh1
				RollCallString,
			iqsda02AudioDataGroup1BitdepthCh1
				RollCallString,
			iqsda02AudioDataGroup1EnableAlarmCh2
				INTEGER,
			iqsda02AudioDataGroup1TypeCh2
				RollCallString,
			iqsda02AudioDataGroup1BitdepthCh2
				RollCallString,
			iqsda02AudioDataGroup1EnableAlarmCh3
				INTEGER,
			iqsda02AudioDataGroup1TypeCh3
				RollCallString,
			iqsda02AudioDataGroup1BitdepthCh3
				RollCallString,
			iqsda02AudioDataGroup1EnableAlarmCh4
				INTEGER,
			iqsda02AudioDataGroup1TypeCh4
				RollCallString,
			iqsda02AudioDataGroup1BitdepthCh4
				RollCallString,
			iqsda02AudioDataGroup2EnableAlarmCh5
				INTEGER,
			iqsda02AudioDataGroup2TypeCh5
				RollCallString,
			iqsda02AudioDataGroup2BitdepthCh5
				RollCallString,
			iqsda02AudioDataGroup2EnableAlarmCh6
				INTEGER,
			iqsda02AudioDataGroup2TypeCh6
				RollCallString,
			iqsda02AudioDataGroup2BitdepthCh6
				RollCallString,
			iqsda02AudioDataGroup2EnableAlarmCh7
				INTEGER,
			iqsda02AudioDataGroup2TypeCh7
				RollCallString,
			iqsda02AudioDataGroup2BitdepthCh7
				RollCallString,
			iqsda02AudioDataGroup2EnableAlarmCh8
				INTEGER,
			iqsda02AudioDataGroup2TypeCh8
				RollCallString,
			iqsda02AudioDataGroup2BitdepthCh8
				RollCallString,
			iqsda02AudioDataGroup3EnableAlarmCh9
				INTEGER,
			iqsda02AudioDataGroup3TypeCh9
				RollCallString,
			iqsda02AudioDataGroup3BitdepthCh9
				RollCallString,
			iqsda02AudioDataGroup3EnableAlarmCh10
				INTEGER,
			iqsda02AudioDataGroup3TypeCh10
				RollCallString,
			iqsda02AudioDataGroup3BitdepthCh10
				RollCallString,
			iqsda02AudioDataGroup3EnableAlarmCh11
				INTEGER,
			iqsda02AudioDataGroup3TypeCh11
				RollCallString,
			iqsda02AudioDataGroup3BitdepthCh11
				RollCallString,
			iqsda02AudioDataGroup3EnableAlarmCh12
				INTEGER,
			iqsda02AudioDataGroup3TypeCh12
				RollCallString,
			iqsda02AudioDataGroup3BitdepthCh12
				RollCallString,
			iqsda02AudioDataGroup4EnableAlarmCh13
				INTEGER,
			iqsda02AudioDataGroup4TypeCh13
				RollCallString,
			iqsda02AudioDataGroup4BitdepthCh13
				RollCallString,
			iqsda02AudioDataGroup4EnableAlarmCh14
				INTEGER,
			iqsda02AudioDataGroup4TypeCh14
				RollCallString,
			iqsda02AudioDataGroup4BitdepthCh14
				RollCallString,
			iqsda02AudioDataGroup4EnableAlarmCh15
				INTEGER,
			iqsda02AudioDataGroup4TypeCh15
				RollCallString,
			iqsda02AudioDataGroup4BitdepthCh15
				RollCallString,
			iqsda02AudioDataGroup4EnableAlarmCh16
				INTEGER,
			iqsda02AudioDataGroup4TypeCh16
				RollCallString,
			iqsda02AudioDataGroup4BitdepthCh16
				RollCallString,
			iqsda02AudioDataDolbyEStatusEnableAlarmPair1
				INTEGER,
			iqsda02AudioDataDolbyEStatusStatusPair1
				RollCallString,
			iqsda02AudioDataDolbyEStatusEnableAlarmPair2
				INTEGER,
			iqsda02AudioDataDolbyEStatusStatusPair2
				RollCallString,
			iqsda02AudioDataDolbyEStatusEnableAlarmPair3
				INTEGER,
			iqsda02AudioDataDolbyEStatusStatusPair3
				RollCallString,
			iqsda02AudioDataDolbyEStatusEnableAlarmPair4
				INTEGER,
			iqsda02AudioDataDolbyEStatusStatusPair4
				RollCallString,
			iqsda02AudioDataDolbyEStatusEnableAlarmPair5
				INTEGER,
			iqsda02AudioDataDolbyEStatusStatusPair5
				RollCallString,
			iqsda02AudioDataDolbyEStatusEnableAlarmPair6
				INTEGER,
			iqsda02AudioDataDolbyEStatusStatusPair6
				RollCallString,
			iqsda02AudioDataDolbyEStatusEnableAlarmPair7
				INTEGER,
			iqsda02AudioDataDolbyEStatusStatusPair7
				RollCallString,
			iqsda02AudioDataDolbyEStatusEnableAlarmPair8
				INTEGER,
			iqsda02AudioDataDolbyEStatusStatusPair8
				RollCallString,
			iqsda02AudioLevelDetDuplicateSettingsChannelIndex
				INTEGER,
			iqsda02HyperionAudioLevelDetAverageAudioLevel
				RollCallString,
			iqsda02AudioLevelDetOverloadDetectorEnableAlarm
				INTEGER,
			iqsda02AudioLevelDetOverloadDetectorAlarm
				RollCallString,
			iqsda02AudioLevelDetOverloadDetectorLeveldB
				INTEGER,
			iqsda02AudioLevelDetOverloadDetectorWarningsecs
				INTEGER,
			iqsda02AudioLevelDetOverloadDetectorFailsecs
				INTEGER,
			iqsda02AudioLevelDetOverloadDetectorFailHoldsecs
				INTEGER,
			iqsda02AudioLevelDetOverloadDetectorAlarmReset
				INTEGER,
			iqsda02AudioLevelDetLoudDetectorEnableAlarm
				INTEGER,
			iqsda02AudioLevelDetLoudDetectorAlarm
				RollCallString,
			iqsda02AudioLevelDetLoudDetectorLeveldB
				INTEGER,
			iqsda02AudioLevelDetLoudDetectorWarningsecs
				INTEGER,
			iqsda02AudioLevelDetLoudDetectorFailsecs
				INTEGER,
			iqsda02AudioLevelDetLoudDetectorFailHoldsecs
				INTEGER,
			iqsda02AudioLevelDetQuietDetectorEnableAlarm
				INTEGER,
			iqsda02AudioLevelDetQuietDetectorAlarm
				RollCallString,
			iqsda02AudioLevelDetQuietDetectorLeveldB
				INTEGER,
			iqsda02AudioLevelDetQuietDetectorWarningsecs
				INTEGER,
			iqsda02AudioLevelDetQuietDetectorFailsecs
				INTEGER,
			iqsda02AudioLevelDetQuietDetectorFailHoldsecs
				INTEGER,
			iqsda02AudioLevelDetSilenceDetectorEnableAlarm
				INTEGER,
			iqsda02AudioLevelDetSilenceDetectorAlarm
				RollCallString,
			iqsda02AudioLevelDetSilenceDetectorLeveldB
				INTEGER,
			iqsda02AudioLevelDetSilenceDetectorWarningsecs
				INTEGER,
			iqsda02AudioLevelDetSilenceDetectorFailsecs
				INTEGER,
			iqsda02AudioLevelDetSilenceDetectorFailHoldsecs
				INTEGER,
			iqsda02AudioLevelDetDuplicateSettingsCopyFromChannel
				INTEGER,
			iqsda02AudioLevelDetDuplicateSettingsCopySettings
				INTEGER,
			iqsda02HyperionAudioLevelDet
				INTEGER,
			iqsda02HyperionAudioLevelIndRollMapAudLvlEn
				INTEGER,
			iqsda02HyperionAudioLevelIndOSDMarker
				INTEGER,
			iqsda02HyperionAudioLevelIndRollMapAudLvl
				RollCallString,
			iqsda02HyperionAudioLevelIndEnableChannel1
				INTEGER,
			iqsda02HyperionAudioLevelIndChannel1
				RollCallString,
			iqsda02HyperionAudioLevelIndEnableChannel2
				INTEGER,
			iqsda02HyperionAudioLevelIndChannel2
				RollCallString,
			iqsda02HyperionAudioLevelIndEnableChannel3
				INTEGER,
			iqsda02HyperionAudioLevelIndChannel3
				RollCallString,
			iqsda02HyperionAudioLevelIndEnableChannel4
				INTEGER,
			iqsda02HyperionAudioLevelIndChannel4
				RollCallString,
			iqsda02HyperionAudioLevelIndEnableChannel5
				INTEGER,
			iqsda02HyperionAudioLevelIndChannel5
				RollCallString,
			iqsda02HyperionAudioLevelIndEnableChannel6
				INTEGER,
			iqsda02HyperionAudioLevelIndChannel6
				RollCallString,
			iqsda02HyperionAudioLevelIndEnableChannel7
				INTEGER,
			iqsda02HyperionAudioLevelIndChannel7
				RollCallString,
			iqsda02HyperionAudioLevelIndEnableChannel8
				INTEGER,
			iqsda02HyperionAudioLevelIndChannel8
				RollCallString,
			iqsda02HyperionAudioLevelIndEnableChannel9
				INTEGER,
			iqsda02HyperionAudioLevelIndChannel9
				RollCallString,
			iqsda02HyperionAudioLevelIndEnableChannel10
				INTEGER,
			iqsda02HyperionAudioLevelIndChannel10
				RollCallString,
			iqsda02HyperionAudioLevelIndEnableChannel11
				INTEGER,
			iqsda02HyperionAudioLevelIndChannel11
				RollCallString,
			iqsda02HyperionAudioLevelIndEnableChannel12
				INTEGER,
			iqsda02HyperionAudioLevelIndChannel12
				RollCallString,
			iqsda02HyperionAudioLevelIndEnableChannel13
				INTEGER,
			iqsda02HyperionAudioLevelIndChannel13
				RollCallString,
			iqsda02HyperionAudioLevelIndEnableChannel14
				INTEGER,
			iqsda02HyperionAudioLevelIndChannel14
				RollCallString,
			iqsda02HyperionAudioLevelIndEnableChannel15
				INTEGER,
			iqsda02HyperionAudioLevelIndChannel15
				RollCallString,
			iqsda02HyperionAudioLevelIndEnableChannel16
				INTEGER,
			iqsda02HyperionAudioLevelIndChannel16
				RollCallString,
			iqsda02HyperionClippingDetectorThreshold
				INTEGER,
			iqsda02HyperionClippingDetectorSensitivity
				INTEGER,
			iqsda02HyperionClippingDetectorStatusCh1
				RollCallString,
			iqsda02HyperionClippingDetectorEnableAlarmCh1
				INTEGER,
			iqsda02HyperionClippingDetectorStatusCh2
				RollCallString,
			iqsda02HyperionClippingDetectorEnableAlarmCh2
				INTEGER,
			iqsda02HyperionClippingDetectorStatusCh3
				RollCallString,
			iqsda02HyperionClippingDetectorEnableAlarmCh3
				INTEGER,
			iqsda02HyperionClippingDetectorStatusCh4
				RollCallString,
			iqsda02HyperionClippingDetectorEnableAlarmCh4
				INTEGER,
			iqsda02HyperionClippingDetectorStatusCh5
				RollCallString,
			iqsda02HyperionClippingDetectorEnableAlarmCh5
				INTEGER,
			iqsda02HyperionClippingDetectorStatusCh6
				RollCallString,
			iqsda02HyperionClippingDetectorEnableAlarmCh6
				INTEGER,
			iqsda02HyperionClippingDetectorStatusCh7
				RollCallString,
			iqsda02HyperionClippingDetectorEnableAlarmCh7
				INTEGER,
			iqsda02HyperionClippingDetectorStatusCh8
				RollCallString,
			iqsda02HyperionClippingDetectorEnableAlarmCh8
				INTEGER,
			iqsda02HyperionClippingDetectorStatusCh9
				RollCallString,
			iqsda02HyperionClippingDetectorEnableAlarmCh9
				INTEGER,
			iqsda02HyperionClippingDetectorStatusCh10
				RollCallString,
			iqsda02HyperionClippingDetectorEnableAlarmCh10
				INTEGER,
			iqsda02HyperionClippingDetectorStatusCh11
				RollCallString,
			iqsda02HyperionClippingDetectorEnableAlarmCh11
				INTEGER,
			iqsda02HyperionClippingDetectorStatusCh12
				RollCallString,
			iqsda02HyperionClippingDetectorEnableAlarmCh12
				INTEGER,
			iqsda02HyperionClippingDetectorStatusCh13
				RollCallString,
			iqsda02HyperionClippingDetectorEnableAlarmCh13
				INTEGER,
			iqsda02HyperionClippingDetectorStatusCh14
				RollCallString,
			iqsda02HyperionClippingDetectorEnableAlarmCh14
				INTEGER,
			iqsda02HyperionClippingDetectorStatusCh15
				RollCallString,
			iqsda02HyperionClippingDetectorEnableAlarmCh15
				INTEGER,
			iqsda02HyperionClippingDetectorStatusCh16
				RollCallString,
			iqsda02HyperionClippingDetectorEnableAlarmCh16
				INTEGER,
			iqsda02AudioLikenessDetector1Likeness
				RollCallString,
			iqsda02AudioLikenessDetector1State
				RollCallString,
			iqsda02AudioLikenessDetector1SelectChannelA
				INTEGER,
			iqsda02AudioLikenessDetector1SelectChannelB
				INTEGER,
			iqsda02AudioLikenessDetector1EnableAlarm
				INTEGER,
			iqsda02AudioLikenessDetector2Likeness
				RollCallString,
			iqsda02AudioLikenessDetector2State
				RollCallString,
			iqsda02AudioLikenessDetector2SelectChannelA
				INTEGER,
			iqsda02AudioLikenessDetector2SelectChannelB
				INTEGER,
			iqsda02AudioLikenessDetector2AlarmEnable
				INTEGER,
			iqsda02AudioLikenessDetector3Likeness
				RollCallString,
			iqsda02AudioLikenessDetector3State
				RollCallString,
			iqsda02AudioLikenessDetector3SelectChannelA
				INTEGER,
			iqsda02AudioLikenessDetector3SelectChannelB
				INTEGER,
			iqsda02AudioLikenessDetector3AlarmEnable
				INTEGER,
			iqsda02AudioLikenessDetector4Likeness
				RollCallString,
			iqsda02AudioLikenessDetector4State
				RollCallString,
			iqsda02AudioLikenessDetector4SelectChannelA
				INTEGER,
			iqsda02AudioLikenessDetector4SelectChannelB
				INTEGER,
			iqsda02AudioLikenessDetector4AlarmEnable
				INTEGER,
			iqsda02UMIDReaderDetectonYOnly
				INTEGER,
			iqsda02UMIDReaderUMIDPresence
				RollCallString,
			iqsda02UMIDReaderFoundOnLine
				RollCallString,
			iqsda02ReaderUniversalLabelVersionNumber
				RollCallString,
			iqsda02ReaderUniversalLabelMaterialType
				RollCallString,
			iqsda02ReaderUniversalLabelIdentMatNumGen
				RollCallString,
			iqsda02ReaderUniversalLabelIdentInstNumGen
				RollCallString,
			iqsda02UMIDReaderInstanceNumber
				RollCallString,
			iqsda02ReaderMaterialNumber1_4
				RollCallString,
			iqsda02ReaderMaterialNumber5_8
				RollCallString,
			iqsda02ReaderMaterialNumber9_12
				RollCallString,
			iqsda02ReaderMaterialNumber13_16
				RollCallString,
			iqsda02UMIDReaderCount
				RollCallString,
			iqsda02HyperionUMIDUMIDDelete
				INTEGER,
			iqsda02UMIDGeneratorEnable
				INTEGER,
			iqsda02UMIDGeneratorGeneratorStatus
				RollCallString,
			iqsda02UMIDGeneratorGenerateonYOnly
				INTEGER,
			iqsda02UMIDGeneratorTake
				INTEGER,
			iqsda02UMIDGeneratorLineNumber
				INTEGER,
			iqsda02GeneratorUniversalLabelVersionNumber
				INTEGER,
			iqsda02GeneratorUniversalLabelMaterialType
				INTEGER,
			iqsda02GeneratorUniversalLabelIdentofMaterial
				INTEGER,
			iqsda02GeneratorUniversalLabelIdentofInstance
				INTEGER,
			iqsda02UMIDGeneratorInstanceNum
				RollCallString,
			iqsda02UMIDGeneratorMaterialNum1_4
				RollCallString,
			iqsda02UMIDGeneratorMaterialNum5_8
				RollCallString,
			iqsda02UMIDGeneratorMaterialNum9_12
				RollCallString,
			iqsda02UMIDGeneratorMaterialNum13_16
				RollCallString,
			iqsda02HyperionUMIDUMIDAlarmEnable
				INTEGER,
			iqsda02PIDReaderPIDPresence
				RollCallString,
			iqsda02PIDReaderFoundOnLine
				RollCallString,
			iqsda02PIDReaderHouseID
				RollCallString,
			iqsda02PIDReaderProgramTitle
				RollCallString,
			iqsda02PIDReaderSegmentNumber
				RollCallString,
			iqsda02PIDReaderDuration
				RollCallString,
			iqsda02PIDReaderFrameRate
				RollCallString,
			iqsda02PIDReaderCount
				RollCallString,
			iqsda02HyperionPIDPIDDelete
				INTEGER,
			iqsda02PIDGeneratorEnable
				INTEGER,
			iqsda02PIDGeneratorGeneratorStatus
				RollCallString,
			iqsda02PIDGeneratorTake
				INTEGER,
			iqsda02PIDGeneratorLineNumber
				INTEGER,
			iqsda02PIDGeneratorHouseID
				RollCallString,
			iqsda02PIDGeneratorProgramTitle
				RollCallString,
			iqsda02PIDGeneratorProgramTitleEn
				INTEGER,
			iqsda02PIDGeneratorSegmentNumber
				RollCallString,
			iqsda02PIDGeneratorSegmentNumberEn
				INTEGER,
			iqsda02PIDGeneratorDuration
				RollCallString,
			iqsda02PIDGeneratorDurationEn
				INTEGER,
			iqsda02PIDGeneratorFrameRateEn
				INTEGER,
			iqsda02PIDGeneratorFrameRate
				INTEGER,
			iqsda02HyperionPIDPIDAlarmEnable
				INTEGER,
			iqsda02HyperionOSDOSDPassword
				RollCallString,
			iqsda02HyperionOSDOSDEnable
				INTEGER,
			iqsda02HyperionOSDOSDEnableoutput7
				INTEGER,
			iqsda02OSDStillishDetWindowOSWinEn
				INTEGER,
			iqsda02OSDStillishDetWindowXPosition
				INTEGER,
			iqsda02OSDStillishDetWindowWidth
				INTEGER,
			iqsda02OSDStillishDetWindowYPosition
				INTEGER,
			iqsda02OSDStillishDetWindowHeight
				INTEGER,
			iqsda02OSDStillishDetWindowWindowMode
				INTEGER,
			iqsda02OSDStillishDetWindowDetectFullScreen
				INTEGER,
			iqsda02OSDBlackishDetWindowOSWinEn
				INTEGER,
			iqsda02OSDBlackishDetWindowXPosition
				INTEGER,
			iqsda02OSDBlackishDetWindowWidth
				INTEGER,
			iqsda02OSDBlackishDetWindowYPosition
				INTEGER,
			iqsda02OSDBlackishDetWindowHeight
				INTEGER,
			iqsda02OSDBlackishDetWindowWindowMode
				INTEGER,
			iqsda02OSDBlackishDetWindowDetectFullScreen
				INTEGER,
			iqsda02OSDOnScreenDispEnIndicators
				INTEGER,
			iqsda02OSDOnScreenDispEnAudioLevelInds
				INTEGER,
			iqsda02OSDOnScreenDispEnTimecode
				INTEGER,
			iqsda02OSDOnScreenDispEnGreyBackground
				INTEGER,
			iqsda02OSDOnScreenDispEnInput1Name
				INTEGER,
			iqsda02OSDOnScreenDispEnCaption1Edit
				RollCallString,
			iqsda02OSDOnScreenDispEnCaption1Enable
				INTEGER,
			iqsda02OSDOnScreenDispEnCaption2Edit
				RollCallString,
			iqsda02OSDOnScreenDispEnCaption2Enable
				INTEGER,
			iqsda02OSDOnScreenDispEnContentAdvisory
				INTEGER,
			iqsda02OSDOnScreenDispEnIncomingPID
				INTEGER,
			iqsda02OSDOnScreenDispEnOutgoingPID
				INTEGER,
			iqsda02OSDOnScreenDispEnAudioLvlIndZoom
				INTEGER,
			iqsda02HyperionHyperionDetStatus
				INTEGER,
			iqsda02MemoriesMemorySave
				INTEGER,
			iqsda02MemoriesMemoryRecall
				INTEGER,
			iqsda02MemoriesMemory1Name
				RollCallString,
			iqsda02MemoriesMemory2Name
				RollCallString,
			iqsda02MemoriesMemory3Name
				RollCallString,
			iqsda02MemoriesMemory4Name
				RollCallString,
			iqsda02MemoriesMemory5Name
				RollCallString,
			iqsda02MemoriesMemory6Name
				RollCallString,
			iqsda02MemoriesMemory7Name
				RollCallString,
			iqsda02MemoriesMemory8Name
				RollCallString,
			iqsda02MemoriesMemory9Name
				RollCallString,
			iqsda02MemoriesMemory10Name
				RollCallString,
			iqsda02MemoriesMemory11Name
				RollCallString,
			iqsda02MemoriesMemory12Name
				RollCallString,
			iqsda02MemoriesMemory13Name
				RollCallString,
			iqsda02MemoriesMemory14Name
				RollCallString,
			iqsda02MemoriesMemory15Name
				RollCallString,
			iqsda02MemoriesMemory16Name
				RollCallString,
			iqsda02LoggingMiscTimecodelogEnable
				INTEGER,
			iqsda02LoggingMiscLogSerialNoEnable
				INTEGER,
			iqsda02LoggingMiscSerialNo
				RollCallString,
			iqsda02LoggingMiscLogOSVersionEnable
				INTEGER,
			iqsda02LoggingMiscOSVersion
				RollCallString,
			iqsda02LoggingMiscLogBuildNoEnable
				INTEGER,
			iqsda02LoggingMiscBuildNo
				RollCallString,
			iqsda02LoggingMiscLogHardwareVerEnable
				INTEGER,
			iqsda02LoggingMiscHardwareVer
				RollCallString,
			iqsda02LoggingMiscLogFirmwareVerEnable
				INTEGER,
			iqsda02LoggingMiscFirmwareVer
				RollCallString,
			iqsda02LoggingMiscLogUpTimeEnable
				INTEGER,
			iqsda02LoggingMiscUpTime
				RollCallString,
			iqsda02LoggingMiscRollTracksEnable
				INTEGER,
			iqsda02LoggingMiscRollTracks
				RollCallString,
			iqsda02LoggingMiscOSDStatusEnable
				INTEGER,
			iqsda02LoggingMiscOSDStatus
				RollCallString,
			iqsda02LoggingInput1InputIdentEnable
				INTEGER,
			iqsda02LoggingInput1InputIdent
				RollCallString,
			iqsda02LoggingInput1InputNameEnable
				INTEGER,
			iqsda02LoggingInput1InputName
				RollCallString,
			iqsda02LoggingInput1InputTypeEnable
				INTEGER,
			iqsda02LoggingInput1InputType
				RollCallString,
			iqsda02LoggingInput1InputStateEnable
				INTEGER,
			iqsda02LoggingInput1InputState
				RollCallString,
			iqsda02LoggingInput1InputStandardEnable
				INTEGER,
			iqsda02LoggingInput1InputStandard
				RollCallString,
			iqsda02LoggingInput1EDHEnable
				INTEGER,
			iqsda02LoggingInput1EDH
				RollCallString,
			iqsda02LoggingInput1CRCEnable
				INTEGER,
			iqsda02LoggingInput1CRC
				RollCallString,
			iqsda02LoggingInp1Monitor1HyperionSummaryEnable
				INTEGER,
			iqsda02LoggingInp1Monitor1HyperionSummary
				RollCallString,
			iqsda02LoggingInp1Monitor1StillishEnable
				INTEGER,
			iqsda02LoggingInp1Monitor1Stillish
				RollCallString,
			iqsda02LoggingInp1Monitor1StillishLogOption
				INTEGER,
			iqsda02LoggingInp1Monitor1FreezeEnable
				INTEGER,
			iqsda02LoggingInp1Monitor1Freeze
				RollCallString,
			iqsda02LoggingInp1Monitor1FreezeLogOption
				INTEGER,
			iqsda02LoggingInp1Monitor1BlackEnable
				INTEGER,
			iqsda02LoggingInp1Monitor1Black
				RollCallString,
			iqsda02LoggingInp1Monitor1BlackLogOption
				INTEGER,
			iqsda02LoggingInp1Monitor1BlackishEnable
				INTEGER,
			iqsda02LoggingInp1Monitor1Blackish
				RollCallString,
			iqsda02LoggingInp1Monitor1BlackishLogOption
				INTEGER,
			iqsda02LoggingInp1Monitor1CldCapStateEnable
				INTEGER,
			iqsda02LoggingInp1Monitor1ClosedCapState
				RollCallString,
			iqsda02LoggingInp1Monitor1ClosedCapLogOption
				INTEGER,
			iqsda02LoggingInp1Monitor1CldCapTypeEnable
				INTEGER,
			iqsda02LoggingInp1Monitor1ClosedCapType
				RollCallString,
			iqsda02LoggingInp1Monitor1CldCapTitleEnable
				INTEGER,
			iqsda02LoggingInp1Monitor1ClosedCapTitle
				RollCallString,
			iqsda02LoggingInp1Monitor2YBitDepthEnable
				INTEGER,
			iqsda02LoggingInp1Monitor2YBitDepth
				RollCallString,
			iqsda02LoggingInp1Monitor2CBitDepthEnable
				INTEGER,
			iqsda02LoggingInp1Monitor2CBitDepth
				RollCallString,
			iqsda02LoggingInp1Monitor2VideoYLvlHighEnable
				INTEGER,
			iqsda02LoggingInp1Monitor2VideoYLevelHigh
				RollCallString,
			iqsda02LoggingInp1Monitor2VideoCLvlHighEnable
				INTEGER,
			iqsda02LoggingInp1Monitor2VideoCLevelHigh
				RollCallString,
			iqsda02LoggingInp1Monitor2VideoYLvlLowEnable
				INTEGER,
			iqsda02LoggingInp1Monitor2VideoYLevelLow
				RollCallString,
			iqsda02LoggingInp1Monitor2VideoCLvlLowEnable
				INTEGER,
			iqsda02LoggingInp1Monitor2VideoCLevelLow
				RollCallString,
			iqsda02LoggingInp1Monitor2APLEnable
				INTEGER,
			iqsda02LoggingInp1Monitor2APL
				RollCallString,
			iqsda02LoggingInp1Monitor2VITCStateEnable
				INTEGER,
			iqsda02LoggingInp1Monitor2VITCState
				RollCallString,
			iqsda02LoggingInp1Monitor2CAStateEnable
				INTEGER,
			iqsda02LoggingInp1Monitor2CAState
				RollCallString,
			iqsda02LoggingInp1Monitor2CASystemEnable
				INTEGER,
			iqsda02LoggingInp1Monitor2CASystem
				RollCallString,
			iqsda02LoggingInp1Monitor2CAAgeRatingEnable
				INTEGER,
			iqsda02LoggingInp1Monitor2CAAgeRating
				RollCallString,
			iqsda02LoggingInp1Monitor2ANCTimcodeStateEnable
				INTEGER,
			iqsda02LoggingInp1Monitor2ANCTimecodeState
				RollCallString,
			iqsda02LoggingInp1Monitor2User1DIDNameEnable
				INTEGER,
			iqsda02LoggingInp1Monitor2User1DIDName
				RollCallString,
			iqsda02LoggingInp1Monitor2User1DIDStateEnable
				INTEGER,
			iqsda02LoggingInp1Monitor2User1DIDState
				RollCallString,
			iqsda02LoggingInp1Monitor2User2DIDNameEnable
				INTEGER,
			iqsda02LoggingInp1Monitor2User2DIDName
				RollCallString,
			iqsda02LoggingInp1Monitor2User2DIDStateEnable
				INTEGER,
			iqsda02LoggingInp1Monitor2User2DIDState
				RollCallString,
			iqsda02LoggingInp1Monitor2WSSStateEnable
				INTEGER,
			iqsda02LoggingInp1Monitor2WSSState
				RollCallString,
			iqsda02LoggingInp1Monitor2VIStateEnable
				INTEGER,
			iqsda02LoggingInp1Monitor2VIState
				RollCallString,
			iqsda02LoggingInp1Monitor2WSSEnable
				INTEGER,
			iqsda02LoggingInp1Monitor2WSS
				RollCallString,
			iqsda02LoggingInp1Monitor2VIEnable
				INTEGER,
			iqsda02LoggingInp1Monitor2VI
				RollCallString,
			iqsda02LoggingInp1Monitor2WSSAspectEnable
				INTEGER,
			iqsda02LoggingInp1Monitor2WSSAspect
				RollCallString,
			iqsda02LoggingInp1Monitor2VIAspectEnable
				INTEGER,
			iqsda02LoggingInp1Monitor2VIAspect
				RollCallString,
			iqsda02LoggingInp1AudStateEmbCh1StateEnable
				INTEGER,
			iqsda02LoggingInp1AudStateEmbCh1State
				RollCallString,
			iqsda02LoggingInp1AudStateEmbCh2StateEnable
				INTEGER,
			iqsda02LoggingInp1AudStateEmbCh2State
				RollCallString,
			iqsda02LoggingInp1AudStateEmbCh3StateEnable
				INTEGER,
			iqsda02LoggingInp1AudStateEmbCh3State
				RollCallString,
			iqsda02LoggingInp1AudStateEmbCh4StateEnable
				INTEGER,
			iqsda02LoggingInp1AudStateEmbCh4State
				RollCallString,
			iqsda02LoggingInp1AudStateEmbCh5StateEnable
				INTEGER,
			iqsda02LoggingInp1AudStateEmbCh5State
				RollCallString,
			iqsda02LoggingInp1AudStateEmbCh6StateEnable
				INTEGER,
			iqsda02LoggingInp1AudStateEmbCh6State
				RollCallString,
			iqsda02LoggingInp1AudStateEmbCh7StateEnable
				INTEGER,
			iqsda02LoggingInp1AudStateEmbCh7State
				RollCallString,
			iqsda02LoggingInp1AudStateEmbCh8StateEnable
				INTEGER,
			iqsda02LoggingInp1AudStateEmbCh8State
				RollCallString,
			iqsda02LoggingInp1AudStateEmbCh9StateEnable
				INTEGER,
			iqsda02LoggingInp1AudStateEmbCh9State
				RollCallString,
			iqsda02LoggingInp1AudStateEmbCh10StateEnable
				INTEGER,
			iqsda02LoggingInp1AudStateEmbCh10State
				RollCallString,
			iqsda02LoggingInp1AudStateEmbCh11StateEnable
				INTEGER,
			iqsda02LoggingInp1AudStateEmbCh11State
				RollCallString,
			iqsda02LoggingInp1AudStateEmbCh12StateEnable
				INTEGER,
			iqsda02LoggingInp1AudStateEmbCh12State
				RollCallString,
			iqsda02LoggingInp1AudStateEmbCh13StateEnable
				INTEGER,
			iqsda02LoggingInp1AudStateEmbCh13State
				RollCallString,
			iqsda02LoggingInp1AudStateEmbCh14StateEnable
				INTEGER,
			iqsda02LoggingInp1AudStateEmbCh14State
				RollCallString,
			iqsda02LoggingInp1AudStateEmbCh15StateEnable
				INTEGER,
			iqsda02LoggingInp1AudStateEmbCh15State
				RollCallString,
			iqsda02LoggingInp1AudStateEmbCh16StateEnable
				INTEGER,
			iqsda02LoggingInp1AudStateEmbCh16State
				RollCallString,
			iqsda02LoggingInp1AudTypeEmbCh1TypeEnable
				INTEGER,
			iqsda02LoggingInp1AudTypeEmbCh1Type
				RollCallString,
			iqsda02LoggingInp1AudTypeEmbCh2TypeEnable
				INTEGER,
			iqsda02LoggingInp1AudTypeEmbCh2Type
				RollCallString,
			iqsda02LoggingInp1AudTypeEmbCh3TypeEnable
				INTEGER,
			iqsda02LoggingInp1AudTypeEmbCh3Type
				RollCallString,
			iqsda02LoggingInp1AudTypeEmbCh4TypeEnable
				INTEGER,
			iqsda02LoggingInp1AudTypeEmbCh4Type
				RollCallString,
			iqsda02LoggingInp1AudTypeEmbCh5TypeEnable
				INTEGER,
			iqsda02LoggingInp1AudTypeEmbCh5Type
				RollCallString,
			iqsda02LoggingInp1AudTypeEmbCh6TypeEnable
				INTEGER,
			iqsda02LoggingInp1AudTypeEmbCh6Type
				RollCallString,
			iqsda02LoggingInp1AudTypeEmbCh7TypeEnable
				INTEGER,
			iqsda02LoggingInp1AudTypeEmbCh7Type
				RollCallString,
			iqsda02LoggingInp1AudTypeEmbCh8TypeEnable
				INTEGER,
			iqsda02LoggingInp1AudTypeEmbCh8Type
				RollCallString,
			iqsda02LoggingInp1AudTypeEmbCh9TypeEnable
				INTEGER,
			iqsda02LoggingInp1AudTypeEmbCh9Type
				RollCallString,
			iqsda02LoggingInp1AudTypeEmbCh10TypeEnable
				INTEGER,
			iqsda02LoggingInp1AudTypeEmbCh10Type
				RollCallString,
			iqsda02LoggingInp1AudTypeEmbCh11TypeEnable
				INTEGER,
			iqsda02LoggingInp1AudTypeEmbCh11Type
				RollCallString,
			iqsda02LoggingInp1AudTypeEmbCh12TypeEnable
				INTEGER,
			iqsda02LoggingInp1AudTypeEmbCh12Type
				RollCallString,
			iqsda02LoggingInp1AudTypeEmbCh13TypeEnable
				INTEGER,
			iqsda02LoggingInp1AudTypeEmbCh13Type
				RollCallString,
			iqsda02LoggingInp1AudTypeEmbCh14TypeEnable
				INTEGER,
			iqsda02LoggingInp1AudTypeEmbCh14Type
				RollCallString,
			iqsda02LoggingInp1AudTypeEmbCh15TypeEnable
				INTEGER,
			iqsda02LoggingInp1AudTypeEmbCh15Type
				RollCallString,
			iqsda02LoggingInp1AudTypeEmbCh16TypeEnable
				INTEGER,
			iqsda02LoggingInp1AudTypeEmbCh16Type
				RollCallString,
			iqsda02LoggingInp1DolbyEStatePair1Enable
				INTEGER,
			iqsda02LoggingInp1DolbyEStatePair1State
				RollCallString,
			iqsda02LoggingInp1DolbyEStatePair2Enable
				INTEGER,
			iqsda02LoggingInp1DolbyEStatePair2State
				RollCallString,
			iqsda02LoggingInp1DolbyEStatePair3Enable
				INTEGER,
			iqsda02LoggingInp1DolbyEStatePair3State
				RollCallString,
			iqsda02LoggingInp1DolbyEStatePair4Enable
				INTEGER,
			iqsda02LoggingInp1DolbyEStatePair4State
				RollCallString,
			iqsda02LoggingInp1DolbyEStatePair5Enable
				INTEGER,
			iqsda02LoggingInp1DolbyEStatePair5State
				RollCallString,
			iqsda02LoggingInp1DolbyEStatePair6Enable
				INTEGER,
			iqsda02LoggingInp1DolbyEStatePair6State
				RollCallString,
			iqsda02LoggingInp1DolbyEStatePair7Enable
				INTEGER,
			iqsda02LoggingInp1DolbyEStatePair7State
				RollCallString,
			iqsda02LoggingInp1DolbyEStatePair8Enable
				INTEGER,
			iqsda02LoggingInp1DolbyEStatePair8State
				RollCallString,
			iqsda02LoggingInp1BitDepthEmbCh1BitDepthEnable
				INTEGER,
			iqsda02LoggingInp1BitDepthEmbCh1BitDepth
				RollCallString,
			iqsda02LoggingInp1BitDepthEmbCh2BitDepthEnable
				INTEGER,
			iqsda02LoggingInp1BitDepthEmbCh2BitDepth
				RollCallString,
			iqsda02LoggingInp1BitDepthEmbCh3BitDepthEnable
				INTEGER,
			iqsda02LoggingInp1BitDepthEmbCh3BitDepth
				RollCallString,
			iqsda02LoggingInp1BitDepthEmbCh4BitDepthEnable
				INTEGER,
			iqsda02LoggingInp1BitDepthEmbCh4BitDepth
				RollCallString,
			iqsda02LoggingInp1BitDepthEmbCh5BitDepthEnable
				INTEGER,
			iqsda02LoggingInp1BitDepthEmbCh5BitDepth
				RollCallString,
			iqsda02LoggingInp1BitDepthEmbCh6BitDepthEnable
				INTEGER,
			iqsda02LoggingInp1BitDepthEmbCh6BitDepth
				RollCallString,
			iqsda02LoggingInp1BitDepthEmbCh7BitDepthEnable
				INTEGER,
			iqsda02LoggingInp1BitDepthEmbCh7BitDepth
				RollCallString,
			iqsda02LoggingInp1BitDepthEmbCh8BitDepthEnable
				INTEGER,
			iqsda02LoggingInp1BitDepthEmbCh8BitDepth
				RollCallString,
			iqsda02LoggingInp1BitDepthEmbCh9BitDepthEnable
				INTEGER,
			iqsda02LoggingInp1BitDepthEmbCh9BitDepth
				RollCallString,
			iqsda02LoggingInp1BitDepthEmbCh10BitDepthEnable
				INTEGER,
			iqsda02LoggingInp1BitDepthEmbCh10BitDepth
				RollCallString,
			iqsda02LoggingInp1BitDepthEmbCh11BitDepthEnable
				INTEGER,
			iqsda02LoggingInp1BitDepthEmbCh11BitDepth
				RollCallString,
			iqsda02LoggingInp1BitDepthEmbCh12BitDepthEnable
				INTEGER,
			iqsda02LoggingInp1BitDepthEmbCh12BitDepth
				RollCallString,
			iqsda02LoggingInp1BitDepthEmbCh13BitDepthEnable
				INTEGER,
			iqsda02LoggingInp1BitDepthEmbCh13BitDepth
				RollCallString,
			iqsda02LoggingInp1BitDepthEmbCh14BitDepthEnable
				INTEGER,
			iqsda02LoggingInp1BitDepthEmbCh14BitDepth
				RollCallString,
			iqsda02LoggingInp1BitDepthEmbCh15BitDepthEnable
				INTEGER,
			iqsda02LoggingInp1BitDepthEmbCh15BitDepth
				RollCallString,
			iqsda02LoggingInp1BitDepthEmbCh16BitDepthEnable
				INTEGER,
			iqsda02LoggingInp1BitDepthEmbCh16BitDepth
				RollCallString,
			iqsda02LoggingInp1LevelEmbCh1LevelEnable
				INTEGER,
			iqsda02LoggingInp1LevelEmbCh1Level
				RollCallString,
			iqsda02LoggingInp1LevelEmbCh2LevelEnable
				INTEGER,
			iqsda02LoggingInp1LevelEmbCh2Level
				RollCallString,
			iqsda02LoggingInp1LevelEmbCh3LevelEnable
				INTEGER,
			iqsda02LoggingInp1LevelEmbCh3Level
				RollCallString,
			iqsda02LoggingInp1LevelEmbCh4LevelEnable
				INTEGER,
			iqsda02LoggingInp1LevelEmbCh4Level
				RollCallString,
			iqsda02LoggingInp1LevelEmbCh5LevelEnable
				INTEGER,
			iqsda02LoggingInp1LevelEmbCh5Level
				RollCallString,
			iqsda02LoggingInp1LevelEmbCh6LevelEnable
				INTEGER,
			iqsda02LoggingInp1LevelEmbCh6Level
				RollCallString,
			iqsda02LoggingInp1LevelEmbCh7LevelEnable
				INTEGER,
			iqsda02LoggingInp1LevelEmbCh7Level
				RollCallString,
			iqsda02LoggingInp1LevelEmbCh8LevelEnable
				INTEGER,
			iqsda02LoggingInp1LevelEmbCh8Level
				RollCallString,
			iqsda02LoggingInp1LevelEmbCh9LevelEnable
				INTEGER,
			iqsda02LoggingInp1LevelEmbCh9Level
				RollCallString,
			iqsda02LoggingInp1LevelEmbCh10LevelEnable
				INTEGER,
			iqsda02LoggingInp1LevelEmbCh10Level
				RollCallString,
			iqsda02LoggingInp1LevelEmbCh11LevelEnable
				INTEGER,
			iqsda02LoggingInp1LevelEmbCh11Level
				RollCallString,
			iqsda02LoggingInp1LevelEmbCh12LevelEnable
				INTEGER,
			iqsda02LoggingInp1LevelEmbCh12Level
				RollCallString,
			iqsda02LoggingInp1LevelEmbCh13LevelEnable
				INTEGER,
			iqsda02LoggingInp1LevelEmbCh13Level
				RollCallString,
			iqsda02LoggingInp1LevelEmbCh14LevelEnable
				INTEGER,
			iqsda02LoggingInp1LevelEmbCh14Level
				RollCallString,
			iqsda02LoggingInp1LevelEmbCh15LevelEnable
				INTEGER,
			iqsda02LoggingInp1LevelEmbCh15Level
				RollCallString,
			iqsda02LoggingInp1LevelEmbCh16LevelEnable
				INTEGER,
			iqsda02LoggingInp1LevelEmbCh16Level
				RollCallString,
			iqsda02LoggingInp1ClippingEmbCh1LevelEnable
				INTEGER,
			iqsda02LoggingInp1ClippingEmbCh1Level
				RollCallString,
			iqsda02LoggingInp1ClippingEmbCh2LevelEnable
				INTEGER,
			iqsda02LoggingInp1ClippingEmbCh2Level
				RollCallString,
			iqsda02LoggingInp1ClippingEmbCh3LevelEnable
				INTEGER,
			iqsda02LoggingInp1ClippingEmbCh3Level
				RollCallString,
			iqsda02LoggingInp1ClippingEmbCh4LevelEnable
				INTEGER,
			iqsda02LoggingInp1ClippingEmbCh4Level
				RollCallString,
			iqsda02LoggingInp1ClippingEmbCh5LevelEnable
				INTEGER,
			iqsda02LoggingInp1ClippingEmbCh5Level
				RollCallString,
			iqsda02LoggingInp1ClippingEmbCh6LevelEnable
				INTEGER,
			iqsda02LoggingInp1ClippingEmbCh6Level
				RollCallString,
			iqsda02LoggingInp1ClippingEmbCh7LevelEnable
				INTEGER,
			iqsda02LoggingInp1ClippingEmbCh7Level
				RollCallString,
			iqsda02LoggingInp1ClippingEmbCh8LevelEnable
				INTEGER,
			iqsda02LoggingInp1ClippingEmbCh8Level
				RollCallString,
			iqsda02LoggingInp1ClippingEmbCh9LevelEnable
				INTEGER,
			iqsda02LoggingInp1ClippingEmbCh9Level
				RollCallString,
			iqsda02LoggingInp1ClippingEmbCh10LevelEnable
				INTEGER,
			iqsda02LoggingInp1ClippingEmbCh10Level
				RollCallString,
			iqsda02LoggingInp1ClippingEmbCh11LevelEnable
				INTEGER,
			iqsda02LoggingInp1ClippingEmbCh11Level
				RollCallString,
			iqsda02LoggingInp1ClippingEmbCh12LevelEnable
				INTEGER,
			iqsda02LoggingInp1ClippingEmbCh12Level
				RollCallString,
			iqsda02LoggingInp1ClippingEmbCh13LevelEnable
				INTEGER,
			iqsda02LoggingInp1ClippingEmbCh13Level
				RollCallString,
			iqsda02LoggingInp1ClippingEmbCh14LevelEnable
				INTEGER,
			iqsda02LoggingInp1ClippingEmbCh14Level
				RollCallString,
			iqsda02LoggingInp1ClippingEmbCh15LevelEnable
				INTEGER,
			iqsda02LoggingInp1ClippingEmbCh15Level
				RollCallString,
			iqsda02LoggingInp1ClippingEmbCh16LevelEnable
				INTEGER,
			iqsda02LoggingInp1ClippingEmbCh16Level
				RollCallString,
			iqsda02LoggingInp1LikenessDetector1ChansEnable
				INTEGER,
			iqsda02LoggingInp1LikenessDetector1Chans
				RollCallString,
			iqsda02LoggingInp1LikenessDetector1StateEnable
				INTEGER,
			iqsda02LoggingInp1LikenessDetector1State
				RollCallString,
			iqsda02LoggingInp1LikenessDetector2ChansEnable
				INTEGER,
			iqsda02LoggingInp1LikenessDetector2Chans
				RollCallString,
			iqsda02LoggingInp1LikenessDetector2StateEnable
				INTEGER,
			iqsda02LoggingInp1LikenessDetector2State
				RollCallString,
			iqsda02LoggingInp1LikenessDetector3ChansEnable
				INTEGER,
			iqsda02LoggingInp1LikenessDetector3Chans
				RollCallString,
			iqsda02LoggingInp1LikenessDetector3StateEnable
				INTEGER,
			iqsda02LoggingInp1LikenessDetector3State
				RollCallString,
			iqsda02LoggingInp1LikenessDetector4ChansEnable
				INTEGER,
			iqsda02LoggingInp1LikenessDetector4Chans
				RollCallString,
			iqsda02LoggingInp1LikenessDetector4StateEnable
				INTEGER,
			iqsda02LoggingInp1LikenessDetector4State
				RollCallString,
			iqsda02LoggingOut1UMIDUMIDStateEnable
				INTEGER,
			iqsda02LoggingOut1UMIDUMIDState
				RollCallString,
			iqsda02LoggingOut1UMIDOutputUMIDEnable
				INTEGER,
			iqsda02LoggingOut1UMIDOutputUMID1_8
				RollCallString,
			iqsda02LoggingOut1UMIDOutputUMID9_16
				RollCallString,
			iqsda02LoggingOut1UMIDOutputUMID17_24
				RollCallString,
			iqsda02LoggingOut1UMIDOutputUMID25_32
				RollCallString,
			iqsda02LoggingInp1UMIDUMIDStateEnable
				INTEGER,
			iqsda02LoggingInp1UMIDUMIDState
				RollCallString,
			iqsda02LoggingInp1UMIDUMIDCurrentEnable
				INTEGER,
			iqsda02LoggingInp1UMIDUMIDCurrent1_8
				RollCallString,
			iqsda02LoggingInp1UMIDUMIDCurrent9_16
				RollCallString,
			iqsda02LoggingInp1UMIDUMIDCurrent17_24
				RollCallString,
			iqsda02LoggingInp1UMIDUMIDCurrent25_32
				RollCallString,
			iqsda02LoggingInp1UMIDUMIDPreviousEnable
				INTEGER,
			iqsda02LoggingInp1UMIDUMIDPrev1_8
				RollCallString,
			iqsda02LoggingInp1UMIDUMIDPrev9_16
				RollCallString,
			iqsda02LoggingInp1UMIDUMIDPrev17_24
				RollCallString,
			iqsda02LoggingInp1UMIDUMIDPrev25_32
				RollCallString,
			iqsda02LoggingInp1UMIDUMIDPreviousCountEnable
				INTEGER,
			iqsda02LoggingInp1UMIDUMIDPrevCount
				RollCallString,
			iqsda02LoggingOut1PIDPIDStateEnable
				INTEGER,
			iqsda02LoggingOut1PIDPIDState
				RollCallString,
			iqsda02LoggingOut1PIDPIDHouseIDEnable
				INTEGER,
			iqsda02LoggingOut1PIDPIDHouseID
				RollCallString,
			iqsda02LoggingOut1PIDPIDTitleEnable
				INTEGER,
			iqsda02LoggingOut1PIDPIDTitle
				RollCallString,
			iqsda02LoggingOut1PIDSegmentNumberEnable
				INTEGER,
			iqsda02LoggingOut1PIDSegmentNumber
				RollCallString,
			iqsda02LoggingOut1PIDDurationEnable
				INTEGER,
			iqsda02LoggingOut1PIDDuration
				RollCallString,
			iqsda02LoggingOut1PIDFrameRateEnable
				INTEGER,
			iqsda02LoggingOut1PIDFrameRate
				RollCallString,
			iqsda02LoggingInp1PIDPIDStateEnable
				INTEGER,
			iqsda02LoggingInp1PIDPIDState
				RollCallString,
			iqsda02LoggingInp1PIDPIDHouseIDEnable
				INTEGER,
			iqsda02LoggingInp1PIDPIDHouseID
				RollCallString,
			iqsda02LoggingInp1PIDPIDTitleEnable
				INTEGER,
			iqsda02LoggingInp1PIDPIDTitle
				RollCallString,
			iqsda02LoggingInp1PIDSegmentNumberEnable
				INTEGER,
			iqsda02LoggingInp1PIDSegmentNumber
				RollCallString,
			iqsda02LoggingInp1PIDDurationEnable
				INTEGER,
			iqsda02LoggingInp1PIDDuration
				RollCallString,
			iqsda02LoggingInp1PIDFrameRateEnable
				INTEGER,
			iqsda02LoggingInp1PIDFrameRate
				RollCallString,
			iqsda02LoggingInp1PIDPreviousHouseIDEnable
				INTEGER,
			iqsda02LoggingInp1PIDPreviousHouseID
				RollCallString,
			iqsda02LoggingInp1PIDPreviousTitleEnable
				INTEGER,
			iqsda02LoggingInp1PIDPreviousTitle
				RollCallString,
			iqsda02LoggingInp1PIDPreviousSegNumEnable
				INTEGER,
			iqsda02LoggingInp1PIDPreviousSegNum
				RollCallString,
			iqsda02LoggingInp1PIDPreviousDurationEnable
				INTEGER,
			iqsda02LoggingInp1PIDPreviousDuration
				RollCallString,
			iqsda02LoggingInp1PIDPreviousFrameRateEnable
				INTEGER,
			iqsda02LoggingInp1PIDPreviousFrameRate
				RollCallString,
			iqsda02LoggingInp1PIDPreviousCountEnable
				INTEGER,
			iqsda02LoggingInp1PIDPreviousCount
				RollCallString,
			iqsda02RollcallRollTrackDisableAll
				INTEGER,
			iqsda02RollcallRollTrackIndex
				INTEGER,
			iqsda02RollcallRollTrackSource
				INTEGER,
			iqsda02RollcallRollTrackAddress
				RollCallString,
			iqsda02RollcallRollTrackCommand
				RollCallString,
			iqsda02RollcallRollTrackStatus
				RollCallString,
			iqsda02RollcallRollTrackSending
				RollCallString,
			iqsda02SetupProduct
				RollCallString,
			iqsda02SetupProductRelease
				RollCallString,
			iqsda02SetupProductBuild
				RollCallString,
			iqsda02SetupProductKOS
				RollCallString,
			iqsda02SetupProductSerial
				RollCallString,
			iqsda02SetupProductFirmware
				RollCallString,
			iqsda02SetupProductPCB
				RollCallString,
			iqsda02SetupProductFactoryDefault
				INTEGER,
			iqsda02SetupProductRestart
				INTEGER,
			iqsda02SetupInput1Name
				RollCallString
		}

	iqsda02SlotIndex OBJECT-TYPE
		SYNTAX		Unsigned32
		MAX-ACCESS		not-accessible
		STATUS			current
		DESCRIPTION
				"The unique Index value for each slot.  Its value
					ranges between 1 and the value of slotNumber."
		::= { iqsda02CmdEntry 0 }


	iqsda02HyperionBlackishBlackBlackishLevel OBJECT-TYPE
		SYNTAX		RollCallString
		MAX-ACCESS		read-only
		STATUS			current
		DESCRIPTION
				"TYPE: - Display
				 PAGE: - Blackish/Black
					Blackish Level  cmdID= 1241  format=   "
		::= { iqsda02CmdEntry 1241 }


	iqsda02HyperionBlackishBlackMinLevelThres OBJECT-TYPE
		SYNTAX		INTEGER
		MAX-ACCESS		read-write
		STATUS			current
		DESCRIPTION
				"TYPE: - Number
				 PAGE: - Blackish/Black
					Min Level Thres  cmdID= 1226  min= 0  max= 100  step= 1  format= %0.0f  div_scale= 1
					Min = 0  Max = 100  Step = 1 "
		::= { iqsda02CmdEntry 1226 }


	iqsda02TemporalControlBlackishEnableAlarm OBJECT-TYPE
		SYNTAX		INTEGER { disable(0), enable(1) }
		MAX-ACCESS		read-write
		STATUS			current
		DESCRIPTION
				"TYPE: - Checkbox
				 PAGE: - Blackish/Black
					Enable Alarm  cmdID= 1236 "
		::= { iqsda02CmdEntry 1236 }


	iqsda02TemporalControlBlackishAlarm OBJECT-TYPE
		SYNTAX		RollCallString
		MAX-ACCESS		read-only
		STATUS			current
		DESCRIPTION
				"TYPE: - Display
				 PAGE: - Blackish/Black
					Alarm  cmdID= 1240  format=   "
		::= { iqsda02CmdEntry 1240 }


	iqsda02TemporalControlBlackishFailCount OBJECT-TYPE
		SYNTAX		INTEGER
		MAX-ACCESS		read-write
		STATUS			current
		DESCRIPTION
				"TYPE: - Number
				 PAGE: - Blackish/Black
					Fail Count  cmdID= 1237  min= 0  max= 16000  step= 1  format= %0.0f  div_scale= 1
					Min = 0  Max = 16000  Step = 1 "
		::= { iqsda02CmdEntry 1237 }


	iqsda02TemporalControlBlackishWarningCount OBJECT-TYPE
		SYNTAX		INTEGER
		MAX-ACCESS		read-write
		STATUS			current
		DESCRIPTION
				"TYPE: - Number
				 PAGE: - Blackish/Black
					Warning Count  cmdID= 1238  min= 0  max= 16000  step= 1  format= %0.0f  div_scale= 1
					Min = 0  Max = 16000  Step = 1 "
		::= { iqsda02CmdEntry 1238 }


	iqsda02TemporalControlBlackishFailHoldCount OBJECT-TYPE
		SYNTAX		INTEGER
		MAX-ACCESS		read-write
		STATUS			current
		DESCRIPTION
				"TYPE: - Number
				 PAGE: - Blackish/Black
					Fail Hold Count  cmdID= 1239  min= 0  max= 16000  step= 1  format= %0.0f  div_scale= 1
					Min = 0  Max = 16000  Step = 1 "
		::= { iqsda02CmdEntry 1239 }


	iqsda02TemporalControlBlackishResetAlarm OBJECT-TYPE
		SYNTAX		INTEGER { noAction(0),val_Reset_Alarm(1) }
		MAX-ACCESS		read-write
		STATUS			current
		DESCRIPTION
				"TYPE: - Button
				 PAGE: - Blackish/Black
					Reset Alarm  cmdID= 1244  value= 1  "
		::= { iqsda02CmdEntry 1244 }


	iqsda02TemporalControlBlackEnableAlarm OBJECT-TYPE
		SYNTAX		INTEGER { disable(0), enable(1) }
		MAX-ACCESS		read-write
		STATUS			current
		DESCRIPTION
				"TYPE: - Checkbox
				 PAGE: - Blackish/Black
					Enable Alarm  cmdID= 1231 "
		::= { iqsda02CmdEntry 1231 }


	iqsda02TemporalControlBlackAlarm OBJECT-TYPE
		SYNTAX		RollCallString
		MAX-ACCESS		read-only
		STATUS			current
		DESCRIPTION
				"TYPE: - Display
				 PAGE: - Blackish/Black
					Alarm  cmdID= 1235  format=   "
		::= { iqsda02CmdEntry 1235 }


	iqsda02TemporalControlBlackFailCount OBJECT-TYPE
		SYNTAX		INTEGER
		MAX-ACCESS		read-write
		STATUS			current
		DESCRIPTION
				"TYPE: - Number
				 PAGE: - Blackish/Black
					Fail Count  cmdID= 1232  min= 0  max= 16000  step= 1  format= %0.0f  div_scale= 1
					Min = 0  Max = 16000  Step = 1 "
		::= { iqsda02CmdEntry 1232 }


	iqsda02TemporalControlBlackWarningCount OBJECT-TYPE
		SYNTAX		INTEGER
		MAX-ACCESS		read-write
		STATUS			current
		DESCRIPTION
				"TYPE: - Number
				 PAGE: - Blackish/Black
					Warning Count  cmdID= 1233  min= 0  max= 16000  step= 1  format= %0.0f  div_scale= 1
					Min = 0  Max = 16000  Step = 1 "
		::= { iqsda02CmdEntry 1233 }


	iqsda02TemporalControlBlackFailHoldCount OBJECT-TYPE
		SYNTAX		INTEGER
		MAX-ACCESS		read-write
		STATUS			current
		DESCRIPTION
				"TYPE: - Number
				 PAGE: - Blackish/Black
					Fail Hold Count  cmdID= 1234  min= 0  max= 16000  step= 1  format= %0.0f  div_scale= 1
					Min = 0  Max = 16000  Step = 1 "
		::= { iqsda02CmdEntry 1234 }


	iqsda02TemporalControlBlackResetAlarm OBJECT-TYPE
		SYNTAX		INTEGER { noAction(0),val_Reset_Alarm(1) }
		MAX-ACCESS		read-write
		STATUS			current
		DESCRIPTION
				"TYPE: - Button
				 PAGE: - Blackish/Black
					Reset Alarm  cmdID= 1243  value= 1  "
		::= { iqsda02CmdEntry 1243 }


	iqsda02VideoMonitorAveragePictureLvlDisplayTimeout OBJECT-TYPE
		SYNTAX		RollCallString
		MAX-ACCESS		read-only
		STATUS			current
		DESCRIPTION
				"TYPE: - Display
				 PAGE: - Blackish/Black
					Display Timeout  cmdID= 1290  format=   "
		::= { iqsda02CmdEntry 1290 }


	iqsda02VideoMonitorAveragePictureLvlHyperionDisplayEn OBJECT-TYPE
		SYNTAX		INTEGER {
							val_Display_Off(0),
							val_Blackish_Black(1),
							val_Stillish_Freeze(2),
							val_Video_Monitor(3),
							val_Closed_Caption(4),
							val_Timecode(5),
							val_User_Anc_Det(6),
							val_Audio_Level_Det(7),
							val_Audio_Level_Ind(8),
							val_Audio_Likeness_Det(9),
							val_UMID(10),
							val_PID(11)
							}
		MAX-ACCESS		read-write
		STATUS			current
		DESCRIPTION
				"TYPE: - RadiobuttonList
				 PAGE: - Blackish/Black
					Hyperion Display En  cmdID= 1221
					Display Off  value= 0
					Blackish/Black  value= 1
					Hyperion Disp En  cmdID= 1221
					Display Off  value= 0
					Blackish/Black  value= 1
					Stillish/Freeze  value= 2
					Video Monitor  value= 3
					Closed Caption  value= 4
					Timecode  value= 5
					User Anc Det.  value= 6
					Audio Level Det  value= 7
					Audio Level Ind  value= 8
					Audio Likeness Det  value= 9
					UMID  value= 10
					PID  value= 11  "
		::= { iqsda02CmdEntry 1221 }


	iqsda02HyperionFreezeStillishStillishLevel OBJECT-TYPE
		SYNTAX		RollCallString
		MAX-ACCESS		read-only
		STATUS			current
		DESCRIPTION
				"TYPE: - Display
				 PAGE: - Freeze/Stillish
					Stillish Level  cmdID= 1200  format=   "
		::= { iqsda02CmdEntry 1200 }


	iqsda02HyperionFreezeStillishMaxLevelThres OBJECT-TYPE
		SYNTAX		INTEGER
		MAX-ACCESS		read-write
		STATUS			current
		DESCRIPTION
				"TYPE: - Number
				 PAGE: - Freeze/Stillish
					Max Level Thres  cmdID= 1203  min= 0  max= 100  step= 1  format= %0.0f  div_scale= 1
					Min = 0  Max = 100  Step = 1 "
		::= { iqsda02CmdEntry 1203 }


	iqsda02TemporalControlStillishEnableAlarm OBJECT-TYPE
		SYNTAX		INTEGER { disable(0), enable(1) }
		MAX-ACCESS		read-write
		STATUS			current
		DESCRIPTION
				"TYPE: - Checkbox
				 PAGE: - Freeze/Stillish
					Enable Alarm  cmdID= 1214 "
		::= { iqsda02CmdEntry 1214 }


	iqsda02TemporalControlStillishAlarm OBJECT-TYPE
		SYNTAX		RollCallString
		MAX-ACCESS		read-only
		STATUS			current
		DESCRIPTION
				"TYPE: - Display
				 PAGE: - Freeze/Stillish
					Alarm  cmdID= 1218  format=   "
		::= { iqsda02CmdEntry 1218 }


	iqsda02TemporalControlStillishFailCount OBJECT-TYPE
		SYNTAX		INTEGER
		MAX-ACCESS		read-write
		STATUS			current
		DESCRIPTION
				"TYPE: - Number
				 PAGE: - Freeze/Stillish
					Fail Count  cmdID= 1215  min= 0  max= 16000  step= 1  format= %0.0f  div_scale= 1
					Min = 0  Max = 16000  Step = 1 "
		::= { iqsda02CmdEntry 1215 }


	iqsda02TemporalControlStillishWarningCount OBJECT-TYPE
		SYNTAX		INTEGER
		MAX-ACCESS		read-write
		STATUS			current
		DESCRIPTION
				"TYPE: - Number
				 PAGE: - Freeze/Stillish
					Warning Count  cmdID= 1216  min= 0  max= 16000  step= 1  format= %0.0f  div_scale= 1
					Min = 0  Max = 16000  Step = 1 "
		::= { iqsda02CmdEntry 1216 }


	iqsda02TemporalControlStillishFailHoldCount OBJECT-TYPE
		SYNTAX		INTEGER
		MAX-ACCESS		read-write
		STATUS			current
		DESCRIPTION
				"TYPE: - Number
				 PAGE: - Freeze/Stillish
					Fail Hold Count  cmdID= 1217  min= 0  max= 16000  step= 1  format= %0.0f  div_scale= 1
					Min = 0  Max = 16000  Step = 1 "
		::= { iqsda02CmdEntry 1217 }


	iqsda02TemporalControlStillishResetAlarm OBJECT-TYPE
		SYNTAX		INTEGER { noAction(0),val_Reset_Alarm(1) }
		MAX-ACCESS		read-write
		STATUS			current
		DESCRIPTION
				"TYPE: - Button
				 PAGE: - Freeze/Stillish
					Reset Alarm  cmdID= 1219  value= 1  "
		::= { iqsda02CmdEntry 1219 }


	iqsda02TemporalControlFreezeEnableAlarm OBJECT-TYPE
		SYNTAX		INTEGER { disable(0), enable(1) }
		MAX-ACCESS		read-write
		STATUS			current
		DESCRIPTION
				"TYPE: - Checkbox
				 PAGE: - Freeze/Stillish
					Enable Alarm  cmdID= 1655 "
		::= { iqsda02CmdEntry 1655 }

	iqsda02TemporalControlFreezeTolerance OBJECT-TYPE
		SYNTAX		INTEGER
		MAX-ACCESS		read-write
		STATUS			current
		DESCRIPTION
				"TYPE: - Number
				 PAGE: - Freeze/Stillish
					Freeze Tolerance (number of frames)  cmdID= 1656  min= 0  max= 10  step= 1  format= %0.0f  div_scale= 1
					Min = 0  Max = 10  Step = 1 "
		::= { iqhip00CmdEntry 1656 }


	iqsda02TemporalControlFreezeAlarm OBJECT-TYPE
		SYNTAX		RollCallString
		MAX-ACCESS		read-only
		STATUS			current
		DESCRIPTION
				"TYPE: - Display
				 PAGE: - Freeze/Stillish
					Alarm  cmdID= 1653  format=   "
		::= { iqsda02CmdEntry 1653 }


	iqsda02TemporalControlFreezeFailCount OBJECT-TYPE
		SYNTAX		INTEGER
		MAX-ACCESS		read-write
		STATUS			current
		DESCRIPTION
				"TYPE: - Number
				 PAGE: - Freeze/Stillish
					Fail Count  cmdID= 1650  min= 2  max= 16000  step= 1  format= %0.0f  div_scale= 1
					Min = 2  Max = 16000  Step = 1 "
		::= { iqsda02CmdEntry 1650 }


	iqsda02TemporalControlFreezeWarningCount OBJECT-TYPE
		SYNTAX		INTEGER
		MAX-ACCESS		read-write
		STATUS			current
		DESCRIPTION
				"TYPE: - Number
				 PAGE: - Freeze/Stillish
					Warning Count  cmdID= 1651  min= 2  max= 16000  step= 1  format= %0.0f  div_scale= 1
					Min = 2  Max = 16000  Step = 1 "
		::= { iqsda02CmdEntry 1651 }


	iqsda02TemporalControlFreezeFailHoldCount OBJECT-TYPE
		SYNTAX		INTEGER
		MAX-ACCESS		read-write
		STATUS			current
		DESCRIPTION
				"TYPE: - Number
				 PAGE: - Freeze/Stillish
					Fail Hold Count  cmdID= 1652  min= 1  max= 16000  step= 1  format= %0.0f  div_scale= 1
					Min = 1  Max = 16000  Step = 1 "
		::= { iqsda02CmdEntry 1652 }


	iqsda02TemporalControlFreezeResetAlarm OBJECT-TYPE
		SYNTAX		INTEGER { noAction(0),val_Reset_Alarm(1) }
		MAX-ACCESS		read-write
		STATUS			current
		DESCRIPTION
				"TYPE: - Button
				 PAGE: - Freeze/Stillish
					Reset Alarm  cmdID= 1654  value= 1  "
		::= { iqsda02CmdEntry 1654 }


	iqsda02VideoMonitorAveragePictureLvlEnableAlarm OBJECT-TYPE
		SYNTAX		INTEGER { disable(0), enable(1) }
		MAX-ACCESS		read-write
		STATUS			current
		DESCRIPTION
				"TYPE: - Checkbox
				 PAGE: - Video Monitor
					Enable Alarm  cmdID= 1326 "
		::= { iqsda02CmdEntry 1326 }


	iqsda02VideoMonitorAveragePictureLvl OBJECT-TYPE
		SYNTAX		RollCallString
		MAX-ACCESS		read-only
		STATUS			current
		DESCRIPTION
				"TYPE: - Display
				 PAGE: - Video Monitor
					Average Picture Lvl  cmdID= 1320  format=   "
		::= { iqsda02CmdEntry 1320 }


	iqsda02VideoMonitorAveragePictureLvlMaxLoggingThres OBJECT-TYPE
		SYNTAX		INTEGER
		MAX-ACCESS		read-write
		STATUS			current
		DESCRIPTION
				"TYPE: - Number
				 PAGE: - Video Monitor
					Max Logging Thres  cmdID= 1324  min= 0  max= 100  step= 1  format= %0.0f  div_scale= 1
					Min = 0  Max = 100  Step = 1 "
		::= { iqsda02CmdEntry 1324 }


	iqsda02VideoMonitorAveragePictureLvlMinLoggingThres OBJECT-TYPE
		SYNTAX		INTEGER
		MAX-ACCESS		read-write
		STATUS			current
		DESCRIPTION
				"TYPE: - Number
				 PAGE: - Video Monitor
					Min Logging Thres  cmdID= 1323  min= 0  max= 100  step= 1  format= %0.0f  div_scale= 1
					Min = 0  Max = 100  Step = 1 "
		::= { iqsda02CmdEntry 1323 }


	iqsda02LumaVideoLevelOverloadStatus OBJECT-TYPE
		SYNTAX		RollCallString
		MAX-ACCESS		read-only
		STATUS			current
		DESCRIPTION
				"TYPE: - Display
				 PAGE: - Video Monitor
					Status  cmdID= 1343  format=   "
		::= { iqsda02CmdEntry 1343 }


	iqsda02LumaVideoLevelOverloadMaximumReading OBJECT-TYPE
		SYNTAX		RollCallString
		MAX-ACCESS		read-only
		STATUS			current
		DESCRIPTION
				"TYPE: - Display
				 PAGE: - Video Monitor
					Maximum Reading  cmdID= 1352  format=   "
		::= { iqsda02CmdEntry 1352 }


	iqsda02LumaVideoLevelOverloadEnableAlarm OBJECT-TYPE
		SYNTAX		INTEGER { disable(0), enable(1) }
		MAX-ACCESS		read-write
		STATUS			current
		DESCRIPTION
				"TYPE: - Checkbox
				 PAGE: - Video Monitor
					Enable Alarm   cmdID= 1349 "
		::= { iqsda02CmdEntry 1349 }


	iqsda02LumaVideoLevelOverloadOverloadThreshold OBJECT-TYPE
		SYNTAX		INTEGER
		MAX-ACCESS		read-write
		STATUS			current
		DESCRIPTION
				"TYPE: - Number
				 PAGE: - Video Monitor
					Overload Threshold  cmdID= 1341  min= 0  max= 1023  step= 1  format= %0.0f  div_scale= 1
					Min = 0  Max = 1023  Step = 1 "
		::= { iqsda02CmdEntry 1341 }


	iqsda02LumaVideoLevelOverloadAvePicAboveThres OBJECT-TYPE
		SYNTAX		INTEGER
		MAX-ACCESS		read-write
		STATUS			current
		DESCRIPTION
				"TYPE: - Number
				 PAGE: - Video Monitor
					Ave Pic Above Thres  cmdID= 1356  min= 0  max= 99  step= 1  format= %0.0f  div_scale= 1
					Min = 0  Max = 99  Step = 1 "
		::= { iqsda02CmdEntry 1356 }


	iqsda02LumaVideoLevelUnderloadStatus OBJECT-TYPE
		SYNTAX		RollCallString
		MAX-ACCESS		read-only
		STATUS			current
		DESCRIPTION
				"TYPE: - Display
				 PAGE: - Video Monitor
					Status  cmdID= 1347  format=   "
		::= { iqsda02CmdEntry 1347 }


	iqsda02LumaVideoLevelUnderloadMinimumReading OBJECT-TYPE
		SYNTAX		RollCallString
		MAX-ACCESS		read-only
		STATUS			current
		DESCRIPTION
				"TYPE: - Display
				 PAGE: - Video Monitor
					Minimum Reading  cmdID= 1353  format=   "
		::= { iqsda02CmdEntry 1353 }


	iqsda02LumaVideoLevelUnderloadEnableAlarm OBJECT-TYPE
		SYNTAX		INTEGER { disable(0), enable(1) }
		MAX-ACCESS		read-write
		STATUS			current
		DESCRIPTION
				"TYPE: - Checkbox
				 PAGE: - Video Monitor
					Enable Alarm  cmdID= 1348 "
		::= { iqsda02CmdEntry 1348 }


	iqsda02LumaVideoLevelUnderloadUnderloadThreshold OBJECT-TYPE
		SYNTAX		INTEGER
		MAX-ACCESS		read-write
		STATUS			current
		DESCRIPTION
				"TYPE: - Number
				 PAGE: - Video Monitor
					Underload Threshold  cmdID= 1345  min= 0  max= 1023  step= 1  format= %0.0f  div_scale= 1
					Min = 0  Max = 1023  Step = 1 "
		::= { iqsda02CmdEntry 1345 }


	iqsda02LumaVideoLevelUnderloadAvePicBelowThres OBJECT-TYPE
		SYNTAX		INTEGER
		MAX-ACCESS		read-write
		STATUS			current
		DESCRIPTION
				"TYPE: - Number
				 PAGE: - Video Monitor
					Ave Pic Below Thres  cmdID= 1357  min= 0  max= 99  step= 1  format= %0.0f  div_scale= 1
					Min = 0  Max = 99  Step = 1 "
		::= { iqsda02CmdEntry 1357 }


	iqsda02ChromaVideoLevelOverloadStatus OBJECT-TYPE
		SYNTAX		RollCallString
		MAX-ACCESS		read-only
		STATUS			current
		DESCRIPTION
				"TYPE: - Display
				 PAGE: - Video Monitor
					Status  cmdID= 1342  format=   "
		::= { iqsda02CmdEntry 1342 }


	iqsda02ChromaVideoLevelOverloadMaximumReading OBJECT-TYPE
		SYNTAX		RollCallString
		MAX-ACCESS		read-only
		STATUS			current
		DESCRIPTION
				"TYPE: - Display
				 PAGE: - Video Monitor
					Maximum Reading  cmdID= 1354  format=   "
		::= { iqsda02CmdEntry 1354 }


	iqsda02ChromaVideoLevelOverloadEnableAlarm OBJECT-TYPE
		SYNTAX		INTEGER { disable(0), enable(1) }
		MAX-ACCESS		read-write
		STATUS			current
		DESCRIPTION
				"TYPE: - Checkbox
				 PAGE: - Video Monitor
					Enable Alarm  cmdID= 1351 "
		::= { iqsda02CmdEntry 1351 }


	iqsda02ChromaVideoLevelOverloadOverloadThreshold OBJECT-TYPE
		SYNTAX		INTEGER
		MAX-ACCESS		read-write
		STATUS			current
		DESCRIPTION
				"TYPE: - Number
				 PAGE: - Video Monitor
					Overload Threshold  cmdID= 1340  min= 0  max= 1023  step= 1  format= %0.0f  div_scale= 1
					Min = 0  Max = 1023  Step = 1 "
		::= { iqsda02CmdEntry 1340 }


	iqsda02ChromaVideoLevelOverloadAvePicAboveThres OBJECT-TYPE
		SYNTAX		INTEGER
		MAX-ACCESS		read-write
		STATUS			current
		DESCRIPTION
				"TYPE: - Number
				 PAGE: - Video Monitor
					Ave Pic Above Thres  cmdID= 1358  min= 0  max= 99  step= 1  format= %0.0f  div_scale= 1
					Min = 0  Max = 99  Step = 1 "
		::= { iqsda02CmdEntry 1358 }


	iqsda02ChromaVideoLevelUnderloadStatus OBJECT-TYPE
		SYNTAX		RollCallString
		MAX-ACCESS		read-only
		STATUS			current
		DESCRIPTION
				"TYPE: - Display
				 PAGE: - Video Monitor
					Status  cmdID= 1346  format=   "
		::= { iqsda02CmdEntry 1346 }


	iqsda02ChromaVideoLevelUnderloadMinimumReading OBJECT-TYPE
		SYNTAX		RollCallString
		MAX-ACCESS		read-only
		STATUS			current
		DESCRIPTION
				"TYPE: - Display
				 PAGE: - Video Monitor
					Minimum Reading  cmdID= 1355  format=   "
		::= { iqsda02CmdEntry 1355 }


	iqsda02ChromaVideoLevelUnderloadEnableAlarm OBJECT-TYPE
		SYNTAX		INTEGER { disable(0), enable(1) }
		MAX-ACCESS		read-write
		STATUS			current
		DESCRIPTION
				"TYPE: - Checkbox
				 PAGE: - Video Monitor
					Enable Alarm  cmdID= 1350 "
		::= { iqsda02CmdEntry 1350 }


	iqsda02ChromaVideoLevelUnderloadUnderloadThreshold OBJECT-TYPE
		SYNTAX		INTEGER
		MAX-ACCESS		read-write
		STATUS			current
		DESCRIPTION
				"TYPE: - Number
				 PAGE: - Video Monitor
					Underload Threshold  cmdID= 1344  min= 0  max= 1023  step= 1  format= %0.0f  div_scale= 1
					Min = 0  Max = 1023  Step = 1 "
		::= { iqsda02CmdEntry 1344 }


	iqsda02ChromaVideoLevelUnderloadAvePicBelowThres OBJECT-TYPE
		SYNTAX		INTEGER
		MAX-ACCESS		read-write
		STATUS			current
		DESCRIPTION
				"TYPE: - Number
				 PAGE: - Video Monitor
					Ave Pic Below Thres  cmdID= 1359  min= 0  max= 99  step= 1  format= %0.0f  div_scale= 1
					Min = 0  Max = 99  Step = 1 "
		::= { iqsda02CmdEntry 1359 }


	iqsda02HyperionVideoMonitorChromaBitDepth OBJECT-TYPE
		SYNTAX		RollCallString
		MAX-ACCESS		read-only
		STATUS			current
		DESCRIPTION
				"TYPE: - Display
				 PAGE: - Video Monitor
					Chroma Bit Depth  cmdID= 1330  format=   "
		::= { iqsda02CmdEntry 1330 }


	iqsda02HyperionVideoMonitorLumaBitDepth OBJECT-TYPE
		SYNTAX		RollCallString
		MAX-ACCESS		read-only
		STATUS			current
		DESCRIPTION
				"TYPE: - Display
				 PAGE: - Video Monitor
					Luma Bit Depth  cmdID= 1331  format=   "
		::= { iqsda02CmdEntry 1331 }


	iqsda02ClosedCaptionsCCCEA608BState OBJECT-TYPE
		SYNTAX		RollCallString
		MAX-ACCESS		read-only
		STATUS			current
		DESCRIPTION
				"TYPE: - Display
				 PAGE: - Closed Captions
					State  cmdID= 1368  format=   "
		::= { iqsda02CmdEntry 1368 }


	iqsda02ClosedCaptionsCCCEA608BTitle1 OBJECT-TYPE
		SYNTAX		RollCallString
		MAX-ACCESS		read-only
		STATUS			current
		DESCRIPTION
				"TYPE: - Display
				 PAGE: - Closed Captions
					Title 1  cmdID= 1371  format=   "
		::= { iqsda02CmdEntry 1371 }


	iqsda02ClosedCaptionsCCCEA608BTitle2 OBJECT-TYPE
		SYNTAX		RollCallString
		MAX-ACCESS		read-only
		STATUS			current
		DESCRIPTION
				"TYPE: - Display
				 PAGE: - Closed Captions
					Title 2  cmdID= 1372  format=   "
		::= { iqsda02CmdEntry 1372 }


	iqsda02ClosedCaptionsCCCEA708BField1 OBJECT-TYPE
		SYNTAX		RollCallString
		MAX-ACCESS		read-only
		STATUS			current
		DESCRIPTION
				"TYPE: - Display
				 PAGE: - Closed Captions
					Field 1  cmdID= 1366  format=   "
		::= { iqsda02CmdEntry 1366 }


	iqsda02ClosedCaptionsCCCEA708BField2 OBJECT-TYPE
		SYNTAX		RollCallString
		MAX-ACCESS		read-only
		STATUS			current
		DESCRIPTION
				"TYPE: - Display
				 PAGE: - Closed Captions
					Field 2  cmdID= 1367  format=   "
		::= { iqsda02CmdEntry 1367 }


	iqsda02ClosedCaptionsTemporalControlEnableAlarm OBJECT-TYPE
		SYNTAX		INTEGER { disable(0), enable(1) }
		MAX-ACCESS		read-write
		STATUS			current
		DESCRIPTION
				"TYPE: - Checkbox
				 PAGE: - Closed Captions
					Enable Alarm  cmdID= 1370 "
		::= { iqsda02CmdEntry 1370 }


	iqsda02ClosedCaptionsTemporalControlAlarm OBJECT-TYPE
		SYNTAX		RollCallString
		MAX-ACCESS		read-only
		STATUS			current
		DESCRIPTION
				"TYPE: - Display
				 PAGE: - Closed Captions
					Alarm  cmdID= 1365  format=   "
		::= { iqsda02CmdEntry 1365 }


	iqsda02ClosedCaptionsTemporalControlFailCount OBJECT-TYPE
		SYNTAX		INTEGER
		MAX-ACCESS		read-write
		STATUS			current
		DESCRIPTION
				"TYPE: - Number
				 PAGE: - Closed Captions
					Fail Count  cmdID= 1362  min= 0  max= 16000  step= 1  format= %0.0f  div_scale= 1
					Min = 0  Max = 16000  Step = 1 "
		::= { iqsda02CmdEntry 1362 }


	iqsda02ClosedCaptionsTemporalControlWarningCount OBJECT-TYPE
		SYNTAX		INTEGER
		MAX-ACCESS		read-write
		STATUS			current
		DESCRIPTION
				"TYPE: - Number
				 PAGE: - Closed Captions
					Warning Count  cmdID= 1363  min= 0  max= 16000  step= 1  format= %0.0f  div_scale= 1
					Min = 0  Max = 16000  Step = 1 "
		::= { iqsda02CmdEntry 1363 }


	iqsda02ClosedCaptionsTemporalControlFailHoldCount OBJECT-TYPE
		SYNTAX		INTEGER
		MAX-ACCESS		read-write
		STATUS			current
		DESCRIPTION
				"TYPE: - Number
				 PAGE: - Closed Captions
					Fail Hold Count  cmdID= 1364  min= 0  max= 16000  step= 1  format= %0.0f  div_scale= 1
					Min = 0  Max = 16000  Step = 1 "
		::= { iqsda02CmdEntry 1364 }


	iqsda02ClosedCaptionsTemporalControlResetAlarm OBJECT-TYPE
		SYNTAX		INTEGER { noAction(0),val_Reset_Alarm(1) }
		MAX-ACCESS		read-write
		STATUS			current
		DESCRIPTION
				"TYPE: - Button
				 PAGE: - Closed Captions
					Reset Alarm  cmdID= 1369  value= 1  "
		::= { iqsda02CmdEntry 1369 }


	iqsda02AncillaryDataContentAdvisoryEnableAlarm OBJECT-TYPE
		SYNTAX		INTEGER { disable(0), enable(1) }
		MAX-ACCESS		read-write
		STATUS			current
		DESCRIPTION
				"TYPE: - Checkbox
				 PAGE: - Ancillary Data
					Enable Alarm  cmdID= 1402 "
		::= { iqsda02CmdEntry 1402 }


	iqsda02AncillaryDataContentAdvisorySystem OBJECT-TYPE
		SYNTAX		RollCallString
		MAX-ACCESS		read-only
		STATUS			current
		DESCRIPTION
				"TYPE: - Display
				 PAGE: - Ancillary Data
					System  cmdID= 1400  format=   "
		::= { iqsda02CmdEntry 1400 }


	iqsda02AncillaryDataContentAdvisoryRating OBJECT-TYPE
		SYNTAX		RollCallString
		MAX-ACCESS		read-only
		STATUS			current
		DESCRIPTION
				"TYPE: - Display
				 PAGE: - Ancillary Data
					Rating  cmdID= 1401  format=   "
		::= { iqsda02CmdEntry 1401 }


	iqsda02TimeCodeAncTimeCodeEnableAlarm OBJECT-TYPE
		SYNTAX		INTEGER { disable(0), enable(1) }
		MAX-ACCESS		read-write
		STATUS			current
		DESCRIPTION
				"TYPE: - Checkbox
				 PAGE: - Ancillary Data
					Enable Alarm  cmdID= 1337 "
		::= { iqsda02CmdEntry 1337 }


	iqsda02TimeCodeAncTimeCodeField1 OBJECT-TYPE
		SYNTAX		RollCallString
		MAX-ACCESS		read-only
		STATUS			current
		DESCRIPTION
				"TYPE: - Display
				 PAGE: - Ancillary Data
					Field 1  cmdID= 1333  format=   "
		::= { iqsda02CmdEntry 1333 }


	iqsda02TimeCodeAncTimeCodeField2 OBJECT-TYPE
		SYNTAX		RollCallString
		MAX-ACCESS		read-only
		STATUS			current
		DESCRIPTION
				"TYPE: - Display
				 PAGE: - Ancillary Data
					Field 2  cmdID= 1334  format=   "
		::= { iqsda02CmdEntry 1334 }


	iqsda02TimeCodeVITCEnableAlarm OBJECT-TYPE
		SYNTAX		INTEGER { disable(0), enable(1) }
		MAX-ACCESS		read-write
		STATUS			current
		DESCRIPTION
				"TYPE: - Checkbox
				 PAGE: - Ancillary Data
					Enable Alarm  cmdID= 1802 "
		::= { iqsda02CmdEntry 1802 }


	iqsda02TimeCodeVITCField1 OBJECT-TYPE
		SYNTAX		RollCallString
		MAX-ACCESS		read-only
		STATUS			current
		DESCRIPTION
				"TYPE: - Display
				 PAGE: - Ancillary Data
					Field 1  cmdID= 1800  format=   "
		::= { iqsda02CmdEntry 1800 }


	iqsda02TimeCodeVITCField2 OBJECT-TYPE
		SYNTAX		RollCallString
		MAX-ACCESS		read-only
		STATUS			current
		DESCRIPTION
				"TYPE: - Display
				 PAGE: - Ancillary Data
					Field 2  cmdID= 1801  format=   "
		::= { iqsda02CmdEntry 1801 }


	iqsda02AncillaryDataTimeCodeCurrentTimeCode OBJECT-TYPE
		SYNTAX		RollCallString
		MAX-ACCESS		read-only
		STATUS			current
		DESCRIPTION
				"TYPE: - Display
				 PAGE: - Ancillary Data
					Current Time Code  cmdID= 1338  format=   "
		::= { iqsda02CmdEntry 1338 }


	iqsda02AncillaryDataTimeCodeSDTimeCodeSel OBJECT-TYPE
		SYNTAX		INTEGER {
							val_Auto(0),
							val_VITC(1),
							val_Anc(2)
							}
		MAX-ACCESS		read-write
		STATUS			current
		DESCRIPTION
				"TYPE: - RadiobuttonList
				 PAGE: - Ancillary Data
					SD Time Code Sel  cmdID= 1820
					Auto  value= 0
					VITC  value= 1
					Anc  value= 2  "
		::= { iqsda02CmdEntry 1820 }


	iqsda02AncillaryDataUserAncDet1EnableAlarm OBJECT-TYPE
		SYNTAX		INTEGER { disable(0), enable(1) }
		MAX-ACCESS		read-write
		STATUS			current
		DESCRIPTION
				"TYPE: - Checkbox
				 PAGE: - Ancillary Data
					Enable Alarm  cmdID= 1390 "
		::= { iqsda02CmdEntry 1390 }


	iqsda02AncillaryDataUserAncDet1DIDType OBJECT-TYPE
		SYNTAX		INTEGER {
							val_Type_1(1),
							val_Type_2(0)
							}
		MAX-ACCESS		read-write
		STATUS			current
		DESCRIPTION
				"TYPE: - RadiobuttonList
				 PAGE: - Ancillary Data
					DID Type  cmdID= 1382
					Type 1  value= 1
					Type 2  value= 0  "
		::= { iqsda02CmdEntry 1382 }


	iqsda02AncillaryDataUserAncDet1DIDselect OBJECT-TYPE
		SYNTAX		INTEGER
		MAX-ACCESS		read-write
		STATUS			current
		DESCRIPTION
				"TYPE: - Number
				 PAGE: - Ancillary Data
					DID select  cmdID= 1380  min= 0  max= 255  step= 1  format= %0.0f  div_scale= 1
					Min = 0  Max = 255  Step = 1 "
		::= { iqsda02CmdEntry 1380 }


	iqsda02AncillaryDataUserAncDet1SDIDselect OBJECT-TYPE
		SYNTAX		INTEGER
		MAX-ACCESS		read-write
		STATUS			current
		DESCRIPTION
				"TYPE: - Number
				 PAGE: - Ancillary Data
					SDID select  cmdID= 1381  min= 0  max= 255  step= 1  format= %0.0f  div_scale= 1
					Min = 0  Max = 255  Step = 1 "
		::= { iqsda02CmdEntry 1381 }


	iqsda02AncillaryDataUserAncDet1Field1 OBJECT-TYPE
		SYNTAX		RollCallString
		MAX-ACCESS		read-only
		STATUS			current
		DESCRIPTION
				"TYPE: - Display
				 PAGE: - Ancillary Data
					Field 1  cmdID= 1386  format=   "
		::= { iqsda02CmdEntry 1386 }


	iqsda02AncillaryDataUserAncDet1Field2 OBJECT-TYPE
		SYNTAX		RollCallString
		MAX-ACCESS		read-only
		STATUS			current
		DESCRIPTION
				"TYPE: - Display
				 PAGE: - Ancillary Data
					Field 2  cmdID= 1387  format=   "
		::= { iqsda02CmdEntry 1387 }


	iqsda02AncillaryDataUserAncDet1Name OBJECT-TYPE
		SYNTAX		RollCallString
		MAX-ACCESS		read-write
		STATUS			current
		DESCRIPTION
				"TYPE: - Editstring
				 PAGE: - Ancillary Data
					Name  cmdID= 1391  "
		::= { iqsda02CmdEntry 1391 }


	iqsda02AncillaryDataUserAncDet2EnableAlarm OBJECT-TYPE
		SYNTAX		INTEGER { disable(0), enable(1) }
		MAX-ACCESS		read-write
		STATUS			current
		DESCRIPTION
				"TYPE: - Checkbox
				 PAGE: - Ancillary Data
					Enable Alarm  cmdID= 1392 "
		::= { iqsda02CmdEntry 1392 }


	iqsda02AncillaryDataUserAncDet2DIDType OBJECT-TYPE
		SYNTAX		INTEGER {
							val_Type_1(1),
							val_Type_2(0)
							}
		MAX-ACCESS		read-write
		STATUS			current
		DESCRIPTION
				"TYPE: - RadiobuttonList
				 PAGE: - Ancillary Data
					DID Type  cmdID= 1385
					Type 1  value= 1
					Type 2  value= 0  "
		::= { iqsda02CmdEntry 1385 }


	iqsda02AncillaryDataUserAncDet2DIDselect OBJECT-TYPE
		SYNTAX		INTEGER
		MAX-ACCESS		read-write
		STATUS			current
		DESCRIPTION
				"TYPE: - Number
				 PAGE: - Ancillary Data
					DID select  cmdID= 1383  min= 0  max= 255  step= 1  format= %0.0f  div_scale= 1
					Min = 0  Max = 255  Step = 1 "
		::= { iqsda02CmdEntry 1383 }


	iqsda02AncillaryDataUserAncDet2SDIDselect OBJECT-TYPE
		SYNTAX		INTEGER
		MAX-ACCESS		read-write
		STATUS			current
		DESCRIPTION
				"TYPE: - Number
				 PAGE: - Ancillary Data
					SDID select  cmdID= 1384  min= 0  max= 255  step= 1  format= %0.0f  div_scale= 1
					Min = 0  Max = 255  Step = 1 "
		::= { iqsda02CmdEntry 1384 }


	iqsda02AncillaryDataUserAncDet2Field1 OBJECT-TYPE
		SYNTAX		RollCallString
		MAX-ACCESS		read-only
		STATUS			current
		DESCRIPTION
				"TYPE: - Display
				 PAGE: - Ancillary Data
					Field 1  cmdID= 1388  format=   "
		::= { iqsda02CmdEntry 1388 }


	iqsda02AncillaryDataUserAncDet2Field2 OBJECT-TYPE
		SYNTAX		RollCallString
		MAX-ACCESS		read-only
		STATUS			current
		DESCRIPTION
				"TYPE: - Display
				 PAGE: - Ancillary Data
					Field 2  cmdID= 1389  format=   "
		::= { iqsda02CmdEntry 1389 }


	iqsda02AncillaryDataUserAncDet2Name OBJECT-TYPE
		SYNTAX		RollCallString
		MAX-ACCESS		read-write
		STATUS			current
		DESCRIPTION
				"TYPE: - Editstring
				 PAGE: - Ancillary Data
					Name  cmdID= 1393  "
		::= { iqsda02CmdEntry 1393 }


	iqsda02AncillaryDataWSSVIInputWSSPresence OBJECT-TYPE
		SYNTAX		RollCallString
		MAX-ACCESS		read-only
		STATUS			current
		DESCRIPTION
				"TYPE: - Display
				 PAGE: - Ancillary Data
					WSS Presence   cmdID= 1420  format=   "
		::= { iqsda02CmdEntry 1420 }


	iqsda02AncillaryDataWSSVIInputWSSEnableAlarm OBJECT-TYPE
		SYNTAX		INTEGER { disable(0), enable(1) }
		MAX-ACCESS		read-write
		STATUS			current
		DESCRIPTION
				"TYPE: - Checkbox
				 PAGE: - Ancillary Data
					WSS Enable Alarm  cmdID= 1421 "
		::= { iqsda02CmdEntry 1421 }


	iqsda02AncillaryDataWSSVIInputWSSData OBJECT-TYPE
		SYNTAX		RollCallString
		MAX-ACCESS		read-only
		STATUS			current
		DESCRIPTION
				"TYPE: - Display
				 PAGE: - Ancillary Data
					WSS Data  cmdID= 1425  format=   "
		::= { iqsda02CmdEntry 1425 }


	iqsda02AncillaryDataWSSVIInputWSSScanSys OBJECT-TYPE
		SYNTAX		RollCallString
		MAX-ACCESS		read-only
		STATUS			current
		DESCRIPTION
				"TYPE: - Display
				 PAGE: - Ancillary Data
					WSS Scan Sys  cmdID= 1426  format=   "
		::= { iqsda02CmdEntry 1426 }


	iqsda02AncillaryDataWSSVIInputWSSType OBJECT-TYPE
		SYNTAX		INTEGER {
							val_ETSI(1),
							val_AFD(2),
							val_AFD_and_ScanSys(3)
							}
		MAX-ACCESS		read-write
		STATUS			current
		DESCRIPTION
				"TYPE: - RadiobuttonList
				 PAGE: - Ancillary Data
					WSS Type  cmdID= 1424
					ETSI  value= 1
					AFD  value= 2
					AFD and ScanSys  value= 3  "
		::= { iqsda02CmdEntry 1424 }


	iqsda02AncillaryDataWSSVIInputVIPresence OBJECT-TYPE
		SYNTAX		RollCallString
		MAX-ACCESS		read-only
		STATUS			current
		DESCRIPTION
				"TYPE: - Display
				 PAGE: - Ancillary Data
					VI Presence   cmdID= 1422  format=   "
		::= { iqsda02CmdEntry 1422 }


	iqsda02AncillaryDataWSSVIInputVIEnableAlarm OBJECT-TYPE
		SYNTAX		INTEGER { disable(0), enable(1) }
		MAX-ACCESS		read-write
		STATUS			current
		DESCRIPTION
				"TYPE: - Checkbox
				 PAGE: - Ancillary Data
					VI Enable Alarm  cmdID= 1423 "
		::= { iqsda02CmdEntry 1423 }


	iqsda02AncillaryDataWSSVIInputVIType OBJECT-TYPE
		SYNTAX		INTEGER {
							val_SMPTE(1),
							val_AFD(2),
							val_Legacy_AFD(3),
							val_Legacy_AFD_and_SS(4)
							}
		MAX-ACCESS		read-write
		STATUS			current
		DESCRIPTION
				"TYPE: - RadiobuttonList
				 PAGE: - Ancillary Data
					VI Type  cmdID= 1427
					SMPTE  value= 1
					AFD  value= 2
					Legacy AFD  value= 3
					Legacy AFD and SS  value= 4  "
		::= { iqsda02CmdEntry 1427 }


	iqsda02AncillaryDataWSSVIInputVIData OBJECT-TYPE
		SYNTAX		RollCallString
		MAX-ACCESS		read-only
		STATUS			current
		DESCRIPTION
				"TYPE: - Display
				 PAGE: - Ancillary Data
					VI Data  cmdID= 1429  format=   "
		::= { iqsda02CmdEntry 1429 }


	iqsda02AncillaryDataWSSVIInputVIScanSys OBJECT-TYPE
		SYNTAX		RollCallString
		MAX-ACCESS		read-only
		STATUS			current
		DESCRIPTION
				"TYPE: - Display
				 PAGE: - Ancillary Data
					VI Scan Sys  cmdID= 1428  format=   "
		::= { iqsda02CmdEntry 1428 }


	iqsda02HyperionAudioDataActiveAudioCh OBJECT-TYPE
		SYNTAX		RollCallString
		MAX-ACCESS		read-only
		STATUS			current
		DESCRIPTION
				"TYPE: - Display
				 PAGE: - Audio Data
					Active Audio Ch  cmdID= 1332  format=   "
		::= { iqsda02CmdEntry 1332 }


	iqsda02AudioDataGroup1EnableAlarmCh1 OBJECT-TYPE
		SYNTAX		INTEGER { disable(0), enable(1) }
		MAX-ACCESS		read-write
		STATUS			current
		DESCRIPTION
				"TYPE: - Checkbox
				 PAGE: - Audio Data
					Enable Alarm Ch 1  cmdID= 1520 "
		::= { iqsda02CmdEntry 1520 }


	iqsda02AudioDataGroup1TypeCh1 OBJECT-TYPE
		SYNTAX		RollCallString
		MAX-ACCESS		read-only
		STATUS			current
		DESCRIPTION
				"TYPE: - Display
				 PAGE: - Audio Data
					Type Ch 1  cmdID= 1500  format=   "
		::= { iqsda02CmdEntry 1500 }


	iqsda02AudioDataGroup1BitdepthCh1 OBJECT-TYPE
		SYNTAX		RollCallString
		MAX-ACCESS		read-only
		STATUS			current
		DESCRIPTION
				"TYPE: - Display
				 PAGE: - Audio Data
					Bit depth Ch 1  cmdID= 1550  format=   "
		::= { iqsda02CmdEntry 1550 }


	iqsda02AudioDataGroup1EnableAlarmCh2 OBJECT-TYPE
		SYNTAX		INTEGER { disable(0), enable(1) }
		MAX-ACCESS		read-write
		STATUS			current
		DESCRIPTION
				"TYPE: - Checkbox
				 PAGE: - Audio Data
					Enable Alarm Ch 2  cmdID= 1521 "
		::= { iqsda02CmdEntry 1521 }


	iqsda02AudioDataGroup1TypeCh2 OBJECT-TYPE
		SYNTAX		RollCallString
		MAX-ACCESS		read-only
		STATUS			current
		DESCRIPTION
				"TYPE: - Display
				 PAGE: - Audio Data
					Type Ch 2  cmdID= 1501  format=   "
		::= { iqsda02CmdEntry 1501 }


	iqsda02AudioDataGroup1BitdepthCh2 OBJECT-TYPE
		SYNTAX		RollCallString
		MAX-ACCESS		read-only
		STATUS			current
		DESCRIPTION
				"TYPE: - Display
				 PAGE: - Audio Data
					Bit depth Ch2  cmdID= 1551  format=   "
		::= { iqsda02CmdEntry 1551 }


	iqsda02AudioDataGroup1EnableAlarmCh3 OBJECT-TYPE
		SYNTAX		INTEGER { disable(0), enable(1) }
		MAX-ACCESS		read-write
		STATUS			current
		DESCRIPTION
				"TYPE: - Checkbox
				 PAGE: - Audio Data
					Enable Alarm Ch 3  cmdID= 1522 "
		::= { iqsda02CmdEntry 1522 }


	iqsda02AudioDataGroup1TypeCh3 OBJECT-TYPE
		SYNTAX		RollCallString
		MAX-ACCESS		read-only
		STATUS			current
		DESCRIPTION
				"TYPE: - Display
				 PAGE: - Audio Data
					Type Ch 3  cmdID= 1502  format=   "
		::= { iqsda02CmdEntry 1502 }


	iqsda02AudioDataGroup1BitdepthCh3 OBJECT-TYPE
		SYNTAX		RollCallString
		MAX-ACCESS		read-only
		STATUS			current
		DESCRIPTION
				"TYPE: - Display
				 PAGE: - Audio Data
					Bit depth Ch3  cmdID= 1552  format=   "
		::= { iqsda02CmdEntry 1552 }


	iqsda02AudioDataGroup1EnableAlarmCh4 OBJECT-TYPE
		SYNTAX		INTEGER { disable(0), enable(1) }
		MAX-ACCESS		read-write
		STATUS			current
		DESCRIPTION
				"TYPE: - Checkbox
				 PAGE: - Audio Data
					Enable Alarm Ch 4  cmdID= 1523 "
		::= { iqsda02CmdEntry 1523 }


	iqsda02AudioDataGroup1TypeCh4 OBJECT-TYPE
		SYNTAX		RollCallString
		MAX-ACCESS		read-only
		STATUS			current
		DESCRIPTION
				"TYPE: - Display
				 PAGE: - Audio Data
					Type Ch 4  cmdID= 1503  format=   "
		::= { iqsda02CmdEntry 1503 }


	iqsda02AudioDataGroup1BitdepthCh4 OBJECT-TYPE
		SYNTAX		RollCallString
		MAX-ACCESS		read-only
		STATUS			current
		DESCRIPTION
				"TYPE: - Display
				 PAGE: - Audio Data
					Bit depth Ch4  cmdID= 1553  format=   "
		::= { iqsda02CmdEntry 1553 }


	iqsda02AudioDataGroup2EnableAlarmCh5 OBJECT-TYPE
		SYNTAX		INTEGER { disable(0), enable(1) }
		MAX-ACCESS		read-write
		STATUS			current
		DESCRIPTION
				"TYPE: - Checkbox
				 PAGE: - Audio Data
					Enable Alarm Ch 5  cmdID= 1524 "
		::= { iqsda02CmdEntry 1524 }


	iqsda02AudioDataGroup2TypeCh5 OBJECT-TYPE
		SYNTAX		RollCallString
		MAX-ACCESS		read-only
		STATUS			current
		DESCRIPTION
				"TYPE: - Display
				 PAGE: - Audio Data
					Type Ch 5  cmdID= 1504  format=   "
		::= { iqsda02CmdEntry 1504 }


	iqsda02AudioDataGroup2BitdepthCh5 OBJECT-TYPE
		SYNTAX		RollCallString
		MAX-ACCESS		read-only
		STATUS			current
		DESCRIPTION
				"TYPE: - Display
				 PAGE: - Audio Data
					Bit depth Ch 5  cmdID= 1554  format=   "
		::= { iqsda02CmdEntry 1554 }


	iqsda02AudioDataGroup2EnableAlarmCh6 OBJECT-TYPE
		SYNTAX		INTEGER { disable(0), enable(1) }
		MAX-ACCESS		read-write
		STATUS			current
		DESCRIPTION
				"TYPE: - Checkbox
				 PAGE: - Audio Data
					Enable Alarm Ch 6  cmdID= 1525 "
		::= { iqsda02CmdEntry 1525 }


	iqsda02AudioDataGroup2TypeCh6 OBJECT-TYPE
		SYNTAX		RollCallString
		MAX-ACCESS		read-only
		STATUS			current
		DESCRIPTION
				"TYPE: - Display
				 PAGE: - Audio Data
					Type Ch 6  cmdID= 1505  format=   "
		::= { iqsda02CmdEntry 1505 }


	iqsda02AudioDataGroup2BitdepthCh6 OBJECT-TYPE
		SYNTAX		RollCallString
		MAX-ACCESS		read-only
		STATUS			current
		DESCRIPTION
				"TYPE: - Display
				 PAGE: - Audio Data
					Bit depth Ch 6  cmdID= 1555  format=   "
		::= { iqsda02CmdEntry 1555 }


	iqsda02AudioDataGroup2EnableAlarmCh7 OBJECT-TYPE
		SYNTAX		INTEGER { disable(0), enable(1) }
		MAX-ACCESS		read-write
		STATUS			current
		DESCRIPTION
				"TYPE: - Checkbox
				 PAGE: - Audio Data
					Enable Alarm Ch 7  cmdID= 1526 "
		::= { iqsda02CmdEntry 1526 }


	iqsda02AudioDataGroup2TypeCh7 OBJECT-TYPE
		SYNTAX		RollCallString
		MAX-ACCESS		read-only
		STATUS			current
		DESCRIPTION
				"TYPE: - Display
				 PAGE: - Audio Data
					Type Ch 7  cmdID= 1506  format=   "
		::= { iqsda02CmdEntry 1506 }


	iqsda02AudioDataGroup2BitdepthCh7 OBJECT-TYPE
		SYNTAX		RollCallString
		MAX-ACCESS		read-only
		STATUS			current
		DESCRIPTION
				"TYPE: - Display
				 PAGE: - Audio Data
					Bit depth Ch 7  cmdID= 1556  format=   "
		::= { iqsda02CmdEntry 1556 }


	iqsda02AudioDataGroup2EnableAlarmCh8 OBJECT-TYPE
		SYNTAX		INTEGER { disable(0), enable(1) }
		MAX-ACCESS		read-write
		STATUS			current
		DESCRIPTION
				"TYPE: - Checkbox
				 PAGE: - Audio Data
					Enable Alarm Ch 8  cmdID= 1527 "
		::= { iqsda02CmdEntry 1527 }


	iqsda02AudioDataGroup2TypeCh8 OBJECT-TYPE
		SYNTAX		RollCallString
		MAX-ACCESS		read-only
		STATUS			current
		DESCRIPTION
				"TYPE: - Display
				 PAGE: - Audio Data
					Type Ch 8  cmdID= 1507  format=   "
		::= { iqsda02CmdEntry 1507 }


	iqsda02AudioDataGroup2BitdepthCh8 OBJECT-TYPE
		SYNTAX		RollCallString
		MAX-ACCESS		read-only
		STATUS			current
		DESCRIPTION
				"TYPE: - Display
				 PAGE: - Audio Data
					Bit depth Ch 8  cmdID= 1557  format=   "
		::= { iqsda02CmdEntry 1557 }


	iqsda02AudioDataGroup3EnableAlarmCh9 OBJECT-TYPE
		SYNTAX		INTEGER { disable(0), enable(1) }
		MAX-ACCESS		read-write
		STATUS			current
		DESCRIPTION
				"TYPE: - Checkbox
				 PAGE: - Audio Data
					Enable Alarm Ch 9  cmdID= 1528 "
		::= { iqsda02CmdEntry 1528 }


	iqsda02AudioDataGroup3TypeCh9 OBJECT-TYPE
		SYNTAX		RollCallString
		MAX-ACCESS		read-only
		STATUS			current
		DESCRIPTION
				"TYPE: - Display
				 PAGE: - Audio Data
					Type Ch 9  cmdID= 1508  format=   "
		::= { iqsda02CmdEntry 1508 }


	iqsda02AudioDataGroup3BitdepthCh9 OBJECT-TYPE
		SYNTAX		RollCallString
		MAX-ACCESS		read-only
		STATUS			current
		DESCRIPTION
				"TYPE: - Display
				 PAGE: - Audio Data
					Bit depth Ch 9  cmdID= 1558  format=   "
		::= { iqsda02CmdEntry 1558 }


	iqsda02AudioDataGroup3EnableAlarmCh10 OBJECT-TYPE
		SYNTAX		INTEGER { disable(0), enable(1) }
		MAX-ACCESS		read-write
		STATUS			current
		DESCRIPTION
				"TYPE: - Checkbox
				 PAGE: - Audio Data
					Enable Alarm Ch 10  cmdID= 1529 "
		::= { iqsda02CmdEntry 1529 }


	iqsda02AudioDataGroup3TypeCh10 OBJECT-TYPE
		SYNTAX		RollCallString
		MAX-ACCESS		read-only
		STATUS			current
		DESCRIPTION
				"TYPE: - Display
				 PAGE: - Audio Data
					Type Ch 10  cmdID= 1509  format=   "
		::= { iqsda02CmdEntry 1509 }


	iqsda02AudioDataGroup3BitdepthCh10 OBJECT-TYPE
		SYNTAX		RollCallString
		MAX-ACCESS		read-only
		STATUS			current
		DESCRIPTION
				"TYPE: - Display
				 PAGE: - Audio Data
					Bit depth Ch 10  cmdID= 1559  format=   "
		::= { iqsda02CmdEntry 1559 }


	iqsda02AudioDataGroup3EnableAlarmCh11 OBJECT-TYPE
		SYNTAX		INTEGER { disable(0), enable(1) }
		MAX-ACCESS		read-write
		STATUS			current
		DESCRIPTION
				"TYPE: - Checkbox
				 PAGE: - Audio Data
					Enable Alarm Ch 11  cmdID= 1530 "
		::= { iqsda02CmdEntry 1530 }


	iqsda02AudioDataGroup3TypeCh11 OBJECT-TYPE
		SYNTAX		RollCallString
		MAX-ACCESS		read-only
		STATUS			current
		DESCRIPTION
				"TYPE: - Display
				 PAGE: - Audio Data
					Type Ch 11  cmdID= 1510  format=   "
		::= { iqsda02CmdEntry 1510 }


	iqsda02AudioDataGroup3BitdepthCh11 OBJECT-TYPE
		SYNTAX		RollCallString
		MAX-ACCESS		read-only
		STATUS			current
		DESCRIPTION
				"TYPE: - Display
				 PAGE: - Audio Data
					Bit depth Ch 11  cmdID= 1560  format=   "
		::= { iqsda02CmdEntry 1560 }


	iqsda02AudioDataGroup3EnableAlarmCh12 OBJECT-TYPE
		SYNTAX		INTEGER { disable(0), enable(1) }
		MAX-ACCESS		read-write
		STATUS			current
		DESCRIPTION
				"TYPE: - Checkbox
				 PAGE: - Audio Data
					Enable Alarm Ch 12  cmdID= 1531 "
		::= { iqsda02CmdEntry 1531 }


	iqsda02AudioDataGroup3TypeCh12 OBJECT-TYPE
		SYNTAX		RollCallString
		MAX-ACCESS		read-only
		STATUS			current
		DESCRIPTION
				"TYPE: - Display
				 PAGE: - Audio Data
					Type Ch 12  cmdID= 1511  format=   "
		::= { iqsda02CmdEntry 1511 }


	iqsda02AudioDataGroup3BitdepthCh12 OBJECT-TYPE
		SYNTAX		RollCallString
		MAX-ACCESS		read-only
		STATUS			current
		DESCRIPTION
				"TYPE: - Display
				 PAGE: - Audio Data
					Bit depth Ch 12  cmdID= 1561  format=   "
		::= { iqsda02CmdEntry 1561 }


	iqsda02AudioDataGroup4EnableAlarmCh13 OBJECT-TYPE
		SYNTAX		INTEGER { disable(0), enable(1) }
		MAX-ACCESS		read-write
		STATUS			current
		DESCRIPTION
				"TYPE: - Checkbox
				 PAGE: - Audio Data
					Enable Alarm Ch 13  cmdID= 1532 "
		::= { iqsda02CmdEntry 1532 }


	iqsda02AudioDataGroup4TypeCh13 OBJECT-TYPE
		SYNTAX		RollCallString
		MAX-ACCESS		read-only
		STATUS			current
		DESCRIPTION
				"TYPE: - Display
				 PAGE: - Audio Data
					Type Ch 13  cmdID= 1512  format=   "
		::= { iqsda02CmdEntry 1512 }


	iqsda02AudioDataGroup4BitdepthCh13 OBJECT-TYPE
		SYNTAX		RollCallString
		MAX-ACCESS		read-only
		STATUS			current
		DESCRIPTION
				"TYPE: - Display
				 PAGE: - Audio Data
					Bit depth Ch 13  cmdID= 1562  format=   "
		::= { iqsda02CmdEntry 1562 }


	iqsda02AudioDataGroup4EnableAlarmCh14 OBJECT-TYPE
		SYNTAX		INTEGER { disable(0), enable(1) }
		MAX-ACCESS		read-write
		STATUS			current
		DESCRIPTION
				"TYPE: - Checkbox
				 PAGE: - Audio Data
					Enable Alarm Ch 14  cmdID= 1533 "
		::= { iqsda02CmdEntry 1533 }


	iqsda02AudioDataGroup4TypeCh14 OBJECT-TYPE
		SYNTAX		RollCallString
		MAX-ACCESS		read-only
		STATUS			current
		DESCRIPTION
				"TYPE: - Display
				 PAGE: - Audio Data
					Type Ch 14  cmdID= 1513  format=   "
		::= { iqsda02CmdEntry 1513 }


	iqsda02AudioDataGroup4BitdepthCh14 OBJECT-TYPE
		SYNTAX		RollCallString
		MAX-ACCESS		read-only
		STATUS			current
		DESCRIPTION
				"TYPE: - Display
				 PAGE: - Audio Data
					Bit depth Ch 14  cmdID= 1563  format=   "
		::= { iqsda02CmdEntry 1563 }


	iqsda02AudioDataGroup4EnableAlarmCh15 OBJECT-TYPE
		SYNTAX		INTEGER { disable(0), enable(1) }
		MAX-ACCESS		read-write
		STATUS			current
		DESCRIPTION
				"TYPE: - Checkbox
				 PAGE: - Audio Data
					Enable Alarm Ch 15  cmdID= 1534 "
		::= { iqsda02CmdEntry 1534 }


	iqsda02AudioDataGroup4TypeCh15 OBJECT-TYPE
		SYNTAX		RollCallString
		MAX-ACCESS		read-only
		STATUS			current
		DESCRIPTION
				"TYPE: - Display
				 PAGE: - Audio Data
					Type Ch 15  cmdID= 1514  format=   "
		::= { iqsda02CmdEntry 1514 }


	iqsda02AudioDataGroup4BitdepthCh15 OBJECT-TYPE
		SYNTAX		RollCallString
		MAX-ACCESS		read-only
		STATUS			current
		DESCRIPTION
				"TYPE: - Display
				 PAGE: - Audio Data
					Bit depth Ch 15  cmdID= 1564  format=   "
		::= { iqsda02CmdEntry 1564 }


	iqsda02AudioDataGroup4EnableAlarmCh16 OBJECT-TYPE
		SYNTAX		INTEGER { disable(0), enable(1) }
		MAX-ACCESS		read-write
		STATUS			current
		DESCRIPTION
				"TYPE: - Checkbox
				 PAGE: - Audio Data
					Enable Alarm Ch 16  cmdID= 1535 "
		::= { iqsda02CmdEntry 1535 }


	iqsda02AudioDataGroup4TypeCh16 OBJECT-TYPE
		SYNTAX		RollCallString
		MAX-ACCESS		read-only
		STATUS			current
		DESCRIPTION
				"TYPE: - Display
				 PAGE: - Audio Data
					Type Ch 16  cmdID= 1515  format=   "
		::= { iqsda02CmdEntry 1515 }


	iqsda02AudioDataGroup4BitdepthCh16 OBJECT-TYPE
		SYNTAX		RollCallString
		MAX-ACCESS		read-only
		STATUS			current
		DESCRIPTION
				"TYPE: - Display
				 PAGE: - Audio Data
					Bit depth Ch 16  cmdID= 1565  format=   "
		::= { iqsda02CmdEntry 1565 }


	iqsda02AudioDataDolbyEStatusEnableAlarmPair1 OBJECT-TYPE
		SYNTAX		INTEGER { disable(0), enable(1) }
		MAX-ACCESS		read-write
		STATUS			current
		DESCRIPTION
				"TYPE: - Checkbox
				 PAGE: - Audio Data
					Enable Alarm Pair 1  cmdID= 1490 "
		::= { iqsda02CmdEntry 1490 }


	iqsda02AudioDataDolbyEStatusStatusPair1 OBJECT-TYPE
		SYNTAX		RollCallString
		MAX-ACCESS		read-only
		STATUS			current
		DESCRIPTION
				"TYPE: - Display
				 PAGE: - Audio Data
					Status Pair 1  cmdID= 1480  format=   "
		::= { iqsda02CmdEntry 1480 }


	iqsda02AudioDataDolbyEStatusEnableAlarmPair2 OBJECT-TYPE
		SYNTAX		INTEGER { disable(0), enable(1) }
		MAX-ACCESS		read-write
		STATUS			current
		DESCRIPTION
				"TYPE: - Checkbox
				 PAGE: - Audio Data
					Enable Alarm Pair 2  cmdID= 1491 "
		::= { iqsda02CmdEntry 1491 }


	iqsda02AudioDataDolbyEStatusStatusPair2 OBJECT-TYPE
		SYNTAX		RollCallString
		MAX-ACCESS		read-only
		STATUS			current
		DESCRIPTION
				"TYPE: - Display
				 PAGE: - Audio Data
					Status Pair 2  cmdID= 1481  format=   "
		::= { iqsda02CmdEntry 1481 }


	iqsda02AudioDataDolbyEStatusEnableAlarmPair3 OBJECT-TYPE
		SYNTAX		INTEGER { disable(0), enable(1) }
		MAX-ACCESS		read-write
		STATUS			current
		DESCRIPTION
				"TYPE: - Checkbox
				 PAGE: - Audio Data
					Enable Alarm Pair 3  cmdID= 1492 "
		::= { iqsda02CmdEntry 1492 }


	iqsda02AudioDataDolbyEStatusStatusPair3 OBJECT-TYPE
		SYNTAX		RollCallString
		MAX-ACCESS		read-only
		STATUS			current
		DESCRIPTION
				"TYPE: - Display
				 PAGE: - Audio Data
					Status Pair 3  cmdID= 1482  format=   "
		::= { iqsda02CmdEntry 1482 }


	iqsda02AudioDataDolbyEStatusEnableAlarmPair4 OBJECT-TYPE
		SYNTAX		INTEGER { disable(0), enable(1) }
		MAX-ACCESS		read-write
		STATUS			current
		DESCRIPTION
				"TYPE: - Checkbox
				 PAGE: - Audio Data
					Enable Alarm Pair 4  cmdID= 1493 "
		::= { iqsda02CmdEntry 1493 }


	iqsda02AudioDataDolbyEStatusStatusPair4 OBJECT-TYPE
		SYNTAX		RollCallString
		MAX-ACCESS		read-only
		STATUS			current
		DESCRIPTION
				"TYPE: - Display
				 PAGE: - Audio Data
					Status Pair 4  cmdID= 1483  format=   "
		::= { iqsda02CmdEntry 1483 }


	iqsda02AudioDataDolbyEStatusEnableAlarmPair5 OBJECT-TYPE
		SYNTAX		INTEGER { disable(0), enable(1) }
		MAX-ACCESS		read-write
		STATUS			current
		DESCRIPTION
				"TYPE: - Checkbox
				 PAGE: - Audio Data
					Enable Alarm Pair 5  cmdID= 1494 "
		::= { iqsda02CmdEntry 1494 }


	iqsda02AudioDataDolbyEStatusStatusPair5 OBJECT-TYPE
		SYNTAX		RollCallString
		MAX-ACCESS		read-only
		STATUS			current
		DESCRIPTION
				"TYPE: - Display
				 PAGE: - Audio Data
					Status Pair 5  cmdID= 1484  format=   "
		::= { iqsda02CmdEntry 1484 }


	iqsda02AudioDataDolbyEStatusEnableAlarmPair6 OBJECT-TYPE
		SYNTAX		INTEGER { disable(0), enable(1) }
		MAX-ACCESS		read-write
		STATUS			current
		DESCRIPTION
				"TYPE: - Checkbox
				 PAGE: - Audio Data
					Enable Alarm Pair 6  cmdID= 1495 "
		::= { iqsda02CmdEntry 1495 }


	iqsda02AudioDataDolbyEStatusStatusPair6 OBJECT-TYPE
		SYNTAX		RollCallString
		MAX-ACCESS		read-only
		STATUS			current
		DESCRIPTION
				"TYPE: - Display
				 PAGE: - Audio Data
					Status Pair 6  cmdID= 1485  format=   "
		::= { iqsda02CmdEntry 1485 }


	iqsda02AudioDataDolbyEStatusEnableAlarmPair7 OBJECT-TYPE
		SYNTAX		INTEGER { disable(0), enable(1) }
		MAX-ACCESS		read-write
		STATUS			current
		DESCRIPTION
				"TYPE: - Checkbox
				 PAGE: - Audio Data
					Enable Alarm Pair 7  cmdID= 1496 "
		::= { iqsda02CmdEntry 1496 }


	iqsda02AudioDataDolbyEStatusStatusPair7 OBJECT-TYPE
		SYNTAX		RollCallString
		MAX-ACCESS		read-only
		STATUS			current
		DESCRIPTION
				"TYPE: - Display
				 PAGE: - Audio Data
					Status Pair 7  cmdID= 1486  format=   "
		::= { iqsda02CmdEntry 1486 }


	iqsda02AudioDataDolbyEStatusEnableAlarmPair8 OBJECT-TYPE
		SYNTAX		INTEGER { disable(0), enable(1) }
		MAX-ACCESS		read-write
		STATUS			current
		DESCRIPTION
				"TYPE: - Checkbox
				 PAGE: - Audio Data
					Enable Alarm Pair 8  cmdID= 1497 "
		::= { iqsda02CmdEntry 1497 }


	iqsda02AudioDataDolbyEStatusStatusPair8 OBJECT-TYPE
		SYNTAX		RollCallString
		MAX-ACCESS		read-only
		STATUS			current
		DESCRIPTION
				"TYPE: - Display
				 PAGE: - Audio Data
					Status Pair 8  cmdID= 1487  format=   "
		::= { iqsda02CmdEntry 1487 }


	iqsda02AudioLevelDetDuplicateSettingsChannelIndex OBJECT-TYPE
		SYNTAX		INTEGER
		MAX-ACCESS		read-write
		STATUS			current
		DESCRIPTION
				"TYPE: - Number
				 PAGE: - Audio Level Det
					Channel Index  cmdID= 3001  min= 1  max= 16  step= 1  format= %0.0f  div_scale= 1
					Min = 1  Max = 16  Step = 1 "
		::= { iqsda02CmdEntry 3001 }


	iqsda02HyperionAudioLevelDetAverageAudioLevel OBJECT-TYPE
		SYNTAX		RollCallString
		MAX-ACCESS		read-only
		STATUS			current
		DESCRIPTION
				"TYPE: - Display
				 PAGE: - Audio Level Det
					Average Audio Level  cmdID= 3000  format=   "
		::= { iqsda02CmdEntry 3000 }


	iqsda02AudioLevelDetOverloadDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3006 "
		::= { iqsda02CmdEntry 3006 }


	iqsda02AudioLevelDetOverloadDetectorAlarm OBJECT-TYPE
		SYNTAX		RollCallString
		MAX-ACCESS		read-only
		STATUS			current
		DESCRIPTION
				"TYPE: - Display
				 PAGE: - Audio Level Det
					Alarm  cmdID= 3007  format=   "
		::= { iqsda02CmdEntry 3007 }


	iqsda02AudioLevelDetOverloadDetectorLeveldB OBJECT-TYPE
		SYNTAX		INTEGER
		MAX-ACCESS		read-write
		STATUS			current
		DESCRIPTION
				"TYPE: - Number
				 PAGE: - Audio Level Det
					Level (dB)  cmdID= 3002  min= -15  max= 0  step= 1  format= %0.0f  div_scale= 1
					Min = -15  Max = 0  Step = 1 "
		::= { iqsda02CmdEntry 3002 }


	iqsda02AudioLevelDetOverloadDetectorWarningsecs OBJECT-TYPE
		SYNTAX		INTEGER
		MAX-ACCESS		read-write
		STATUS			current
		DESCRIPTION
				"TYPE: - Number
				 PAGE: - Audio Level Det
					Warning (secs)  cmdID= 3003  min= 1  max= 120  step= 1  format= %0.0f  div_scale= 1
					Min = 1  Max = 120  Step = 1 "
		::= { iqsda02CmdEntry 3003 }


	iqsda02AudioLevelDetOverloadDetectorFailsecs OBJECT-TYPE
		SYNTAX		INTEGER
		MAX-ACCESS		read-write
		STATUS			current
		DESCRIPTION
				"TYPE: - Number
				 PAGE: - Audio Level Det
					Fail (secs)  cmdID= 3004  min= 1  max= 120  step= 1  format= %0.0f  div_scale= 1
					Min = 1  Max = 120  Step = 1 "
		::= { iqsda02CmdEntry 3004 }


	iqsda02AudioLevelDetOverloadDetectorFailHoldsecs OBJECT-TYPE
		SYNTAX		INTEGER
		MAX-ACCESS		read-write
		STATUS			current
		DESCRIPTION
				"TYPE: - Number
				 PAGE: - Audio Level Det
					Fail Hold (secs)  cmdID= 3005  min= 1  max= 120  step= 1  format= %0.0f  div_scale= 1
					Min = 1  Max = 120  Step = 1 "
		::= { iqsda02CmdEntry 3005 }


	iqsda02AudioLevelDetOverloadDetectorAlarmReset OBJECT-TYPE
		SYNTAX		INTEGER {
							val_Alarm_Reset_Ch1(1),
							val_Alarm_Reset_Ch2(2),
							val_Alarm_Reset_Ch3(3),
							val_Alarm_Reset_Ch4(4)
							}
		MAX-ACCESS		read-write
		STATUS			current
		DESCRIPTION
				"TYPE: - Button
				 PAGE: - Audio Level Det
					Alarm Reset  cmdID= 3032  value= 1
					Alarm Reset  cmdID= 3032  value= 2
					Alarm Reset  cmdID= 3032  value= 3
					Alarm Reset  cmdID= 3032  value= 4  "
		::= { iqsda02CmdEntry 3032 }


	iqsda02AudioLevelDetLoudDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3012 "
		::= { iqsda02CmdEntry 3012 }


	iqsda02AudioLevelDetLoudDetectorAlarm OBJECT-TYPE
		SYNTAX		RollCallString
		MAX-ACCESS		read-only
		STATUS			current
		DESCRIPTION
				"TYPE: - Display
				 PAGE: - Audio Level Det
					Alarm  cmdID= 3013  format=   "
		::= { iqsda02CmdEntry 3013 }


	iqsda02AudioLevelDetLoudDetectorLeveldB OBJECT-TYPE
		SYNTAX		INTEGER
		MAX-ACCESS		read-write
		STATUS			current
		DESCRIPTION
				"TYPE: - Number
				 PAGE: - Audio Level Det
					Level (dB)  cmdID= 3008  min= -25  max= 0  step= 1  format= %0.0f  div_scale= 1
					Min = -25  Max = 0  Step = 1 "
		::= { iqsda02CmdEntry 3008 }


	iqsda02AudioLevelDetLoudDetectorWarningsecs OBJECT-TYPE
		SYNTAX		INTEGER
		MAX-ACCESS		read-write
		STATUS			current
		DESCRIPTION
				"TYPE: - Number
				 PAGE: - Audio Level Det
					Warning (secs)  cmdID= 3009  min= 1  max= 120  step= 1  format= %0.0f  div_scale= 1
					Min = 1  Max = 120  Step = 1 "
		::= { iqsda02CmdEntry 3009 }


	iqsda02AudioLevelDetLoudDetectorFailsecs OBJECT-TYPE
		SYNTAX		INTEGER
		MAX-ACCESS		read-write
		STATUS			current
		DESCRIPTION
				"TYPE: - Number
				 PAGE: - Audio Level Det
					Fail (secs)  cmdID= 3010  min= 1  max= 120  step= 1  format= %0.0f  div_scale= 1
					Min = 1  Max = 120  Step = 1 "
		::= { iqsda02CmdEntry 3010 }


	iqsda02AudioLevelDetLoudDetectorFailHoldsecs OBJECT-TYPE
		SYNTAX		INTEGER
		MAX-ACCESS		read-write
		STATUS			current
		DESCRIPTION
				"TYPE: - Number
				 PAGE: - Audio Level Det
					Fail Hold (secs)  cmdID= 3011  min= 1  max= 120  step= 1  format= %0.0f  div_scale= 1
					Min = 1  Max = 120  Step = 1 "
		::= { iqsda02CmdEntry 3011 }


	iqsda02AudioLevelDetQuietDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3018 "
		::= { iqsda02CmdEntry 3018 }


	iqsda02AudioLevelDetQuietDetectorAlarm OBJECT-TYPE
		SYNTAX		RollCallString
		MAX-ACCESS		read-only
		STATUS			current
		DESCRIPTION
				"TYPE: - Display
				 PAGE: - Audio Level Det
					Alarm  cmdID= 3019  format=   "
		::= { iqsda02CmdEntry 3019 }


	iqsda02AudioLevelDetQuietDetectorLeveldB OBJECT-TYPE
		SYNTAX		INTEGER
		MAX-ACCESS		read-write
		STATUS			current
		DESCRIPTION
				"TYPE: - Number
				 PAGE: - Audio Level Det
					Level (dB)  cmdID= 3014  min= -50  max= -10  step= 1  format= %0.0f  div_scale= 1
					Min = -50  Max = -10  Step = 1 "
		::= { iqsda02CmdEntry 3014 }


	iqsda02AudioLevelDetQuietDetectorWarningsecs OBJECT-TYPE
		SYNTAX		INTEGER
		MAX-ACCESS		read-write
		STATUS			current
		DESCRIPTION
				"TYPE: - Number
				 PAGE: - Audio Level Det
					Warning (secs)  cmdID= 3015  min= 1  max= 120  step= 1  format= %0.0f  div_scale= 1
					Min = 1  Max = 120  Step = 1 "
		::= { iqsda02CmdEntry 3015 }


	iqsda02AudioLevelDetQuietDetectorFailsecs OBJECT-TYPE
		SYNTAX		INTEGER
		MAX-ACCESS		read-write
		STATUS			current
		DESCRIPTION
				"TYPE: - Number
				 PAGE: - Audio Level Det
					Fail (secs)  cmdID= 3016  min= 1  max= 120  step= 1  format= %0.0f  div_scale= 1
					Min = 1  Max = 120  Step = 1 "
		::= { iqsda02CmdEntry 3016 }


	iqsda02AudioLevelDetQuietDetectorFailHoldsecs OBJECT-TYPE
		SYNTAX		INTEGER
		MAX-ACCESS		read-write
		STATUS			current
		DESCRIPTION
				"TYPE: - Number
				 PAGE: - Audio Level Det
					Fail Hold (secs)  cmdID= 3017  min= 1  max= 120  step= 1  format= %0.0f  div_scale= 1
					Min = 1  Max = 120  Step = 1 "
		::= { iqsda02CmdEntry 3017 }


	iqsda02AudioLevelDetSilenceDetectorEnableAlarm OBJECT-TYPE
		SYNTAX		INTEGER { disable(0), enable(1) }
		MAX-ACCESS		read-write
		STATUS			current
		DESCRIPTION
				"TYPE: - Checkbox
				 PAGE: - Audio Level Det
					Enable Alarm  cmdID= 3024 "
		::= { iqsda02CmdEntry 3024 }


	iqsda02AudioLevelDetSilenceDetectorAlarm OBJECT-TYPE
		SYNTAX		RollCallString
		MAX-ACCESS		read-only
		STATUS			current
		DESCRIPTION
				"TYPE: - Display
				 PAGE: - Audio Level Det
					Alarm  cmdID= 3025  format=   "
		::= { iqsda02CmdEntry 3025 }


	iqsda02AudioLevelDetSilenceDetectorLeveldB OBJECT-TYPE
		SYNTAX		INTEGER
		MAX-ACCESS		read-write
		STATUS			current
		DESCRIPTION
				"TYPE: - Number
				 PAGE: - Audio Level Det
					Level (dB)  cmdID= 3020  min= -99  max= -60  step= 1  format= %0.0f  div_scale= 1
					Min = -99  Max = -60  Step = 1 "
		::= { iqsda02CmdEntry 3020 }


	iqsda02AudioLevelDetSilenceDetectorWarningsecs OBJECT-TYPE
		SYNTAX		INTEGER
		MAX-ACCESS		read-write
		STATUS			current
		DESCRIPTION
				"TYPE: - Number
				 PAGE: - Audio Level Det
					Warning (secs)  cmdID= 3021  min= 1  max= 120  step= 1  format= %0.0f  div_scale= 1
					Min = 1  Max = 120  Step = 1 "
		::= { iqsda02CmdEntry 3021 }


	iqsda02AudioLevelDetSilenceDetectorFailsecs OBJECT-TYPE
		SYNTAX		INTEGER
		MAX-ACCESS		read-write
		STATUS			current
		DESCRIPTION
				"TYPE: - Number
				 PAGE: - Audio Level Det
					Fail (secs)  cmdID= 3022  min= 1  max= 120  step= 1  format= %0.0f  div_scale= 1
					Min = 1  Max = 120  Step = 1 "
		::= { iqsda02CmdEntry 3022 }


	iqsda02AudioLevelDetSilenceDetectorFailHoldsecs OBJECT-TYPE
		SYNTAX		INTEGER
		MAX-ACCESS		read-write
		STATUS			current
		DESCRIPTION
				"TYPE: - Number
				 PAGE: - Audio Level Det
					Fail Hold (secs)  cmdID= 3023  min= 1  max= 120  step= 1  format= %0.0f  div_scale= 1
					Min = 1  Max = 120  Step = 1 "
		::= { iqsda02CmdEntry 3023 }


	iqsda02AudioLevelDetDuplicateSettingsCopyFromChannel OBJECT-TYPE
		SYNTAX		INTEGER
		MAX-ACCESS		read-write
		STATUS			current
		DESCRIPTION
				"TYPE: - Number
				 PAGE: - Audio Level Det
					Copy From Channel  cmdID= 3030  min= 1  max= 16  step= 1  format= %0.0f  div_scale= 1
					Min = 1  Max = 16  Step = 1 "
		::= { iqsda02CmdEntry 3030 }


	iqsda02AudioLevelDetDuplicateSettingsCopySettings OBJECT-TYPE
		SYNTAX		INTEGER { noAction(0),val_Copy_Settings(1) }
		MAX-ACCESS		read-write
		STATUS			current
		DESCRIPTION
				"TYPE: - Button
				 PAGE: - Audio Level Det
					Copy Settings  cmdID= 3031  value= 1  "
		::= { iqsda02CmdEntry 3031 }


	iqsda02HyperionAudioLevelDet OBJECT-TYPE
		SYNTAX		INTEGER {
							val_Enable_All_Chan_Det(17),
							val_Disable_All_Chan_De(16),
							}
		MAX-ACCESS		read-write
		STATUS			current
		DESCRIPTION
				"TYPE: - RadiobuttonList
				 PAGE: - Audio Level Det
					Alarm All Chans  cmdID= 3040
					Enable All Chan Det  value= 17
					Disable All Chan De  value= 16
					Alarm Indexed Chan  cmdID= 3040 "
		::= { iqsda02CmdEntry 3040 }


	iqsda02HyperionAudioLevelIndRollMapAudLvlEn OBJECT-TYPE
		SYNTAX		INTEGER { disable(0), enable(1) }
		MAX-ACCESS		read-write
		STATUS			current
		DESCRIPTION
				"TYPE: - Checkbox
				 PAGE: - Audio Level Ind
					RollMap Aud Lvl En  cmdID= 38275 "
		::= { iqsda02CmdEntry 38275 }


	iqsda02HyperionAudioLevelIndOSDMarker OBJECT-TYPE
		SYNTAX		INTEGER
		MAX-ACCESS		read-write
		STATUS			current
		DESCRIPTION
				"TYPE: - Number
				 PAGE: - Audio Level Ind
					OSD Marker  cmdID= 3150  min= -102  max= 0  step= 1  format= %0.0f  div_scale= 1
					Min = -102  Max = 0  Step = 1 "
		::= { iqsda02CmdEntry 3150 }


	iqsda02HyperionAudioLevelIndRollMapAudLvl OBJECT-TYPE
		SYNTAX		RollCallString
		MAX-ACCESS		read-only
		STATUS			current
		DESCRIPTION
				"TYPE: - Display
				 PAGE: - Audio Level Ind
					RollMap Aud Lvl  cmdID= 38276  format=   "
		::= { iqsda02CmdEntry 38276 }


	iqsda02HyperionAudioLevelIndEnableChannel1 OBJECT-TYPE
		SYNTAX		INTEGER { disable(0), enable(1) }
		MAX-ACCESS		read-write
		STATUS			current
		DESCRIPTION
				"TYPE: - Checkbox
				 PAGE: - Audio Level Ind
					Enable Channel 1  cmdID= 1582 "
		::= { iqsda02CmdEntry 1582 }


	iqsda02HyperionAudioLevelIndChannel1 OBJECT-TYPE
		SYNTAX		RollCallString
		MAX-ACCESS		read-only
		STATUS			current
		DESCRIPTION
				"TYPE: - Display
				 PAGE: - Audio Level Ind
					Channel 1  cmdID= 1566  format=   "
		::= { iqsda02CmdEntry 1566 }


	iqsda02HyperionAudioLevelIndEnableChannel2 OBJECT-TYPE
		SYNTAX		INTEGER { disable(0), enable(1) }
		MAX-ACCESS		read-write
		STATUS			current
		DESCRIPTION
				"TYPE: - Checkbox
				 PAGE: - Audio Level Ind
					Enable Channel 2  cmdID= 1583 "
		::= { iqsda02CmdEntry 1583 }


	iqsda02HyperionAudioLevelIndChannel2 OBJECT-TYPE
		SYNTAX		RollCallString
		MAX-ACCESS		read-only
		STATUS			current
		DESCRIPTION
				"TYPE: - Display
				 PAGE: - Audio Level Ind
					Channel 2  cmdID= 1567  format=   "
		::= { iqsda02CmdEntry 1567 }


	iqsda02HyperionAudioLevelIndEnableChannel3 OBJECT-TYPE
		SYNTAX		INTEGER { disable(0), enable(1) }
		MAX-ACCESS		read-write
		STATUS			current
		DESCRIPTION
				"TYPE: - Checkbox
				 PAGE: - Audio Level Ind
					Enable Channel 3  cmdID= 1584 "
		::= { iqsda02CmdEntry 1584 }


	iqsda02HyperionAudioLevelIndChannel3 OBJECT-TYPE
		SYNTAX		RollCallString
		MAX-ACCESS		read-only
		STATUS			current
		DESCRIPTION
				"TYPE: - Display
				 PAGE: - Audio Level Ind
					Channel 3  cmdID= 1568  format=   "
		::= { iqsda02CmdEntry 1568 }


	iqsda02HyperionAudioLevelIndEnableChannel4 OBJECT-TYPE
		SYNTAX		INTEGER { disable(0), enable(1) }
		MAX-ACCESS		read-write
		STATUS			current
		DESCRIPTION
				"TYPE: - Checkbox
				 PAGE: - Audio Level Ind
					Enable Channel 4  cmdID= 1585 "
		::= { iqsda02CmdEntry 1585 }


	iqsda02HyperionAudioLevelIndChannel4 OBJECT-TYPE
		SYNTAX		RollCallString
		MAX-ACCESS		read-only
		STATUS			current
		DESCRIPTION
				"TYPE: - Display
				 PAGE: - Audio Level Ind
					Channel 4  cmdID= 1569  format=   "
		::= { iqsda02CmdEntry 1569 }


	iqsda02HyperionAudioLevelIndEnableChannel5 OBJECT-TYPE
		SYNTAX		INTEGER { disable(0), enable(1) }
		MAX-ACCESS		read-write
		STATUS			current
		DESCRIPTION
				"TYPE: - Checkbox
				 PAGE: - Audio Level Ind
					Enable Channel 5  cmdID= 1586 "
		::= { iqsda02CmdEntry 1586 }


	iqsda02HyperionAudioLevelIndChannel5 OBJECT-TYPE
		SYNTAX		RollCallString
		MAX-ACCESS		read-only
		STATUS			current
		DESCRIPTION
				"TYPE: - Display
				 PAGE: - Audio Level Ind
					Channel 5  cmdID= 1570  format=   "
		::= { iqsda02CmdEntry 1570 }


	iqsda02HyperionAudioLevelIndEnableChannel6 OBJECT-TYPE
		SYNTAX		INTEGER { disable(0), enable(1) }
		MAX-ACCESS		read-write
		STATUS			current
		DESCRIPTION
				"TYPE: - Checkbox
				 PAGE: - Audio Level Ind
					Enable Channel 6  cmdID= 1587 "
		::= { iqsda02CmdEntry 1587 }


	iqsda02HyperionAudioLevelIndChannel6 OBJECT-TYPE
		SYNTAX		RollCallString
		MAX-ACCESS		read-only
		STATUS			current
		DESCRIPTION
				"TYPE: - Display
				 PAGE: - Audio Level Ind
					Channel 6  cmdID= 1571  format=   "
		::= { iqsda02CmdEntry 1571 }


	iqsda02HyperionAudioLevelIndEnableChannel7 OBJECT-TYPE
		SYNTAX		INTEGER { disable(0), enable(1) }
		MAX-ACCESS		read-write
		STATUS			current
		DESCRIPTION
				"TYPE: - Checkbox
				 PAGE: - Audio Level Ind
					Enable Channel 7  cmdID= 1588 "
		::= { iqsda02CmdEntry 1588 }


	iqsda02HyperionAudioLevelIndChannel7 OBJECT-TYPE
		SYNTAX		RollCallString
		MAX-ACCESS		read-only
		STATUS			current
		DESCRIPTION
				"TYPE: - Display
				 PAGE: - Audio Level Ind
					Channel 7  cmdID= 1572  format=   "
		::= { iqsda02CmdEntry 1572 }


	iqsda02HyperionAudioLevelIndEnableChannel8 OBJECT-TYPE
		SYNTAX		INTEGER { disable(0), enable(1) }
		MAX-ACCESS		read-write
		STATUS			current
		DESCRIPTION
				"TYPE: - Checkbox
				 PAGE: - Audio Level Ind
					Enable Channel 8  cmdID= 1589 "
		::= { iqsda02CmdEntry 1589 }


	iqsda02HyperionAudioLevelIndChannel8 OBJECT-TYPE
		SYNTAX		RollCallString
		MAX-ACCESS		read-only
		STATUS			current
		DESCRIPTION
				"TYPE: - Display
				 PAGE: - Audio Level Ind
					Channel 8  cmdID= 1573  format=   "
		::= { iqsda02CmdEntry 1573 }


	iqsda02HyperionAudioLevelIndEnableChannel9 OBJECT-TYPE
		SYNTAX		INTEGER { disable(0), enable(1) }
		MAX-ACCESS		read-write
		STATUS			current
		DESCRIPTION
				"TYPE: - Checkbox
				 PAGE: - Audio Level Ind
					Enable Channel 9  cmdID= 1590 "
		::= { iqsda02CmdEntry 1590 }


	iqsda02HyperionAudioLevelIndChannel9 OBJECT-TYPE
		SYNTAX		RollCallString
		MAX-ACCESS		read-only
		STATUS			current
		DESCRIPTION
				"TYPE: - Display
				 PAGE: - Audio Level Ind
					Channel 9  cmdID= 1574  format=   "
		::= { iqsda02CmdEntry 1574 }


	iqsda02HyperionAudioLevelIndEnableChannel10 OBJECT-TYPE
		SYNTAX		INTEGER { disable(0), enable(1) }
		MAX-ACCESS		read-write
		STATUS			current
		DESCRIPTION
				"TYPE: - Checkbox
				 PAGE: - Audio Level Ind
					Enable Channel 10  cmdID= 1591 "
		::= { iqsda02CmdEntry 1591 }


	iqsda02HyperionAudioLevelIndChannel10 OBJECT-TYPE
		SYNTAX		RollCallString
		MAX-ACCESS		read-only
		STATUS			current
		DESCRIPTION
				"TYPE: - Display
				 PAGE: - Audio Level Ind
					Channel 10  cmdID= 1575  format=   "
		::= { iqsda02CmdEntry 1575 }


	iqsda02HyperionAudioLevelIndEnableChannel11 OBJECT-TYPE
		SYNTAX		INTEGER { disable(0), enable(1) }
		MAX-ACCESS		read-write
		STATUS			current
		DESCRIPTION
				"TYPE: - Checkbox
				 PAGE: - Audio Level Ind
					Enable Channel 11  cmdID= 1592 "
		::= { iqsda02CmdEntry 1592 }


	iqsda02HyperionAudioLevelIndChannel11 OBJECT-TYPE
		SYNTAX		RollCallString
		MAX-ACCESS		read-only
		STATUS			current
		DESCRIPTION
				"TYPE: - Display
				 PAGE: - Audio Level Ind
					Channel 11  cmdID= 1576  format=   "
		::= { iqsda02CmdEntry 1576 }


	iqsda02HyperionAudioLevelIndEnableChannel12 OBJECT-TYPE
		SYNTAX		INTEGER { disable(0), enable(1) }
		MAX-ACCESS		read-write
		STATUS			current
		DESCRIPTION
				"TYPE: - Checkbox
				 PAGE: - Audio Level Ind
					Enable Channel 12  cmdID= 1593 "
		::= { iqsda02CmdEntry 1593 }


	iqsda02HyperionAudioLevelIndChannel12 OBJECT-TYPE
		SYNTAX		RollCallString
		MAX-ACCESS		read-only
		STATUS			current
		DESCRIPTION
				"TYPE: - Display
				 PAGE: - Audio Level Ind
					Channel 12  cmdID= 1577  format=   "
		::= { iqsda02CmdEntry 1577 }


	iqsda02HyperionAudioLevelIndEnableChannel13 OBJECT-TYPE
		SYNTAX		INTEGER { disable(0), enable(1) }
		MAX-ACCESS		read-write
		STATUS			current
		DESCRIPTION
				"TYPE: - Checkbox
				 PAGE: - Audio Level Ind
					Enable Channel 13  cmdID= 1594 "
		::= { iqsda02CmdEntry 1594 }


	iqsda02HyperionAudioLevelIndChannel13 OBJECT-TYPE
		SYNTAX		RollCallString
		MAX-ACCESS		read-only
		STATUS			current
		DESCRIPTION
				"TYPE: - Display
				 PAGE: - Audio Level Ind
					Channel 13  cmdID= 1578  format=   "
		::= { iqsda02CmdEntry 1578 }


	iqsda02HyperionAudioLevelIndEnableChannel14 OBJECT-TYPE
		SYNTAX		INTEGER { disable(0), enable(1) }
		MAX-ACCESS		read-write
		STATUS			current
		DESCRIPTION
				"TYPE: - Checkbox
				 PAGE: - Audio Level Ind
					Enable Channel 14  cmdID= 1595 "
		::= { iqsda02CmdEntry 1595 }


	iqsda02HyperionAudioLevelIndChannel14 OBJECT-TYPE
		SYNTAX		RollCallString
		MAX-ACCESS		read-only
		STATUS			current
		DESCRIPTION
				"TYPE: - Display
				 PAGE: - Audio Level Ind
					Channel 14  cmdID= 1579  format=   "
		::= { iqsda02CmdEntry 1579 }


	iqsda02HyperionAudioLevelIndEnableChannel15 OBJECT-TYPE
		SYNTAX		INTEGER { disable(0), enable(1) }
		MAX-ACCESS		read-write
		STATUS			current
		DESCRIPTION
				"TYPE: - Checkbox
				 PAGE: - Audio Level Ind
					Enable Channel 15  cmdID= 1596 "
		::= { iqsda02CmdEntry 1596 }


	iqsda02HyperionAudioLevelIndChannel15 OBJECT-TYPE
		SYNTAX		RollCallString
		MAX-ACCESS		read-only
		STATUS			current
		DESCRIPTION
				"TYPE: - Display
				 PAGE: - Audio Level Ind
					Channel 15  cmdID= 1580  format=   "
		::= { iqsda02CmdEntry 1580 }


	iqsda02HyperionAudioLevelIndEnableChannel16 OBJECT-TYPE
		SYNTAX		INTEGER { disable(0), enable(1) }
		MAX-ACCESS		read-write
		STATUS			current
		DESCRIPTION
				"TYPE: - Checkbox
				 PAGE: - Audio Level Ind
					Enable Channel 16  cmdID= 1597 "
		::= { iqsda02CmdEntry 1597 }


	iqsda02HyperionAudioLevelIndChannel16 OBJECT-TYPE
		SYNTAX		RollCallString
		MAX-ACCESS		read-only
		STATUS			current
		DESCRIPTION
				"TYPE: - Display
				 PAGE: - Audio Level Ind
					Channel 16  cmdID= 1581  format=   "
		::= { iqsda02CmdEntry 1581 }


	iqsda02HyperionClippingDetectorThreshold OBJECT-TYPE
		SYNTAX		INTEGER
		MAX-ACCESS		read-write
		STATUS			current
		DESCRIPTION
				"TYPE: - Number
				 PAGE: - Clipping Detector
					Threshold  cmdID= 3140  min= 0  max= 4  step= 1  format= %0.0f  div_scale= 1
					Min = 0  Max = 4  Step = 1 "
		::= { iqsda02CmdEntry 3140 }


	iqsda02HyperionClippingDetectorSensitivity OBJECT-TYPE
		SYNTAX		INTEGER
		MAX-ACCESS		read-write
		STATUS			current
		DESCRIPTION
				"TYPE: - Number
				 PAGE: - Clipping Detector
					Sensitivity  cmdID= 3141  min= 1  max= 100  step= 1  format= %0.0f  div_scale= 1
					Min = 1  Max = 100  Step = 1 "
		::= { iqsda02CmdEntry 3141 }


	iqsda02HyperionClippingDetectorStatusCh1 OBJECT-TYPE
		SYNTAX		RollCallString
		MAX-ACCESS		read-only
		STATUS			current
		DESCRIPTION
				"TYPE: - Display
				 PAGE: - Clipping Detector
					Status Ch 1  cmdID= 3180  format=   "
		::= { iqsda02CmdEntry 3180 }


	iqsda02HyperionClippingDetectorEnableAlarmCh1 OBJECT-TYPE
		SYNTAX		INTEGER { disable(0), enable(1) }
		MAX-ACCESS		read-write
		STATUS			current
		DESCRIPTION
				"TYPE: - Checkbox
				 PAGE: - Clipping Detector
					Enable Alarm Ch 1  cmdID= 3220 "
		::= { iqsda02CmdEntry 3220 }


	iqsda02HyperionClippingDetectorStatusCh2 OBJECT-TYPE
		SYNTAX		RollCallString
		MAX-ACCESS		read-only
		STATUS			current
		DESCRIPTION
				"TYPE: - Display
				 PAGE: - Clipping Detector
					Status Ch 2  cmdID= 3181  format=   "
		::= { iqsda02CmdEntry 3181 }


	iqsda02HyperionClippingDetectorEnableAlarmCh2 OBJECT-TYPE
		SYNTAX		INTEGER { disable(0), enable(1) }
		MAX-ACCESS		read-write
		STATUS			current
		DESCRIPTION
				"TYPE: - Checkbox
				 PAGE: - Clipping Detector
					Enable Alarm Ch 2  cmdID= 3221 "
		::= { iqsda02CmdEntry 3221 }


	iqsda02HyperionClippingDetectorStatusCh3 OBJECT-TYPE
		SYNTAX		RollCallString
		MAX-ACCESS		read-only
		STATUS			current
		DESCRIPTION
				"TYPE: - Display
				 PAGE: - Clipping Detector
					Status Ch 3  cmdID= 3182  format=   "
		::= { iqsda02CmdEntry 3182 }


	iqsda02HyperionClippingDetectorEnableAlarmCh3 OBJECT-TYPE
		SYNTAX		INTEGER { disable(0), enable(1) }
		MAX-ACCESS		read-write
		STATUS			current
		DESCRIPTION
				"TYPE: - Checkbox
				 PAGE: - Clipping Detector
					Enable Alarm Ch 3  cmdID= 3222 "
		::= { iqsda02CmdEntry 3222 }


	iqsda02HyperionClippingDetectorStatusCh4 OBJECT-TYPE
		SYNTAX		RollCallString
		MAX-ACCESS		read-only
		STATUS			current
		DESCRIPTION
				"TYPE: - Display
				 PAGE: - Clipping Detector
					Status Ch 4  cmdID= 3183  format=   "
		::= { iqsda02CmdEntry 3183 }


	iqsda02HyperionClippingDetectorEnableAlarmCh4 OBJECT-TYPE
		SYNTAX		INTEGER { disable(0), enable(1) }
		MAX-ACCESS		read-write
		STATUS			current
		DESCRIPTION
				"TYPE: - Checkbox
				 PAGE: - Clipping Detector
					Enable Alarm Ch 4  cmdID= 3223 "
		::= { iqsda02CmdEntry 3223 }


	iqsda02HyperionClippingDetectorStatusCh5 OBJECT-TYPE
		SYNTAX		RollCallString
		MAX-ACCESS		read-only
		STATUS			current
		DESCRIPTION
				"TYPE: - Display
				 PAGE: - Clipping Detector
					Status Ch 5  cmdID= 3184  format=   "
		::= { iqsda02CmdEntry 3184 }


	iqsda02HyperionClippingDetectorEnableAlarmCh5 OBJECT-TYPE
		SYNTAX		INTEGER { disable(0), enable(1) }
		MAX-ACCESS		read-write
		STATUS			current
		DESCRIPTION
				"TYPE: - Checkbox
				 PAGE: - Clipping Detector
					Enable Alarm Ch 5  cmdID= 3224 "
		::= { iqsda02CmdEntry 3224 }


	iqsda02HyperionClippingDetectorStatusCh6 OBJECT-TYPE
		SYNTAX		RollCallString
		MAX-ACCESS		read-only
		STATUS			current
		DESCRIPTION
				"TYPE: - Display
				 PAGE: - Clipping Detector
					Status Ch 6  cmdID= 3185  format=   "
		::= { iqsda02CmdEntry 3185 }


	iqsda02HyperionClippingDetectorEnableAlarmCh6 OBJECT-TYPE
		SYNTAX		INTEGER { disable(0), enable(1) }
		MAX-ACCESS		read-write
		STATUS			current
		DESCRIPTION
				"TYPE: - Checkbox
				 PAGE: - Clipping Detector
					Enable Alarm Ch 6  cmdID= 3225 "
		::= { iqsda02CmdEntry 3225 }


	iqsda02HyperionClippingDetectorStatusCh7 OBJECT-TYPE
		SYNTAX		RollCallString
		MAX-ACCESS		read-only
		STATUS			current
		DESCRIPTION
				"TYPE: - Display
				 PAGE: - Clipping Detector
					Status Ch 7  cmdID= 3186  format=   "
		::= { iqsda02CmdEntry 3186 }


	iqsda02HyperionClippingDetectorEnableAlarmCh7 OBJECT-TYPE
		SYNTAX		INTEGER { disable(0), enable(1) }
		MAX-ACCESS		read-write
		STATUS			current
		DESCRIPTION
				"TYPE: - Checkbox
				 PAGE: - Clipping Detector
					Enable Alarm Ch 7  cmdID= 3226 "
		::= { iqsda02CmdEntry 3226 }


	iqsda02HyperionClippingDetectorStatusCh8 OBJECT-TYPE
		SYNTAX		RollCallString
		MAX-ACCESS		read-only
		STATUS			current
		DESCRIPTION
				"TYPE: - Display
				 PAGE: - Clipping Detector
					Status Ch 8  cmdID= 3187  format=   "
		::= { iqsda02CmdEntry 3187 }


	iqsda02HyperionClippingDetectorEnableAlarmCh8 OBJECT-TYPE
		SYNTAX		INTEGER { disable(0), enable(1) }
		MAX-ACCESS		read-write
		STATUS			current
		DESCRIPTION
				"TYPE: - Checkbox
				 PAGE: - Clipping Detector
					Enable Alarm Ch 8  cmdID= 3227 "
		::= { iqsda02CmdEntry 3227 }


	iqsda02HyperionClippingDetectorStatusCh9 OBJECT-TYPE
		SYNTAX		RollCallString
		MAX-ACCESS		read-only
		STATUS			current
		DESCRIPTION
				"TYPE: - Display
				 PAGE: - Clipping Detector
					Status Ch 9  cmdID= 3188  format=   "
		::= { iqsda02CmdEntry 3188 }


	iqsda02HyperionClippingDetectorEnableAlarmCh9 OBJECT-TYPE
		SYNTAX		INTEGER { disable(0), enable(1) }
		MAX-ACCESS		read-write
		STATUS			current
		DESCRIPTION
				"TYPE: - Checkbox
				 PAGE: - Clipping Detector
					Enable Alarm Ch 9  cmdID= 3228 "
		::= { iqsda02CmdEntry 3228 }


	iqsda02HyperionClippingDetectorStatusCh10 OBJECT-TYPE
		SYNTAX		RollCallString
		MAX-ACCESS		read-only
		STATUS			current
		DESCRIPTION
				"TYPE: - Display
				 PAGE: - Clipping Detector
					Status Ch 10  cmdID= 3189  format=   "
		::= { iqsda02CmdEntry 3189 }


	iqsda02HyperionClippingDetectorEnableAlarmCh10 OBJECT-TYPE
		SYNTAX		INTEGER { disable(0), enable(1) }
		MAX-ACCESS		read-write
		STATUS			current
		DESCRIPTION
				"TYPE: - Checkbox
				 PAGE: - Clipping Detector
					Enable Alarm Ch 10  cmdID= 3229 "
		::= { iqsda02CmdEntry 3229 }


	iqsda02HyperionClippingDetectorStatusCh11 OBJECT-TYPE
		SYNTAX		RollCallString
		MAX-ACCESS		read-only
		STATUS			current
		DESCRIPTION
				"TYPE: - Display
				 PAGE: - Clipping Detector
					Status Ch 11  cmdID= 3190  format=   "
		::= { iqsda02CmdEntry 3190 }


	iqsda02HyperionClippingDetectorEnableAlarmCh11 OBJECT-TYPE
		SYNTAX		INTEGER { disable(0), enable(1) }
		MAX-ACCESS		read-write
		STATUS			current
		DESCRIPTION
				"TYPE: - Checkbox
				 PAGE: - Clipping Detector
					Enable Alarm Ch 11  cmdID= 3230 "
		::= { iqsda02CmdEntry 3230 }


	iqsda02HyperionClippingDetectorStatusCh12 OBJECT-TYPE
		SYNTAX		RollCallString
		MAX-ACCESS		read-only
		STATUS			current
		DESCRIPTION
				"TYPE: - Display
				 PAGE: - Clipping Detector
					Status Ch 12  cmdID= 3191  format=   "
		::= { iqsda02CmdEntry 3191 }


	iqsda02HyperionClippingDetectorEnableAlarmCh12 OBJECT-TYPE
		SYNTAX		INTEGER { disable(0), enable(1) }
		MAX-ACCESS		read-write
		STATUS			current
		DESCRIPTION
				"TYPE: - Checkbox
				 PAGE: - Clipping Detector
					Enable Alarm Ch 12  cmdID= 3231 "
		::= { iqsda02CmdEntry 3231 }


	iqsda02HyperionClippingDetectorStatusCh13 OBJECT-TYPE
		SYNTAX		RollCallString
		MAX-ACCESS		read-only
		STATUS			current
		DESCRIPTION
				"TYPE: - Display
				 PAGE: - Clipping Detector
					Status Ch 13  cmdID= 3192  format=   "
		::= { iqsda02CmdEntry 3192 }


	iqsda02HyperionClippingDetectorEnableAlarmCh13 OBJECT-TYPE
		SYNTAX		INTEGER { disable(0), enable(1) }
		MAX-ACCESS		read-write
		STATUS			current
		DESCRIPTION
				"TYPE: - Checkbox
				 PAGE: - Clipping Detector
					Enable Alarm Ch 13  cmdID= 3232 "
		::= { iqsda02CmdEntry 3232 }


	iqsda02HyperionClippingDetectorStatusCh14 OBJECT-TYPE
		SYNTAX		RollCallString
		MAX-ACCESS		read-only
		STATUS			current
		DESCRIPTION
				"TYPE: - Display
				 PAGE: - Clipping Detector
					Status Ch 14  cmdID= 3193  format=   "
		::= { iqsda02CmdEntry 3193 }


	iqsda02HyperionClippingDetectorEnableAlarmCh14 OBJECT-TYPE
		SYNTAX		INTEGER { disable(0), enable(1) }
		MAX-ACCESS		read-write
		STATUS			current
		DESCRIPTION
				"TYPE: - Checkbox
				 PAGE: - Clipping Detector
					Enable Alarm Ch 14  cmdID= 3233 "
		::= { iqsda02CmdEntry 3233 }


	iqsda02HyperionClippingDetectorStatusCh15 OBJECT-TYPE
		SYNTAX		RollCallString
		MAX-ACCESS		read-only
		STATUS			current
		DESCRIPTION
				"TYPE: - Display
				 PAGE: - Clipping Detector
					Status Ch 15  cmdID= 3194  format=   "
		::= { iqsda02CmdEntry 3194 }


	iqsda02HyperionClippingDetectorEnableAlarmCh15 OBJECT-TYPE
		SYNTAX		INTEGER { disable(0), enable(1) }
		MAX-ACCESS		read-write
		STATUS			current
		DESCRIPTION
				"TYPE: - Checkbox
				 PAGE: - Clipping Detector
					Enable Alarm Ch 15  cmdID= 3234 "
		::= { iqsda02CmdEntry 3234 }


	iqsda02HyperionClippingDetectorStatusCh16 OBJECT-TYPE
		SYNTAX		RollCallString
		MAX-ACCESS		read-only
		STATUS			current
		DESCRIPTION
				"TYPE: - Display
				 PAGE: - Clipping Detector
					Status Ch 16  cmdID= 3195  format=   "
		::= { iqsda02CmdEntry 3195 }


	iqsda02HyperionClippingDetectorEnableAlarmCh16 OBJECT-TYPE
		SYNTAX		INTEGER { disable(0), enable(1) }
		MAX-ACCESS		read-write
		STATUS			current
		DESCRIPTION
				"TYPE: - Checkbox
				 PAGE: - Clipping Detector
					Enable Alarm Ch 16  cmdID= 3235 "
		::= { iqsda02CmdEntry 3235 }


	iqsda02AudioLikenessDetector1Likeness OBJECT-TYPE
		SYNTAX		RollCallString
		MAX-ACCESS		read-only
		STATUS			current
		DESCRIPTION
				"TYPE: - Display
				 PAGE: - Audio Likeness
					Likeness  cmdID= 3120  format=   "
		::= { iqsda02CmdEntry 3120 }


	iqsda02AudioLikenessDetector1State OBJECT-TYPE
		SYNTAX		RollCallString
		MAX-ACCESS		read-only
		STATUS			current
		DESCRIPTION
				"TYPE: - Display
				 PAGE: - Audio Likeness
					State  cmdID= 3130  format=   "
		::= { iqsda02CmdEntry 3130 }


	iqsda02AudioLikenessDetector1SelectChannelA OBJECT-TYPE
		SYNTAX		INTEGER
		MAX-ACCESS		read-write
		STATUS			current
		DESCRIPTION
				"TYPE: - Number
				 PAGE: - Audio Likeness
					Select Channel A  cmdID= 3100  min= 1  max= 16  step= 1  format= %0.0f  div_scale= 1
					Min = 1  Max = 16  Step = 1 "
		::= { iqsda02CmdEntry 3100 }


	iqsda02AudioLikenessDetector1SelectChannelB OBJECT-TYPE
		SYNTAX		INTEGER
		MAX-ACCESS		read-write
		STATUS			current
		DESCRIPTION
				"TYPE: - Number
				 PAGE: - Audio Likeness
					Select Channel B  cmdID= 3101  min= 1  max= 16  step= 1  format= %0.0f  div_scale= 1
					Min = 1  Max = 16  Step = 1 "
		::= { iqsda02CmdEntry 3101 }


	iqsda02AudioLikenessDetector1EnableAlarm OBJECT-TYPE
		SYNTAX		INTEGER { disable(0), enable(1) }
		MAX-ACCESS		read-write
		STATUS			current
		DESCRIPTION
				"TYPE: - Checkbox
				 PAGE: - Audio Likeness
					Enable Alarm  cmdID= 3108 "
		::= { iqsda02CmdEntry 3108 }


	iqsda02AudioLikenessDetector2Likeness OBJECT-TYPE
		SYNTAX		RollCallString
		MAX-ACCESS		read-only
		STATUS			current
		DESCRIPTION
				"TYPE: - Display
				 PAGE: - Audio Likeness
					Likeness  cmdID= 3121  format=   "
		::= { iqsda02CmdEntry 3121 }


	iqsda02AudioLikenessDetector2State OBJECT-TYPE
		SYNTAX		RollCallString
		MAX-ACCESS		read-only
		STATUS			current
		DESCRIPTION
				"TYPE: - Display
				 PAGE: - Audio Likeness
					State  cmdID= 3131  format=   "
		::= { iqsda02CmdEntry 3131 }


	iqsda02AudioLikenessDetector2SelectChannelA OBJECT-TYPE
		SYNTAX		INTEGER
		MAX-ACCESS		read-write
		STATUS			current
		DESCRIPTION
				"TYPE: - Number
				 PAGE: - Audio Likeness
					Select Channel A  cmdID= 3102  min= 1  max= 16  step= 1  format= %0.0f  div_scale= 1
					Min = 1  Max = 16  Step = 1 "
		::= { iqsda02CmdEntry 3102 }


	iqsda02AudioLikenessDetector2SelectChannelB OBJECT-TYPE
		SYNTAX		INTEGER
		MAX-ACCESS		read-write
		STATUS			current
		DESCRIPTION
				"TYPE: - Number
				 PAGE: - Audio Likeness
					Select Channel B  cmdID= 3103  min= 1  max= 16  step= 1  format= %0.0f  div_scale= 1
					Min = 1  Max = 16  Step = 1 "
		::= { iqsda02CmdEntry 3103 }


	iqsda02AudioLikenessDetector2AlarmEnable OBJECT-TYPE
		SYNTAX		INTEGER { disable(0), enable(1) }
		MAX-ACCESS		read-write
		STATUS			current
		DESCRIPTION
				"TYPE: - Checkbox
				 PAGE: - Audio Likeness
					Alarm Enable  cmdID= 3109 "
		::= { iqsda02CmdEntry 3109 }


	iqsda02AudioLikenessDetector3Likeness OBJECT-TYPE
		SYNTAX		RollCallString
		MAX-ACCESS		read-only
		STATUS			current
		DESCRIPTION
				"TYPE: - Display
				 PAGE: - Audio Likeness
					Likeness  cmdID= 3122  format=   "
		::= { iqsda02CmdEntry 3122 }


	iqsda02AudioLikenessDetector3State OBJECT-TYPE
		SYNTAX		RollCallString
		MAX-ACCESS		read-only
		STATUS			current
		DESCRIPTION
				"TYPE: - Display
				 PAGE: - Audio Likeness
					State  cmdID= 3132  format=   "
		::= { iqsda02CmdEntry 3132 }


	iqsda02AudioLikenessDetector3SelectChannelA OBJECT-TYPE
		SYNTAX		INTEGER
		MAX-ACCESS		read-write
		STATUS			current
		DESCRIPTION
				"TYPE: - Number
				 PAGE: - Audio Likeness
					Select Channel A  cmdID= 3104  min= 1  max= 16  step= 1  format= %0.0f  div_scale= 1
					Min = 1  Max = 16  Step = 1 "
		::= { iqsda02CmdEntry 3104 }


	iqsda02AudioLikenessDetector3SelectChannelB OBJECT-TYPE
		SYNTAX		INTEGER
		MAX-ACCESS		read-write
		STATUS			current
		DESCRIPTION
				"TYPE: - Number
				 PAGE: - Audio Likeness
					Select Channel B  cmdID= 3105  min= 1  max= 16  step= 1  format= %0.0f  div_scale= 1
					Min = 1  Max = 16  Step = 1 "
		::= { iqsda02CmdEntry 3105 }


	iqsda02AudioLikenessDetector3AlarmEnable OBJECT-TYPE
		SYNTAX		INTEGER { disable(0), enable(1) }
		MAX-ACCESS		read-write
		STATUS			current
		DESCRIPTION
				"TYPE: - Checkbox
				 PAGE: - Audio Likeness
					Alarm Enable  cmdID= 3110 "
		::= { iqsda02CmdEntry 3110 }


	iqsda02AudioLikenessDetector4Likeness OBJECT-TYPE
		SYNTAX		RollCallString
		MAX-ACCESS		read-only
		STATUS			current
		DESCRIPTION
				"TYPE: - Display
				 PAGE: - Audio Likeness
					Likeness  cmdID= 3123  format=   "
		::= { iqsda02CmdEntry 3123 }


	iqsda02AudioLikenessDetector4State OBJECT-TYPE
		SYNTAX		RollCallString
		MAX-ACCESS		read-only
		STATUS			current
		DESCRIPTION
				"TYPE: - Display
				 PAGE: - Audio Likeness
					State  cmdID= 3133  format=   "
		::= { iqsda02CmdEntry 3133 }


	iqsda02AudioLikenessDetector4SelectChannelA OBJECT-TYPE
		SYNTAX		INTEGER
		MAX-ACCESS		read-write
		STATUS			current
		DESCRIPTION
				"TYPE: - Number
				 PAGE: - Audio Likeness
					Select Channel A  cmdID= 3106  min= 1  max= 16  step= 1  format= %0.0f  div_scale= 1
					Min = 1  Max = 16  Step = 1 "
		::= { iqsda02CmdEntry 3106 }


	iqsda02AudioLikenessDetector4SelectChannelB OBJECT-TYPE
		SYNTAX		INTEGER
		MAX-ACCESS		read-write
		STATUS			current
		DESCRIPTION
				"TYPE: - Number
				 PAGE: - Audio Likeness
					Select Channel B  cmdID= 3107  min= 1  max= 16  step= 1  format= %0.0f  div_scale= 1
					Min = 1  Max = 16  Step = 1 "
		::= { iqsda02CmdEntry 3107 }


	iqsda02AudioLikenessDetector4AlarmEnable OBJECT-TYPE
		SYNTAX		INTEGER { disable(0), enable(1) }
		MAX-ACCESS		read-write
		STATUS			current
		DESCRIPTION
				"TYPE: - Checkbox
				 PAGE: - Audio Likeness
					Alarm Enable  cmdID= 3111 "
		::= { iqsda02CmdEntry 3111 }


	iqsda02UMIDReaderDetectonYOnly OBJECT-TYPE
		SYNTAX		INTEGER { disable(0), enable(1) }
		MAX-ACCESS		read-write
		STATUS			current
		DESCRIPTION
				"TYPE: - Checkbox
				 PAGE: - UMID
					Detect on Y Only  cmdID= 1742 "
		::= { iqsda02CmdEntry 1742 }


	iqsda02UMIDReaderUMIDPresence OBJECT-TYPE
		SYNTAX		RollCallString
		MAX-ACCESS		read-only
		STATUS			current
		DESCRIPTION
				"TYPE: - Display
				 PAGE: - UMID
					UMID Presence  cmdID= 1730  format=   "
		::= { iqsda02CmdEntry 1730 }


	iqsda02UMIDReaderFoundOnLine OBJECT-TYPE
		SYNTAX		RollCallString
		MAX-ACCESS		read-only
		STATUS			current
		DESCRIPTION
				"TYPE: - Display
				 PAGE: - UMID
					Found On Line:  cmdID= 1731  format=   "
		::= { iqsda02CmdEntry 1731 }


	iqsda02ReaderUniversalLabelVersionNumber OBJECT-TYPE
		SYNTAX		RollCallString
		MAX-ACCESS		read-only
		STATUS			current
		DESCRIPTION
				"TYPE: - Display
				 PAGE: - UMID
					Version Number  cmdID= 1732  format=   "
		::= { iqsda02CmdEntry 1732 }


	iqsda02ReaderUniversalLabelMaterialType OBJECT-TYPE
		SYNTAX		RollCallString
		MAX-ACCESS		read-only
		STATUS			current
		DESCRIPTION
				"TYPE: - Display
				 PAGE: - UMID
					Material Type  cmdID= 1733  format=   "
		::= { iqsda02CmdEntry 1733 }


	iqsda02ReaderUniversalLabelIdentMatNumGen OBJECT-TYPE
		SYNTAX		RollCallString
		MAX-ACCESS		read-only
		STATUS			current
		DESCRIPTION
				"TYPE: - Display
				 PAGE: - UMID
					Ident Mat Num Gen  cmdID= 1734  format=   "
		::= { iqsda02CmdEntry 1734 }


	iqsda02ReaderUniversalLabelIdentInstNumGen OBJECT-TYPE
		SYNTAX		RollCallString
		MAX-ACCESS		read-only
		STATUS			current
		DESCRIPTION
				"TYPE: - Display
				 PAGE: - UMID
					Ident Inst Num Gen  cmdID= 1735  format=   "
		::= { iqsda02CmdEntry 1735 }


	iqsda02UMIDReaderInstanceNumber OBJECT-TYPE
		SYNTAX		RollCallString
		MAX-ACCESS		read-only
		STATUS			current
		DESCRIPTION
				"TYPE: - Display
				 PAGE: - UMID
					Instance Number  cmdID= 1736  format=   "
		::= { iqsda02CmdEntry 1736 }


	iqsda02ReaderMaterialNumber1_4 OBJECT-TYPE
		SYNTAX		RollCallString
		MAX-ACCESS		read-only
		STATUS			current
		DESCRIPTION
				"TYPE: - Display
				 PAGE: - UMID
					Material Num 1-4  cmdID= 1737  format=   "
		::= { iqsda02CmdEntry 1737 }


	iqsda02ReaderMaterialNumber5_8 OBJECT-TYPE
		SYNTAX		RollCallString
		MAX-ACCESS		read-only
		STATUS			current
		DESCRIPTION
				"TYPE: - Display
				 PAGE: - UMID
					Material Num 5-8  cmdID= 1738  format=   "
		::= { iqsda02CmdEntry 1738 }


	iqsda02ReaderMaterialNumber9_12 OBJECT-TYPE
		SYNTAX		RollCallString
		MAX-ACCESS		read-only
		STATUS			current
		DESCRIPTION
				"TYPE: - Display
				 PAGE: - UMID
					Material Num 9-12  cmdID= 1739  format=   "
		::= { iqsda02CmdEntry 1739 }


	iqsda02ReaderMaterialNumber13_16 OBJECT-TYPE
		SYNTAX		RollCallString
		MAX-ACCESS		read-only
		STATUS			current
		DESCRIPTION
				"TYPE: - Display
				 PAGE: - UMID
					Material Num 13-16  cmdID= 1740  format=   "
		::= { iqsda02CmdEntry 1740 }


	iqsda02UMIDReaderCount OBJECT-TYPE
		SYNTAX		RollCallString
		MAX-ACCESS		read-only
		STATUS			current
		DESCRIPTION
				"TYPE: - Display
				 PAGE: - UMID
					Count  cmdID= 1741  format=   "
		::= { iqsda02CmdEntry 1741 }


	iqsda02HyperionUMIDUMIDDelete OBJECT-TYPE
		SYNTAX		INTEGER { disable(0), enable(1) }
		MAX-ACCESS		read-write
		STATUS			current
		DESCRIPTION
				"TYPE: - Checkbox
				 PAGE: - UMID
					UMID Delete  cmdID= 1720 "
		::= { iqsda02CmdEntry 1720 }


	iqsda02UMIDGeneratorEnable OBJECT-TYPE
		SYNTAX		INTEGER { disable(0), enable(1) }
		MAX-ACCESS		read-write
		STATUS			current
		DESCRIPTION
				"TYPE: - Checkbox
				 PAGE: - UMID
					Enable  cmdID= 1700 "
		::= { iqsda02CmdEntry 1700 }


	iqsda02UMIDGeneratorGeneratorStatus OBJECT-TYPE
		SYNTAX		RollCallString
		MAX-ACCESS		read-only
		STATUS			current
		DESCRIPTION
				"TYPE: - Display
				 PAGE: - UMID
					Generator Status  cmdID= 1713  format=   "
		::= { iqsda02CmdEntry 1713 }


	iqsda02UMIDGeneratorGenerateonYOnly OBJECT-TYPE
		SYNTAX		INTEGER { disable(0), enable(1) }
		MAX-ACCESS		read-write
		STATUS			current
		DESCRIPTION
				"TYPE: - Checkbox
				 PAGE: - UMID
					Generate on Y Only  cmdID= 1712 "
		::= { iqsda02CmdEntry 1712 }


	iqsda02UMIDGeneratorTake OBJECT-TYPE
		SYNTAX		INTEGER { noAction(0),val_Take(1) }
		MAX-ACCESS		read-write
		STATUS			current
		DESCRIPTION
				"TYPE: - Button
				 PAGE: - UMID
					Take  cmdID= 1711  value= 1  "
		::= { iqsda02CmdEntry 1711 }


	iqsda02UMIDGeneratorLineNumber OBJECT-TYPE
		SYNTAX		INTEGER {
							val_Line_8(8),
							val_Line_9(9),
							val_Line_10(10),
							val_Line_11(11),
							val_Line_12(12),
							val_Line_13(13),
							val_Line_14(14),
							val_Line_15(15),
							val_Line_16(16),
							val_Line_17(17),
							val_Line_18(18),
							val_Line_19(19),
							val_Line_20(20)
							}
		MAX-ACCESS		read-write
		STATUS			current
		DESCRIPTION
				"TYPE: - RadiobuttonList
				 PAGE: - UMID
					Line Number  cmdID= 1701
					Line 8  value= 8
					Line 9  value= 9
					Line 10  value= 10
					Line 11  value= 11
					Line 12  value= 12
					Line 13  value= 13
					Line 14  value= 14
					Line 15  value= 15
					Line 16  value= 16
					Line 17  value= 17
					Line 18  value= 18
					Line 19  value= 19
					Line 20  value= 20  "
		::= { iqsda02CmdEntry 1701 }


	iqsda02GeneratorUniversalLabelVersionNumber OBJECT-TYPE
		SYNTAX		INTEGER
		MAX-ACCESS		read-write
		STATUS			current
		DESCRIPTION
				"TYPE: - Number
				 PAGE: - UMID
					Version Number  cmdID= 1703  min= 0  max= 255  step= 1  format= %0.0f  div_scale= 1
					Min = 0  Max = 255  Step = 1 "
		::= { iqsda02CmdEntry 1703 }


	iqsda02GeneratorUniversalLabelMaterialType OBJECT-TYPE
		SYNTAX		INTEGER
		MAX-ACCESS		read-write
		STATUS			current
		DESCRIPTION
				"TYPE: - Number
				 PAGE: - UMID
					Material Type  cmdID= 1704  min= 1  max= 15  step= 1  format= %0.0f  div_scale= 1
					Min = 1  Max = 15  Step = 1 "
		::= { iqsda02CmdEntry 1704 }


	iqsda02GeneratorUniversalLabelIdentofMaterial OBJECT-TYPE
		SYNTAX		INTEGER
		MAX-ACCESS		read-write
		STATUS			current
		DESCRIPTION
				"TYPE: - Number
				 PAGE: - UMID
					Ident of Material  cmdID= 1705  min= 0  max= 7  step= 1  format= %0.0f  div_scale= 1
					Min = 0  Max = 7  Step = 1 "
		::= { iqsda02CmdEntry 1705 }


	iqsda02GeneratorUniversalLabelIdentofInstance OBJECT-TYPE
		SYNTAX		INTEGER
		MAX-ACCESS		read-write
		STATUS			current
		DESCRIPTION
				"TYPE: - Number
				 PAGE: - UMID
					Ident of Instance  cmdID= 1706  min= 0  max= 15  step= 1  format= %0.0f  div_scale= 1
					Min = 0  Max = 15  Step = 1 "
		::= { iqsda02CmdEntry 1706 }


	iqsda02UMIDGeneratorInstanceNum OBJECT-TYPE
		SYNTAX		RollCallString
		MAX-ACCESS		read-write
		STATUS			current
		DESCRIPTION
				"TYPE: - Editstring
				 PAGE: - UMID
					Instance Num  cmdID= 1702  "
		::= { iqsda02CmdEntry 1702 }


	iqsda02UMIDGeneratorMaterialNum1_4 OBJECT-TYPE
		SYNTAX		RollCallString
		MAX-ACCESS		read-write
		STATUS			current
		DESCRIPTION
				"TYPE: - Editstring
				 PAGE: - UMID
					Material Num 1-4  cmdID= 1707  "
		::= { iqsda02CmdEntry 1707 }


	iqsda02UMIDGeneratorMaterialNum5_8 OBJECT-TYPE
		SYNTAX		RollCallString
		MAX-ACCESS		read-write
		STATUS			current
		DESCRIPTION
				"TYPE: - Editstring
				 PAGE: - UMID
					Material Num 5-8  cmdID= 1708  "
		::= { iqsda02CmdEntry 1708 }


	iqsda02UMIDGeneratorMaterialNum9_12 OBJECT-TYPE
		SYNTAX		RollCallString
		MAX-ACCESS		read-write
		STATUS			current
		DESCRIPTION
				"TYPE: - Editstring
				 PAGE: - UMID
					Material Num 9-12  cmdID= 1709  "
		::= { iqsda02CmdEntry 1709 }


	iqsda02UMIDGeneratorMaterialNum13_16 OBJECT-TYPE
		SYNTAX		RollCallString
		MAX-ACCESS		read-write
		STATUS			current
		DESCRIPTION
				"TYPE: - Editstring
				 PAGE: - UMID
					Material Num 13-16  cmdID= 1710  "
		::= { iqsda02CmdEntry 1710 }


	iqsda02HyperionUMIDUMIDAlarmEnable OBJECT-TYPE
		SYNTAX		INTEGER { disable(0), enable(1) }
		MAX-ACCESS		read-write
		STATUS			current
		DESCRIPTION
				"TYPE: - Checkbox
				 PAGE: - UMID
					UMID Alarm Enable  cmdID= 1744 "
		::= { iqsda02CmdEntry 1744 }


	iqsda02PIDReaderPIDPresence OBJECT-TYPE
		SYNTAX		RollCallString
		MAX-ACCESS		read-only
		STATUS			current
		DESCRIPTION
				"TYPE: - Display
				 PAGE: - PID
					PID Presence  cmdID= 1930  format=   "
		::= { iqsda02CmdEntry 1930 }


	iqsda02PIDReaderFoundOnLine OBJECT-TYPE
		SYNTAX		RollCallString
		MAX-ACCESS		read-only
		STATUS			current
		DESCRIPTION
				"TYPE: - Display
				 PAGE: - PID
					Found On Line:  cmdID= 1932  format=   "
		::= { iqsda02CmdEntry 1932 }


	iqsda02PIDReaderHouseID OBJECT-TYPE
		SYNTAX		RollCallString
		MAX-ACCESS		read-only
		STATUS			current
		DESCRIPTION
				"TYPE: - Display
				 PAGE: - PID
					House ID  cmdID= 1931  format=   "
		::= { iqsda02CmdEntry 1931 }


	iqsda02PIDReaderProgramTitle OBJECT-TYPE
		SYNTAX		RollCallString
		MAX-ACCESS		read-only
		STATUS			current
		DESCRIPTION
				"TYPE: - Display
				 PAGE: - PID
					Program Title  cmdID= 1933  format=   "
		::= { iqsda02CmdEntry 1933 }


	iqsda02PIDReaderSegmentNumber OBJECT-TYPE
		SYNTAX		RollCallString
		MAX-ACCESS		read-only
		STATUS			current
		DESCRIPTION
				"TYPE: - Display
				 PAGE: - PID
					Segment Number  cmdID= 1934  format=   "
		::= { iqsda02CmdEntry 1934 }


	iqsda02PIDReaderDuration OBJECT-TYPE
		SYNTAX		RollCallString
		MAX-ACCESS		read-only
		STATUS			current
		DESCRIPTION
				"TYPE: - Display
				 PAGE: - PID
					Duration  cmdID= 1935  format=   "
		::= { iqsda02CmdEntry 1935 }


	iqsda02PIDReaderFrameRate OBJECT-TYPE
		SYNTAX		RollCallString
		MAX-ACCESS		read-only
		STATUS			current
		DESCRIPTION
				"TYPE: - Display
				 PAGE: - PID
					Frame Rate  cmdID= 1936  format=   "
		::= { iqsda02CmdEntry 1936 }


	iqsda02PIDReaderCount OBJECT-TYPE
		SYNTAX		RollCallString
		MAX-ACCESS		read-only
		STATUS			current
		DESCRIPTION
				"TYPE: - Display
				 PAGE: - PID
					Count  cmdID= 1937  format=   "
		::= { iqsda02CmdEntry 1937 }


	iqsda02HyperionPIDPIDDelete OBJECT-TYPE
		SYNTAX		INTEGER { disable(0), enable(1) }
		MAX-ACCESS		read-write
		STATUS			current
		DESCRIPTION
				"TYPE: - Checkbox
				 PAGE: - PID
					PID Delete  cmdID= 1920 "
		::= { iqsda02CmdEntry 1920 }


	iqsda02PIDGeneratorEnable OBJECT-TYPE
		SYNTAX		INTEGER { disable(0), enable(1) }
		MAX-ACCESS		read-write
		STATUS			current
		DESCRIPTION
				"TYPE: - Checkbox
				 PAGE: - PID
					Enable  cmdID= 1900 "
		::= { iqsda02CmdEntry 1900 }


	iqsda02PIDGeneratorGeneratorStatus OBJECT-TYPE
		SYNTAX		RollCallString
		MAX-ACCESS		read-only
		STATUS			current
		DESCRIPTION
				"TYPE: - Display
				 PAGE: - PID
					Generator Status  cmdID= 1912  format=   "
		::= { iqsda02CmdEntry 1912 }


	iqsda02PIDGeneratorTake OBJECT-TYPE
		SYNTAX		INTEGER { noAction(0),val_Take(1) }
		MAX-ACCESS		read-write
		STATUS			current
		DESCRIPTION
				"TYPE: - Button
				 PAGE: - PID
					Take  cmdID= 1911  value= 1  "
		::= { iqsda02CmdEntry 1911 }


	iqsda02PIDGeneratorLineNumber OBJECT-TYPE
		SYNTAX		INTEGER {
							val_Line_8(8),
							val_Line_9(9),
							val_Line_10(10),
							val_Line_11(11),
							val_Line_12(12),
							val_Line_13(13),
							val_Line_14(14),
							val_Line_15(15),
							val_Line_16(16),
							val_Line_17(17),
							val_Line_18(18),
							val_Line_19(19),
							val_Line_20(20)
							}
		MAX-ACCESS		read-write
		STATUS			current
		DESCRIPTION
				"TYPE: - RadiobuttonList
				 PAGE: - PID
					Line Number  cmdID= 1901
					Line 8  value= 8
					Line 9  value= 9
					Line 10  value= 10
					Line 11  value= 11
					Line 12  value= 12
					Line 13  value= 13
					Line 14  value= 14
					Line 15  value= 15
					Line 16  value= 16
					Line 17  value= 17
					Line 18  value= 18
					Line 19  value= 19
					Line 20  value= 20  "
		::= { iqsda02CmdEntry 1901 }


	iqsda02PIDGeneratorHouseID OBJECT-TYPE
		SYNTAX		RollCallString
		MAX-ACCESS		read-write
		STATUS			current
		DESCRIPTION
				"TYPE: - Editstring
				 PAGE: - PID
					House ID  cmdID= 1902  "
		::= { iqsda02CmdEntry 1902 }


	iqsda02PIDGeneratorProgramTitle OBJECT-TYPE
		SYNTAX		RollCallString
		MAX-ACCESS		read-write
		STATUS			current
		DESCRIPTION
				"TYPE: - Editstring
				 PAGE: - PID
					Program Title  cmdID= 1903  "
		::= { iqsda02CmdEntry 1903 }


	iqsda02PIDGeneratorProgramTitleEn OBJECT-TYPE
		SYNTAX		INTEGER { disable(0), enable(1) }
		MAX-ACCESS		read-write
		STATUS			current
		DESCRIPTION
				"TYPE: - Checkbox
				 PAGE: - PID
					Program Title En  cmdID= 1907 "
		::= { iqsda02CmdEntry 1907 }


	iqsda02PIDGeneratorSegmentNumber OBJECT-TYPE
		SYNTAX		RollCallString
		MAX-ACCESS		read-write
		STATUS			current
		DESCRIPTION
				"TYPE: - Editstring
				 PAGE: - PID
					Segment Number  cmdID= 1904  "
		::= { iqsda02CmdEntry 1904 }


	iqsda02PIDGeneratorSegmentNumberEn OBJECT-TYPE
		SYNTAX		INTEGER { disable(0), enable(1) }
		MAX-ACCESS		read-write
		STATUS			current
		DESCRIPTION
				"TYPE: - Checkbox
				 PAGE: - PID
					Segment Number En  cmdID= 1908 "
		::= { iqsda02CmdEntry 1908 }


	iqsda02PIDGeneratorDuration OBJECT-TYPE
		SYNTAX		RollCallString
		MAX-ACCESS		read-write
		STATUS			current
		DESCRIPTION
				"TYPE: - Editstring
				 PAGE: - PID
					Duration  cmdID= 1905  "
		::= { iqsda02CmdEntry 1905 }


	iqsda02PIDGeneratorDurationEn OBJECT-TYPE
		SYNTAX		INTEGER { disable(0), enable(1) }
		MAX-ACCESS		read-write
		STATUS			current
		DESCRIPTION
				"TYPE: - Checkbox
				 PAGE: - PID
					Duration En  cmdID= 1909 "
		::= { iqsda02CmdEntry 1909 }


	iqsda02PIDGeneratorFrameRateEn OBJECT-TYPE
		SYNTAX		INTEGER { disable(0), enable(1) }
		MAX-ACCESS		read-write
		STATUS			current
		DESCRIPTION
				"TYPE: - Checkbox
				 PAGE: - PID
					Frame Rate En  cmdID= 1910 "
		::= { iqsda02CmdEntry 1910 }


	iqsda02PIDGeneratorFrameRate OBJECT-TYPE
		SYNTAX		INTEGER {
							val_Follow_Input(0),
							val_23_976(1),
							val_24_000(2),
							val_25_000(3),
							val_29_970(4),
							val_30_000(5),
							val_50_000(6),
							val_59_940(7),
							val_60_000(8)
							}
		MAX-ACCESS		read-write
		STATUS			current
		DESCRIPTION
				"TYPE: - RadiobuttonList
				 PAGE: - PID
					Frame Rate  cmdID= 1906
					Follow Input  value= 0
					23.976  value= 1
					24.000  value= 2
					25.000  value= 3
					29.970  value= 4
					30.000  value= 5
					50.000  value= 6
					59.940  value= 7
					60.000  value= 8  "
		::= { iqsda02CmdEntry 1906 }


	iqsda02HyperionPIDPIDAlarmEnable OBJECT-TYPE
		SYNTAX		INTEGER { disable(0), enable(1) }
		MAX-ACCESS		read-write
		STATUS			current
		DESCRIPTION
				"TYPE: - Checkbox
				 PAGE: - PID
					PID Alarm Enable  cmdID= 1938 "
		::= { iqsda02CmdEntry 1938 }


	iqsda02HyperionOSDOSDPassword OBJECT-TYPE
		SYNTAX		RollCallString
		MAX-ACCESS		read-write
		STATUS			current
		DESCRIPTION
				"TYPE: - Editstring
				 PAGE: - OSD
					OSD Password: !!!  cmdID= 5001  "
		::= { iqsda02CmdEntry 5001 }


	iqsda02HyperionOSDOSDEnable OBJECT-TYPE
		SYNTAX		INTEGER { disable(0), enable(1) }
		MAX-ACCESS		read-write
		STATUS			current
		DESCRIPTION
				"TYPE: - Checkbox
				 PAGE: - OSD
					OSD Enable  cmdID= 5000 "
		::= { iqsda02CmdEntry 5000 }


	iqsda02HyperionOSDOSDEnableoutput7 OBJECT-TYPE
		SYNTAX		INTEGER { disable(0), enable(1) }
		MAX-ACCESS		read-write
		STATUS			current
		DESCRIPTION
				"TYPE: - Checkbox
				 PAGE: - OSD
					OSD Enable output 7  cmdID= 5019 "
		::= { iqsda02CmdEntry 5019 }


	iqsda02OSDStillishDetWindowOSWinEn OBJECT-TYPE
		SYNTAX		INTEGER { disable(0), enable(1) }
		MAX-ACCESS		read-write
		STATUS			current
		DESCRIPTION
				"TYPE: - Checkbox
				 PAGE: - OSD
					OS Win En  cmdID= 1212 "
		::= { iqsda02CmdEntry 1212 }


	iqsda02OSDStillishDetWindowXPosition OBJECT-TYPE
		SYNTAX		INTEGER
		MAX-ACCESS		read-write
		STATUS			current
		DESCRIPTION
				"TYPE: - Number
				 PAGE: - OSD
					X Position  cmdID= 1208  min= 0  max= 3000  step= 1  format= %0.0f  div_scale= 1
					Min = 0  Max = 3000  Step = 1 "
		::= { iqsda02CmdEntry 1208 }


	iqsda02OSDStillishDetWindowWidth OBJECT-TYPE
		SYNTAX		INTEGER
		MAX-ACCESS		read-write
		STATUS			current
		DESCRIPTION
				"TYPE: - Number
				 PAGE: - OSD
					Width  cmdID= 1209  min= 0  max= 3000  step= 1  format= %0.0f  div_scale= 1
					Min = 0  Max = 3000  Step = 1 "
		::= { iqsda02CmdEntry 1209 }


	iqsda02OSDStillishDetWindowYPosition OBJECT-TYPE
		SYNTAX		INTEGER
		MAX-ACCESS		read-write
		STATUS			current
		DESCRIPTION
				"TYPE: - Number
				 PAGE: - OSD
					Y Position  cmdID= 1206  min= 0  max= 25000  step= 1  format= %0.0f  div_scale= 1
					Min = 0  Max = 25000  Step = 1 "
		::= { iqsda02CmdEntry 1206 }


	iqsda02OSDStillishDetWindowHeight OBJECT-TYPE
		SYNTAX		INTEGER
		MAX-ACCESS		read-write
		STATUS			current
		DESCRIPTION
				"TYPE: - Number
				 PAGE: - OSD
					Height  cmdID= 1207  min= 0  max= 25000  step= 1  format= %0.0f  div_scale= 1
					Min = 0  Max = 25000  Step = 1 "
		::= { iqsda02CmdEntry 1207 }


	iqsda02OSDStillishDetWindowWindowMode OBJECT-TYPE
		SYNTAX		INTEGER {
							val_Inside_Window(0),
							val_Outside_Window(1)
							}
		MAX-ACCESS		read-write
		STATUS			current
		DESCRIPTION
				"TYPE: - RadiobuttonList
				 PAGE: - OSD
					Window Mode  cmdID= 1205
					Inside Window  value= 0
					Outside Window  value= 1  "
		::= { iqsda02CmdEntry 1205 }


	iqsda02OSDStillishDetWindowDetectFullScreen OBJECT-TYPE
		SYNTAX		INTEGER { noAction(0),val_Detect_Full_Screen(1) }
		MAX-ACCESS		read-write
		STATUS			current
		DESCRIPTION
				"TYPE: - Button
				 PAGE: - OSD
					Detect Full Screen  cmdID= 1220  value= 1  "
		::= { iqsda02CmdEntry 1220 }


	iqsda02OSDBlackishDetWindowOSWinEn OBJECT-TYPE
		SYNTAX		INTEGER { disable(0), enable(1) }
		MAX-ACCESS		read-write
		STATUS			current
		DESCRIPTION
				"TYPE: - Checkbox
				 PAGE: - OSD
					OS Win En  cmdID= 1227 "
		::= { iqsda02CmdEntry 1227 }


	iqsda02OSDBlackishDetWindowXPosition OBJECT-TYPE
		SYNTAX		INTEGER
		MAX-ACCESS		read-write
		STATUS			current
		DESCRIPTION
				"TYPE: - Number
				 PAGE: - OSD
					X Position  cmdID= 1222  min= 0  max= 3000  step= 1  format= %0.0f  div_scale= 1
					Min = 0  Max = 3000  Step = 1 "
		::= { iqsda02CmdEntry 1222 }


	iqsda02OSDBlackishDetWindowWidth OBJECT-TYPE
		SYNTAX		INTEGER
		MAX-ACCESS		read-write
		STATUS			current
		DESCRIPTION
				"TYPE: - Number
				 PAGE: - OSD
					Width  cmdID= 1223  min= 0  max= 3000  step= 1  format= %0.0f  div_scale= 1
					Min = 0  Max = 3000  Step = 1 "
		::= { iqsda02CmdEntry 1223 }


	iqsda02OSDBlackishDetWindowYPosition OBJECT-TYPE
		SYNTAX		INTEGER
		MAX-ACCESS		read-write
		STATUS			current
		DESCRIPTION
				"TYPE: - Number
				 PAGE: - OSD
					Y Position  cmdID= 1224  min= 0  max= 25000  step= 1  format= %0.0f  div_scale= 1
					Min = 0  Max = 25000  Step = 1 "
		::= { iqsda02CmdEntry 1224 }


	iqsda02OSDBlackishDetWindowHeight OBJECT-TYPE
		SYNTAX		INTEGER
		MAX-ACCESS		read-write
		STATUS			current
		DESCRIPTION
				"TYPE: - Number
				 PAGE: - OSD
					Height  cmdID= 1225  min= 0  max= 25000  step= 1  format= %0.0f  div_scale= 1
					Min = 0  Max = 25000  Step = 1 "
		::= { iqsda02CmdEntry 1225 }


	iqsda02OSDBlackishDetWindowWindowMode OBJECT-TYPE
		SYNTAX		INTEGER {
							val_Inside_Window(0),
							val_Outside_Window(1)
							}
		MAX-ACCESS		read-write
		STATUS			current
		DESCRIPTION
				"TYPE: - RadiobuttonList
				 PAGE: - OSD
					Window Mode  cmdID= 1229
					Inside Window  value= 0
					Outside Window  value= 1  "
		::= { iqsda02CmdEntry 1229 }


	iqsda02OSDBlackishDetWindowDetectFullScreen OBJECT-TYPE
		SYNTAX		INTEGER { noAction(0),val_Detect_Full_Screen(1) }
		MAX-ACCESS		read-write
		STATUS			current
		DESCRIPTION
				"TYPE: - Button
				 PAGE: - OSD
					Detect Full Screen  cmdID= 1242  value= 1  "
		::= { iqsda02CmdEntry 1242 }


	iqsda02OSDOnScreenDispEnIndicators OBJECT-TYPE
		SYNTAX		INTEGER { disable(0), enable(1) }
		MAX-ACCESS		read-write
		STATUS			current
		DESCRIPTION
				"TYPE: - Checkbox
				 PAGE: - OSD
					Indicators   cmdID= 5002 "
		::= { iqsda02CmdEntry 5002 }


	iqsda02OSDOnScreenDispEnAudioLevelInds OBJECT-TYPE
		SYNTAX		INTEGER { disable(0), enable(1) }
		MAX-ACCESS		read-write
		STATUS			current
		DESCRIPTION
				"TYPE: - Checkbox
				 PAGE: - OSD
					Audio Level Inds  cmdID= 5004 "
		::= { iqsda02CmdEntry 5004 }


	iqsda02OSDOnScreenDispEnTimecode OBJECT-TYPE
		SYNTAX		INTEGER { disable(0), enable(1) }
		MAX-ACCESS		read-write
		STATUS			current
		DESCRIPTION
				"TYPE: - Checkbox
				 PAGE: - OSD
					Timecode  cmdID= 5007 "
		::= { iqsda02CmdEntry 5007 }


	iqsda02OSDOnScreenDispEnGreyBackground OBJECT-TYPE
		SYNTAX		INTEGER { disable(0), enable(1) }
		MAX-ACCESS		read-write
		STATUS			current
		DESCRIPTION
				"TYPE: - Checkbox
				 PAGE: - OSD
					Grey Background  cmdID= 5015 "
		::= { iqsda02CmdEntry 5015 }


	iqsda02OSDOnScreenDispEnInput1Name OBJECT-TYPE
		SYNTAX		INTEGER { disable(0), enable(1) }
		MAX-ACCESS		read-write
		STATUS			current
		DESCRIPTION
				"TYPE: - Checkbox
				 PAGE: - OSD
					Input 1 Name  cmdID= 5010 "
		::= { iqsda02CmdEntry 5010 }


	iqsda02OSDOnScreenDispEnCaption1Edit OBJECT-TYPE
		SYNTAX		RollCallString
		MAX-ACCESS		read-write
		STATUS			current
		DESCRIPTION
				"TYPE: - Editstring
				 PAGE: - OSD
					Caption 1 Edit  cmdID= 5012  "
		::= { iqsda02CmdEntry 5012 }


	iqsda02OSDOnScreenDispEnCaption1Enable OBJECT-TYPE
		SYNTAX		INTEGER { disable(0), enable(1) }
		MAX-ACCESS		read-write
		STATUS			current
		DESCRIPTION
				"TYPE: - Checkbox
				 PAGE: - OSD
					Caption 1 Enable  cmdID= 5011 "
		::= { iqsda02CmdEntry 5011 }


	iqsda02OSDOnScreenDispEnCaption2Edit OBJECT-TYPE
		SYNTAX		RollCallString
		MAX-ACCESS		read-write
		STATUS			current
		DESCRIPTION
				"TYPE: - Editstring
				 PAGE: - OSD
					Caption 2 Edit  cmdID= 5014  "
		::= { iqsda02CmdEntry 5014 }


	iqsda02OSDOnScreenDispEnCaption2Enable OBJECT-TYPE
		SYNTAX		INTEGER { disable(0), enable(1) }
		MAX-ACCESS		read-write
		STATUS			current
		DESCRIPTION
				"TYPE: - Checkbox
				 PAGE: - OSD
					Caption 2 Enable  cmdID= 5013 "
		::= { iqsda02CmdEntry 5013 }


	iqsda02OSDOnScreenDispEnContentAdvisory OBJECT-TYPE
		SYNTAX		INTEGER { disable(0), enable(1) }
		MAX-ACCESS		read-write
		STATUS			current
		DESCRIPTION
				"TYPE: - Checkbox
				 PAGE: - OSD
					Content Advisory  cmdID= 5016 "
		::= { iqsda02CmdEntry 5016 }


	iqsda02OSDOnScreenDispEnIncomingPID OBJECT-TYPE
		SYNTAX		INTEGER { disable(0), enable(1) }
		MAX-ACCESS		read-write
		STATUS			current
		DESCRIPTION
				"TYPE: - Checkbox
				 PAGE: - OSD
					Incoming PID  cmdID= 5017 "
		::= { iqsda02CmdEntry 5017 }


	iqsda02OSDOnScreenDispEnOutgoingPID OBJECT-TYPE
		SYNTAX		INTEGER { disable(0), enable(1) }
		MAX-ACCESS		read-write
		STATUS			current
		DESCRIPTION
				"TYPE: - Checkbox
				 PAGE: - OSD
					Outgoing PID  cmdID= 5018 "
		::= { iqsda02CmdEntry 5018 }


	iqsda02OSDOnScreenDispEnAudioLvlIndZoom OBJECT-TYPE
		SYNTAX		INTEGER { disable(0), enable(1) }
		MAX-ACCESS		read-write
		STATUS			current
		DESCRIPTION
				"TYPE: - Checkbox
				 PAGE: - OSD
					Audio Lvl Ind Zoom  cmdID= 5003 "
		::= { iqsda02CmdEntry 5003 }


	iqsda02HyperionHyperionDetStatus OBJECT-TYPE
		SYNTAX		INTEGER
		MAX-ACCESS		read-write
		STATUS			current
		DESCRIPTION
				"TYPE: - Number
					Hyperion Det Status  cmdID= 5050  min= 0  max= 63  step= 1  format= %0.0f  div_scale= 1
					Min = 0  Max = 63  Step = 1 "
		::= { iqsda02CmdEntry 5050 }


	iqsda02MemoriesMemorySave OBJECT-TYPE
		SYNTAX		INTEGER {
							val_Save_1(1),
							val_Save_2(2),
							val_Save_3(3),
							val_Save_4(4),
							val_Save_5(5),
							val_Save_6(6),
							val_Save_7(7),
							val_Save_8(8),
							val_Save_9(9),
							val_Save_10(10),
							val_Save_11(11),
							val_Save_12(12),
							val_Save_13(13),
							val_Save_14(14),
							val_Save_15(15),
							val_Save_16(16)
							}
		MAX-ACCESS		read-write
		STATUS			current
		DESCRIPTION
				"TYPE: - Button
				 PAGE: - Memories
					Save 1  cmdID= 1600  value= 1
					Save 2  cmdID= 1600  value= 2
					Save 3  cmdID= 1600  value= 3
					Save 4  cmdID= 1600  value= 4
					Save 5  cmdID= 1600  value= 5
					Save 6  cmdID= 1600  value= 6
					Save 7  cmdID= 1600  value= 7
					Save 8  cmdID= 1600  value= 8
					Save 9  cmdID= 1600  value= 9
					Save 10  cmdID= 1600  value= 10
					Save 11  cmdID= 1600  value= 11
					Save 12  cmdID= 1600  value= 12
					Save 13  cmdID= 1600  value= 13
					Save 14  cmdID= 1600  value= 14
					Save 15  cmdID= 1600  value= 15
					Save 16  cmdID= 1600  value= 16  "
		::= { iqsda02CmdEntry 1600 }


	iqsda02MemoriesMemoryRecall OBJECT-TYPE
		SYNTAX		INTEGER {
							val_Recall_1(1),
							val_Recall_2(2),
							val_Recall_3(3),
							val_Recall_4(4),
							val_Recall_5(5),
							val_Recall_6(6),
							val_Recall_7(7),
							val_Recall_8(8),
							val_Recall_9(9),
							val_Recall_10(10),
							val_Recall_11(11),
							val_Recall_12(12),
							val_Recall_13(13),
							val_Recall_14(14),
							val_Recall_15(15),
							val_Recall_16(16)
							}
		MAX-ACCESS		read-write
		STATUS			current
		DESCRIPTION
				"TYPE: - Button
				 PAGE: - Memories
					Recall 1  cmdID= 1601  value= 1
					Recall 2  cmdID= 1601  value= 2
					Recall 3  cmdID= 1601  value= 3
					Recall 4  cmdID= 1601  value= 4
					Recall 5  cmdID= 1601  value= 5
					Recall 6  cmdID= 1601  value= 6
					Recall 7  cmdID= 1601  value= 7
					Recall 8  cmdID= 1601  value= 8
					Recall 9  cmdID= 1601  value= 9
					Recall 10  cmdID= 1601  value= 10
					Recall 11  cmdID= 1601  value= 11
					Recall 12  cmdID= 1601  value= 12
					Recall 13  cmdID= 1601  value= 13
					Recall 14  cmdID= 1601  value= 14
					Recall 15  cmdID= 1601  value= 15
					Recall 16  cmdID= 1601  value= 16  "
		::= { iqsda02CmdEntry 1601 }


	iqsda02MemoriesMemory1Name OBJECT-TYPE
		SYNTAX		RollCallString
		MAX-ACCESS		read-write
		STATUS			current
		DESCRIPTION
				"TYPE: - Editstring
				 PAGE: - Memories
					Name 1  cmdID= 5541  "
		::= { iqsda02CmdEntry 5541 }


	iqsda02MemoriesMemory2Name OBJECT-TYPE
		SYNTAX		RollCallString
		MAX-ACCESS		read-write
		STATUS			current
		DESCRIPTION
				"TYPE: - Editstring
				 PAGE: - Memories
					Name 2  cmdID= 5542  "
		::= { iqsda02CmdEntry 5542 }


	iqsda02MemoriesMemory3Name OBJECT-TYPE
		SYNTAX		RollCallString
		MAX-ACCESS		read-write
		STATUS			current
		DESCRIPTION
				"TYPE: - Editstring
				 PAGE: - Memories
					Name 3  cmdID= 5543  "
		::= { iqsda02CmdEntry 5543 }


	iqsda02MemoriesMemory4Name OBJECT-TYPE
		SYNTAX		RollCallString
		MAX-ACCESS		read-write
		STATUS			current
		DESCRIPTION
				"TYPE: - Editstring
				 PAGE: - Memories
					Name 4  cmdID= 5544  "
		::= { iqsda02CmdEntry 5544 }


	iqsda02MemoriesMemory5Name OBJECT-TYPE
		SYNTAX		RollCallString
		MAX-ACCESS		read-write
		STATUS			current
		DESCRIPTION
				"TYPE: - Editstring
				 PAGE: - Memories
					Name 5  cmdID= 5545  "
		::= { iqsda02CmdEntry 5545 }


	iqsda02MemoriesMemory6Name OBJECT-TYPE
		SYNTAX		RollCallString
		MAX-ACCESS		read-write
		STATUS			current
		DESCRIPTION
				"TYPE: - Editstring
				 PAGE: - Memories
					Name 6  cmdID= 5546  "
		::= { iqsda02CmdEntry 5546 }


	iqsda02MemoriesMemory7Name OBJECT-TYPE
		SYNTAX		RollCallString
		MAX-ACCESS		read-write
		STATUS			current
		DESCRIPTION
				"TYPE: - Editstring
				 PAGE: - Memories
					Name 7  cmdID= 5547  "
		::= { iqsda02CmdEntry 5547 }


	iqsda02MemoriesMemory8Name OBJECT-TYPE
		SYNTAX		RollCallString
		MAX-ACCESS		read-write
		STATUS			current
		DESCRIPTION
				"TYPE: - Editstring
				 PAGE: - Memories
					Name 8  cmdID= 5548  "
		::= { iqsda02CmdEntry 5548 }


	iqsda02MemoriesMemory9Name OBJECT-TYPE
		SYNTAX		RollCallString
		MAX-ACCESS		read-write
		STATUS			current
		DESCRIPTION
				"TYPE: - Editstring
				 PAGE: - Memories
					Name 9  cmdID= 5549  "
		::= { iqsda02CmdEntry 5549 }


	iqsda02MemoriesMemory10Name OBJECT-TYPE
		SYNTAX		RollCallString
		MAX-ACCESS		read-write
		STATUS			current
		DESCRIPTION
				"TYPE: - Editstring
				 PAGE: - Memories
					Name 10  cmdID= 5550  "
		::= { iqsda02CmdEntry 5550 }


	iqsda02MemoriesMemory11Name OBJECT-TYPE
		SYNTAX		RollCallString
		MAX-ACCESS		read-write
		STATUS			current
		DESCRIPTION
				"TYPE: - Editstring
				 PAGE: - Memories
					Name 11  cmdID= 5551  "
		::= { iqsda02CmdEntry 5551 }


	iqsda02MemoriesMemory12Name OBJECT-TYPE
		SYNTAX		RollCallString
		MAX-ACCESS		read-write
		STATUS			current
		DESCRIPTION
				"TYPE: - Editstring
				 PAGE: - Memories
					Name 12  cmdID= 5552  "
		::= { iqsda02CmdEntry 5552 }


	iqsda02MemoriesMemory13Name OBJECT-TYPE
		SYNTAX		RollCallString
		MAX-ACCESS		read-write
		STATUS			current
		DESCRIPTION
				"TYPE: - Editstring
				 PAGE: - Memories
					Name 13  cmdID= 5553  "
		::= { iqsda02CmdEntry 5553 }


	iqsda02MemoriesMemory14Name OBJECT-TYPE
		SYNTAX		RollCallString
		MAX-ACCESS		read-write
		STATUS			current
		DESCRIPTION
				"TYPE: - Editstring
				 PAGE: - Memories
					Name 14  cmdID= 5554  "
		::= { iqsda02CmdEntry 5554 }


	iqsda02MemoriesMemory15Name OBJECT-TYPE
		SYNTAX		RollCallString
		MAX-ACCESS		read-write
		STATUS			current
		DESCRIPTION
				"TYPE: - Editstring
				 PAGE: - Memories
					Name 15  cmdID= 5555  "
		::= { iqsda02CmdEntry 5555 }


	iqsda02MemoriesMemory16Name OBJECT-TYPE
		SYNTAX		RollCallString
		MAX-ACCESS		read-write
		STATUS			current
		DESCRIPTION
				"TYPE: - Editstring
				 PAGE: - Memories
					Name 16  cmdID= 5556  "
		::= { iqsda02CmdEntry 5556 }


	iqsda02LoggingMiscTimecodelogEnable OBJECT-TYPE
		SYNTAX		INTEGER { disable(0), enable(1) }
		MAX-ACCESS		read-write
		STATUS			current
		DESCRIPTION
				"TYPE: - Checkbox
				 PAGE: - Logging
					Timecode log En  cmdID= 35999 "
		::= { iqsda02CmdEntry 35999 }


	iqsda02LoggingMiscLogSerialNoEnable OBJECT-TYPE
		SYNTAX		INTEGER { disable(0), enable(1) }
		MAX-ACCESS		read-write
		STATUS			current
		DESCRIPTION
				"TYPE: - Checkbox
				 PAGE: - Logging
					Log Serial No.  cmdID= 1000 "
		::= { iqsda02CmdEntry 1000 }


	iqsda02LoggingMiscSerialNo OBJECT-TYPE
		SYNTAX		RollCallString
		MAX-ACCESS		read-only
		STATUS			current
		DESCRIPTION
				"TYPE: - Display
				 PAGE: - Logging
					Serial No.=  cmdID= 2000  format=   "
		::= { iqsda02CmdEntry 2000 }


	iqsda02LoggingMiscLogOSVersionEnable OBJECT-TYPE
		SYNTAX		INTEGER { disable(0), enable(1) }
		MAX-ACCESS		read-write
		STATUS			current
		DESCRIPTION
				"TYPE: - Checkbox
				 PAGE: - Logging
					Log OS Version  cmdID= 1001 "
		::= { iqsda02CmdEntry 1001 }


	iqsda02LoggingMiscOSVersion OBJECT-TYPE
		SYNTAX		RollCallString
		MAX-ACCESS		read-only
		STATUS			current
		DESCRIPTION
				"TYPE: - Display
				 PAGE: - Logging
					OS Version=  cmdID= 2001  format=   "
		::= { iqsda02CmdEntry 2001 }


	iqsda02LoggingMiscLogBuildNoEnable OBJECT-TYPE
		SYNTAX		INTEGER { disable(0), enable(1) }
		MAX-ACCESS		read-write
		STATUS			current
		DESCRIPTION
				"TYPE: - Checkbox
				 PAGE: - Logging
					Log Build No.  cmdID= 1002 "
		::= { iqsda02CmdEntry 1002 }


	iqsda02LoggingMiscBuildNo OBJECT-TYPE
		SYNTAX		RollCallString
		MAX-ACCESS		read-only
		STATUS			current
		DESCRIPTION
				"TYPE: - Display
				 PAGE: - Logging
					Build No.=  cmdID= 2002  format=   "
		::= { iqsda02CmdEntry 2002 }


	iqsda02LoggingMiscLogHardwareVerEnable OBJECT-TYPE
		SYNTAX		INTEGER { disable(0), enable(1) }
		MAX-ACCESS		read-write
		STATUS			current
		DESCRIPTION
				"TYPE: - Checkbox
				 PAGE: - Logging
					Log Hardware Ver.  cmdID= 1003 "
		::= { iqsda02CmdEntry 1003 }


	iqsda02LoggingMiscHardwareVer OBJECT-TYPE
		SYNTAX		RollCallString
		MAX-ACCESS		read-only
		STATUS			current
		DESCRIPTION
				"TYPE: - Display
				 PAGE: - Logging
					Hardware Ver.=  cmdID= 2003  format=   "
		::= { iqsda02CmdEntry 2003 }


	iqsda02LoggingMiscLogFirmwareVerEnable OBJECT-TYPE
		SYNTAX		INTEGER { disable(0), enable(1) }
		MAX-ACCESS		read-write
		STATUS			current
		DESCRIPTION
				"TYPE: - Checkbox
				 PAGE: - Logging
					Log Firmware Ver.  cmdID= 1004 "
		::= { iqsda02CmdEntry 1004 }


	iqsda02LoggingMiscFirmwareVer OBJECT-TYPE
		SYNTAX		RollCallString
		MAX-ACCESS		read-only
		STATUS			current
		DESCRIPTION
				"TYPE: - Display
				 PAGE: - Logging
					Firmware Ver.=  cmdID= 2004  format=   "
		::= { iqsda02CmdEntry 2004 }


	iqsda02LoggingMiscLogUpTimeEnable OBJECT-TYPE
		SYNTAX		INTEGER { disable(0), enable(1) }
		MAX-ACCESS		read-write
		STATUS			current
		DESCRIPTION
				"TYPE: - Checkbox
				 PAGE: - Logging
					Log Up Time  cmdID= 1005 "
		::= { iqsda02CmdEntry 1005 }


	iqsda02LoggingMiscUpTime OBJECT-TYPE
		SYNTAX		RollCallString
		MAX-ACCESS		read-only
		STATUS			current
		DESCRIPTION
				"TYPE: - Display
				 PAGE: - Logging
					Up Time=  cmdID= 2005  format=   "
		::= { iqsda02CmdEntry 2005 }


	iqsda02LoggingMiscRollTracksEnable OBJECT-TYPE
		SYNTAX		INTEGER { disable(0), enable(1) }
		MAX-ACCESS		read-write
		STATUS			current
		DESCRIPTION
				"TYPE: - Checkbox
				 PAGE: - Logging
					RollTracks  cmdID= 1158 "
		::= { iqsda02CmdEntry 1158 }


	iqsda02LoggingMiscRollTracks OBJECT-TYPE
		SYNTAX		RollCallString
		MAX-ACCESS		read-only
		STATUS			current
		DESCRIPTION
				"TYPE: - Display
				 PAGE: - Logging
					RollTracks=  cmdID= 2158  format=   "
		::= { iqsda02CmdEntry 2158 }


	iqsda02LoggingMiscOSDStatusEnable OBJECT-TYPE
		SYNTAX		INTEGER { disable(0), enable(1) }
		MAX-ACCESS		read-write
		STATUS			current
		DESCRIPTION
				"TYPE: - Checkbox
				 PAGE: - Logging
					OSD Status  cmdID= 1159 "
		::= { iqsda02CmdEntry 1159 }


	iqsda02LoggingMiscOSDStatus OBJECT-TYPE
		SYNTAX		RollCallString
		MAX-ACCESS		read-only
		STATUS			current
		DESCRIPTION
				"TYPE: - Display
				 PAGE: - Logging
					OSD Status=  cmdID= 2159  format=   "
		::= { iqsda02CmdEntry 2159 }


	iqsda02LoggingInput1InputIdentEnable OBJECT-TYPE
		SYNTAX		INTEGER { disable(0), enable(1) }
		MAX-ACCESS		read-write
		STATUS			current
		DESCRIPTION
				"TYPE: - Checkbox
				 PAGE: - Logging
					Input Ident  cmdID= 1130 "
		::= { iqsda02CmdEntry 1130 }


	iqsda02LoggingInput1InputIdent OBJECT-TYPE
		SYNTAX		RollCallString
		MAX-ACCESS		read-only
		STATUS			current
		DESCRIPTION
				"TYPE: - Display
				 PAGE: - Logging
					Input Ident=  cmdID= 2130  format=   "
		::= { iqsda02CmdEntry 2130 }


	iqsda02LoggingInput1InputNameEnable OBJECT-TYPE
		SYNTAX		INTEGER { disable(0), enable(1) }
		MAX-ACCESS		read-write
		STATUS			current
		DESCRIPTION
				"TYPE: - Checkbox
				 PAGE: - Logging
					Input Name  cmdID= 1095 "
		::= { iqsda02CmdEntry 1095 }


	iqsda02LoggingInput1InputName OBJECT-TYPE
		SYNTAX		RollCallString
		MAX-ACCESS		read-only
		STATUS			current
		DESCRIPTION
				"TYPE: - Display
				 PAGE: - Logging
					Input Name=  cmdID= 2095  format=   "
		::= { iqsda02CmdEntry 2095 }


	iqsda02LoggingInput1InputTypeEnable OBJECT-TYPE
		SYNTAX		INTEGER { disable(0), enable(1) }
		MAX-ACCESS		read-write
		STATUS			current
		DESCRIPTION
				"TYPE: - Checkbox
				 PAGE: - Logging
					Input Type  cmdID= 1096 "
		::= { iqsda02CmdEntry 1096 }


	iqsda02LoggingInput1InputType OBJECT-TYPE
		SYNTAX		RollCallString
		MAX-ACCESS		read-only
		STATUS			current
		DESCRIPTION
				"TYPE: - Display
				 PAGE: - Logging
					Input Type=  cmdID= 2096  format=   "
		::= { iqsda02CmdEntry 2096 }


	iqsda02LoggingInput1InputStateEnable OBJECT-TYPE
		SYNTAX		INTEGER { disable(0), enable(1) }
		MAX-ACCESS		read-write
		STATUS			current
		DESCRIPTION
				"TYPE: - Checkbox
				 PAGE: - Logging
					Input State  cmdID= 1006 "
		::= { iqsda02CmdEntry 1006 }


	iqsda02LoggingInput1InputState OBJECT-TYPE
		SYNTAX		RollCallString
		MAX-ACCESS		read-only
		STATUS			current
		DESCRIPTION
				"TYPE: - Display
				 PAGE: - Logging
					Input State=  cmdID= 2006  format=   "
		::= { iqsda02CmdEntry 2006 }


	iqsda02LoggingInput1InputStandardEnable OBJECT-TYPE
		SYNTAX		INTEGER { disable(0), enable(1) }
		MAX-ACCESS		read-write
		STATUS			current
		DESCRIPTION
				"TYPE: - Checkbox
				 PAGE: - Logging
					Input Standard  cmdID= 1007 "
		::= { iqsda02CmdEntry 1007 }


	iqsda02LoggingInput1InputStandard OBJECT-TYPE
		SYNTAX		RollCallString
		MAX-ACCESS		read-only
		STATUS			current
		DESCRIPTION
				"TYPE: - Display
				 PAGE: - Logging
					Input Standard=  cmdID= 2007  format=   "
		::= { iqsda02CmdEntry 2007 }


	iqsda02LoggingInput1EDHEnable OBJECT-TYPE
		SYNTAX		INTEGER { disable(0), enable(1) }
		MAX-ACCESS		read-write
		STATUS			current
		DESCRIPTION
				"TYPE: - Checkbox
				 PAGE: - Logging
					EDH  cmdID= 1093 "
		::= { iqsda02CmdEntry 1093 }


	iqsda02LoggingInput1EDH OBJECT-TYPE
		SYNTAX		RollCallString
		MAX-ACCESS		read-only
		STATUS			current
		DESCRIPTION
				"TYPE: - Display
				 PAGE: - Logging
					EDH=  cmdID= 2093  format=   "
		::= { iqsda02CmdEntry 2093 }


	iqsda02LoggingInput1CRCEnable OBJECT-TYPE
		SYNTAX		INTEGER { disable(0), enable(1) }
		MAX-ACCESS		read-write
		STATUS			current
		DESCRIPTION
				"TYPE: - Checkbox
				 PAGE: - Logging
					CRC  cmdID= 1094 "
		::= { iqsda02CmdEntry 1094 }


	iqsda02LoggingInput1CRC OBJECT-TYPE
		SYNTAX		RollCallString
		MAX-ACCESS		read-only
		STATUS			current
		DESCRIPTION
				"TYPE: - Display
				 PAGE: - Logging
					CRC=  cmdID= 2094  format=   "
		::= { iqsda02CmdEntry 2094 }


	iqsda02LoggingInp1Monitor1HyperionSummaryEnable OBJECT-TYPE
		SYNTAX		INTEGER { disable(0), enable(1) }
		MAX-ACCESS		read-write
		STATUS			current
		DESCRIPTION
				"TYPE: - Checkbox
				 PAGE: - Logging
					Hyperion Summary  cmdID= 1129 "
		::= { iqsda02CmdEntry 1129 }


	iqsda02LoggingInp1Monitor1HyperionSummary OBJECT-TYPE
		SYNTAX		RollCallString
		MAX-ACCESS		read-only
		STATUS			current
		DESCRIPTION
				"TYPE: - Display
				 PAGE: - Logging
					Hyperion Summary =  cmdID= 2129  format=   "
		::= { iqsda02CmdEntry 2129 }


	iqsda02LoggingInp1Monitor1StillishEnable OBJECT-TYPE
		SYNTAX		INTEGER { disable(0), enable(1) }
		MAX-ACCESS		read-write
		STATUS			current
		DESCRIPTION
				"TYPE: - Checkbox
				 PAGE: - Logging
					Stillish Enable  cmdID= 1008 "
		::= { iqsda02CmdEntry 1008 }


	iqsda02LoggingInp1Monitor1Stillish OBJECT-TYPE
		SYNTAX		RollCallString
		MAX-ACCESS		read-only
		STATUS			current
		DESCRIPTION
				"TYPE: - Display
				 PAGE: - Logging
					Stillish=  cmdID= 2008  format=   "
		::= { iqsda02CmdEntry 2008 }


	iqsda02LoggingInp1Monitor1StillishLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Stillish Log Option  cmdID= 3300
					Timecode At Start  value= 0
					Timecode At Fail  value= 1  "
		::= { iqsda02CmdEntry 3300 }


	iqsda02LoggingInp1Monitor1FreezeEnable OBJECT-TYPE
		SYNTAX		INTEGER { disable(0), enable(1) }
		MAX-ACCESS		read-write
		STATUS			current
		DESCRIPTION
				"TYPE: - Checkbox
				 PAGE: - Logging
					Freeze Enable  cmdID= 1131 "
		::= { iqsda02CmdEntry 1131 }


	iqsda02LoggingInp1Monitor1Freeze OBJECT-TYPE
		SYNTAX		RollCallString
		MAX-ACCESS		read-only
		STATUS			current
		DESCRIPTION
				"TYPE: - Display
				 PAGE: - Logging
					Freeze=  cmdID= 2131  format=   "
		::= { iqsda02CmdEntry 2131 }


	iqsda02LoggingInp1Monitor1FreezeLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Freeze Log Option  cmdID= 3301
					Timecode At Start  value= 0
					Timecode At Fail  value= 1  "
		::= { iqsda02CmdEntry 3301 }


	iqsda02LoggingInp1Monitor1BlackEnable OBJECT-TYPE
		SYNTAX		INTEGER { disable(0), enable(1) }
		MAX-ACCESS		read-write
		STATUS			current
		DESCRIPTION
				"TYPE: - Checkbox
				 PAGE: - Logging
					Black Enable  cmdID= 1009 "
		::= { iqsda02CmdEntry 1009 }


	iqsda02LoggingInp1Monitor1Black OBJECT-TYPE
		SYNTAX		RollCallString
		MAX-ACCESS		read-only
		STATUS			current
		DESCRIPTION
				"TYPE: - Display
				 PAGE: - Logging
					Black=  cmdID= 2009  format=   "
		::= { iqsda02CmdEntry 2009 }


	iqsda02LoggingInp1Monitor1BlackLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Black Log Option  cmdID= 3302
					Timecode At Start  value= 0
					Timecode At Fail  value= 1  "
		::= { iqsda02CmdEntry 3302 }


	iqsda02LoggingInp1Monitor1BlackishEnable OBJECT-TYPE
		SYNTAX		INTEGER { disable(0), enable(1) }
		MAX-ACCESS		read-write
		STATUS			current
		DESCRIPTION
				"TYPE: - Checkbox
				 PAGE: - Logging
					Blackish Enable  cmdID= 1010 "
		::= { iqsda02CmdEntry 1010 }


	iqsda02LoggingInp1Monitor1Blackish OBJECT-TYPE
		SYNTAX		RollCallString
		MAX-ACCESS		read-only
		STATUS			current
		DESCRIPTION
				"TYPE: - Display
				 PAGE: - Logging
					Blackish=  cmdID= 2010  format=   "
		::= { iqsda02CmdEntry 2010 }


	iqsda02LoggingInp1Monitor1BlackishLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Blackish Log Option  cmdID= 3303
					Timecode At Start  value= 0
					Timecode At Fail  value= 1  "
		::= { iqsda02CmdEntry 3303 }


	iqsda02LoggingInp1Monitor1CldCapStateEnable OBJECT-TYPE
		SYNTAX		INTEGER { disable(0), enable(1) }
		MAX-ACCESS		read-write
		STATUS			current
		DESCRIPTION
				"TYPE: - Checkbox
				 PAGE: - Logging
					Cld. Cap.State En  cmdID= 1011 "
		::= { iqsda02CmdEntry 1011 }


	iqsda02LoggingInp1Monitor1ClosedCapState OBJECT-TYPE
		SYNTAX		RollCallString
		MAX-ACCESS		read-only
		STATUS			current
		DESCRIPTION
				"TYPE: - Display
				 PAGE: - Logging
					Closed Cap. State =  cmdID= 2011  format=   "
		::= { iqsda02CmdEntry 2011 }


	iqsda02LoggingInp1Monitor1ClosedCapLogOption OBJECT-TYPE
		SYNTAX		INTEGER {
							val_Timecode_At_Start(0),
							val_Timecode_At_Fail(1)
							}
		MAX-ACCESS		read-write
		STATUS			current
		DESCRIPTION
				"TYPE: - RadiobuttonList
				 PAGE: - Logging
					Closed Cap Log Opt  cmdID= 3304
					Timecode At Start  value= 0
					Timecode At Fail  value= 1  "
		::= { iqsda02CmdEntry 3304 }


	iqsda02LoggingInp1Monitor1CldCapTypeEnable OBJECT-TYPE
		SYNTAX		INTEGER { disable(0), enable(1) }
		MAX-ACCESS		read-write
		STATUS			current
		DESCRIPTION
				"TYPE: - Checkbox
				 PAGE: - Logging
					Cld. Cap.Type En  cmdID= 1012 "
		::= { iqsda02CmdEntry 1012 }


	iqsda02LoggingInp1Monitor1ClosedCapType OBJECT-TYPE
		SYNTAX		RollCallString
		MAX-ACCESS		read-only
		STATUS			current
		DESCRIPTION
				"TYPE: - Display
				 PAGE: - Logging
					Closed Cap.Type=  cmdID= 2012  format=   "
		::= { iqsda02CmdEntry 2012 }


	iqsda02LoggingInp1Monitor1CldCapTitleEnable OBJECT-TYPE
		SYNTAX		INTEGER { disable(0), enable(1) }
		MAX-ACCESS		read-write
		STATUS			current
		DESCRIPTION
				"TYPE: - Checkbox
				 PAGE: - Logging
					Cld. Cap.Title En  cmdID= 1164 "
		::= { iqsda02CmdEntry 1164 }


	iqsda02LoggingInp1Monitor1ClosedCapTitle OBJECT-TYPE
		SYNTAX		RollCallString
		MAX-ACCESS		read-only
		STATUS			current
		DESCRIPTION
				"TYPE: - Display
				 PAGE: - Logging
					Closed Cap.Title=  cmdID= 2164  format=   "
		::= { iqsda02CmdEntry 2164 }


	iqsda02LoggingInp1Monitor2YBitDepthEnable OBJECT-TYPE
		SYNTAX		INTEGER { disable(0), enable(1) }
		MAX-ACCESS		read-write
		STATUS			current
		DESCRIPTION
				"TYPE: - Checkbox
				 PAGE: - Logging
					Y Bit Depth Enable  cmdID= 1017 "
		::= { iqsda02CmdEntry 1017 }


	iqsda02LoggingInp1Monitor2YBitDepth OBJECT-TYPE
		SYNTAX		RollCallString
		MAX-ACCESS		read-only
		STATUS			current
		DESCRIPTION
				"TYPE: - Display
				 PAGE: - Logging
					Y Bit Depth=  cmdID= 2017  format=   "
		::= { iqsda02CmdEntry 2017 }


	iqsda02LoggingInp1Monitor2CBitDepthEnable OBJECT-TYPE
		SYNTAX		INTEGER { disable(0), enable(1) }
		MAX-ACCESS		read-write
		STATUS			current
		DESCRIPTION
				"TYPE: - Checkbox
				 PAGE: - Logging
					C Bit Depth Enable  cmdID= 1018 "
		::= { iqsda02CmdEntry 1018 }


	iqsda02LoggingInp1Monitor2CBitDepth OBJECT-TYPE
		SYNTAX		RollCallString
		MAX-ACCESS		read-only
		STATUS			current
		DESCRIPTION
				"TYPE: - Display
				 PAGE: - Logging
					C Bit Depth=  cmdID= 2018  format=   "
		::= { iqsda02CmdEntry 2018 }


	iqsda02LoggingInp1Monitor2VideoYLvlHighEnable OBJECT-TYPE
		SYNTAX		INTEGER { disable(0), enable(1) }
		MAX-ACCESS		read-write
		STATUS			current
		DESCRIPTION
				"TYPE: - Checkbox
				 PAGE: - Logging
					Video Y Lvl. High E  cmdID= 1019 "
		::= { iqsda02CmdEntry 1019 }


	iqsda02LoggingInp1Monitor2VideoYLevelHigh OBJECT-TYPE
		SYNTAX		RollCallString
		MAX-ACCESS		read-only
		STATUS			current
		DESCRIPTION
				"TYPE: - Display
				 PAGE: - Logging
					Video Y Level High=  cmdID= 2019  format=   "
		::= { iqsda02CmdEntry 2019 }


	iqsda02LoggingInp1Monitor2VideoCLvlHighEnable OBJECT-TYPE
		SYNTAX		INTEGER { disable(0), enable(1) }
		MAX-ACCESS		read-write
		STATUS			current
		DESCRIPTION
				"TYPE: - Checkbox
				 PAGE: - Logging
					Video C Lvl. High E  cmdID= 1020 "
		::= { iqsda02CmdEntry 1020 }


	iqsda02LoggingInp1Monitor2VideoCLevelHigh OBJECT-TYPE
		SYNTAX		RollCallString
		MAX-ACCESS		read-only
		STATUS			current
		DESCRIPTION
				"TYPE: - Display
				 PAGE: - Logging
					Video C Level High=  cmdID= 2020  format=   "
		::= { iqsda02CmdEntry 2020 }


	iqsda02LoggingInp1Monitor2VideoYLvlLowEnable OBJECT-TYPE
		SYNTAX		INTEGER { disable(0), enable(1) }
		MAX-ACCESS		read-write
		STATUS			current
		DESCRIPTION
				"TYPE: - Checkbox
				 PAGE: - Logging
					Video Y Lvl. Low En  cmdID= 1021 "
		::= { iqsda02CmdEntry 1021 }


	iqsda02LoggingInp1Monitor2VideoYLevelLow OBJECT-TYPE
		SYNTAX		RollCallString
		MAX-ACCESS		read-only
		STATUS			current
		DESCRIPTION
				"TYPE: - Display
				 PAGE: - Logging
					Video Y Level Low=  cmdID= 2021  format=   "
		::= { iqsda02CmdEntry 2021 }


	iqsda02LoggingInp1Monitor2VideoCLvlLowEnable OBJECT-TYPE
		SYNTAX		INTEGER { disable(0), enable(1) }
		MAX-ACCESS		read-write
		STATUS			current
		DESCRIPTION
				"TYPE: - Checkbox
				 PAGE: - Logging
					Video C Lvl. Low En  cmdID= 1022 "
		::= { iqsda02CmdEntry 1022 }


	iqsda02LoggingInp1Monitor2VideoCLevelLow OBJECT-TYPE
		SYNTAX		RollCallString
		MAX-ACCESS		read-only
		STATUS			current
		DESCRIPTION
				"TYPE: - Display
				 PAGE: - Logging
					Video C Level Low=  cmdID= 2022  format=   "
		::= { iqsda02CmdEntry 2022 }


	iqsda02LoggingInp1Monitor2APLEnable OBJECT-TYPE
		SYNTAX		INTEGER { disable(0), enable(1) }
		MAX-ACCESS		read-write
		STATUS			current
		DESCRIPTION
				"TYPE: - Checkbox
				 PAGE: - Logging
					APL Enable  cmdID= 1023 "
		::= { iqsda02CmdEntry 1023 }


	iqsda02LoggingInp1Monitor2APL OBJECT-TYPE
		SYNTAX		RollCallString
		MAX-ACCESS		read-only
		STATUS			current
		DESCRIPTION
				"TYPE: - Display
				 PAGE: - Logging
					APL=  cmdID= 2023  format=   "
		::= { iqsda02CmdEntry 2023 }


	iqsda02LoggingInp1Monitor2VITCStateEnable OBJECT-TYPE
		SYNTAX		INTEGER { disable(0), enable(1) }
		MAX-ACCESS		read-write
		STATUS			current
		DESCRIPTION
				"TYPE: - Checkbox
				 PAGE: - Logging
					VITC State Enable  cmdID= 1024 "
		::= { iqsda02CmdEntry 1024 }


	iqsda02LoggingInp1Monitor2VITCState OBJECT-TYPE
		SYNTAX		RollCallString
		MAX-ACCESS		read-only
		STATUS			current
		DESCRIPTION
				"TYPE: - Display
				 PAGE: - Logging
					VITC State=  cmdID= 2024  format=   "
		::= { iqsda02CmdEntry 2024 }


	iqsda02LoggingInp1Monitor2CAStateEnable OBJECT-TYPE
		SYNTAX		INTEGER { disable(0), enable(1) }
		MAX-ACCESS		read-write
		STATUS			current
		DESCRIPTION
				"TYPE: - Checkbox
				 PAGE: - Logging
					CA State Enable  cmdID= 1025 "
		::= { iqsda02CmdEntry 1025 }


	iqsda02LoggingInp1Monitor2CAState OBJECT-TYPE
		SYNTAX		RollCallString
		MAX-ACCESS		read-only
		STATUS			current
		DESCRIPTION
				"TYPE: - Display
				 PAGE: - Logging
					CA State=  cmdID= 2025  format=   "
		::= { iqsda02CmdEntry 2025 }


	iqsda02LoggingInp1Monitor2CASystemEnable OBJECT-TYPE
		SYNTAX		INTEGER { disable(0), enable(1) }
		MAX-ACCESS		read-write
		STATUS			current
		DESCRIPTION
				"TYPE: - Checkbox
				 PAGE: - Logging
					CA System Enable  cmdID= 1026 "
		::= { iqsda02CmdEntry 1026 }


	iqsda02LoggingInp1Monitor2CASystem OBJECT-TYPE
		SYNTAX		RollCallString
		MAX-ACCESS		read-only
		STATUS			current
		DESCRIPTION
				"TYPE: - Display
				 PAGE: - Logging
					CA System=  cmdID= 2026  format=   "
		::= { iqsda02CmdEntry 2026 }


	iqsda02LoggingInp1Monitor2CAAgeRatingEnable OBJECT-TYPE
		SYNTAX		INTEGER { disable(0), enable(1) }
		MAX-ACCESS		read-write
		STATUS			current
		DESCRIPTION
				"TYPE: - Checkbox
				 PAGE: - Logging
					CA Age Rating En  cmdID= 1027 "
		::= { iqsda02CmdEntry 1027 }


	iqsda02LoggingInp1Monitor2CAAgeRating OBJECT-TYPE
		SYNTAX		RollCallString
		MAX-ACCESS		read-only
		STATUS			current
		DESCRIPTION
				"TYPE: - Display
				 PAGE: - Logging
					CA Age Rating=  cmdID= 2027  format=   "
		::= { iqsda02CmdEntry 2027 }


	iqsda02LoggingInp1Monitor2ANCTimcodeStateEnable OBJECT-TYPE
		SYNTAX		INTEGER { disable(0), enable(1) }
		MAX-ACCESS		read-write
		STATUS			current
		DESCRIPTION
				"TYPE: - Checkbox
				 PAGE: - Logging
					ANC Tim.code State   cmdID= 1092 "
		::= { iqsda02CmdEntry 1092 }


	iqsda02LoggingInp1Monitor2ANCTimecodeState OBJECT-TYPE
		SYNTAX		RollCallString
		MAX-ACCESS		read-only
		STATUS			current
		DESCRIPTION
				"TYPE: - Display
				 PAGE: - Logging
					ANC Timecode State=  cmdID= 2092  format=   "
		::= { iqsda02CmdEntry 2092 }


	iqsda02LoggingInp1Monitor2User1DIDNameEnable OBJECT-TYPE
		SYNTAX		INTEGER { disable(0), enable(1) }
		MAX-ACCESS		read-write
		STATUS			current
		DESCRIPTION
				"TYPE: - Checkbox
				 PAGE: - Logging
					User 1 DID Name En  cmdID= 1097 "
		::= { iqsda02CmdEntry 1097 }


	iqsda02LoggingInp1Monitor2User1DIDName OBJECT-TYPE
		SYNTAX		RollCallString
		MAX-ACCESS		read-only
		STATUS			current
		DESCRIPTION
				"TYPE: - Display
				 PAGE: - Logging
					User 1 DID Name=  cmdID= 2097  format=   "
		::= { iqsda02CmdEntry 2097 }


	iqsda02LoggingInp1Monitor2User1DIDStateEnable OBJECT-TYPE
		SYNTAX		INTEGER { disable(0), enable(1) }
		MAX-ACCESS		read-write
		STATUS			current
		DESCRIPTION
				"TYPE: - Checkbox
				 PAGE: - Logging
					User 1 DID State En  cmdID= 1098 "
		::= { iqsda02CmdEntry 1098 }


	iqsda02LoggingInp1Monitor2User1DIDState OBJECT-TYPE
		SYNTAX		RollCallString
		MAX-ACCESS		read-only
		STATUS			current
		DESCRIPTION
				"TYPE: - Display
				 PAGE: - Logging
					User 1 DID State=  cmdID= 2098  format=   "
		::= { iqsda02CmdEntry 2098 }


	iqsda02LoggingInp1Monitor2User2DIDNameEnable OBJECT-TYPE
		SYNTAX		INTEGER { disable(0), enable(1) }
		MAX-ACCESS		read-write
		STATUS			current
		DESCRIPTION
				"TYPE: - Checkbox
				 PAGE: - Logging
					User 2 DID Name En  cmdID= 1099 "
		::= { iqsda02CmdEntry 1099 }


	iqsda02LoggingInp1Monitor2User2DIDName OBJECT-TYPE
		SYNTAX		RollCallString
		MAX-ACCESS		read-only
		STATUS			current
		DESCRIPTION
				"TYPE: - Display
				 PAGE: - Logging
					User 2 DID Name=  cmdID= 2099  format=   "
		::= { iqsda02CmdEntry 2099 }


	iqsda02LoggingInp1Monitor2User2DIDStateEnable OBJECT-TYPE
		SYNTAX		INTEGER { disable(0), enable(1) }
		MAX-ACCESS		read-write
		STATUS			current
		DESCRIPTION
				"TYPE: - Checkbox
				 PAGE: - Logging
					User 2 DID State En  cmdID= 1100 "
		::= { iqsda02CmdEntry 1100 }


	iqsda02LoggingInp1Monitor2User2DIDState OBJECT-TYPE
		SYNTAX		RollCallString
		MAX-ACCESS		read-only
		STATUS			current
		DESCRIPTION
				"TYPE: - Display
				 PAGE: - Logging
					User 2 DID State=  cmdID= 2100  format=   "
		::= { iqsda02CmdEntry 2100 }


	iqsda02LoggingInp1Monitor2WSSStateEnable OBJECT-TYPE
		SYNTAX		INTEGER { disable(0), enable(1) }
		MAX-ACCESS		read-write
		STATUS			current
		DESCRIPTION
				"TYPE: - Checkbox
				 PAGE: - Logging
					WSS State Enable  cmdID= 1132 "
		::= { iqsda02CmdEntry 1132 }


	iqsda02LoggingInp1Monitor2WSSState OBJECT-TYPE
		SYNTAX		RollCallString
		MAX-ACCESS		read-only
		STATUS			current
		DESCRIPTION
				"TYPE: - Display
				 PAGE: - Logging
					WSS State=  cmdID= 2132  format=   "
		::= { iqsda02CmdEntry 2132 }


	iqsda02LoggingInp1Monitor2VIStateEnable OBJECT-TYPE
		SYNTAX		INTEGER { disable(0), enable(1) }
		MAX-ACCESS		read-write
		STATUS			current
		DESCRIPTION
				"TYPE: - Checkbox
				 PAGE: - Logging
					VI State Enable  cmdID= 1133 "
		::= { iqsda02CmdEntry 1133 }


	iqsda02LoggingInp1Monitor2VIState OBJECT-TYPE
		SYNTAX		RollCallString
		MAX-ACCESS		read-only
		STATUS			current
		DESCRIPTION
				"TYPE: - Display
				 PAGE: - Logging
					VI State=  cmdID= 2133  format=   "
		::= { iqsda02CmdEntry 2133 }


	iqsda02LoggingInp1Monitor2WSSEnable OBJECT-TYPE
		SYNTAX		INTEGER { disable(0), enable(1) }
		MAX-ACCESS		read-write
		STATUS			current
		DESCRIPTION
				"TYPE: - Checkbox
				 PAGE: - Logging
					WSS Enable  cmdID= 1160 "
		::= { iqsda02CmdEntry 1160 }


	iqsda02LoggingInp1Monitor2WSS OBJECT-TYPE
		SYNTAX		RollCallString
		MAX-ACCESS		read-only
		STATUS			current
		DESCRIPTION
				"TYPE: - Display
				 PAGE: - Logging
					WSS=  cmdID= 2160  format=   "
		::= { iqsda02CmdEntry 2160 }


	iqsda02LoggingInp1Monitor2VIEnable OBJECT-TYPE
		SYNTAX		INTEGER { disable(0), enable(1) }
		MAX-ACCESS		read-write
		STATUS			current
		DESCRIPTION
				"TYPE: - Checkbox
				 PAGE: - Logging
					VI Enable  cmdID= 1161 "
		::= { iqsda02CmdEntry 1161 }


	iqsda02LoggingInp1Monitor2VI OBJECT-TYPE
		SYNTAX		RollCallString
		MAX-ACCESS		read-only
		STATUS			current
		DESCRIPTION
				"TYPE: - Display
				 PAGE: - Logging
					VI=  cmdID= 2161  format=   "
		::= { iqsda02CmdEntry 2161 }


	iqsda02LoggingInp1Monitor2WSSAspectEnable OBJECT-TYPE
		SYNTAX		INTEGER { disable(0), enable(1) }
		MAX-ACCESS		read-write
		STATUS			current
		DESCRIPTION
				"TYPE: - Checkbox
				 PAGE: - Logging
					WSS Aspect Enable  cmdID= 1162 "
		::= { iqsda02CmdEntry 1162 }


	iqsda02LoggingInp1Monitor2WSSAspect OBJECT-TYPE
		SYNTAX		RollCallString
		MAX-ACCESS		read-only
		STATUS			current
		DESCRIPTION
				"TYPE: - Display
				 PAGE: - Logging
					WSS Aspect=  cmdID= 2162  format=   "
		::= { iqsda02CmdEntry 2162 }


	iqsda02LoggingInp1Monitor2VIAspectEnable OBJECT-TYPE
		SYNTAX		INTEGER { disable(0), enable(1) }
		MAX-ACCESS		read-write
		STATUS			current
		DESCRIPTION
				"TYPE: - Checkbox
				 PAGE: - Logging
					VI Aspect Enable  cmdID= 1163 "
		::= { iqsda02CmdEntry 1163 }


	iqsda02LoggingInp1Monitor2VIAspect OBJECT-TYPE
		SYNTAX		RollCallString
		MAX-ACCESS		read-only
		STATUS			current
		DESCRIPTION
				"TYPE: - Display
				 PAGE: - Logging
					VI Aspect=  cmdID= 2163  format=   "
		::= { iqsda02CmdEntry 2163 }


	iqsda02LoggingInp1AudStateEmbCh1StateEnable OBJECT-TYPE
		SYNTAX		INTEGER { disable(0), enable(1) }
		MAX-ACCESS		read-write
		STATUS			current
		DESCRIPTION
				"TYPE: - Checkbox
				 PAGE: - Logging- Inp 1 Aud State
					Emb Ch 1 State  cmdID= 1028 "
		::= { iqsda02CmdEntry 1028 }


	iqsda02LoggingInp1AudStateEmbCh1State OBJECT-TYPE
		SYNTAX		RollCallString
		MAX-ACCESS		read-only
		STATUS			current
		DESCRIPTION
				"TYPE: - Display
				 PAGE: - Logging- Inp 1 Aud State
					Emb Ch 1 State=  cmdID= 2028  format=   "
		::= { iqsda02CmdEntry 2028 }


	iqsda02LoggingInp1AudStateEmbCh2StateEnable OBJECT-TYPE
		SYNTAX		INTEGER { disable(0), enable(1) }
		MAX-ACCESS		read-write
		STATUS			current
		DESCRIPTION
				"TYPE: - Checkbox
				 PAGE: - Logging- Inp 1 Aud State
					Emb Ch 2 State  cmdID= 1029 "
		::= { iqsda02CmdEntry 1029 }


	iqsda02LoggingInp1AudStateEmbCh2State OBJECT-TYPE
		SYNTAX		RollCallString
		MAX-ACCESS		read-only
		STATUS			current
		DESCRIPTION
				"TYPE: - Display
				 PAGE: - Logging- Inp 1 Aud State
					Emb Ch 2 State=  cmdID= 2029  format=   "
		::= { iqsda02CmdEntry 2029 }


	iqsda02LoggingInp1AudStateEmbCh3StateEnable OBJECT-TYPE
		SYNTAX		INTEGER { disable(0), enable(1) }
		MAX-ACCESS		read-write
		STATUS			current
		DESCRIPTION
				"TYPE: - Checkbox
				 PAGE: - Logging- Inp 1 Aud State
					Emb Ch 3 State  cmdID= 1030 "
		::= { iqsda02CmdEntry 1030 }


	iqsda02LoggingInp1AudStateEmbCh3State OBJECT-TYPE
		SYNTAX		RollCallString
		MAX-ACCESS		read-only
		STATUS			current
		DESCRIPTION
				"TYPE: - Display
				 PAGE: - Logging- Inp 1 Aud State
					Emb Ch 3 State=  cmdID= 2030  format=   "
		::= { iqsda02CmdEntry 2030 }


	iqsda02LoggingInp1AudStateEmbCh4StateEnable OBJECT-TYPE
		SYNTAX		INTEGER { disable(0), enable(1) }
		MAX-ACCESS		read-write
		STATUS			current
		DESCRIPTION
				"TYPE: - Checkbox
				 PAGE: - Logging- Inp 1 Aud State
					Emb Ch 4 State  cmdID= 1031 "
		::= { iqsda02CmdEntry 1031 }


	iqsda02LoggingInp1AudStateEmbCh4State OBJECT-TYPE
		SYNTAX		RollCallString
		MAX-ACCESS		read-only
		STATUS			current
		DESCRIPTION
				"TYPE: - Display
				 PAGE: - Logging- Inp 1 Aud State
					Emb Ch 4 State=  cmdID= 2031  format=   "
		::= { iqsda02CmdEntry 2031 }


	iqsda02LoggingInp1AudStateEmbCh5StateEnable OBJECT-TYPE
		SYNTAX		INTEGER { disable(0), enable(1) }
		MAX-ACCESS		read-write
		STATUS			current
		DESCRIPTION
				"TYPE: - Checkbox
				 PAGE: - Logging- Inp 1 Aud State
					Emb Ch 5 State  cmdID= 1032 "
		::= { iqsda02CmdEntry 1032 }


	iqsda02LoggingInp1AudStateEmbCh5State OBJECT-TYPE
		SYNTAX		RollCallString
		MAX-ACCESS		read-only
		STATUS			current
		DESCRIPTION
				"TYPE: - Display
				 PAGE: - Logging- Inp 1 Aud State
					Emb Ch 5 State=  cmdID= 2032  format=   "
		::= { iqsda02CmdEntry 2032 }


	iqsda02LoggingInp1AudStateEmbCh6StateEnable OBJECT-TYPE
		SYNTAX		INTEGER { disable(0), enable(1) }
		MAX-ACCESS		read-write
		STATUS			current
		DESCRIPTION
				"TYPE: - Checkbox
				 PAGE: - Logging- Inp 1 Aud State
					Emb Ch 6 State  cmdID= 1033 "
		::= { iqsda02CmdEntry 1033 }


	iqsda02LoggingInp1AudStateEmbCh6State OBJECT-TYPE
		SYNTAX		RollCallString
		MAX-ACCESS		read-only
		STATUS			current
		DESCRIPTION
				"TYPE: - Display
				 PAGE: - Logging- Inp 1 Aud State
					Emb Ch 6 State=  cmdID= 2033  format=   "
		::= { iqsda02CmdEntry 2033 }


	iqsda02LoggingInp1AudStateEmbCh7StateEnable OBJECT-TYPE
		SYNTAX		INTEGER { disable(0), enable(1) }
		MAX-ACCESS		read-write
		STATUS			current
		DESCRIPTION
				"TYPE: - Checkbox
				 PAGE: - Logging- Inp 1 Aud State
					Emb Ch 7 State  cmdID= 1034 "
		::= { iqsda02CmdEntry 1034 }


	iqsda02LoggingInp1AudStateEmbCh7State OBJECT-TYPE
		SYNTAX		RollCallString
		MAX-ACCESS		read-only
		STATUS			current
		DESCRIPTION
				"TYPE: - Display
				 PAGE: - Logging- Inp 1 Aud State
					Emb Ch 7 State=  cmdID= 2034  format=   "
		::= { iqsda02CmdEntry 2034 }


	iqsda02LoggingInp1AudStateEmbCh8StateEnable OBJECT-TYPE
		SYNTAX		INTEGER { disable(0), enable(1) }
		MAX-ACCESS		read-write
		STATUS			current
		DESCRIPTION
				"TYPE: - Checkbox
				 PAGE: - Logging- Inp 1 Aud State
					Emb Ch 8 State  cmdID= 1035 "
		::= { iqsda02CmdEntry 1035 }


	iqsda02LoggingInp1AudStateEmbCh8State OBJECT-TYPE
		SYNTAX		RollCallString
		MAX-ACCESS		read-only
		STATUS			current
		DESCRIPTION
				"TYPE: - Display
				 PAGE: - Logging- Inp 1 Aud State
					Emb Ch 8 State=  cmdID= 2035  format=   "
		::= { iqsda02CmdEntry 2035 }


	iqsda02LoggingInp1AudStateEmbCh9StateEnable OBJECT-TYPE
		SYNTAX		INTEGER { disable(0), enable(1) }
		MAX-ACCESS		read-write
		STATUS			current
		DESCRIPTION
				"TYPE: - Checkbox
				 PAGE: - Logging- Inp 1 Aud State
					Emb Ch 9 State  cmdID= 1036 "
		::= { iqsda02CmdEntry 1036 }


	iqsda02LoggingInp1AudStateEmbCh9State OBJECT-TYPE
		SYNTAX		RollCallString
		MAX-ACCESS		read-only
		STATUS			current
		DESCRIPTION
				"TYPE: - Display
				 PAGE: - Logging- Inp 1 Aud State
					Emb Ch 9 State=  cmdID= 2036  format=   "
		::= { iqsda02CmdEntry 2036 }


	iqsda02LoggingInp1AudStateEmbCh10StateEnable OBJECT-TYPE
		SYNTAX		INTEGER { disable(0), enable(1) }
		MAX-ACCESS		read-write
		STATUS			current
		DESCRIPTION
				"TYPE: - Checkbox
				 PAGE: - Logging- Inp 1 Aud State
					Emb Ch 10 State  cmdID= 1037 "
		::= { iqsda02CmdEntry 1037 }


	iqsda02LoggingInp1AudStateEmbCh10State OBJECT-TYPE
		SYNTAX		RollCallString
		MAX-ACCESS		read-only
		STATUS			current
		DESCRIPTION
				"TYPE: - Display
				 PAGE: - Logging- Inp 1 Aud State
					Emb Ch 10 State=  cmdID= 2037  format=   "
		::= { iqsda02CmdEntry 2037 }


	iqsda02LoggingInp1AudStateEmbCh11StateEnable OBJECT-TYPE
		SYNTAX		INTEGER { disable(0), enable(1) }
		MAX-ACCESS		read-write
		STATUS			current
		DESCRIPTION
				"TYPE: - Checkbox
				 PAGE: - Logging- Inp 1 Aud State
					Emb Ch 11 State  cmdID= 1038 "
		::= { iqsda02CmdEntry 1038 }


	iqsda02LoggingInp1AudStateEmbCh11State OBJECT-TYPE
		SYNTAX		RollCallString
		MAX-ACCESS		read-only
		STATUS			current
		DESCRIPTION
				"TYPE: - Display
				 PAGE: - Logging- Inp 1 Aud State
					Emb Ch 11 State=  cmdID= 2038  format=   "
		::= { iqsda02CmdEntry 2038 }


	iqsda02LoggingInp1AudStateEmbCh12StateEnable OBJECT-TYPE
		SYNTAX		INTEGER { disable(0), enable(1) }
		MAX-ACCESS		read-write
		STATUS			current
		DESCRIPTION
				"TYPE: - Checkbox
				 PAGE: - Logging- Inp 1 Aud State
					Emb Ch 12 State  cmdID= 1039 "
		::= { iqsda02CmdEntry 1039 }


	iqsda02LoggingInp1AudStateEmbCh12State OBJECT-TYPE
		SYNTAX		RollCallString
		MAX-ACCESS		read-only
		STATUS			current
		DESCRIPTION
				"TYPE: - Display
				 PAGE: - Logging- Inp 1 Aud State
					Emb Ch 12 State=  cmdID= 2039  format=   "
		::= { iqsda02CmdEntry 2039 }


	iqsda02LoggingInp1AudStateEmbCh13StateEnable OBJECT-TYPE
		SYNTAX		INTEGER { disable(0), enable(1) }
		MAX-ACCESS		read-write
		STATUS			current
		DESCRIPTION
				"TYPE: - Checkbox
				 PAGE: - Logging- Inp 1 Aud State
					Emb Ch 13 State  cmdID= 1040 "
		::= { iqsda02CmdEntry 1040 }


	iqsda02LoggingInp1AudStateEmbCh13State OBJECT-TYPE
		SYNTAX		RollCallString
		MAX-ACCESS		read-only
		STATUS			current
		DESCRIPTION
				"TYPE: - Display
				 PAGE: - Logging- Inp 1 Aud State
					Emb Ch 13 State=  cmdID= 2040  format=   "
		::= { iqsda02CmdEntry 2040 }


	iqsda02LoggingInp1AudStateEmbCh14StateEnable OBJECT-TYPE
		SYNTAX		INTEGER { disable(0), enable(1) }
		MAX-ACCESS		read-write
		STATUS			current
		DESCRIPTION
				"TYPE: - Checkbox
				 PAGE: - Logging- Inp 1 Aud State
					Emb Ch 14 State  cmdID= 1041 "
		::= { iqsda02CmdEntry 1041 }


	iqsda02LoggingInp1AudStateEmbCh14State OBJECT-TYPE
		SYNTAX		RollCallString
		MAX-ACCESS		read-only
		STATUS			current
		DESCRIPTION
				"TYPE: - Display
				 PAGE: - Logging- Inp 1 Aud State
					Emb Ch 14 State=  cmdID= 2041  format=   "
		::= { iqsda02CmdEntry 2041 }


	iqsda02LoggingInp1AudStateEmbCh15StateEnable OBJECT-TYPE
		SYNTAX		INTEGER { disable(0), enable(1) }
		MAX-ACCESS		read-write
		STATUS			current
		DESCRIPTION
				"TYPE: - Checkbox
				 PAGE: - Logging- Inp 1 Aud State
					Emb Ch 15 State  cmdID= 1042 "
		::= { iqsda02CmdEntry 1042 }


	iqsda02LoggingInp1AudStateEmbCh15State OBJECT-TYPE
		SYNTAX		RollCallString
		MAX-ACCESS		read-only
		STATUS			current
		DESCRIPTION
				"TYPE: - Display
				 PAGE: - Logging- Inp 1 Aud State
					Emb Ch 15 State=  cmdID= 2042  format=   "
		::= { iqsda02CmdEntry 2042 }


	iqsda02LoggingInp1AudStateEmbCh16StateEnable OBJECT-TYPE
		SYNTAX		INTEGER { disable(0), enable(1) }
		MAX-ACCESS		read-write
		STATUS			current
		DESCRIPTION
				"TYPE: - Checkbox
				 PAGE: - Logging- Inp 1 Aud State
					Emb Ch 16 State  cmdID= 1043 "
		::= { iqsda02CmdEntry 1043 }


	iqsda02LoggingInp1AudStateEmbCh16State OBJECT-TYPE
		SYNTAX		RollCallString
		MAX-ACCESS		read-only
		STATUS			current
		DESCRIPTION
				"TYPE: - Display
				 PAGE: - Logging- Inp 1 Aud State
					Emb Ch 16 State=  cmdID= 2043  format=   "
		::= { iqsda02CmdEntry 2043 }


	iqsda02LoggingInp1AudTypeEmbCh1TypeEnable OBJECT-TYPE
		SYNTAX		INTEGER { disable(0), enable(1) }
		MAX-ACCESS		read-write
		STATUS			current
		DESCRIPTION
				"TYPE: - Checkbox
				 PAGE: - Logging- Inp 1 Aud Type
					Emb Ch 1 Type  cmdID= 1044 "
		::= { iqsda02CmdEntry 1044 }


	iqsda02LoggingInp1AudTypeEmbCh1Type OBJECT-TYPE
		SYNTAX		RollCallString
		MAX-ACCESS		read-only
		STATUS			current
		DESCRIPTION
				"TYPE: - Display
				 PAGE: - Logging- Inp 1 Aud Type
					Emb Ch 1 Type=  cmdID= 2044  format=   "
		::= { iqsda02CmdEntry 2044 }


	iqsda02LoggingInp1AudTypeEmbCh2TypeEnable OBJECT-TYPE
		SYNTAX		INTEGER { disable(0), enable(1) }
		MAX-ACCESS		read-write
		STATUS			current
		DESCRIPTION
				"TYPE: - Checkbox
				 PAGE: - Logging- Inp 1 Aud Type
					Emb Ch 2 Type  cmdID= 1045 "
		::= { iqsda02CmdEntry 1045 }


	iqsda02LoggingInp1AudTypeEmbCh2Type OBJECT-TYPE
		SYNTAX		RollCallString
		MAX-ACCESS		read-only
		STATUS			current
		DESCRIPTION
				"TYPE: - Display
				 PAGE: - Logging- Inp 1 Aud Type
					Emb Ch 2 Type=  cmdID= 2045  format=   "
		::= { iqsda02CmdEntry 2045 }


	iqsda02LoggingInp1AudTypeEmbCh3TypeEnable OBJECT-TYPE
		SYNTAX		INTEGER { disable(0), enable(1) }
		MAX-ACCESS		read-write
		STATUS			current
		DESCRIPTION
				"TYPE: - Checkbox
				 PAGE: - Logging- Inp 1 Aud Type
					Emb Ch 3 Type  cmdID= 1046 "
		::= { iqsda02CmdEntry 1046 }


	iqsda02LoggingInp1AudTypeEmbCh3Type OBJECT-TYPE
		SYNTAX		RollCallString
		MAX-ACCESS		read-only
		STATUS			current
		DESCRIPTION
				"TYPE: - Display
				 PAGE: - Logging- Inp 1 Aud Type
					Emb Ch 3 Type=  cmdID= 2046  format=   "
		::= { iqsda02CmdEntry 2046 }


	iqsda02LoggingInp1AudTypeEmbCh4TypeEnable OBJECT-TYPE
		SYNTAX		INTEGER { disable(0), enable(1) }
		MAX-ACCESS		read-write
		STATUS			current
		DESCRIPTION
				"TYPE: - Checkbox
				 PAGE: - Logging- Inp 1 Aud Type
					Emb Ch 4 Type  cmdID= 1047 "
		::= { iqsda02CmdEntry 1047 }


	iqsda02LoggingInp1AudTypeEmbCh4Type OBJECT-TYPE
		SYNTAX		RollCallString
		MAX-ACCESS		read-only
		STATUS			current
		DESCRIPTION
				"TYPE: - Display
				 PAGE: - Logging- Inp 1 Aud Type
					Emb Ch 4 Type=  cmdID= 2047  format=   "
		::= { iqsda02CmdEntry 2047 }


	iqsda02LoggingInp1AudTypeEmbCh5TypeEnable OBJECT-TYPE
		SYNTAX		INTEGER { disable(0), enable(1) }
		MAX-ACCESS		read-write
		STATUS			current
		DESCRIPTION
				"TYPE: - Checkbox
				 PAGE: - Logging- Inp 1 Aud Type
					Emb Ch 5 Type  cmdID= 1048 "
		::= { iqsda02CmdEntry 1048 }


	iqsda02LoggingInp1AudTypeEmbCh5Type OBJECT-TYPE
		SYNTAX		RollCallString
		MAX-ACCESS		read-only
		STATUS			current
		DESCRIPTION
				"TYPE: - Display
				 PAGE: - Logging- Inp 1 Aud Type
					Emb Ch 5 Type=  cmdID= 2048  format=   "
		::= { iqsda02CmdEntry 2048 }


	iqsda02LoggingInp1AudTypeEmbCh6TypeEnable OBJECT-TYPE
		SYNTAX		INTEGER { disable(0), enable(1) }
		MAX-ACCESS		read-write
		STATUS			current
		DESCRIPTION
				"TYPE: - Checkbox
				 PAGE: - Logging- Inp 1 Aud Type
					Emb Ch 6 Type  cmdID= 1049 "
		::= { iqsda02CmdEntry 1049 }


	iqsda02LoggingInp1AudTypeEmbCh6Type OBJECT-TYPE
		SYNTAX		RollCallString
		MAX-ACCESS		read-only
		STATUS			current
		DESCRIPTION
				"TYPE: - Display
				 PAGE: - Logging- Inp 1 Aud Type
					Emb Ch 6 Type=  cmdID= 2049  format=   "
		::= { iqsda02CmdEntry 2049 }


	iqsda02LoggingInp1AudTypeEmbCh7TypeEnable OBJECT-TYPE
		SYNTAX		INTEGER { disable(0), enable(1) }
		MAX-ACCESS		read-write
		STATUS			current
		DESCRIPTION
				"TYPE: - Checkbox
				 PAGE: - Logging- Inp 1 Aud Type
					Emb Ch 7 Type  cmdID= 1050 "
		::= { iqsda02CmdEntry 1050 }


	iqsda02LoggingInp1AudTypeEmbCh7Type OBJECT-TYPE
		SYNTAX		RollCallString
		MAX-ACCESS		read-only
		STATUS			current
		DESCRIPTION
				"TYPE: - Display
				 PAGE: - Logging- Inp 1 Aud Type
					Emb Ch 7 Type=  cmdID= 2050  format=   "
		::= { iqsda02CmdEntry 2050 }


	iqsda02LoggingInp1AudTypeEmbCh8TypeEnable OBJECT-TYPE
		SYNTAX		INTEGER { disable(0), enable(1) }
		MAX-ACCESS		read-write
		STATUS			current
		DESCRIPTION
				"TYPE: - Checkbox
				 PAGE: - Logging- Inp 1 Aud Type
					Emb Ch 8 Type  cmdID= 1051 "
		::= { iqsda02CmdEntry 1051 }


	iqsda02LoggingInp1AudTypeEmbCh8Type OBJECT-TYPE
		SYNTAX		RollCallString
		MAX-ACCESS		read-only
		STATUS			current
		DESCRIPTION
				"TYPE: - Display
				 PAGE: - Logging- Inp 1 Aud Type
					Emb Ch 8 Type=  cmdID= 2051  format=   "
		::= { iqsda02CmdEntry 2051 }


	iqsda02LoggingInp1AudTypeEmbCh9TypeEnable OBJECT-TYPE
		SYNTAX		INTEGER { disable(0), enable(1) }
		MAX-ACCESS		read-write
		STATUS			current
		DESCRIPTION
				"TYPE: - Checkbox
				 PAGE: - Logging- Inp 1 Aud Type
					Emb Ch 9 Type  cmdID= 1052 "
		::= { iqsda02CmdEntry 1052 }


	iqsda02LoggingInp1AudTypeEmbCh9Type OBJECT-TYPE
		SYNTAX		RollCallString
		MAX-ACCESS		read-only
		STATUS			current
		DESCRIPTION
				"TYPE: - Display
				 PAGE: - Logging- Inp 1 Aud Type
					Emb Ch 9 Type=  cmdID= 2052  format=   "
		::= { iqsda02CmdEntry 2052 }


	iqsda02LoggingInp1AudTypeEmbCh10TypeEnable OBJECT-TYPE
		SYNTAX		INTEGER { disable(0), enable(1) }
		MAX-ACCESS		read-write
		STATUS			current
		DESCRIPTION
				"TYPE: - Checkbox
				 PAGE: - Logging- Inp 1 Aud Type
					Emb Ch 10 Type  cmdID= 1053 "
		::= { iqsda02CmdEntry 1053 }


	iqsda02LoggingInp1AudTypeEmbCh10Type OBJECT-TYPE
		SYNTAX		RollCallString
		MAX-ACCESS		read-only
		STATUS			current
		DESCRIPTION
				"TYPE: - Display
				 PAGE: - Logging- Inp 1 Aud Type
					Emb Ch 10 Type=  cmdID= 2053  format=   "
		::= { iqsda02CmdEntry 2053 }


	iqsda02LoggingInp1AudTypeEmbCh11TypeEnable OBJECT-TYPE
		SYNTAX		INTEGER { disable(0), enable(1) }
		MAX-ACCESS		read-write
		STATUS			current
		DESCRIPTION
				"TYPE: - Checkbox
				 PAGE: - Logging- Inp 1 Aud Type
					Emb Ch 11 Type  cmdID= 1054 "
		::= { iqsda02CmdEntry 1054 }


	iqsda02LoggingInp1AudTypeEmbCh11Type OBJECT-TYPE
		SYNTAX		RollCallString
		MAX-ACCESS		read-only
		STATUS			current
		DESCRIPTION
				"TYPE: - Display
				 PAGE: - Logging- Inp 1 Aud Type
					Emb Ch 11 Type=  cmdID= 2054  format=   "
		::= { iqsda02CmdEntry 2054 }


	iqsda02LoggingInp1AudTypeEmbCh12TypeEnable OBJECT-TYPE
		SYNTAX		INTEGER { disable(0), enable(1) }
		MAX-ACCESS		read-write
		STATUS			current
		DESCRIPTION
				"TYPE: - Checkbox
				 PAGE: - Logging- Inp 1 Aud Type
					Emb Ch 12 Type  cmdID= 1055 "
		::= { iqsda02CmdEntry 1055 }


	iqsda02LoggingInp1AudTypeEmbCh12Type OBJECT-TYPE
		SYNTAX		RollCallString
		MAX-ACCESS		read-only
		STATUS			current
		DESCRIPTION
				"TYPE: - Display
				 PAGE: - Logging- Inp 1 Aud Type
					Emb Ch 12 Type=  cmdID= 2055  format=   "
		::= { iqsda02CmdEntry 2055 }


	iqsda02LoggingInp1AudTypeEmbCh13TypeEnable OBJECT-TYPE
		SYNTAX		INTEGER { disable(0), enable(1) }
		MAX-ACCESS		read-write
		STATUS			current
		DESCRIPTION
				"TYPE: - Checkbox
				 PAGE: - Logging- Inp 1 Aud Type
					Emb Ch 13 Type  cmdID= 1056 "
		::= { iqsda02CmdEntry 1056 }


	iqsda02LoggingInp1AudTypeEmbCh13Type OBJECT-TYPE
		SYNTAX		RollCallString
		MAX-ACCESS		read-only
		STATUS			current
		DESCRIPTION
				"TYPE: - Display
				 PAGE: - Logging- Inp 1 Aud Type
					Emb Ch 13 Type=  cmdID= 2056  format=   "
		::= { iqsda02CmdEntry 2056 }


	iqsda02LoggingInp1AudTypeEmbCh14TypeEnable OBJECT-TYPE
		SYNTAX		INTEGER { disable(0), enable(1) }
		MAX-ACCESS		read-write
		STATUS			current
		DESCRIPTION
				"TYPE: - Checkbox
				 PAGE: - Logging- Inp 1 Aud Type
					Emb Ch 14 Type  cmdID= 1057 "
		::= { iqsda02CmdEntry 1057 }


	iqsda02LoggingInp1AudTypeEmbCh14Type OBJECT-TYPE
		SYNTAX		RollCallString
		MAX-ACCESS		read-only
		STATUS			current
		DESCRIPTION
				"TYPE: - Display
				 PAGE: - Logging- Inp 1 Aud Type
					Emb Ch 14 Type=  cmdID= 2057  format=   "
		::= { iqsda02CmdEntry 2057 }


	iqsda02LoggingInp1AudTypeEmbCh15TypeEnable OBJECT-TYPE
		SYNTAX		INTEGER { disable(0), enable(1) }
		MAX-ACCESS		read-write
		STATUS			current
		DESCRIPTION
				"TYPE: - Checkbox
				 PAGE: - Logging- Inp 1 Aud Type
					Emb Ch 15 Type  cmdID= 1058 "
		::= { iqsda02CmdEntry 1058 }


	iqsda02LoggingInp1AudTypeEmbCh15Type OBJECT-TYPE
		SYNTAX		RollCallString
		MAX-ACCESS		read-only
		STATUS			current
		DESCRIPTION
				"TYPE: - Display
				 PAGE: - Logging- Inp 1 Aud Type
					Emb Ch 15 Type=  cmdID= 2058  format=   "
		::= { iqsda02CmdEntry 2058 }


	iqsda02LoggingInp1AudTypeEmbCh16TypeEnable OBJECT-TYPE
		SYNTAX		INTEGER { disable(0), enable(1) }
		MAX-ACCESS		read-write
		STATUS			current
		DESCRIPTION
				"TYPE: - Checkbox
				 PAGE: - Logging- Inp 1 Aud Type
					Emb Ch 16 Type  cmdID= 1059 "
		::= { iqsda02CmdEntry 1059 }


	iqsda02LoggingInp1AudTypeEmbCh16Type OBJECT-TYPE
		SYNTAX		RollCallString
		MAX-ACCESS		read-only
		STATUS			current
		DESCRIPTION
				"TYPE: - Display
				 PAGE: - Logging- Inp 1 Aud Type
					Emb Ch 16 Type=  cmdID= 2059  format=   "
		::= { iqsda02CmdEntry 2059 }


	iqsda02LoggingInp1DolbyEStatePair1Enable OBJECT-TYPE
		SYNTAX		INTEGER { disable(0), enable(1) }
		MAX-ACCESS		read-write
		STATUS			current
		DESCRIPTION
				"TYPE: - Checkbox
				 PAGE: - Logging- Inp 1 Dolby E State
					Pair 1 Enable  cmdID= 1150 "
		::= { iqsda02CmdEntry 1150 }


	iqsda02LoggingInp1DolbyEStatePair1State OBJECT-TYPE
		SYNTAX		RollCallString
		MAX-ACCESS		read-only
		STATUS			current
		DESCRIPTION
				"TYPE: - Display
				 PAGE: - Logging- Inp 1 Dolby E State
					Pair 1 State=  cmdID= 2150  format=   "
		::= { iqsda02CmdEntry 2150 }


	iqsda02LoggingInp1DolbyEStatePair2Enable OBJECT-TYPE
		SYNTAX		INTEGER { disable(0), enable(1) }
		MAX-ACCESS		read-write
		STATUS			current
		DESCRIPTION
				"TYPE: - Checkbox
				 PAGE: - Logging- Inp 1 Dolby E State
					Pair 2 Enable  cmdID= 1151 "
		::= { iqsda02CmdEntry 1151 }


	iqsda02LoggingInp1DolbyEStatePair2State OBJECT-TYPE
		SYNTAX		RollCallString
		MAX-ACCESS		read-only
		STATUS			current
		DESCRIPTION
				"TYPE: - Display
				 PAGE: - Logging- Inp 1 Dolby E State
					Pair 2 State=  cmdID= 2151  format=   "
		::= { iqsda02CmdEntry 2151 }


	iqsda02LoggingInp1DolbyEStatePair3Enable OBJECT-TYPE
		SYNTAX		INTEGER { disable(0), enable(1) }
		MAX-ACCESS		read-write
		STATUS			current
		DESCRIPTION
				"TYPE: - Checkbox
				 PAGE: - Logging- Inp 1 Dolby E State
					Pair 3 Enable  cmdID= 1152 "
		::= { iqsda02CmdEntry 1152 }


	iqsda02LoggingInp1DolbyEStatePair3State OBJECT-TYPE
		SYNTAX		RollCallString
		MAX-ACCESS		read-only
		STATUS			current
		DESCRIPTION
				"TYPE: - Display
				 PAGE: - Logging- Inp 1 Dolby E State
					Pair 3 State=  cmdID= 2152  format=   "
		::= { iqsda02CmdEntry 2152 }


	iqsda02LoggingInp1DolbyEStatePair4Enable OBJECT-TYPE
		SYNTAX		INTEGER { disable(0), enable(1) }
		MAX-ACCESS		read-write
		STATUS			current
		DESCRIPTION
				"TYPE: - Checkbox
				 PAGE: - Logging- Inp 1 Dolby E State
					Pair 4 Enable  cmdID= 1153 "
		::= { iqsda02CmdEntry 1153 }


	iqsda02LoggingInp1DolbyEStatePair4State OBJECT-TYPE
		SYNTAX		RollCallString
		MAX-ACCESS		read-only
		STATUS			current
		DESCRIPTION
				"TYPE: - Display
				 PAGE: - Logging- Inp 1 Dolby E State
					Pair 4 State=  cmdID= 2153  format=   "
		::= { iqsda02CmdEntry 2153 }


	iqsda02LoggingInp1DolbyEStatePair5Enable OBJECT-TYPE
		SYNTAX		INTEGER { disable(0), enable(1) }
		MAX-ACCESS		read-write
		STATUS			current
		DESCRIPTION
				"TYPE: - Checkbox
				 PAGE: - Logging- Inp 1 Dolby E State
					Pair 5 Enable  cmdID= 1154 "
		::= { iqsda02CmdEntry 1154 }


	iqsda02LoggingInp1DolbyEStatePair5State OBJECT-TYPE
		SYNTAX		RollCallString
		MAX-ACCESS		read-only
		STATUS			current
		DESCRIPTION
				"TYPE: - Display
				 PAGE: - Logging- Inp 1 Dolby E State
					Pair 5 State=  cmdID= 2154  format=   "
		::= { iqsda02CmdEntry 2154 }


	iqsda02LoggingInp1DolbyEStatePair6Enable OBJECT-TYPE
		SYNTAX		INTEGER { disable(0), enable(1) }
		MAX-ACCESS		read-write
		STATUS			current
		DESCRIPTION
				"TYPE: - Checkbox
				 PAGE: - Logging- Inp 1 Dolby E State
					Pair 6 Enable  cmdID= 1155 "
		::= { iqsda02CmdEntry 1155 }


	iqsda02LoggingInp1DolbyEStatePair6State OBJECT-TYPE
		SYNTAX		RollCallString
		MAX-ACCESS		read-only
		STATUS			current
		DESCRIPTION
				"TYPE: - Display
				 PAGE: - Logging- Inp 1 Dolby E State
					Pair 6 State=  cmdID= 2155  format=   "
		::= { iqsda02CmdEntry 2155 }


	iqsda02LoggingInp1DolbyEStatePair7Enable OBJECT-TYPE
		SYNTAX		INTEGER { disable(0), enable(1) }
		MAX-ACCESS		read-write
		STATUS			current
		DESCRIPTION
				"TYPE: - Checkbox
				 PAGE: - Logging- Inp 1 Dolby E State
					Pair 7 Enable  cmdID= 1156 "
		::= { iqsda02CmdEntry 1156 }


	iqsda02LoggingInp1DolbyEStatePair7State OBJECT-TYPE
		SYNTAX		RollCallString
		MAX-ACCESS		read-only
		STATUS			current
		DESCRIPTION
				"TYPE: - Display
				 PAGE: - Logging- Inp 1 Dolby E State
					Pair 7 State=  cmdID= 2156  format=   "
		::= { iqsda02CmdEntry 2156 }


	iqsda02LoggingInp1DolbyEStatePair8Enable OBJECT-TYPE
		SYNTAX		INTEGER { disable(0), enable(1) }
		MAX-ACCESS		read-write
		STATUS			current
		DESCRIPTION
				"TYPE: - Checkbox
				 PAGE: - Logging- Inp 1 Dolby E State
					Pair 8 Enable  cmdID= 1157 "
		::= { iqsda02CmdEntry 1157 }


	iqsda02LoggingInp1DolbyEStatePair8State OBJECT-TYPE
		SYNTAX		RollCallString
		MAX-ACCESS		read-only
		STATUS			current
		DESCRIPTION
				"TYPE: - Display
				 PAGE: - Logging- Inp 1 Dolby E State
					Pair 8 State=  cmdID= 2157  format=   "
		::= { iqsda02CmdEntry 2157 }


	iqsda02LoggingInp1BitDepthEmbCh1BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 1 Bit Depth  cmdID= 1060 "
		::= { iqsda02CmdEntry 1060 }


	iqsda02LoggingInp1BitDepthEmbCh1BitDepth OBJECT-TYPE
		SYNTAX		RollCallString
		MAX-ACCESS		read-only
		STATUS			current
		DESCRIPTION
				"TYPE: - Display
				 PAGE: - Logging- Inp 1 Bit Depth
					Emb Ch 1 Bit Depth=  cmdID= 2060  format=   "
		::= { iqsda02CmdEntry 2060 }


	iqsda02LoggingInp1BitDepthEmbCh2BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 2 Bit Depth  cmdID= 1061 "
		::= { iqsda02CmdEntry 1061 }


	iqsda02LoggingInp1BitDepthEmbCh2BitDepth OBJECT-TYPE
		SYNTAX		RollCallString
		MAX-ACCESS		read-only
		STATUS			current
		DESCRIPTION
				"TYPE: - Display
				 PAGE: - Logging- Inp 1 Bit Depth
					Emb Ch 2 Bit Depth=  cmdID= 2061  format=   "
		::= { iqsda02CmdEntry 2061 }


	iqsda02LoggingInp1BitDepthEmbCh3BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 3 Bit Depth  cmdID= 1062 "
		::= { iqsda02CmdEntry 1062 }


	iqsda02LoggingInp1BitDepthEmbCh3BitDepth OBJECT-TYPE
		SYNTAX		RollCallString
		MAX-ACCESS		read-only
		STATUS			current
		DESCRIPTION
				"TYPE: - Display
				 PAGE: - Logging- Inp 1 Bit Depth
					Emb Ch 3 Bit Depth=  cmdID= 2062  format=   "
		::= { iqsda02CmdEntry 2062 }


	iqsda02LoggingInp1BitDepthEmbCh4BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 4 Bit Depth  cmdID= 1063 "
		::= { iqsda02CmdEntry 1063 }


	iqsda02LoggingInp1BitDepthEmbCh4BitDepth OBJECT-TYPE
		SYNTAX		RollCallString
		MAX-ACCESS		read-only
		STATUS			current
		DESCRIPTION
				"TYPE: - Display
				 PAGE: - Logging- Inp 1 Bit Depth
					Emb Ch 4 Bit Depth=  cmdID= 2063  format=   "
		::= { iqsda02CmdEntry 2063 }


	iqsda02LoggingInp1BitDepthEmbCh5BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 5 Bit Depth  cmdID= 1064 "
		::= { iqsda02CmdEntry 1064 }


	iqsda02LoggingInp1BitDepthEmbCh5BitDepth OBJECT-TYPE
		SYNTAX		RollCallString
		MAX-ACCESS		read-only
		STATUS			current
		DESCRIPTION
				"TYPE: - Display
				 PAGE: - Logging- Inp 1 Bit Depth
					Emb Ch 5 Bit Depth=  cmdID= 2064  format=   "
		::= { iqsda02CmdEntry 2064 }


	iqsda02LoggingInp1BitDepthEmbCh6BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 6 Bit Depth  cmdID= 1065 "
		::= { iqsda02CmdEntry 1065 }


	iqsda02LoggingInp1BitDepthEmbCh6BitDepth OBJECT-TYPE
		SYNTAX		RollCallString
		MAX-ACCESS		read-only
		STATUS			current
		DESCRIPTION
				"TYPE: - Display
				 PAGE: - Logging- Inp 1 Bit Depth
					Emb Ch 6 Bit Depth=  cmdID= 2065  format=   "
		::= { iqsda02CmdEntry 2065 }


	iqsda02LoggingInp1BitDepthEmbCh7BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 7 Bit Depth  cmdID= 1066 "
		::= { iqsda02CmdEntry 1066 }


	iqsda02LoggingInp1BitDepthEmbCh7BitDepth OBJECT-TYPE
		SYNTAX		RollCallString
		MAX-ACCESS		read-only
		STATUS			current
		DESCRIPTION
				"TYPE: - Display
				 PAGE: - Logging- Inp 1 Bit Depth
					Emb Ch 7 Bit Depth=  cmdID= 2066  format=   "
		::= { iqsda02CmdEntry 2066 }


	iqsda02LoggingInp1BitDepthEmbCh8BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 8 Bit Depth  cmdID= 1067 "
		::= { iqsda02CmdEntry 1067 }


	iqsda02LoggingInp1BitDepthEmbCh8BitDepth OBJECT-TYPE
		SYNTAX		RollCallString
		MAX-ACCESS		read-only
		STATUS			current
		DESCRIPTION
				"TYPE: - Display
				 PAGE: - Logging- Inp 1 Bit Depth
					Emb Ch 8 Bit Depth=  cmdID= 2067  format=   "
		::= { iqsda02CmdEntry 2067 }


	iqsda02LoggingInp1BitDepthEmbCh9BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 9 Bit Depth  cmdID= 1068 "
		::= { iqsda02CmdEntry 1068 }


	iqsda02LoggingInp1BitDepthEmbCh9BitDepth OBJECT-TYPE
		SYNTAX		RollCallString
		MAX-ACCESS		read-only
		STATUS			current
		DESCRIPTION
				"TYPE: - Display
				 PAGE: - Logging- Inp 1 Bit Depth
					Emb Ch 9 Bit Depth=  cmdID= 2068  format=   "
		::= { iqsda02CmdEntry 2068 }


	iqsda02LoggingInp1BitDepthEmbCh10BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 10 Bit Depth  cmdID= 1069 "
		::= { iqsda02CmdEntry 1069 }


	iqsda02LoggingInp1BitDepthEmbCh10BitDepth OBJECT-TYPE
		SYNTAX		RollCallString
		MAX-ACCESS		read-only
		STATUS			current
		DESCRIPTION
				"TYPE: - Display
				 PAGE: - Logging- Inp 1 Bit Depth
					Emb Ch 10 Bit Dep=  cmdID= 2069  format=   "
		::= { iqsda02CmdEntry 2069 }


	iqsda02LoggingInp1BitDepthEmbCh11BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 11 Bit Depth  cmdID= 1070 "
		::= { iqsda02CmdEntry 1070 }


	iqsda02LoggingInp1BitDepthEmbCh11BitDepth OBJECT-TYPE
		SYNTAX		RollCallString
		MAX-ACCESS		read-only
		STATUS			current
		DESCRIPTION
				"TYPE: - Display
				 PAGE: - Logging- Inp 1 Bit Depth
					Emb Ch 11 Bit Dep=  cmdID= 2070  format=   "
		::= { iqsda02CmdEntry 2070 }


	iqsda02LoggingInp1BitDepthEmbCh12BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 12 Bit Depth  cmdID= 1071 "
		::= { iqsda02CmdEntry 1071 }


	iqsda02LoggingInp1BitDepthEmbCh12BitDepth OBJECT-TYPE
		SYNTAX		RollCallString
		MAX-ACCESS		read-only
		STATUS			current
		DESCRIPTION
				"TYPE: - Display
				 PAGE: - Logging- Inp 1 Bit Depth
					Emb Ch 12 Bit Dep=  cmdID= 2071  format=   "
		::= { iqsda02CmdEntry 2071 }


	iqsda02LoggingInp1BitDepthEmbCh13BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 13 Bit Depth  cmdID= 1072 "
		::= { iqsda02CmdEntry 1072 }


	iqsda02LoggingInp1BitDepthEmbCh13BitDepth OBJECT-TYPE
		SYNTAX		RollCallString
		MAX-ACCESS		read-only
		STATUS			current
		DESCRIPTION
				"TYPE: - Display
				 PAGE: - Logging- Inp 1 Bit Depth
					Emb Ch 13 Bit Dep=  cmdID= 2072  format=   "
		::= { iqsda02CmdEntry 2072 }


	iqsda02LoggingInp1BitDepthEmbCh14BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 14 Bit Depth  cmdID= 1073 "
		::= { iqsda02CmdEntry 1073 }


	iqsda02LoggingInp1BitDepthEmbCh14BitDepth OBJECT-TYPE
		SYNTAX		RollCallString
		MAX-ACCESS		read-only
		STATUS			current
		DESCRIPTION
				"TYPE: - Display
				 PAGE: - Logging- Inp 1 Bit Depth
					Emb Ch 14 Bit Dep=  cmdID= 2073  format=   "
		::= { iqsda02CmdEntry 2073 }


	iqsda02LoggingInp1BitDepthEmbCh15BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 15 Bit Depth  cmdID= 1074 "
		::= { iqsda02CmdEntry 1074 }


	iqsda02LoggingInp1BitDepthEmbCh15BitDepth OBJECT-TYPE
		SYNTAX		RollCallString
		MAX-ACCESS		read-only
		STATUS			current
		DESCRIPTION
				"TYPE: - Display
				 PAGE: - Logging- Inp 1 Bit Depth
					Emb Ch 15 Bit Dep=  cmdID= 2074  format=   "
		::= { iqsda02CmdEntry 2074 }


	iqsda02LoggingInp1BitDepthEmbCh16BitDepthEnable OBJECT-TYPE
		SYNTAX		INTEGER { disable(0), enable(1) }
		MAX-ACCESS		read-write
		STATUS			current
		DESCRIPTION
				"TYPE: - Checkbox
				 PAGE: - Logging- Inp 1 Bit Depth
					Emb Ch 16 Bit Depth  cmdID= 1075 "
		::= { iqsda02CmdEntry 1075 }


	iqsda02LoggingInp1BitDepthEmbCh16BitDepth OBJECT-TYPE
		SYNTAX		RollCallString
		MAX-ACCESS		read-only
		STATUS			current
		DESCRIPTION
				"TYPE: - Display
				 PAGE: - Logging- Inp 1 Bit Depth
					Emb Ch 16 Bit Dep=  cmdID= 2075  format=   "
		::= { iqsda02CmdEntry 2075 }


	iqsda02LoggingInp1LevelEmbCh1LevelEnable OBJECT-TYPE
		SYNTAX		INTEGER { disable(0), enable(1) }
		MAX-ACCESS		read-write
		STATUS			current
		DESCRIPTION
				"TYPE: - Checkbox
				 PAGE: - Logging- Inp 1 Level
					Emb Ch 1 Level  cmdID= 1076 "
		::= { iqsda02CmdEntry 1076 }


	iqsda02LoggingInp1LevelEmbCh1Level OBJECT-TYPE
		SYNTAX		RollCallString
		MAX-ACCESS		read-only
		STATUS			current
		DESCRIPTION
				"TYPE: - Display
				 PAGE: - Logging- Inp 1 Level
					Emb Ch 1 Level=  cmdID= 2076  format=   "
		::= { iqsda02CmdEntry 2076 }


	iqsda02LoggingInp1LevelEmbCh2LevelEnable OBJECT-TYPE
		SYNTAX		INTEGER { disable(0), enable(1) }
		MAX-ACCESS		read-write
		STATUS			current
		DESCRIPTION
				"TYPE: - Checkbox
				 PAGE: - Logging- Inp 1 Level
					Emb Ch 2 Level  cmdID= 1077 "
		::= { iqsda02CmdEntry 1077 }


	iqsda02LoggingInp1LevelEmbCh2Level OBJECT-TYPE
		SYNTAX		RollCallString
		MAX-ACCESS		read-only
		STATUS			current
		DESCRIPTION
				"TYPE: - Display
				 PAGE: - Logging- Inp 1 Level
					Emb Ch 2 Level=  cmdID= 2077  format=   "
		::= { iqsda02CmdEntry 2077 }


	iqsda02LoggingInp1LevelEmbCh3LevelEnable OBJECT-TYPE
		SYNTAX		INTEGER { disable(0), enable(1) }
		MAX-ACCESS		read-write
		STATUS			current
		DESCRIPTION
				"TYPE: - Checkbox
				 PAGE: - Logging- Inp 1 Level
					Emb Ch 3 Level  cmdID= 1078 "
		::= { iqsda02CmdEntry 1078 }


	iqsda02LoggingInp1LevelEmbCh3Level OBJECT-TYPE
		SYNTAX		RollCallString
		MAX-ACCESS		read-only
		STATUS			current
		DESCRIPTION
				"TYPE: - Display
				 PAGE: - Logging- Inp 1 Level
					Emb Ch 3 Level=  cmdID= 2078  format=   "
		::= { iqsda02CmdEntry 2078 }


	iqsda02LoggingInp1LevelEmbCh4LevelEnable OBJECT-TYPE
		SYNTAX		INTEGER { disable(0), enable(1) }
		MAX-ACCESS		read-write
		STATUS			current
		DESCRIPTION
				"TYPE: - Checkbox
				 PAGE: - Logging- Inp 1 Level
					Emb Ch 4 Level  cmdID= 1079 "
		::= { iqsda02CmdEntry 1079 }


	iqsda02LoggingInp1LevelEmbCh4Level OBJECT-TYPE
		SYNTAX		RollCallString
		MAX-ACCESS		read-only
		STATUS			current
		DESCRIPTION
				"TYPE: - Display
				 PAGE: - Logging- Inp 1 Level
					Emb Ch 4 Level=  cmdID= 2079  format=   "
		::= { iqsda02CmdEntry 2079 }


	iqsda02LoggingInp1LevelEmbCh5LevelEnable OBJECT-TYPE
		SYNTAX		INTEGER { disable(0), enable(1) }
		MAX-ACCESS		read-write
		STATUS			current
		DESCRIPTION
				"TYPE: - Checkbox
				 PAGE: - Logging- Inp 1 Level
					Emb Ch 5 Level  cmdID= 1080 "
		::= { iqsda02CmdEntry 1080 }


	iqsda02LoggingInp1LevelEmbCh5Level OBJECT-TYPE
		SYNTAX		RollCallString
		MAX-ACCESS		read-only
		STATUS			current
		DESCRIPTION
				"TYPE: - Display
				 PAGE: - Logging- Inp 1 Level
					Emb Ch 5 Level=  cmdID= 2080  format=   "
		::= { iqsda02CmdEntry 2080 }


	iqsda02LoggingInp1LevelEmbCh6LevelEnable OBJECT-TYPE
		SYNTAX		INTEGER { disable(0), enable(1) }
		MAX-ACCESS		read-write
		STATUS			current
		DESCRIPTION
				"TYPE: - Checkbox
				 PAGE: - Logging- Inp 1 Level
					Emb Ch 6 Level  cmdID= 1081 "
		::= { iqsda02CmdEntry 1081 }


	iqsda02LoggingInp1LevelEmbCh6Level OBJECT-TYPE
		SYNTAX		RollCallString
		MAX-ACCESS		read-only
		STATUS			current
		DESCRIPTION
				"TYPE: - Display
				 PAGE: - Logging- Inp 1 Level
					Emb Ch 6 Level=  cmdID= 2081  format=   "
		::= { iqsda02CmdEntry 2081 }


	iqsda02LoggingInp1LevelEmbCh7LevelEnable OBJECT-TYPE
		SYNTAX		INTEGER { disable(0), enable(1) }
		MAX-ACCESS		read-write
		STATUS			current
		DESCRIPTION
				"TYPE: - Checkbox
				 PAGE: - Logging- Inp 1 Level
					Emb Ch 7 Level  cmdID= 1082 "
		::= { iqsda02CmdEntry 1082 }


	iqsda02LoggingInp1LevelEmbCh7Level OBJECT-TYPE
		SYNTAX		RollCallString
		MAX-ACCESS		read-only
		STATUS			current
		DESCRIPTION
				"TYPE: - Display
				 PAGE: - Logging- Inp 1 Level
					Emb Ch 7 Level=  cmdID= 2082  format=   "
		::= { iqsda02CmdEntry 2082 }


	iqsda02LoggingInp1LevelEmbCh8LevelEnable OBJECT-TYPE
		SYNTAX		INTEGER { disable(0), enable(1) }
		MAX-ACCESS		read-write
		STATUS			current
		DESCRIPTION
				"TYPE: - Checkbox
				 PAGE: - Logging- Inp 1 Level
					Emb Ch 8 Level  cmdID= 1083 "
		::= { iqsda02CmdEntry 1083 }


	iqsda02LoggingInp1LevelEmbCh8Level OBJECT-TYPE
		SYNTAX		RollCallString
		MAX-ACCESS		read-only
		STATUS			current
		DESCRIPTION
				"TYPE: - Display
				 PAGE: - Logging- Inp 1 Level
					Emb Ch 8 Level=  cmdID= 2083  format=   "
		::= { iqsda02CmdEntry 2083 }


	iqsda02LoggingInp1LevelEmbCh9LevelEnable OBJECT-TYPE
		SYNTAX		INTEGER { disable(0), enable(1) }
		MAX-ACCESS		read-write
		STATUS			current
		DESCRIPTION
				"TYPE: - Checkbox
				 PAGE: - Logging- Inp 1 Level
					Emb Ch 9 Level  cmdID= 1084 "
		::= { iqsda02CmdEntry 1084 }


	iqsda02LoggingInp1LevelEmbCh9Level OBJECT-TYPE
		SYNTAX		RollCallString
		MAX-ACCESS		read-only
		STATUS			current
		DESCRIPTION
				"TYPE: - Display
				 PAGE: - Logging- Inp 1 Level
					Emb Ch 9 Level=  cmdID= 2084  format=   "
		::= { iqsda02CmdEntry 2084 }


	iqsda02LoggingInp1LevelEmbCh10LevelEnable OBJECT-TYPE
		SYNTAX		INTEGER { disable(0), enable(1) }
		MAX-ACCESS		read-write
		STATUS			current
		DESCRIPTION
				"TYPE: - Checkbox
				 PAGE: - Logging- Inp 1 Level
					Emb Ch 10 Level  cmdID= 1085 "
		::= { iqsda02CmdEntry 1085 }


	iqsda02LoggingInp1LevelEmbCh10Level OBJECT-TYPE
		SYNTAX		RollCallString
		MAX-ACCESS		read-only
		STATUS			current
		DESCRIPTION
				"TYPE: - Display
				 PAGE: - Logging- Inp 1 Level
					Emb Ch 10 Level=  cmdID= 2085  format=   "
		::= { iqsda02CmdEntry 2085 }


	iqsda02LoggingInp1LevelEmbCh11LevelEnable OBJECT-TYPE
		SYNTAX		INTEGER { disable(0), enable(1) }
		MAX-ACCESS		read-write
		STATUS			current
		DESCRIPTION
				"TYPE: - Checkbox
				 PAGE: - Logging- Inp 1 Level
					Emb Ch 11 Level  cmdID= 1086 "
		::= { iqsda02CmdEntry 1086 }


	iqsda02LoggingInp1LevelEmbCh11Level OBJECT-TYPE
		SYNTAX		RollCallString
		MAX-ACCESS		read-only
		STATUS			current
		DESCRIPTION
				"TYPE: - Display
				 PAGE: - Logging- Inp 1 Level
					Emb Ch 11 Level=  cmdID= 2086  format=   "
		::= { iqsda02CmdEntry 2086 }


	iqsda02LoggingInp1LevelEmbCh12LevelEnable OBJECT-TYPE
		SYNTAX		INTEGER { disable(0), enable(1) }
		MAX-ACCESS		read-write
		STATUS			current
		DESCRIPTION
				"TYPE: - Checkbox
				 PAGE: - Logging- Inp 1 Level
					Emb Ch 12 Level  cmdID= 1087 "
		::= { iqsda02CmdEntry 1087 }


	iqsda02LoggingInp1LevelEmbCh12Level OBJECT-TYPE
		SYNTAX		RollCallString
		MAX-ACCESS		read-only
		STATUS			current
		DESCRIPTION
				"TYPE: - Display
				 PAGE: - Logging- Inp 1 Level
					Emb Ch 12 Level=  cmdID= 2087  format=   "
		::= { iqsda02CmdEntry 2087 }


	iqsda02LoggingInp1LevelEmbCh13LevelEnable OBJECT-TYPE
		SYNTAX		INTEGER { disable(0), enable(1) }
		MAX-ACCESS		read-write
		STATUS			current
		DESCRIPTION
				"TYPE: - Checkbox
				 PAGE: - Logging- Inp 1 Level
					Emb Ch 13 Level  cmdID= 1088 "
		::= { iqsda02CmdEntry 1088 }


	iqsda02LoggingInp1LevelEmbCh13Level OBJECT-TYPE
		SYNTAX		RollCallString
		MAX-ACCESS		read-only
		STATUS			current
		DESCRIPTION
				"TYPE: - Display
				 PAGE: - Logging- Inp 1 Level
					Emb Ch 13 Level=  cmdID= 2088  format=   "
		::= { iqsda02CmdEntry 2088 }


	iqsda02LoggingInp1LevelEmbCh14LevelEnable OBJECT-TYPE
		SYNTAX		INTEGER { disable(0), enable(1) }
		MAX-ACCESS		read-write
		STATUS			current
		DESCRIPTION
				"TYPE: - Checkbox
				 PAGE: - Logging- Inp 1 Level
					Emb Ch 14 Level  cmdID= 1089 "
		::= { iqsda02CmdEntry 1089 }


	iqsda02LoggingInp1LevelEmbCh14Level OBJECT-TYPE
		SYNTAX		RollCallString
		MAX-ACCESS		read-only
		STATUS			current
		DESCRIPTION
				"TYPE: - Display
				 PAGE: - Logging- Inp 1 Level
					Emb Ch 14 Level=  cmdID= 2089  format=   "
		::= { iqsda02CmdEntry 2089 }


	iqsda02LoggingInp1LevelEmbCh15LevelEnable OBJECT-TYPE
		SYNTAX		INTEGER { disable(0), enable(1) }
		MAX-ACCESS		read-write
		STATUS			current
		DESCRIPTION
				"TYPE: - Checkbox
				 PAGE: - Logging- Inp 1 Level
					Emb Ch 15 Level  cmdID= 1090 "
		::= { iqsda02CmdEntry 1090 }


	iqsda02LoggingInp1LevelEmbCh15Level OBJECT-TYPE
		SYNTAX		RollCallString
		MAX-ACCESS		read-only
		STATUS			current
		DESCRIPTION
				"TYPE: - Display
				 PAGE: - Logging- Inp 1 Level
					Emb Ch 15 Level=  cmdID= 2090  format=   "
		::= { iqsda02CmdEntry 2090 }


	iqsda02LoggingInp1LevelEmbCh16LevelEnable OBJECT-TYPE
		SYNTAX		INTEGER { disable(0), enable(1) }
		MAX-ACCESS		read-write
		STATUS			current
		DESCRIPTION
				"TYPE: - Checkbox
				 PAGE: - Logging- Inp 1 Level
					Emb Ch 16 Level  cmdID= 1091 "
		::= { iqsda02CmdEntry 1091 }


	iqsda02LoggingInp1LevelEmbCh16Level OBJECT-TYPE
		SYNTAX		RollCallString
		MAX-ACCESS		read-only
		STATUS			current
		DESCRIPTION
				"TYPE: - Display
				 PAGE: - Logging- Inp 1 Level
					Emb Ch 16 Level=  cmdID= 2091  format=   "
		::= { iqsda02CmdEntry 2091 }


	iqsda02LoggingInp1ClippingEmbCh1LevelEnable OBJECT-TYPE
		SYNTAX		INTEGER { disable(0), enable(1) }
		MAX-ACCESS		read-write
		STATUS			current
		DESCRIPTION
				"TYPE: - Checkbox
				 PAGE: - Logging- Inp 1 Clipping
					Emb Ch 1 Level  cmdID= 1134 "
		::= { iqsda02CmdEntry 1134 }


	iqsda02LoggingInp1ClippingEmbCh1Level OBJECT-TYPE
		SYNTAX		RollCallString
		MAX-ACCESS		read-only
		STATUS			current
		DESCRIPTION
				"TYPE: - Display
				 PAGE: - Logging- Inp 1 Clipping
					Emb Ch 1 Level=  cmdID= 2134  format=   "
		::= { iqsda02CmdEntry 2134 }


	iqsda02LoggingInp1ClippingEmbCh2LevelEnable OBJECT-TYPE
		SYNTAX		INTEGER { disable(0), enable(1) }
		MAX-ACCESS		read-write
		STATUS			current
		DESCRIPTION
				"TYPE: - Checkbox
				 PAGE: - Logging- Inp 1 Clipping
					Emb Ch 2 Level  cmdID= 1135 "
		::= { iqsda02CmdEntry 1135 }


	iqsda02LoggingInp1ClippingEmbCh2Level OBJECT-TYPE
		SYNTAX		RollCallString
		MAX-ACCESS		read-only
		STATUS			current
		DESCRIPTION
				"TYPE: - Display
				 PAGE: - Logging- Inp 1 Clipping
					Emb Ch 2 Level=  cmdID= 2135  format=   "
		::= { iqsda02CmdEntry 2135 }


	iqsda02LoggingInp1ClippingEmbCh3LevelEnable OBJECT-TYPE
		SYNTAX		INTEGER { disable(0), enable(1) }
		MAX-ACCESS		read-write
		STATUS			current
		DESCRIPTION
				"TYPE: - Checkbox
				 PAGE: - Logging- Inp 1 Clipping
					Emb Ch 3 Level  cmdID= 1136 "
		::= { iqsda02CmdEntry 1136 }


	iqsda02LoggingInp1ClippingEmbCh3Level OBJECT-TYPE
		SYNTAX		RollCallString
		MAX-ACCESS		read-only
		STATUS			current
		DESCRIPTION
				"TYPE: - Display
				 PAGE: - Logging- Inp 1 Clipping
					Emb Ch 3 Level=  cmdID= 2136  format=   "
		::= { iqsda02CmdEntry 2136 }


	iqsda02LoggingInp1ClippingEmbCh4LevelEnable OBJECT-TYPE
		SYNTAX		INTEGER { disable(0), enable(1) }
		MAX-ACCESS		read-write
		STATUS			current
		DESCRIPTION
				"TYPE: - Checkbox
				 PAGE: - Logging- Inp 1 Clipping
					Emb Ch 4 Level  cmdID= 1137 "
		::= { iqsda02CmdEntry 1137 }


	iqsda02LoggingInp1ClippingEmbCh4Level OBJECT-TYPE
		SYNTAX		RollCallString
		MAX-ACCESS		read-only
		STATUS			current
		DESCRIPTION
				"TYPE: - Display
				 PAGE: - Logging- Inp 1 Clipping
					Emb Ch 4 Level=  cmdID= 2137  format=   "
		::= { iqsda02CmdEntry 2137 }


	iqsda02LoggingInp1ClippingEmbCh5LevelEnable OBJECT-TYPE
		SYNTAX		INTEGER { disable(0), enable(1) }
		MAX-ACCESS		read-write
		STATUS			current
		DESCRIPTION
				"TYPE: - Checkbox
				 PAGE: - Logging- Inp 1 Clipping
					Emb Ch 5 Level  cmdID= 1138 "
		::= { iqsda02CmdEntry 1138 }


	iqsda02LoggingInp1ClippingEmbCh5Level OBJECT-TYPE
		SYNTAX		RollCallString
		MAX-ACCESS		read-only
		STATUS			current
		DESCRIPTION
				"TYPE: - Display
				 PAGE: - Logging- Inp 1 Clipping
					Emb Ch 5 Level=  cmdID= 2138  format=   "
		::= { iqsda02CmdEntry 2138 }


	iqsda02LoggingInp1ClippingEmbCh6LevelEnable OBJECT-TYPE
		SYNTAX		INTEGER { disable(0), enable(1) }
		MAX-ACCESS		read-write
		STATUS			current
		DESCRIPTION
				"TYPE: - Checkbox
				 PAGE: - Logging- Inp 1 Clipping
					Emb Ch 6 Level  cmdID= 1139 "
		::= { iqsda02CmdEntry 1139 }


	iqsda02LoggingInp1ClippingEmbCh6Level OBJECT-TYPE
		SYNTAX		RollCallString
		MAX-ACCESS		read-only
		STATUS			current
		DESCRIPTION
				"TYPE: - Display
				 PAGE: - Logging- Inp 1 Clipping
					Emb Ch 6 Level=  cmdID= 2139  format=   "
		::= { iqsda02CmdEntry 2139 }


	iqsda02LoggingInp1ClippingEmbCh7LevelEnable OBJECT-TYPE
		SYNTAX		INTEGER { disable(0), enable(1) }
		MAX-ACCESS		read-write
		STATUS			current
		DESCRIPTION
				"TYPE: - Checkbox
				 PAGE: - Logging- Inp 1 Clipping
					Emb Ch 7 Level  cmdID= 1140 "
		::= { iqsda02CmdEntry 1140 }


	iqsda02LoggingInp1ClippingEmbCh7Level OBJECT-TYPE
		SYNTAX		RollCallString
		MAX-ACCESS		read-only
		STATUS			current
		DESCRIPTION
				"TYPE: - Display
				 PAGE: - Logging- Inp 1 Clipping
					Emb Ch 7 Level=  cmdID= 2140  format=   "
		::= { iqsda02CmdEntry 2140 }


	iqsda02LoggingInp1ClippingEmbCh8LevelEnable OBJECT-TYPE
		SYNTAX		INTEGER { disable(0), enable(1) }
		MAX-ACCESS		read-write
		STATUS			current
		DESCRIPTION
				"TYPE: - Checkbox
				 PAGE: - Logging- Inp 1 Clipping
					Emb Ch 8 Level  cmdID= 1141 "
		::= { iqsda02CmdEntry 1141 }


	iqsda02LoggingInp1ClippingEmbCh8Level OBJECT-TYPE
		SYNTAX		RollCallString
		MAX-ACCESS		read-only
		STATUS			current
		DESCRIPTION
				"TYPE: - Display
				 PAGE: - Logging- Inp 1 Clipping
					Emb Ch 8 Level=  cmdID= 2141  format=   "
		::= { iqsda02CmdEntry 2141 }


	iqsda02LoggingInp1ClippingEmbCh9LevelEnable OBJECT-TYPE
		SYNTAX		INTEGER { disable(0), enable(1) }
		MAX-ACCESS		read-write
		STATUS			current
		DESCRIPTION
				"TYPE: - Checkbox
				 PAGE: - Logging- Inp 1 Clipping
					Emb Ch 9 Level  cmdID= 1142 "
		::= { iqsda02CmdEntry 1142 }


	iqsda02LoggingInp1ClippingEmbCh9Level OBJECT-TYPE
		SYNTAX		RollCallString
		MAX-ACCESS		read-only
		STATUS			current
		DESCRIPTION
				"TYPE: - Display
				 PAGE: - Logging- Inp 1 Clipping
					Emb Ch 9 Level=  cmdID= 2142  format=   "
		::= { iqsda02CmdEntry 2142 }


	iqsda02LoggingInp1ClippingEmbCh10LevelEnable OBJECT-TYPE
		SYNTAX		INTEGER { disable(0), enable(1) }
		MAX-ACCESS		read-write
		STATUS			current
		DESCRIPTION
				"TYPE: - Checkbox
				 PAGE: - Logging- Inp 1 Clipping
					Emb Ch 10 Level  cmdID= 1143 "
		::= { iqsda02CmdEntry 1143 }


	iqsda02LoggingInp1ClippingEmbCh10Level OBJECT-TYPE
		SYNTAX		RollCallString
		MAX-ACCESS		read-only
		STATUS			current
		DESCRIPTION
				"TYPE: - Display
				 PAGE: - Logging- Inp 1 Clipping
					Emb Ch 10 Level=  cmdID= 2143  format=   "
		::= { iqsda02CmdEntry 2143 }


	iqsda02LoggingInp1ClippingEmbCh11LevelEnable OBJECT-TYPE
		SYNTAX		INTEGER { disable(0), enable(1) }
		MAX-ACCESS		read-write
		STATUS			current
		DESCRIPTION
				"TYPE: - Checkbox
				 PAGE: - Logging- Inp 1 Clipping
					Emb Ch 11 Level  cmdID= 1144 "
		::= { iqsda02CmdEntry 1144 }


	iqsda02LoggingInp1ClippingEmbCh11Level OBJECT-TYPE
		SYNTAX		RollCallString
		MAX-ACCESS		read-only
		STATUS			current
		DESCRIPTION
				"TYPE: - Display
				 PAGE: - Logging- Inp 1 Clipping
					Emb Ch 11 Level=  cmdID= 2144  format=   "
		::= { iqsda02CmdEntry 2144 }


	iqsda02LoggingInp1ClippingEmbCh12LevelEnable OBJECT-TYPE
		SYNTAX		INTEGER { disable(0), enable(1) }
		MAX-ACCESS		read-write
		STATUS			current
		DESCRIPTION
				"TYPE: - Checkbox
				 PAGE: - Logging- Inp 1 Clipping
					Emb Ch 12 Level  cmdID= 1145 "
		::= { iqsda02CmdEntry 1145 }


	iqsda02LoggingInp1ClippingEmbCh12Level OBJECT-TYPE
		SYNTAX		RollCallString
		MAX-ACCESS		read-only
		STATUS			current
		DESCRIPTION
				"TYPE: - Display
				 PAGE: - Logging- Inp 1 Clipping
					Emb Ch 12 Level=  cmdID= 2145  format=   "
		::= { iqsda02CmdEntry 2145 }


	iqsda02LoggingInp1ClippingEmbCh13LevelEnable OBJECT-TYPE
		SYNTAX		INTEGER { disable(0), enable(1) }
		MAX-ACCESS		read-write
		STATUS			current
		DESCRIPTION
				"TYPE: - Checkbox
				 PAGE: - Logging- Inp 1 Clipping
					Emb Ch 13 Level  cmdID= 1146 "
		::= { iqsda02CmdEntry 1146 }


	iqsda02LoggingInp1ClippingEmbCh13Level OBJECT-TYPE
		SYNTAX		RollCallString
		MAX-ACCESS		read-only
		STATUS			current
		DESCRIPTION
				"TYPE: - Display
				 PAGE: - Logging- Inp 1 Clipping
					Emb Ch 13 Level=  cmdID= 2146  format=   "
		::= { iqsda02CmdEntry 2146 }


	iqsda02LoggingInp1ClippingEmbCh14LevelEnable OBJECT-TYPE
		SYNTAX		INTEGER { disable(0), enable(1) }
		MAX-ACCESS		read-write
		STATUS			current
		DESCRIPTION
				"TYPE: - Checkbox
				 PAGE: - Logging- Inp 1 Clipping
					Emb Ch 14 Level  cmdID= 1147 "
		::= { iqsda02CmdEntry 1147 }


	iqsda02LoggingInp1ClippingEmbCh14Level OBJECT-TYPE
		SYNTAX		RollCallString
		MAX-ACCESS		read-only
		STATUS			current
		DESCRIPTION
				"TYPE: - Display
				 PAGE: - Logging- Inp 1 Clipping
					Emb Ch 14 Level=  cmdID= 2147  format=   "
		::= { iqsda02CmdEntry 2147 }


	iqsda02LoggingInp1ClippingEmbCh15LevelEnable OBJECT-TYPE
		SYNTAX		INTEGER { disable(0), enable(1) }
		MAX-ACCESS		read-write
		STATUS			current
		DESCRIPTION
				"TYPE: - Checkbox
				 PAGE: - Logging- Inp 1 Clipping
					Emb Ch 15 Level  cmdID= 1148 "
		::= { iqsda02CmdEntry 1148 }


	iqsda02LoggingInp1ClippingEmbCh15Level OBJECT-TYPE
		SYNTAX		RollCallString
		MAX-ACCESS		read-only
		STATUS			current
		DESCRIPTION
				"TYPE: - Display
				 PAGE: - Logging- Inp 1 Clipping
					Emb Ch 15 Level=  cmdID= 2148  format=   "
		::= { iqsda02CmdEntry 2148 }


	iqsda02LoggingInp1ClippingEmbCh16LevelEnable OBJECT-TYPE
		SYNTAX		INTEGER { disable(0), enable(1) }
		MAX-ACCESS		read-write
		STATUS			current
		DESCRIPTION
				"TYPE: - Checkbox
				 PAGE: - Logging- Inp 1 Clipping
					Emb Ch 16 Level  cmdID= 1149 "
		::= { iqsda02CmdEntry 1149 }


	iqsda02LoggingInp1ClippingEmbCh16Level OBJECT-TYPE
		SYNTAX		RollCallString
		MAX-ACCESS		read-only
		STATUS			current
		DESCRIPTION
				"TYPE: - Display
				 PAGE: - Logging- Inp 1 Clipping
					Emb Ch 16 Level=  cmdID= 2149  format=   "
		::= { iqsda02CmdEntry 2149 }


	iqsda02LoggingInp1LikenessDetector1ChansEnable OBJECT-TYPE
		SYNTAX		INTEGER { disable(0), enable(1) }
		MAX-ACCESS		read-write
		STATUS			current
		DESCRIPTION
				"TYPE: - Checkbox
				 PAGE: - Logging- Inp 1 Likeness
					Detector 1 Chans  cmdID= 1101 "
		::= { iqsda02CmdEntry 1101 }


	iqsda02LoggingInp1LikenessDetector1Chans OBJECT-TYPE
		SYNTAX		RollCallString
		MAX-ACCESS		read-only
		STATUS			current
		DESCRIPTION
				"TYPE: - Display
				 PAGE: - Logging- Inp 1 Likeness
					Detector 1 Chans=  cmdID= 2101  format=   "
		::= { iqsda02CmdEntry 2101 }


	iqsda02LoggingInp1LikenessDetector1StateEnable OBJECT-TYPE
		SYNTAX		INTEGER { disable(0), enable(1) }
		MAX-ACCESS		read-write
		STATUS			current
		DESCRIPTION
				"TYPE: - Checkbox
				 PAGE: - Logging- Inp 1 Likeness
					Detector 1 State  cmdID= 1105 "
		::= { iqsda02CmdEntry 1105 }


	iqsda02LoggingInp1LikenessDetector1State OBJECT-TYPE
		SYNTAX		RollCallString
		MAX-ACCESS		read-only
		STATUS			current
		DESCRIPTION
				"TYPE: - Display
				 PAGE: - Logging- Inp 1 Likeness
					Detector 1 State=  cmdID= 2105  format=   "
		::= { iqsda02CmdEntry 2105 }


	iqsda02LoggingInp1LikenessDetector2ChansEnable OBJECT-TYPE
		SYNTAX		INTEGER { disable(0), enable(1) }
		MAX-ACCESS		read-write
		STATUS			current
		DESCRIPTION
				"TYPE: - Checkbox
				 PAGE: - Logging- Inp 1 Likeness
					Detector 2 Chans  cmdID= 1102 "
		::= { iqsda02CmdEntry 1102 }


	iqsda02LoggingInp1LikenessDetector2Chans OBJECT-TYPE
		SYNTAX		RollCallString
		MAX-ACCESS		read-only
		STATUS			current
		DESCRIPTION
				"TYPE: - Display
				 PAGE: - Logging- Inp 1 Likeness
					Detector 2 Chans=  cmdID= 2102  format=   "
		::= { iqsda02CmdEntry 2102 }


	iqsda02LoggingInp1LikenessDetector2StateEnable OBJECT-TYPE
		SYNTAX		INTEGER { disable(0), enable(1) }
		MAX-ACCESS		read-write
		STATUS			current
		DESCRIPTION
				"TYPE: - Checkbox
				 PAGE: - Logging- Inp 1 Likeness
					Detector 2 State  cmdID= 1106 "
		::= { iqsda02CmdEntry 1106 }


	iqsda02LoggingInp1LikenessDetector2State OBJECT-TYPE
		SYNTAX		RollCallString
		MAX-ACCESS		read-only
		STATUS			current
		DESCRIPTION
				"TYPE: - Display
				 PAGE: - Logging- Inp 1 Likeness
					Detector 2 State=  cmdID= 2106  format=   "
		::= { iqsda02CmdEntry 2106 }


	iqsda02LoggingInp1LikenessDetector3ChansEnable OBJECT-TYPE
		SYNTAX		INTEGER { disable(0), enable(1) }
		MAX-ACCESS		read-write
		STATUS			current
		DESCRIPTION
				"TYPE: - Checkbox
				 PAGE: - Logging- Inp 1 Likeness
					Detector 3 Chans  cmdID= 1103 "
		::= { iqsda02CmdEntry 1103 }


	iqsda02LoggingInp1LikenessDetector3Chans OBJECT-TYPE
		SYNTAX		RollCallString
		MAX-ACCESS		read-only
		STATUS			current
		DESCRIPTION
				"TYPE: - Display
				 PAGE: - Logging- Inp 1 Likeness
					Detector 3 Chans=  cmdID= 2103  format=   "
		::= { iqsda02CmdEntry 2103 }


	iqsda02LoggingInp1LikenessDetector3StateEnable OBJECT-TYPE
		SYNTAX		INTEGER { disable(0), enable(1) }
		MAX-ACCESS		read-write
		STATUS			current
		DESCRIPTION
				"TYPE: - Checkbox
				 PAGE: - Logging- Inp 1 Likeness
					Detector 3 State  cmdID= 1107 "
		::= { iqsda02CmdEntry 1107 }


	iqsda02LoggingInp1LikenessDetector3State OBJECT-TYPE
		SYNTAX		RollCallString
		MAX-ACCESS		read-only
		STATUS			current
		DESCRIPTION
				"TYPE: - Display
				 PAGE: - Logging- Inp 1 Likeness
					Detector 3 State=  cmdID= 2107  format=   "
		::= { iqsda02CmdEntry 2107 }


	iqsda02LoggingInp1LikenessDetector4ChansEnable OBJECT-TYPE
		SYNTAX		INTEGER { disable(0), enable(1) }
		MAX-ACCESS		read-write
		STATUS			current
		DESCRIPTION
				"TYPE: - Checkbox
				 PAGE: - Logging- Inp 1 Likeness
					Detector 4 Chans  cmdID= 1104 "
		::= { iqsda02CmdEntry 1104 }


	iqsda02LoggingInp1LikenessDetector4Chans OBJECT-TYPE
		SYNTAX		RollCallString
		MAX-ACCESS		read-only
		STATUS			current
		DESCRIPTION
				"TYPE: - Display
				 PAGE: - Logging- Inp 1 Likeness
					Detector 4 Chans=  cmdID= 2104  format=   "
		::= { iqsda02CmdEntry 2104 }


	iqsda02LoggingInp1LikenessDetector4StateEnable OBJECT-TYPE
		SYNTAX		INTEGER { disable(0), enable(1) }
		MAX-ACCESS		read-write
		STATUS			current
		DESCRIPTION
				"TYPE: - Checkbox
				 PAGE: - Logging- Inp 1 Likeness
					Detector 4 State  cmdID= 1108 "
		::= { iqsda02CmdEntry 1108 }


	iqsda02LoggingInp1LikenessDetector4State OBJECT-TYPE
		SYNTAX		RollCallString
		MAX-ACCESS		read-only
		STATUS			current
		DESCRIPTION
				"TYPE: - Display
				 PAGE: - Logging- Inp 1 Likeness
					Detector 4 State=  cmdID= 2108  format=   "
		::= { iqsda02CmdEntry 2108 }


	iqsda02LoggingOut1UMIDUMIDStateEnable OBJECT-TYPE
		SYNTAX		INTEGER { disable(0), enable(1) }
		MAX-ACCESS		read-write
		STATUS			current
		DESCRIPTION
				"TYPE: - Checkbox
				 PAGE: - Logging
					UMID State  cmdID= 1121 "
		::= { iqsda02CmdEntry 1121 }


	iqsda02LoggingOut1UMIDUMIDState OBJECT-TYPE
		SYNTAX		RollCallString
		MAX-ACCESS		read-only
		STATUS			current
		DESCRIPTION
				"TYPE: - Display
				 PAGE: - Logging
					UMID State=  cmdID= 2121  format=   "
		::= { iqsda02CmdEntry 2121 }


	iqsda02LoggingOut1UMIDOutputUMIDEnable OBJECT-TYPE
		SYNTAX		INTEGER { disable(0), enable(1) }
		MAX-ACCESS		read-write
		STATUS			current
		DESCRIPTION
				"TYPE: - Checkbox
				 PAGE: - Logging
					Output UMID  cmdID= 1122 "
		::= { iqsda02CmdEntry 1122 }


	iqsda02LoggingOut1UMIDOutputUMID1_8 OBJECT-TYPE
		SYNTAX		RollCallString
		MAX-ACCESS		read-only
		STATUS			current
		DESCRIPTION
				"TYPE: - Display
				 PAGE: - Logging
					Output UMID 1-8=  cmdID= 2122  format=   "
		::= { iqsda02CmdEntry 2122 }


	iqsda02LoggingOut1UMIDOutputUMID9_16 OBJECT-TYPE
		SYNTAX		RollCallString
		MAX-ACCESS		read-only
		STATUS			current
		DESCRIPTION
				"TYPE: - Display
				 PAGE: - Logging
					Output UMID 9-16=  cmdID= 4101  format=   "
		::= { iqsda02CmdEntry 4101 }


	iqsda02LoggingOut1UMIDOutputUMID17_24 OBJECT-TYPE
		SYNTAX		RollCallString
		MAX-ACCESS		read-only
		STATUS			current
		DESCRIPTION
				"TYPE: - Display
				 PAGE: - Logging
					Output UMID 17-24=  cmdID= 4102  format=   "
		::= { iqsda02CmdEntry 4102 }


	iqsda02LoggingOut1UMIDOutputUMID25_32 OBJECT-TYPE
		SYNTAX		RollCallString
		MAX-ACCESS		read-only
		STATUS			current
		DESCRIPTION
				"TYPE: - Display
				 PAGE: - Logging
					Output UMID 25-32=  cmdID= 4103  format=   "
		::= { iqsda02CmdEntry 4103 }


	iqsda02LoggingInp1UMIDUMIDStateEnable OBJECT-TYPE
		SYNTAX		INTEGER { disable(0), enable(1) }
		MAX-ACCESS		read-write
		STATUS			current
		DESCRIPTION
				"TYPE: - Checkbox
				 PAGE: - Logging
					UMID State  cmdID= 1013 "
		::= { iqsda02CmdEntry 1013 }


	iqsda02LoggingInp1UMIDUMIDState OBJECT-TYPE
		SYNTAX		RollCallString
		MAX-ACCESS		read-only
		STATUS			current
		DESCRIPTION
				"TYPE: - Display
				 PAGE: - Logging
					UMID State=  cmdID= 2013  format=   "
		::= { iqsda02CmdEntry 2013 }


	iqsda02LoggingInp1UMIDUMIDCurrentEnable OBJECT-TYPE
		SYNTAX		INTEGER { disable(0), enable(1) }
		MAX-ACCESS		read-write
		STATUS			current
		DESCRIPTION
				"TYPE: - Checkbox
				 PAGE: - Logging
					UMID Current 1-8  cmdID= 1014 "
		::= { iqsda02CmdEntry 1014 }


	iqsda02LoggingInp1UMIDUMIDCurrent1_8 OBJECT-TYPE
		SYNTAX		RollCallString
		MAX-ACCESS		read-only
		STATUS			current
		DESCRIPTION
				"TYPE: - Display
				 PAGE: - Logging
					UMID Current 1-8=  cmdID= 2014  format=   "
		::= { iqsda02CmdEntry 2014 }


	iqsda02LoggingInp1UMIDUMIDCurrent9_16 OBJECT-TYPE
		SYNTAX		RollCallString
		MAX-ACCESS		read-only
		STATUS			current
		DESCRIPTION
				"TYPE: - Display
				 PAGE: - Logging
					UMID Current 9-16=  cmdID= 4104  format=   "
		::= { iqsda02CmdEntry 4104 }


	iqsda02LoggingInp1UMIDUMIDCurrent17_24 OBJECT-TYPE
		SYNTAX		RollCallString
		MAX-ACCESS		read-only
		STATUS			current
		DESCRIPTION
				"TYPE: - Display
				 PAGE: - Logging
					UMID Current 17-24=  cmdID= 4105  format=   "
		::= { iqsda02CmdEntry 4105 }


	iqsda02LoggingInp1UMIDUMIDCurrent25_32 OBJECT-TYPE
		SYNTAX		RollCallString
		MAX-ACCESS		read-only
		STATUS			current
		DESCRIPTION
				"TYPE: - Display
				 PAGE: - Logging
					UMID Current 25-32=  cmdID= 4106  format=   "
		::= { iqsda02CmdEntry 4106 }


	iqsda02LoggingInp1UMIDUMIDPreviousEnable OBJECT-TYPE
		SYNTAX		INTEGER { disable(0), enable(1) }
		MAX-ACCESS		read-write
		STATUS			current
		DESCRIPTION
				"TYPE: - Checkbox
				 PAGE: - Logging
					UMID Previous 1-8  cmdID= 1015 "
		::= { iqsda02CmdEntry 1015 }


	iqsda02LoggingInp1UMIDUMIDPrev1_8 OBJECT-TYPE
		SYNTAX		RollCallString
		MAX-ACCESS		read-only
		STATUS			current
		DESCRIPTION
				"TYPE: - Display
				 PAGE: - Logging
					UMID Prev 1-8=  cmdID= 2015  format=   "
		::= { iqsda02CmdEntry 2015 }


	iqsda02LoggingInp1UMIDUMIDPrev9_16 OBJECT-TYPE
		SYNTAX		RollCallString
		MAX-ACCESS		read-only
		STATUS			current
		DESCRIPTION
				"TYPE: - Display
				 PAGE: - Logging
					UMID Prev 9-16=  cmdID= 4107  format=   "
		::= { iqsda02CmdEntry 4107 }


	iqsda02LoggingInp1UMIDUMIDPrev17_24 OBJECT-TYPE
		SYNTAX		RollCallString
		MAX-ACCESS		read-only
		STATUS			current
		DESCRIPTION
				"TYPE: - Display
				 PAGE: - Logging
					UMID Prev 17-24=  cmdID= 4108  format=   "
		::= { iqsda02CmdEntry 4108 }


	iqsda02LoggingInp1UMIDUMIDPrev25_32 OBJECT-TYPE
		SYNTAX		RollCallString
		MAX-ACCESS		read-only
		STATUS			current
		DESCRIPTION
				"TYPE: - Display
				 PAGE: - Logging
					UMID Prev 25-32=  cmdID= 4109  format=   "
		::= { iqsda02CmdEntry 4109 }


	iqsda02LoggingInp1UMIDUMIDPreviousCountEnable OBJECT-TYPE
		SYNTAX		INTEGER { disable(0), enable(1) }
		MAX-ACCESS		read-write
		STATUS			current
		DESCRIPTION
				"TYPE: - Checkbox
				 PAGE: - Logging
					UMID Previous Count  cmdID= 1016 "
		::= { iqsda02CmdEntry 1016 }


	iqsda02LoggingInp1UMIDUMIDPrevCount OBJECT-TYPE
		SYNTAX		RollCallString
		MAX-ACCESS		read-only
		STATUS			current
		DESCRIPTION
				"TYPE: - Display
				 PAGE: - Logging
					UMID Prev Count=  cmdID= 2016  format=   "
		::= { iqsda02CmdEntry 2016 }


	iqsda02LoggingOut1PIDPIDStateEnable OBJECT-TYPE
		SYNTAX		INTEGER { disable(0), enable(1) }
		MAX-ACCESS		read-write
		STATUS			current
		DESCRIPTION
				"TYPE: - Checkbox
				 PAGE: - Logging
					PID State  cmdID= 1123 "
		::= { iqsda02CmdEntry 1123 }


	iqsda02LoggingOut1PIDPIDState OBJECT-TYPE
		SYNTAX		RollCallString
		MAX-ACCESS		read-only
		STATUS			current
		DESCRIPTION
				"TYPE: - Display
				 PAGE: - Logging
					PID State=  cmdID= 2123  format=   "
		::= { iqsda02CmdEntry 2123 }


	iqsda02LoggingOut1PIDPIDHouseIDEnable OBJECT-TYPE
		SYNTAX		INTEGER { disable(0), enable(1) }
		MAX-ACCESS		read-write
		STATUS			current
		DESCRIPTION
				"TYPE: - Checkbox
				 PAGE: - Logging
					PID House ID  cmdID= 1124 "
		::= { iqsda02CmdEntry 1124 }


	iqsda02LoggingOut1PIDPIDHouseID OBJECT-TYPE
		SYNTAX		RollCallString
		MAX-ACCESS		read-only
		STATUS			current
		DESCRIPTION
				"TYPE: - Display
				 PAGE: - Logging
					PID House ID=  cmdID= 2124  format=   "
		::= { iqsda02CmdEntry 2124 }


	iqsda02LoggingOut1PIDPIDTitleEnable OBJECT-TYPE
		SYNTAX		INTEGER { disable(0), enable(1) }
		MAX-ACCESS		read-write
		STATUS			current
		DESCRIPTION
				"TYPE: - Checkbox
				 PAGE: - Logging
					PID Title  cmdID= 1125 "
		::= { iqsda02CmdEntry 1125 }


	iqsda02LoggingOut1PIDPIDTitle OBJECT-TYPE
		SYNTAX		RollCallString
		MAX-ACCESS		read-only
		STATUS			current
		DESCRIPTION
				"TYPE: - Display
				 PAGE: - Logging
					PID Title=  cmdID= 2125  format=   "
		::= { iqsda02CmdEntry 2125 }


	iqsda02LoggingOut1PIDSegmentNumberEnable OBJECT-TYPE
		SYNTAX		INTEGER { disable(0), enable(1) }
		MAX-ACCESS		read-write
		STATUS			current
		DESCRIPTION
				"TYPE: - Checkbox
				 PAGE: - Logging
					Segment Number  cmdID= 1126 "
		::= { iqsda02CmdEntry 1126 }


	iqsda02LoggingOut1PIDSegmentNumber OBJECT-TYPE
		SYNTAX		RollCallString
		MAX-ACCESS		read-only
		STATUS			current
		DESCRIPTION
				"TYPE: - Display
				 PAGE: - Logging
					Segment Number=  cmdID= 2126  format=   "
		::= { iqsda02CmdEntry 2126 }


	iqsda02LoggingOut1PIDDurationEnable OBJECT-TYPE
		SYNTAX		INTEGER { disable(0), enable(1) }
		MAX-ACCESS		read-write
		STATUS			current
		DESCRIPTION
				"TYPE: - Checkbox
				 PAGE: - Logging
					Duration  cmdID= 1127 "
		::= { iqsda02CmdEntry 1127 }


	iqsda02LoggingOut1PIDDuration OBJECT-TYPE
		SYNTAX		RollCallString
		MAX-ACCESS		read-only
		STATUS			current
		DESCRIPTION
				"TYPE: - Display
				 PAGE: - Logging
					Duration=  cmdID= 2127  format=   "
		::= { iqsda02CmdEntry 2127 }


	iqsda02LoggingOut1PIDFrameRateEnable OBJECT-TYPE
		SYNTAX		INTEGER { disable(0), enable(1) }
		MAX-ACCESS		read-write
		STATUS			current
		DESCRIPTION
				"TYPE: - Checkbox
				 PAGE: - Logging
					Frame Rate  cmdID= 1128 "
		::= { iqsda02CmdEntry 1128 }


	iqsda02LoggingOut1PIDFrameRate OBJECT-TYPE
		SYNTAX		RollCallString
		MAX-ACCESS		read-only
		STATUS			current
		DESCRIPTION
				"TYPE: - Display
				 PAGE: - Logging
					Frame Rate=  cmdID= 2128  format=   "
		::= { iqsda02CmdEntry 2128 }


	iqsda02LoggingInp1PIDPIDStateEnable OBJECT-TYPE
		SYNTAX		INTEGER { disable(0), enable(1) }
		MAX-ACCESS		read-write
		STATUS			current
		DESCRIPTION
				"TYPE: - Checkbox
				 PAGE: - Logging
					PID State  cmdID= 1109 "
		::= { iqsda02CmdEntry 1109 }


	iqsda02LoggingInp1PIDPIDState OBJECT-TYPE
		SYNTAX		RollCallString
		MAX-ACCESS		read-only
		STATUS			current
		DESCRIPTION
				"TYPE: - Display
				 PAGE: - Logging
					PID State=  cmdID= 2109  format=   "
		::= { iqsda02CmdEntry 2109 }


	iqsda02LoggingInp1PIDPIDHouseIDEnable OBJECT-TYPE
		SYNTAX		INTEGER { disable(0), enable(1) }
		MAX-ACCESS		read-write
		STATUS			current
		DESCRIPTION
				"TYPE: - Checkbox
				 PAGE: - Logging
					PID House ID  cmdID= 1110 "
		::= { iqsda02CmdEntry 1110 }


	iqsda02LoggingInp1PIDPIDHouseID OBJECT-TYPE
		SYNTAX		RollCallString
		MAX-ACCESS		read-only
		STATUS			current
		DESCRIPTION
				"TYPE: - Display
				 PAGE: - Logging
					PID House ID=  cmdID= 2110  format=   "
		::= { iqsda02CmdEntry 2110 }


	iqsda02LoggingInp1PIDPIDTitleEnable OBJECT-TYPE
		SYNTAX		INTEGER { disable(0), enable(1) }
		MAX-ACCESS		read-write
		STATUS			current
		DESCRIPTION
				"TYPE: - Checkbox
				 PAGE: - Logging
					PID Title  cmdID= 1111 "
		::= { iqsda02CmdEntry 1111 }


	iqsda02LoggingInp1PIDPIDTitle OBJECT-TYPE
		SYNTAX		RollCallString
		MAX-ACCESS		read-only
		STATUS			current
		DESCRIPTION
				"TYPE: - Display
				 PAGE: - Logging
					PID Title=  cmdID= 2111  format=   "
		::= { iqsda02CmdEntry 2111 }


	iqsda02LoggingInp1PIDSegmentNumberEnable OBJECT-TYPE
		SYNTAX		INTEGER { disable(0), enable(1) }
		MAX-ACCESS		read-write
		STATUS			current
		DESCRIPTION
				"TYPE: - Checkbox
				 PAGE: - Logging
					Segment Number  cmdID= 1112 "
		::= { iqsda02CmdEntry 1112 }


	iqsda02LoggingInp1PIDSegmentNumber OBJECT-TYPE
		SYNTAX		RollCallString
		MAX-ACCESS		read-only
		STATUS			current
		DESCRIPTION
				"TYPE: - Display
				 PAGE: - Logging
					Segment Number=  cmdID= 2112  format=   "
		::= { iqsda02CmdEntry 2112 }


	iqsda02LoggingInp1PIDDurationEnable OBJECT-TYPE
		SYNTAX		INTEGER { disable(0), enable(1) }
		MAX-ACCESS		read-write
		STATUS			current
		DESCRIPTION
				"TYPE: - Checkbox
				 PAGE: - Logging
					Duration  cmdID= 1113 "
		::= { iqsda02CmdEntry 1113 }


	iqsda02LoggingInp1PIDDuration OBJECT-TYPE
		SYNTAX		RollCallString
		MAX-ACCESS		read-only
		STATUS			current
		DESCRIPTION
				"TYPE: - Display
				 PAGE: - Logging
					Duration=  cmdID= 2113  format=   "
		::= { iqsda02CmdEntry 2113 }


	iqsda02LoggingInp1PIDFrameRateEnable OBJECT-TYPE
		SYNTAX		INTEGER { disable(0), enable(1) }
		MAX-ACCESS		read-write
		STATUS			current
		DESCRIPTION
				"TYPE: - Checkbox
				 PAGE: - Logging
					Frame Rate  cmdID= 1114 "
		::= { iqsda02CmdEntry 1114 }


	iqsda02LoggingInp1PIDFrameRate OBJECT-TYPE
		SYNTAX		RollCallString
		MAX-ACCESS		read-only
		STATUS			current
		DESCRIPTION
				"TYPE: - Display
				 PAGE: - Logging
					Frame Rate=  cmdID= 2114  format=   "
		::= { iqsda02CmdEntry 2114 }


	iqsda02LoggingInp1PIDPreviousHouseIDEnable OBJECT-TYPE
		SYNTAX		INTEGER { disable(0), enable(1) }
		MAX-ACCESS		read-write
		STATUS			current
		DESCRIPTION
				"TYPE: - Checkbox
				 PAGE: - Logging
					Previous House ID  cmdID= 1115 "
		::= { iqsda02CmdEntry 1115 }


	iqsda02LoggingInp1PIDPreviousHouseID OBJECT-TYPE
		SYNTAX		RollCallString
		MAX-ACCESS		read-only
		STATUS			current
		DESCRIPTION
				"TYPE: - Display
				 PAGE: - Logging
					Previous House ID=  cmdID= 2115  format=   "
		::= { iqsda02CmdEntry 2115 }


	iqsda02LoggingInp1PIDPreviousTitleEnable OBJECT-TYPE
		SYNTAX		INTEGER { disable(0), enable(1) }
		MAX-ACCESS		read-write
		STATUS			current
		DESCRIPTION
				"TYPE: - Checkbox
				 PAGE: - Logging
					Previous Title  cmdID= 1116 "
		::= { iqsda02CmdEntry 1116 }


	iqsda02LoggingInp1PIDPreviousTitle OBJECT-TYPE
		SYNTAX		RollCallString
		MAX-ACCESS		read-only
		STATUS			current
		DESCRIPTION
				"TYPE: - Display
				 PAGE: - Logging
					Previous Title=  cmdID= 2116  format=   "
		::= { iqsda02CmdEntry 2116 }


	iqsda02LoggingInp1PIDPreviousSegNumEnable OBJECT-TYPE
		SYNTAX		INTEGER { disable(0), enable(1) }
		MAX-ACCESS		read-write
		STATUS			current
		DESCRIPTION
				"TYPE: - Checkbox
				 PAGE: - Logging
					Previous Seg Num  cmdID= 1117 "
		::= { iqsda02CmdEntry 1117 }


	iqsda02LoggingInp1PIDPreviousSegNum OBJECT-TYPE
		SYNTAX		RollCallString
		MAX-ACCESS		read-only
		STATUS			current
		DESCRIPTION
				"TYPE: - Display
				 PAGE: - Logging
					Previous Seg Num=  cmdID= 2117  format=   "
		::= { iqsda02CmdEntry 2117 }


	iqsda02LoggingInp1PIDPreviousDurationEnable OBJECT-TYPE
		SYNTAX		INTEGER { disable(0), enable(1) }
		MAX-ACCESS		read-write
		STATUS			current
		DESCRIPTION
				"TYPE: - Checkbox
				 PAGE: - Logging
					Previous Duration  cmdID= 1118 "
		::= { iqsda02CmdEntry 1118 }


	iqsda02LoggingInp1PIDPreviousDuration OBJECT-TYPE
		SYNTAX		RollCallString
		MAX-ACCESS		read-only
		STATUS			current
		DESCRIPTION
				"TYPE: - Display
				 PAGE: - Logging
					Previous Duration=  cmdID= 2118  format=   "
		::= { iqsda02CmdEntry 2118 }


	iqsda02LoggingInp1PIDPreviousFrameRateEnable OBJECT-TYPE
		SYNTAX		INTEGER { disable(0), enable(1) }
		MAX-ACCESS		read-write
		STATUS			current
		DESCRIPTION
				"TYPE: - Checkbox
				 PAGE: - Logging
					Previous FrameRate  cmdID= 1119 "
		::= { iqsda02CmdEntry 1119 }


	iqsda02LoggingInp1PIDPreviousFrameRate OBJECT-TYPE
		SYNTAX		RollCallString
		MAX-ACCESS		read-only
		STATUS			current
		DESCRIPTION
				"TYPE: - Display
				 PAGE: - Logging
					Previous FrameRate=  cmdID= 2119  format=   "
		::= { iqsda02CmdEntry 2119 }


	iqsda02LoggingInp1PIDPreviousCountEnable OBJECT-TYPE
		SYNTAX		INTEGER { disable(0), enable(1) }
		MAX-ACCESS		read-write
		STATUS			current
		DESCRIPTION
				"TYPE: - Checkbox
				 PAGE: - Logging
					Previous Count  cmdID= 1120 "
		::= { iqsda02CmdEntry 1120 }


	iqsda02LoggingInp1PIDPreviousCount OBJECT-TYPE
		SYNTAX		RollCallString
		MAX-ACCESS		read-only
		STATUS			current
		DESCRIPTION
				"TYPE: - Display
				 PAGE: - Logging
					Previous Count=  cmdID= 2120  format=   "
		::= { iqsda02CmdEntry 2120 }


	iqsda02RollcallRollTrackDisableAll OBJECT-TYPE
		SYNTAX		INTEGER { disable(0), enable(1) }
		MAX-ACCESS		read-write
		STATUS			current
		DESCRIPTION
				"TYPE: - Checkbox
				 PAGE: - Rollcall
					Disable All  cmdID= 1413 "
		::= { iqsda02CmdEntry 1413 }


	iqsda02RollcallRollTrackIndex OBJECT-TYPE
		SYNTAX		INTEGER
		MAX-ACCESS		read-write
		STATUS			current
		DESCRIPTION
				"TYPE: - BarGraph
				 PAGE: - Rollcall
					Index  cmdID= 1415  min= 1  max= 16   step= 1  format= %0.0f  div_scale= 1
					Min = 1  Max = 16  Step = 1 "
		::= { iqsda02CmdEntry 1415 }


	iqsda02RollcallRollTrackSource OBJECT-TYPE
		SYNTAX		INTEGER {
							val_Unused(-1),
							val_Input_OK(0),
							val_Input_None(1),
							val_IP1_1125_1035_30I(2),
							val_IP1_1125_1035_29I(3),
							val_IP1_1125_1080_30I(4),
							val_IP1_1125_1080_29I(5),
							val_IP1_1125_1080_25I(6),
							val_IP1_1125_1080_30P(7),
							val_IP1_1125_1080_29P(8),
							val_IP1_1125_1080_25P(9),
							val_IP1_1125_1080_24P(10),
							val_IP1_1125_1080_23P(11),
							val_IP1_750_720_60P(12),
							val_IP1_750_720_59P(13),
							val_IP1_525_480_29I(14),
							val_IP1_625_576_25I(15),
							val_IP1_1125_1080_24sF(16),
							val_IP1_1125_1080_23sF(17),
							val_IP1_750_720_50P(18),
							val_IP1_750_720_30P(19),
							val_IP1_750_720_29P(20),
							val_IP1_750_720_25P(21),
							val_Hyperion_OK(22),
							val_Hyperion_WARN(23),
							val_Hyperion_FAIL(24),
							val_Hyperion_N_A(25)
							}
		MAX-ACCESS		read-write
		STATUS			current
		DESCRIPTION
				"TYPE: - RadiobuttonList
				 PAGE: - Rollcall
					Source  cmdID= 1416
					Unused  value= -1
					Input OK  value= 0
					Input None  value= 1
					IP1 1125(1035)/30I  value= 2
					IP1 1125(1035)/29I  value= 3
					IP1 1125(1080)/30I  value= 4
					IP1 1125(1080)/29I  value= 5
					IP1 1125(1080)/25I  value= 6
					IP1 1125(1080)/30P  value= 7
					IP1 1125(1080)/29P  value= 8
					IP1 1125(1080)/25P  value= 9
					IP1 1125(1080)/24P  value= 10
					IP1 1125(1080)/23P  value= 11
					IP1 750(720)/60P  value= 12
					IP1 750(720)/59P  value= 13
					IP1 525(480)/29I  value= 14
					IP1 625(576)/25I  value= 15
					IP1 1125(1080)/24sF  value= 16
					IP1 1125(1080)/23sF  value= 17
					IP1 750(720)/50P  value= 18
					IP1 750(720)/30P  value= 19
					IP1 750(720)/29P  value= 20
					IP1 750(720)/25P  value= 21
					Hyperion OK  value= 22
					Hyperion WARN  value= 23
					Hyperion FAIL  value= 24
					Hyperion N/A  value= 25  "
		::= { iqsda02CmdEntry 1416 }


	iqsda02RollcallRollTrackAddress OBJECT-TYPE
		SYNTAX		RollCallString
		MAX-ACCESS		read-write
		STATUS			current
		DESCRIPTION
				"TYPE: - Editstring
				 PAGE: - Rollcall
					Address  cmdID= 1417  "
		::= { iqsda02CmdEntry 1417 }


	iqsda02RollcallRollTrackCommand OBJECT-TYPE
		SYNTAX		RollCallString
		MAX-ACCESS		read-write
		STATUS			current
		DESCRIPTION
				"TYPE: - Editstring
				 PAGE: - Rollcall
					Command  cmdID= 1418  "
		::= { iqsda02CmdEntry 1418 }


	iqsda02RollcallRollTrackStatus OBJECT-TYPE
		SYNTAX		RollCallString
		MAX-ACCESS		read-only
		STATUS			current
		DESCRIPTION
				"TYPE: - Display
				 PAGE: - Rollcall
					Status  cmdID= 1411  format=   "
		::= { iqsda02CmdEntry 1411 }


	iqsda02RollcallRollTrackSending OBJECT-TYPE
		SYNTAX		RollCallString
		MAX-ACCESS		read-only
		STATUS			current
		DESCRIPTION
				"TYPE: - Display
				 PAGE: - Rollcall
					Sending  cmdID= 1414  format=   "
		::= { iqsda02CmdEntry 1414 }


	iqsda02SetupProduct OBJECT-TYPE
		SYNTAX		RollCallString
		MAX-ACCESS		read-only
		STATUS			current
		DESCRIPTION
				"TYPE: - Display
					Product  cmdID= 32771  format=   "
		::= { iqsda02CmdEntry 32771 }


	iqsda02SetupProductRelease OBJECT-TYPE
		SYNTAX		RollCallString
		MAX-ACCESS		read-only
		STATUS			current
		DESCRIPTION
				"TYPE: - Display
					Release  cmdID= 2  format=   "
		::= { iqsda02CmdEntry 2 }


	iqsda02SetupProductBuild OBJECT-TYPE
		SYNTAX		RollCallString
		MAX-ACCESS		read-only
		STATUS			current
		DESCRIPTION
				"TYPE: - Display
					Build  cmdID= 5  format=   "
		::= { iqsda02CmdEntry 5 }


	iqsda02SetupProductKOS OBJECT-TYPE
		SYNTAX		RollCallString
		MAX-ACCESS		read-only
		STATUS			current
		DESCRIPTION
				"TYPE: - Display
					KOS  cmdID= 32772  format=   "
		::= { iqsda02CmdEntry 32772 }


	iqsda02SetupProductSerial OBJECT-TYPE
		SYNTAX		RollCallString
		MAX-ACCESS		read-only
		STATUS			current
		DESCRIPTION
				"TYPE: - Display
					Serial  cmdID= 1  format=   "
		::= { iqsda02CmdEntry 1 }


	iqsda02SetupProductFirmware OBJECT-TYPE
		SYNTAX		RollCallString
		MAX-ACCESS		read-only
		STATUS			current
		DESCRIPTION
				"TYPE: - Display
					Firmware  cmdID= 5100  format=   "
		::= { iqsda02CmdEntry 5100 }


	iqsda02SetupProductPCB OBJECT-TYPE
		SYNTAX		RollCallString
		MAX-ACCESS		read-only
		STATUS			current
		DESCRIPTION
				"TYPE: - Display
					PCB  cmdID= 5101  format=   "
		::= { iqsda02CmdEntry 5101 }


	iqsda02SetupProductFactoryDefault OBJECT-TYPE
		SYNTAX		INTEGER { noAction(0),val_Factory_Default(1) }
		MAX-ACCESS		read-write
		STATUS			current
		DESCRIPTION
				"TYPE: - Button
					Factory Default  cmdID= 5520  value= 1  "
		::= { iqsda02CmdEntry 5520 }


	iqsda02SetupProductRestart OBJECT-TYPE
		SYNTAX		INTEGER {
							val_Restart_Soft_Only(1),
							val_Restart_Soft_Hard(2)
							}
		MAX-ACCESS		read-write
		STATUS			current
		DESCRIPTION
				"TYPE: - Button
					Restart Soft. Only  cmdID= 4  value= 1
					Restart Soft/Hard.  cmdID= 4  value= 2  "
		::= { iqsda02CmdEntry 4 }


	iqsda02SetupInput1Name OBJECT-TYPE
		SYNTAX		RollCallString
		MAX-ACCESS		read-write
		STATUS			current
		DESCRIPTION
				"TYPE: - Editstring
					Name  cmdID= 1336  "
		::= { iqsda02CmdEntry 1336 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: s36093244
--				:
-- Comments		: Serial Number of module
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:12:00
--				:
-- Comments		: Uptime Days:Hours:Mins:Sec
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number or current control sessions.
--
---------------------------------------------------------------------------------------------------
-- Header		: INPUT_1_VI
--
-- MIB ref		: swCardEventLogSlotXX       .10.73.78.80.85.84.95.49.95.86.73
-- absolute OID	: 1.3.6.1.4.1.7995.2.6.1.1.XX.10.73.78.80.85.84.95.49.95.86.73
-- Vary			: YES
--
-- Value(s)		: -
--  Not available
--    =-
--
--  VI Type SMPTE selected
--    =SMPTE
--
--  VI Type is "AFD:SMPTE 2016" selected
--  input is 4x3
--    =AFD:LB 16:9 Top
--    =AFD:LB 14:9 Top
--    =AFD:LB > 16:9 VC
--    =AFD:FF 4:3
--    =AFD:LB 16:9 VC
--    =AFD:LB 14:9 VC
--    =AFD:FF 4:3 alt 14:9 C
--    =AFD:LB 16:9 alt 14:9 C
--    =AFD:LB 16:9 alt 4: C
--
--  input is 16x9
--    =FF 16:9
--    =AFD:PB 14:9 HC
--    =AFD:LB > 16:9 VC
--    =AFD:FF 16:9
--    =AFD:PB 4:3 HC
--    =AFD:FF 16:9 Pro
--    =AFD:PB 14:9 HC
--    =AFD:PB 4:3 alt 14:9 C
--    =AFD:FF 16:9 alt 14:9 C
--    =AFD:FF 16:9 alt 4: C
--
--  VI Type is "Legacy AFD" or "Legacy AFD and ScanSys"
--    =AFD0:CodedFrame
--    =AFD1:4:3
--    =AFD2:16:9
--    =AFD3:14:9
--    =AFD4:(AFD=4)
--    =AFD5:4:3 SP 14:9 C
--    =AFD6:16:9 SP 14:9 C
--    =AFD7:16:9 SP 4:3
-- Comments		:
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				:
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: Disabled
--          No logging info
--              : -
--          No Errors found
--              : OK
--          List of failed RollTracks e.g.
--              : FAIL:1,3,5
-- Comments		:
--
---------------------------------------------------------------------------------------------------
-- Header		: INPUT_1_APL
--
-- MIB ref		: swCardEventLogSlotXX       .11.73.78.80.85.84.95.49.95.65.80.76
-- absolute OID	: 1.3.6.1.4.1.7995.2.6.1.1.XX.11.73.78.80.85.84.95.49.95.65.80.76
-- Vary			: YES
--
-- Value(s)		: OK
--				: Info:OK
--				: WARN:MIN APL
--				: WARN:MAX APL
--				: Info:MIN APL
--				: Info:MAX APL
--				:
-- Comments		:
--
---------------------------------------------------------------------------------------------------
-- Header		: INPUT_1_CRC
--
-- MIB ref		: swCardEventLogSlotXX       .11.73.78.80.85.84.95.49.95.67.82.67
-- absolute OID	: 1.3.6.1.4.1.7995.2.6.1.1.XX.11.73.78.80.85.84.95.49.95.67.82.67
-- Vary			: YES
--
-- Value(s)		: -
--				: OK
--				: WARN:CRC Error
--				:
-- Comments		: This is active with a HD input only
--
---------------------------------------------------------------------------------------------------
-- Header		: INPUT_1_EDH
--
-- MIB ref		: swCardEventLogSlotXX       .11.73.78.80.85.84.95.49.95.69.68.72
-- absolute OID	: 1.3.6.1.4.1.7995.2.6.1.1.XX.11.73.78.80.85.84.95.49.95.69.68.72
-- Vary			: YES
--
-- Value(s)		: OK
--				: NONE
--				: WARN:EDH Error
--				:
-- Comments		: This is active with a SD input only
--
---------------------------------------------------------------------------------------------------
-- Header		: INPUT_1_WSS
--
-- MIB ref		: swCardEventLogSlotXX       .11.73.78.80.85.84.95.49.95.87.83.83
-- absolute OID	: 1.3.6.1.4.1.7995.2.6.1.1.XX.11.73.78.80.85.84.95.49.95.87.83.83
-- Vary			: YES
--
-- Value(s)		:
--          Not available
--              : -
--
--          WSS Type is "ETSI"
--              : ETSI:Parity Error
--              : ETSI:Box 14:9 C
--              : ETSI:Box 14:9 Top
--              : ETSI:Box 16:9 Top
--              : ETSI:FF 16:9 Ana
--              : ETSI:FF 4:3
--              : ETSI:Box 16:9
--              : ETSI:Box > 16:9 C
--              : ETSI:FF4:3 SP 14:9C
--
--          WSS Type is "AFD" or "AFD and ScanSys"
--              : AFD0:CodedFrame
--              : AFD1:4:3
--              : AFD2:16:9
--              : AFD3:14:9
--              : AFD4:(AFD=4)
--              : AFD5:4:3 SP 14:9 C
--              : AFD6:16:9 SP 14:9 C
--              : AFD7:16:9 SP 4:3
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: NO
--
-- Value(s)		: 0006502725
--				:
-- Comments		: Software build verion number
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
-- Vary			: YES
--
-- Value(s)		: INPUT 1 SERIAL IN
--				:
-- Comments		: Edit box, default shown
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: NO
--
-- Value(s)		: HD/SD SDI
--				:
-- Comments		: Fixed, describes the input type
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2008-03-06T17:04:02Z
--				:
-- Comments		: Date/Time of last known restart
--
---------------------------------------------------------------------------------------------------
-- Header		: INPUT_1_BLACK
--
-- MIB ref		: swCardEventLogSlotXX       .13.73.78.80.85.84.95.49.95.66.76.65.67.75
-- absolute OID	: 1.3.6.1.4.1.7995.2.6.1.1.XX.13.73.78.80.85.84.95.49.95.66.76.65.67.75
-- Vary			: YES
--
-- Value(s)		: OK
--				: WARN:BLACK
--				: FAIL:BLACK
--				: Info:OK
--				: Info:BLACK
--				:
-- Comments		:
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: NO
--
-- Value(s)		: SERIAL IN
--				:
-- Comments		: Fixed
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: OK
--				: FAIL:Lost
--				:
-- Comments		:
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 2008-03-06T17:04:02Z
-- Comments		: Date/Time of last control modification
--
---------------------------------------------------------------------------------------------------
-- Header		: OUTPUT_1_UMID
--
-- MIB ref		: swCardEventLogSlotXX       .13.79.85.84.80.85.84.95.49.95.85.77.73.68
-- absolute OID	: 1.3.6.1.4.1.7995.2.6.1.1.XX.13.79.85.84.80.85.84.95.49.95.85.77.73.68
-- Vary			: YES
--
-- Value(s)		: <X........X>
--				: WARN:No UMID
--				: Info:No UMID
--				:
-- Comments		: 64 hex digits to represent 32 byte UMID
--
---------------------------------------------------------------------------------------------------
-- Header		: INPUT_1_FREEZE
--
-- MIB ref		: swCardEventLogSlotXX       .14.73.78.80.85.84.95.49.95.70.82.69.69.90.69
-- absolute OID	: 1.3.6.1.4.1.7995.2.6.1.1.XX.14.73.78.80.85.84.95.49.95.70.82.69.69.90.69
-- Vary			: YES
--
-- Value(s)		:
--          Detector not enabled
--              : Info:OK
--              : Info:Freeze
--
--          Detector enabled
--              : OK
--              : WARN:Freeze
--              : FAIL:Freeze
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: NO
--
-- Value(s)		: 3.6
--				:
-- Comments		: Variable dependant on the Firmware Build
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: NO
--
-- Value(s)		: RDHDAI2X.000
--				:
-- Comments		: Variable dependant on the Hardware Build
--
---------------------------------------------------------------------------------------------------
-- Header		: INPUT_1_BLACKISH
--
-- MIB ref		: swCardEventLogSlotXX       .16.73.78.80.85.84.95.49.95.66.76.65.67.75.73.83.72
-- absolute OID	: 1.3.6.1.4.1.7995.2.6.1.1.XX.16.73.78.80.85.84.95.49.95.66.76.65.67.75.73.83.72
-- Vary			: YES
--
-- Value(s)		: OK
--				: WARN:BLACKISH
--				: FAIL:BLACKISH
--				: Info:OK
--				: Info:BLACKISH
--				:
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: unknown
--				: 1125(1035)/30I
--				: 1125(1035)/29I
--				: 1125(1080)/60P
--				: 1125(1080)/59P
--				: 1125(1080)/50P
--				: 1125(1080)/30I
--				: 1125(1080)/29I
--				: 1125(1080)/25I
--				: 1125(1080)/30P
--				: 1125(1080)/29P
--				: 1125(1080)/25P
--				: 1125(1080)/24P
--				: 1125(1080)/23P
--				: 1250(1080)/50P
--				: 1250(1080)/25I
--				: 750(720)/60P
--				: 750(720)/59P
--				: 525(480)/59P
--				: 525(480)/29I
--				: 625(576)/25I
--				: 525(480)/29I
--				: 625(576)/25I
--				: 1125(1080)/24sF
--				: 1125(1080)/23sF
--				: 525(480)/60P
--				: 525(480)/59P
--				: 625(576)/24sF
--				: 625(576)/23sF
--				: 1250(1152)/25I
--				: 750(720)/50P
--				: 625(576)/50P
--				: 525(480)/60P
--				: 525(480)/59P
--				: 1125(1080)/30sF
--				: 1125(1080)/29sF
--				: 1125(1080)/25sF
--				: 750(720)/30P
--				: 750(720)/29P
--				: 750(720)/25P
--				: 750(720)/24P
--				: 750(720)/23P
--				: 525(480)/29I
--				: 625(576)/25I
--				: 625(576)/24I
--				: 625(576)/23I
--				:
-- Comments		:
--
---------------------------------------------------------------------------------------------------
-- Header		: INPUT_1_STILLISH
--
-- MIB ref		: swCardEventLogSlotXX       .16.73.78.80.85.84.95.49.95.83.84.73.76.76.73.83.72
-- absolute OID	: 1.3.6.1.4.1.7995.2.6.1.1.XX.16.73.78.80.85.84.95.49.95.83.84.73.76.76.73.83.72
-- Vary			: YES
--
-- Value(s)		: OK
--				: WARN:Stillish
--				: FAIL:Stillish
--				: Info:OK
--				: Info:Stillish
--				:
-- Comments		:
--
---------------------------------------------------------------------------------------------------
-- Header		: INPUT_1_VI_STATE
--
-- MIB ref		: swCardEventLogSlotXX       .16.73.78.80.85.84.95.49.95.86.73.95.83.84.65.84.69
-- absolute OID	: 1.3.6.1.4.1.7995.2.6.1.1.XX.16.73.78.80.85.84.95.49.95.86.73.95.83.84.65.84.69
-- Vary			: YES
--
-- Value(s)		: -
--				: OK
--				: FAIL:No VI
--				: Info:OK
--				: Info:No VI
-- Comments		:
--
---------------------------------------------------------------------------------------------------
-- Header		: INPUT_1_PID_STATE
--
-- MIB ref		: swCardEventLogSlotXX       .17.73.78.80.85.84.95.49.95.80.73.68.95.83.84.65.84.69
-- absolute OID	: 1.3.6.1.4.1.7995.2.6.1.1.XX.17.73.78.80.85.84.95.49.95.80.73.68.95.83.84.65.84.69
-- Vary			: YES
--
-- Value(s)		: OK
--              : WARN:No PID
--              : WARN:Multiple Line Error
--              : WARN:Length Error
--              : WARN:Inc House ID
--              : WARN:Illegal Tag Value
--              : WARN:Inc Seg Num Len
--              : WARN:Inc Duration Len
--              : WARN:Inc Frame Rate Len
--              : WARN:Inc Data Count
--              : WARN:Checksum Error
--              : WARN:Not Hyperion PID
--              : WARN:Changing
--              : Info:No PID
--              : Info:Multiple Line Error
--              : Info:Length Error
--              : Info:Inc House ID
--              : Info:Illegal Tag Value
--              : Info:Inc Seg Num Len
--              : Info:Inc Duration Len
--              : Info:Inc Frame Rate Len
--              : Info:Inc Data Count
--              : Info:Checksum Error
--              : Info:Not Hyperion PID
--              : Info:Changing
--				:
-- Comments		:
--
---------------------------------------------------------------------------------------------------
-- Header		: INPUT_1_PID_TITLE
--
-- MIB ref		: swCardEventLogSlotXX       .17.73.78.80.85.84.95.49.95.80.73.68.95.84.73.84.76.69
-- absolute OID	: 1.3.6.1.4.1.7995.2.6.1.1.XX.17.73.78.80.85.84.95.49.95.80.73.68.95.84.73.84.76.69
-- Vary			: YES
--
-- Value(s)		: <19 Characters>
--				: WARN:No PID
--				: Info:No PID
-- Comments		:
--
---------------------------------------------------------------------------------------------------
-- Header		: INPUT_1_VI_ASPECT
--
-- MIB ref		: swCardEventLogSlotXX       .17.73.78.80.85.84.95.49.95.86.73.95.65.83.80.69.67.84
-- absolute OID	: 1.3.6.1.4.1.7995.2.6.1.1.XX.17.73.78.80.85.84.95.49.95.86.73.95.65.83.80.69.67.84
-- Vary			: YES
--
-- Value(s)		: -
--				: 4:3
--				: 16:9
--				: No Info
--				: N/A
-- Comments		:
--
---------------------------------------------------------------------------------------------------
-- Header		: INPUT_1_WSS_STATE
--
-- MIB ref		: swCardEventLogSlotXX       .17.73.78.80.85.84.95.49.95.87.83.83.95.83.84.65.84.69
-- absolute OID	: 1.3.6.1.4.1.7995.2.6.1.1.XX.17.73.78.80.85.84.95.49.95.87.83.83.95.83.84.65.84.69
-- Vary			: YES
--
-- Value(s)		: OK
--              : WARN:Error
--              : FAIL:No WSS
--              : Info:OK
--              : Info:Error
--              : Info:No WSS
--              : -
--				:
-- Comments		:
--
---------------------------------------------------------------------------------------------------
-- Header		: INPUT_1_UMID_STATE
--
-- MIB ref		: swCardEventLogSlotXX       .18.73.78.80.85.84.95.49.95.85.77.73.68.95.83.84.65.84.69
-- absolute OID	: 1.3.6.1.4.1.7995.2.6.1.1.XX.18.73.78.80.85.84.95.49.95.85.77.73.68.95.83.84.65.84.69
-- Vary			: YES
--
-- Value(s)		: OK
--				: WARN:Multiple Line Error
--				: WARN:Length Error
--				: WARN:Checksum Error
--				: WARN:Changing
--				: WARN:No UMID
--				: Info:Multiple Line Error
--				: Info:Length Error
--				: Info:Checksum Error
--				: Info:Changing
--				: Info:No UMID
--				:
-- Comments		:
--
---------------------------------------------------------------------------------------------------
-- Header		: INPUT_1_VITC_STATE
--
-- MIB ref		: swCardEventLogSlotXX       .18.73.78.80.85.84.95.49.95.86.73.84.67.95.83.84.65.84.69
-- absolute OID	: 1.3.6.1.4.1.7995.2.6.1.1.XX.18.73.78.80.85.84.95.49.95.86.73.84.67.95.83.84.65.84.69
-- Vary			: YES
--
-- Value(s)		: OK
--				: FAIL:No VITC
--				: FAIL:No VITC Field 1
--				: FAIL:No VITC Field 2
--				: Info:OK
--				: Info:No VITC
--				: Info:No VITC Field 1
--				: Info:No VITC Field 2
-- Comments		:
--
---------------------------------------------------------------------------------------------------
-- Header		: INPUT_1_WSS_ASPECT
--
-- MIB ref		: swCardEventLogSlotXX       .18.73.78.80.85.84.95.49.95.87.83.83.95.65.83.80.69.67.84
-- absolute OID	: 1.3.6.1.4.1.7995.2.6.1.1.XX.18.73.78.80.85.84.95.49.95.87.83.83.95.65.83.80.69.67.84
-- Vary			: YES
--
-- Value(s)		: -
--				: 4:3
--				: 16:9
--				: No Info
--				: N/A
-- Comments		:
--
---------------------------------------------------------------------------------------------------
-- Header		: OUPUT_1_OSD_STATUS
--
-- MIB ref		: swCardEventLogSlotXX       .18.79.85.80.85.84.95.49.95.79.83.68.95.83.84.65.84.85.83
-- absolute OID	: 1.3.6.1.4.1.7995.2.6.1.1.XX.18.79.85.80.85.84.95.49.95.79.83.68.95.83.84.65.84.85.83
-- Vary			: YES
--
-- Value(s)		: OFF
--				: WARN:ON
-- Comments		:
--
---------------------------------------------------------------------------------------------------
-- Header		: OUTPUT_1_PID_STATE
--
-- MIB ref		: swCardEventLogSlotXX       .18.79.85.84.80.85.84.95.49.95.80.73.68.95.83.84.65.84.69
-- absolute OID	: 1.3.6.1.4.1.7995.2.6.1.1.XX.18.79.85.84.80.85.84.95.49.95.80.73.68.95.83.84.65.84.69
-- Vary			: YES
--
-- Value(s)		: OK
--				: Pass
--				: Overwrite
--				: Deleted
--				: WARN:Multiple Lines
--				: WARN:No PID
--				: Info:Multiple Lines
--				: Info:No PID
--				:
-- Comments		:
--
---------------------------------------------------------------------------------------------------
-- Header		: OUTPUT_1_PID_TITLE
--
-- MIB ref		: swCardEventLogSlotXX       .18.79.85.84.80.85.84.95.49.95.80.73.68.95.84.73.84.76.69
-- absolute OID	: 1.3.6.1.4.1.7995.2.6.1.1.XX.18.79.85.84.80.85.84.95.49.95.80.73.68.95.84.73.84.76.69
-- Vary			: YES
--
-- Value(s)		: <19 Characters>
--				: WARN:No PID
--				: Info:No PID
--				:
-- Comments		:
--
---------------------------------------------------------------------------------------------------
-- Header		: INPUT_1_C_BIT_DEPTH
--
-- MIB ref		: swCardEventLogSlotXX       .19.73.78.80.85.84.95.49.95.67.95.66.73.84.95.68.69.80.84.72
-- absolute OID	: 1.3.6.1.4.1.7995.2.6.1.1.XX.19.73.78.80.85.84.95.49.95.67.95.66.73.84.95.68.69.80.84.72
-- Vary			: YES
--
-- Value(s)		: UNKNOWN
--				: 8
--				: 9
--				: 10
--				:
-- Comments		:
--
---------------------------------------------------------------------------------------------------
-- Header		: INPUT_1_C_VIDEO_LOW
--
-- MIB ref		: swCardEventLogSlotXX       .19.73.78.80.85.84.95.49.95.67.95.86.73.68.69.79.95.76.79.87
-- absolute OID	: 1.3.6.1.4.1.7995.2.6.1.1.XX.19.73.78.80.85.84.95.49.95.67.95.86.73.68.69.79.95.76.79.87
-- Vary			: YES
--
-- Value(s)		: OK
--				: Info:OK
--				: FAIL:Low
--				: Info:Low
--				:
-- Comments		:
--
---------------------------------------------------------------------------------------------------
-- Header		: INPUT_1_PID_SEG_NUM
--
-- MIB ref		: swCardEventLogSlotXX       .19.73.78.80.85.84.95.49.95.80.73.68.95.83.69.71.95.78.85.77
-- absolute OID	: 1.3.6.1.4.1.7995.2.6.1.1.XX.19.73.78.80.85.84.95.49.95.80.73.68.95.83.69.71.95.78.85.77
-- Vary			: YES
--
-- Value(s)		: <0 to 65535>
--				: WARN:No PID
--				: Info:No PID
--				:
-- Comments		:
--
---------------------------------------------------------------------------------------------------
-- Header		: INPUT_1_Y_BIT_DEPTH
--
-- MIB ref		: swCardEventLogSlotXX       .19.73.78.80.85.84.95.49.95.89.95.66.73.84.95.68.69.80.84.72
-- absolute OID	: 1.3.6.1.4.1.7995.2.6.1.1.XX.19.73.78.80.85.84.95.49.95.89.95.66.73.84.95.68.69.80.84.72
-- Vary			: YES
--
-- Value(s)		: UNKNOWN
--				: 8
--				: 9
--				: 10
--				:
-- Comments		:
--
---------------------------------------------------------------------------------------------------
-- Header		: INPUT_1_Y_VIDEO_LOW
--
-- MIB ref		: swCardEventLogSlotXX       .19.73.78.80.85.84.95.49.95.89.95.86.73.68.69.79.95.76.79.87
-- absolute OID	: 1.3.6.1.4.1.7995.2.6.1.1.XX.19.73.78.80.85.84.95.49.95.89.95.86.73.68.69.79.95.76.79.87
-- Vary			: YES
--
-- Value(s)		: OK
--				: Info:OK
--				: FAIL:Low
--				: Info:Low
--				:
-- Comments		:
--
---------------------------------------------------------------------------------------------------
-- Header		: OUTPUT_1_UMID_STATE
--
-- MIB ref		: swCardEventLogSlotXX       .19.79.85.84.80.85.84.95.49.95.85.77.73.68.95.83.84.65.84.69
-- absolute OID	: 1.3.6.1.4.1.7995.2.6.1.1.XX.19.79.85.84.80.85.84.95.49.95.85.77.73.68.95.83.84.65.84.69
-- Vary			: YES
--
-- Value(s)		: **
-- Value(s)		: OK
--				: Pass
--				: Overwrite
--				: Deleted
--				: WARN:Multiple Lines
--				: WARN:No UMID
--				: Info:Multiple Lines
--				: Info:No UMID
--				:
-- Comments		:
--
---------------------------------------------------------------------------------------------------
-- Header		: INPUT_1_C_VIDEO_HIGH
--
-- MIB ref		: swCardEventLogSlotXX       .20.73.78.80.85.84.95.49.95.67.95.86.73.68.69.79.95.72.73.71.72
-- absolute OID	: 1.3.6.1.4.1.7995.2.6.1.1.XX.20.73.78.80.85.84.95.49.95.67.95.86.73.68.69.79.95.72.73.71.72
-- Vary			: YES
--
-- Value(s)		: OK
--				: Info:OK
--				: FAIL:High
--				: Info:High
--				:
-- Comments		:
--
---------------------------------------------------------------------------------------------------
-- Header		: INPUT_1_PID_DURATION
--
-- MIB ref		: swCardEventLogSlotXX       .20.73.78.80.85.84.95.49.95.80.73.68.95.68.85.82.65.84.73.79.78
-- absolute OID	: 1.3.6.1.4.1.7995.2.6.1.1.XX.20.73.78.80.85.84.95.49.95.80.73.68.95.68.85.82.65.84.73.79.78
-- Vary			: YES
--
-- Value(s)		: <0 to 9999999999999999999>
-- Value(s)		: WARN:No PID
-- Value(s)		: Info:No PID
--				:
-- Comments		:
--
---------------------------------------------------------------------------------------------------
-- Header		: INPUT_1_PID_HOUSE_ID
--
-- MIB ref		: swCardEventLogSlotXX       .20.73.78.80.85.84.95.49.95.80.73.68.95.72.79.85.83.69.95.73.68
-- absolute OID	: 1.3.6.1.4.1.7995.2.6.1.1.XX.20.73.78.80.85.84.95.49.95.80.73.68.95.72.79.85.83.69.95.73.68
-- Vary			: YES
--
-- Value(s)		: <19 Characters>
--				: WARN:No PID
--				: Info:No PID
--				:
-- Comments		:
--
---------------------------------------------------------------------------------------------------
-- Header		: INPUT_1_UMID_CURRENT
--
-- MIB ref		: swCardEventLogSlotXX       .20.73.78.80.85.84.95.49.95.85.77.73.68.95.67.85.82.82.69.78.84
-- absolute OID	: 1.3.6.1.4.1.7995.2.6.1.1.XX.20.73.78.80.85.84.95.49.95.85.77.73.68.95.67.85.82.82.69.78.84
-- Vary			: YES
--
-- Value(s)		: <X........X>
--				: WARN:No UMID
--				: Info:No UMID
--				:
-- Comments		: 64 hex digits to represent 32 byte UMID
--
---------------------------------------------------------------------------------------------------
-- Header		: INPUT_1_Y_VIDEO_HIGH
--
-- MIB ref		: swCardEventLogSlotXX       .20.73.78.80.85.84.95.49.95.89.95.86.73.68.69.79.95.72.73.71.72
-- absolute OID	: 1.3.6.1.4.1.7995.2.6.1.1.XX.20.73.78.80.85.84.95.49.95.89.95.86.73.68.69.79.95.72.73.71.72
-- Vary			: YES
--
-- Value(s)		: OK
--				: Info:OK
--				: FAIL:High
--				: Info:High
--				:
-- Comments		:
--
---------------------------------------------------------------------------------------------------
-- Header		: OUTPUT_1_PID_SEG_NUM
--
-- MIB ref		: swCardEventLogSlotXX       .20.79.85.84.80.85.84.95.49.95.80.73.68.95.83.69.71.95.78.85.77
-- absolute OID	: 1.3.6.1.4.1.7995.2.6.1.1.XX.20.79.85.84.80.85.84.95.49.95.80.73.68.95.83.69.71.95.78.85.77
-- Vary			: YES
--
-- Value(s)		: <0 to 65535>
--				: WARN:No PID
--				: Info:No PID
--				:
-- Comments		:
--
---------------------------------------------------------------------------------------------------
-- Header		: INPUT_1_UMID_PREVIOUS
--
-- MIB ref		: swCardEventLogSlotXX       .21.73.78.80.85.84.95.49.95.85.77.73.68.95.80.82.69.86.73.79.85.83
-- absolute OID	: 1.3.6.1.4.1.7995.2.6.1.1.XX.21.73.78.80.85.84.95.49.95.85.77.73.68.95.80.82.69.86.73.79.85.83
-- Vary			: YES
--
-- Value(s)		: <X........X>
--				: WARN:No UMID
--				: Info:No UMID
--				:
-- Comments		: 64 hex digits to represent 32 byte UMID
--
---------------------------------------------------------------------------------------------------
-- Header		: OUTPUT_1_PID_DURATION
--
-- MIB ref		: swCardEventLogSlotXX       .21.79.85.84.80.85.84.95.49.95.80.73.68.95.68.85.82.65.84.73.79.78
-- absolute OID	: 1.3.6.1.4.1.7995.2.6.1.1.XX.21.79.85.84.80.85.84.95.49.95.80.73.68.95.68.85.82.65.84.73.79.78
-- Vary			: YES
--
-- Value(s)		: <0 to 9999999999999999999>
-- Value(s)		: WARN:No PID
-- Value(s)		: Info:No PID
--				:
-- Comments		:
--
---------------------------------------------------------------------------------------------------
-- Header		: OUTPUT_1_PID_HOUSE_ID
--
-- MIB ref		: swCardEventLogSlotXX       .21.79.85.84.80.85.84.95.49.95.80.73.68.95.72.79.85.83.69.95.73.68
-- absolute OID	: 1.3.6.1.4.1.7995.2.6.1.1.XX.21.79.85.84.80.85.84.95.49.95.80.73.68.95.72.79.85.83.69.95.73.68
-- Vary			: YES
--
-- Value(s)		: <19 Characters>
--				: WARN:No PID
--				: Info:No PID
--				:
-- Comments		:
--
---------------------------------------------------------------------------------------------------
-- Header		: INPUT_1_PID_FRAME_RATE
--
-- MIB ref		: swCardEventLogSlotXX       .22.73.78.80.85.84.95.49.95.80.73.68.95.70.82.65.77.69.95.82.65.84.69
-- absolute OID	: 1.3.6.1.4.1.7995.2.6.1.1.XX.22.73.78.80.85.84.95.49.95.80.73.68.95.70.82.65.77.69.95.82.65.84.69
-- Vary			: YES
--
-- Value(s)		: 23.976
--				: 24.000
--				: 25.000
--				: 29.970
--				: 30.000
--				: 50.000
--				: 59.940
--				: 60.000
--				: WARN:No PID
--				: Info:No PID
--				:
-- Comments		:
--
---------------------------------------------------------------------------------------------------
-- Header		: OUTPUT_1_PID_FRAME_RATE
--
-- MIB ref		: swCardEventLogSlotXX       .23.79.85.84.80.85.84.95.49.95.80.73.68.95.70.82.65.77.69.95.82.65.84.69
-- absolute OID	: 1.3.6.1.4.1.7995.2.6.1.1.XX.23.79.85.84.80.85.84.95.49.95.80.73.68.95.70.82.65.77.69.95.82.65.84.69
-- Vary			: YES
--
-- Value(s)		: 23.976
--				: 24.000
--				: 25.000
--				: 29.970
--				: 30.000
--				: 50.000
--				: 59.940
--				: 60.000
--				: WARN:No PID
--				: Info:No PID
--				:
-- Comments		:
--
---------------------------------------------------------------------------------------------------
-- Header		: INPUT_1_HYPERION_SUMMARY
--
-- MIB ref		: swCardEventLogSlotXX       .24.73.78.80.85.84.95.49.95.72.89.80.69.82.73.79.78.95.83.85.77.77.65.82.89
-- absolute OID	: 1.3.6.1.4.1.7995.2.6.1.1.XX.24.73.78.80.85.84.95.49.95.72.89.80.69.82.73.79.78.95.83.85.77.77.65.82.89
-- Vary			: YES
--
-- Value(s)		: OK
--				: UNSUPPORTED
--				: WARN
--				: FAIL
--				:
-- Comments		:
--
---------------------------------------------------------------------------------------------------
-- Header		: INPUT_1_PID_PREVIOUS_COUNT
--
-- MIB ref		: swCardEventLogSlotXX       .26.73.78.80.85.84.95.49.95.80.73.68.95.80.82.69.86.73.79.85.83.95.67.79.85.78.84
-- absolute OID	: 1.3.6.1.4.1.7995.2.6.1.1.XX.26.73.78.80.85.84.95.49.95.80.73.68.95.80.82.69.86.73.79.85.83.95.67.79.85.78.84
-- Vary			: YES
--
-- Value(s)		: -
--				: <100-4294967295>
--				:
-- Comments		:
--
---------------------------------------------------------------------------------------------------
-- Header		: INPUT_1_PID_PREVIOUS_TITLE
--
-- MIB ref		: swCardEventLogSlotXX       .26.73.78.80.85.84.95.49.95.80.73.68.95.80.82.69.86.73.79.85.83.95.84.73.84.76.69
-- absolute OID	: 1.3.6.1.4.1.7995.2.6.1.1.XX.26.73.78.80.85.84.95.49.95.80.73.68.95.80.82.69.86.73.79.85.83.95.84.73.84.76.69
-- Vary			: YES
--
-- Value(s)		: <19 Characters>
--				: WARN:No PID
--				: Info:No PID
--				:
-- Comments		:
--
---------------------------------------------------------------------------------------------------
-- Header		: INPUT_1_CLOSED_CAPTION_TYPE
--
-- MIB ref		: swCardEventLogSlotXX       .27.73.78.80.85.84.95.49.95.67.76.79.83.69.68.95.67.65.80.84.73.79.78.95.84.89.80.69
-- absolute OID	: 1.3.6.1.4.1.7995.2.6.1.1.XX.27.73.78.80.85.84.95.49.95.67.76.79.83.69.68.95.67.65.80.84.73.79.78.95.84.89.80.69
-- Vary			: YES
--
-- Value(s)		: -
--				: EIA708
--				: EIA608
--				:
-- Comments		:
--
---------------------------------------------------------------------------------------------------
-- Header		: INPUT_1_CLOSED_CAPTION_STATE
--
-- MIB ref		: swCardEventLogSlotXX       .28.73.78.80.85.84.95.49.95.67.76.79.83.69.68.95.67.65.80.84.73.79.78.95.83.84.65.84.69
-- absolute OID	: 1.3.6.1.4.1.7995.2.6.1.1.XX.28.73.78.80.85.84.95.49.95.67.76.79.83.69.68.95.67.65.80.84.73.79.78.95.83.84.65.84.69
-- Vary			: YES
--
-- Value(s)		: OK
--				: FAIL:No Closed Caption
--				: WARN:No Closed Caption
--				: Info:OK
--				: Info:No Closed Caption
--				: Info:No Closed Caption
--				: WARN:Checksum Error
--				:
-- Comments		:
--
---------------------------------------------------------------------------------------------------
-- Header		: INPUT_1_CLOSED_CAPTION_TITLE
--
-- MIB ref		: swCardEventLogSlotXX       .28.73.78.80.85.84.95.49.95.67.76.79.83.69.68.95.67.65.80.84.73.79.78.95.84.73.84.76.69
-- absolute OID	: 1.3.6.1.4.1.7995.2.6.1.1.XX.28.73.78.80.85.84.95.49.95.67.76.79.83.69.68.95.67.65.80.84.73.79.78.95.84.73.84.76.69
-- Vary			: YES
--
-- Value(s)		: -
--              : <CC608 Title>   Displays the decoded title
-- Comments		:
--
---------------------------------------------------------------------------------------------------
-- Header		: INPUT_1_EMBED_AUDIO_1_1_TYPE
--
-- MIB ref		: swCardEventLogSlotXX       .28.73.78.80.85.84.95.49.95.69.77.66.69.68.95.65.85.68.73.79.95.49.95.49.95.84.89.80.69
-- absolute OID	: 1.3.6.1.4.1.7995.2.6.1.1.XX.28.73.78.80.85.84.95.49.95.69.77.66.69.68.95.65.85.68.73.79.95.49.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_1_2_TYPE
--
-- MIB ref		: swCardEventLogSlotXX       .28.73.78.80.85.84.95.49.95.69.77.66.69.68.95.65.85.68.73.79.95.49.95.50.95.84.89.80.69
-- absolute OID	: 1.3.6.1.4.1.7995.2.6.1.1.XX.28.73.78.80.85.84.95.49.95.69.77.66.69.68.95.65.85.68.73.79.95.49.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_2_1_TYPE
--
-- MIB ref		: swCardEventLogSlotXX       .28.73.78.80.85.84.95.49.95.69.77.66.69.68.95.65.85.68.73.79.95.50.95.49.95.84.89.80.69
-- absolute OID	: 1.3.6.1.4.1.7995.2.6.1.1.XX.28.73.78.80.85.84.95.49.95.69.77.66.69.68.95.65.85.68.73.79.95.50.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_2_2_TYPE
--
-- MIB ref		: swCardEventLogSlotXX       .28.73.78.80.85.84.95.49.95.69.77.66.69.68.95.65.85.68.73.79.95.50.95.50.95.84.89.80.69
-- absolute OID	: 1.3.6.1.4.1.7995.2.6.1.1.XX.28.73.78.80.85.84.95.49.95.69.77.66.69.68.95.65.85.68.73.79.95.50.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_3_1_TYPE
--
-- MIB ref		: swCardEventLogSlotXX       .28.73.78.80.85.84.95.49.95.69.77.66.69.68.95.65.85.68.73.79.95.51.95.49.95.84.89.80.69
-- absolute OID	: 1.3.6.1.4.1.7995.2.6.1.1.XX.28.73.78.80.85.84.95.49.95.69.77.66.69.68.95.65.85.68.73.79.95.51.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_3_2_TYPE
--
-- MIB ref		: swCardEventLogSlotXX       .28.73.78.80.85.84.95.49.95.69.77.66.69.68.95.65.85.68.73.79.95.51.95.50.95.84.89.80.69
-- absolute OID	: 1.3.6.1.4.1.7995.2.6.1.1.XX.28.73.78.80.85.84.95.49.95.69.77.66.69.68.95.65.85.68.73.79.95.51.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_4_1_TYPE
--
-- MIB ref		: swCardEventLogSlotXX       .28.73.78.80.85.84.95.49.95.69.77.66.69.68.95.65.85.68.73.79.95.52.95.49.95.84.89.80.69
-- absolute OID	: 1.3.6.1.4.1.7995.2.6.1.1.XX.28.73.78.80.85.84.95.49.95.69.77.66.69.68.95.65.85.68.73.79.95.52.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_4_2_TYPE
--
-- MIB ref		: swCardEventLogSlotXX       .28.73.78.80.85.84.95.49.95.69.77.66.69.68.95.65.85.68.73.79.95.52.95.50.95.84.89.80.69
-- absolute OID	: 1.3.6.1.4.1.7995.2.6.1.1.XX.28.73.78.80.85.84.95.49.95.69.77.66.69.68.95.65.85.68.73.79.95.52.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_5_1_TYPE
--
-- MIB ref		: swCardEventLogSlotXX       .28.73.78.80.85.84.95.49.95.69.77.66.69.68.95.65.85.68.73.79.95.53.95.49.95.84.89.80.69
-- absolute OID	: 1.3.6.1.4.1.7995.2.6.1.1.XX.28.73.78.80.85.84.95.49.95.69.77.66.69.68.95.65.85.68.73.79.95.53.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_5_2_TYPE
--
-- MIB ref		: swCardEventLogSlotXX       .28.73.78.80.85.84.95.49.95.69.77.66.69.68.95.65.85.68.73.79.95.53.95.50.95.84.89.80.69
-- absolute OID	: 1.3.6.1.4.1.7995.2.6.1.1.XX.28.73.78.80.85.84.95.49.95.69.77.66.69.68.95.65.85.68.73.79.95.53.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_6_1_TYPE
--
-- MIB ref		: swCardEventLogSlotXX       .28.73.78.80.85.84.95.49.95.69.77.66.69.68.95.65.85.68.73.79.95.54.95.49.95.84.89.80.69
-- absolute OID	: 1.3.6.1.4.1.7995.2.6.1.1.XX.28.73.78.80.85.84.95.49.95.69.77.66.69.68.95.65.85.68.73.79.95.54.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_6_2_TYPE
--
-- MIB ref		: swCardEventLogSlotXX       .28.73.78.80.85.84.95.49.95.69.77.66.69.68.95.65.85.68.73.79.95.54.95.50.95.84.89.80.69
-- absolute OID	: 1.3.6.1.4.1.7995.2.6.1.1.XX.28.73.78.80.85.84.95.49.95.69.77.66.69.68.95.65.85.68.73.79.95.54.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_7_1_TYPE
--
-- MIB ref		: swCardEventLogSlotXX       .28.73.78.80.85.84.95.49.95.69.77.66.69.68.95.65.85.68.73.79.95.55.95.49.95.84.89.80.69
-- absolute OID	: 1.3.6.1.4.1.7995.2.6.1.1.XX.28.73.78.80.85.84.95.49.95.69.77.66.69.68.95.65.85.68.73.79.95.55.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_7_2_TYPE
--
-- MIB ref		: swCardEventLogSlotXX       .28.73.78.80.85.84.95.49.95.69.77.66.69.68.95.65.85.68.73.79.95.55.95.50.95.84.89.80.69
-- absolute OID	: 1.3.6.1.4.1.7995.2.6.1.1.XX.28.73.78.80.85.84.95.49.95.69.77.66.69.68.95.65.85.68.73.79.95.55.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_EMBED_AUDIO_8_1_TYPE
--
-- MIB ref		: swCardEventLogSlotXX       .28.73.78.80.85.84.95.49.95.69.77.66.69.68.95.65.85.68.73.79.95.56.95.49.95.84.89.80.69
-- absolute OID	: 1.3.6.1.4.1.7995.2.6.1.1.XX.28.73.78.80.85.84.95.49.95.69.77.66.69.68.95.65.85.68.73.79.95.56.95.49.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------

-- Header		: INPUT_1_EMBED_AUDIO_8_2_TYPE
--
-- MIB ref		: swCardEventLogSlotXX       .28.73.78.80.85.84.95.49.95.69.77.66.69.68.95.65.85.68.73.79.95.56.95.50.95.84.89.80.69
-- absolute OID	: 1.3.6.1.4.1.7995.2.6.1.1.XX.28.73.78.80.85.84.95.49.95.69.77.66.69.68.95.65.85.68.73.79.95.56.95.50.95.84.89.80.69
-- Vary			: YES
--
-- Value(s)		: PCM
--				: Null Data
--				: Dolby D (AC3)
--				: Time Stamp
--				: MPEG-1 Layer 1,
--				: MPEG-1 Layer 2 or 3
--				: MPEG-2 + Extension
--				: MPEG-2 Layer 1
--				: MPEG-2 Layer 2 or 3
--				: SMPTE KLV
--				: Dolby E
--				: Captioning Data
--				: User Defined
--				: Reserved
--				: WARN:No Input
--				: Info:No Input
--				:
-- Comments		:
--
---------------------------------------------------------------------------------------------------
-- Header		: INPUT_1_PID_PREVIOUS_SEG_NUM
--
-- MIB ref		: swCardEventLogSlotXX       .28.73.78.80.85.84.95.49.95.80.73.68.95.80.82.69.86.73.79.85.83.95.83.69.71.95.78.85.77
-- absolute OID	: 1.3.6.1.4.1.7995.2.6.1.1.XX.28.73.78.80.85.84.95.49.95.80.73.68.95.80.82.69.86.73.79.85.83.95.83.69.71.95.78.85.77
-- Vary			: YES
--
-- Value(s)		: <0 to 65535>
--				: WARN:No PID
--				: Info:No PID
--				:
-- Comments		:
--
---------------------------------------------------------------------------------------------------
-- Header		: INPUT_1_EMBED_AUDIO_1_1_LEVEL
--
-- MIB ref		: swCardEventLogSlotXX       .29.73.78.80.85.84.95.49.95.69.77.66.69.68.95.65.85.68.73.79.95.49.95.49.95.76.69.86.69.76
-- absolute OID	: 1.3.6.1.4.1.7995.2.6.1.1.XX.29.73.78.80.85.84.95.49.95.69.77.66.69.68.95.65.85.68.73.79.95.49.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_1_1_STATE
--
-- MIB ref		: swCardEventLogSlotXX       .29.73.78.80.85.84.95.49.95.69.77.66.69.68.95.65.85.68.73.79.95.49.95.49.95.83.84.65.84.69
-- absolute OID	: 1.3.6.1.4.1.7995.2.6.1.1.XX.29.73.78.80.85.84.95.49.95.69.77.66.69.68.95.65.85.68.73.79.95.49.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_1_2_LEVEL
--
-- MIB ref		: swCardEventLogSlotXX       .29.73.78.80.85.84.95.49.95.69.77.66.69.68.95.65.85.68.73.79.95.49.95.50.95.76.69.86.69.76
-- absolute OID	: 1.3.6.1.4.1.7995.2.6.1.1.XX.29.73.78.80.85.84.95.49.95.69.77.66.69.68.95.65.85.68.73.79.95.49.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_1_2_STATE
--
-- MIB ref		: swCardEventLogSlotXX       .29.73.78.80.85.84.95.49.95.69.77.66.69.68.95.65.85.68.73.79.95.49.95.50.95.83.84.65.84.69
-- absolute OID	: 1.3.6.1.4.1.7995.2.6.1.1.XX.29.73.78.80.85.84.95.49.95.69.77.66.69.68.95.65.85.68.73.79.95.49.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_2_1_LEVEL
--
-- MIB ref		: swCardEventLogSlotXX       .29.73.78.80.85.84.95.49.95.69.77.66.69.68.95.65.85.68.73.79.95.50.95.49.95.76.69.86.69.76
-- absolute OID	: 1.3.6.1.4.1.7995.2.6.1.1.XX.29.73.78.80.85.84.95.49.95.69.77.66.69.68.95.65.85.68.73.79.95.50.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_2_1_STATE
--
-- MIB ref		: swCardEventLogSlotXX       .29.73.78.80.85.84.95.49.95.69.77.66.69.68.95.65.85.68.73.79.95.50.95.49.95.83.84.65.84.69
-- absolute OID	: 1.3.6.1.4.1.7995.2.6.1.1.XX.29.73.78.80.85.84.95.49.95.69.77.66.69.68.95.65.85.68.73.79.95.50.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_2_2_LEVEL
--
-- MIB ref		: swCardEventLogSlotXX       .29.73.78.80.85.84.95.49.95.69.77.66.69.68.95.65.85.68.73.79.95.50.95.50.95.76.69.86.69.76
-- absolute OID	: 1.3.6.1.4.1.7995.2.6.1.1.XX.29.73.78.80.85.84.95.49.95.69.77.66.69.68.95.65.85.68.73.79.95.50.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_2_2_STATE
--
-- MIB ref		: swCardEventLogSlotXX       .29.73.78.80.85.84.95.49.95.69.77.66.69.68.95.65.85.68.73.79.95.50.95.50.95.83.84.65.84.69
-- absolute OID	: 1.3.6.1.4.1.7995.2.6.1.1.XX.29.73.78.80.85.84.95.49.95.69.77.66.69.68.95.65.85.68.73.79.95.50.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_3_1_LEVEL
--
-- MIB ref		: swCardEventLogSlotXX       .29.73.78.80.85.84.95.49.95.69.77.66.69.68.95.65.85.68.73.79.95.51.95.49.95.76.69.86.69.76
-- absolute OID	: 1.3.6.1.4.1.7995.2.6.1.1.XX.29.73.78.80.85.84.95.49.95.69.77.66.69.68.95.65.85.68.73.79.95.51.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_3_1_STATE
--
-- MIB ref		: swCardEventLogSlotXX       .29.73.78.80.85.84.95.49.95.69.77.66.69.68.95.65.85.68.73.79.95.51.95.49.95.83.84.65.84.69
-- absolute OID	: 1.3.6.1.4.1.7995.2.6.1.1.XX.29.73.78.80.85.84.95.49.95.69.77.66.69.68.95.65.85.68.73.79.95.51.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_3_2_LEVEL
--
-- MIB ref		: swCardEventLogSlotXX       .29.73.78.80.85.84.95.49.95.69.77.66.69.68.95.65.85.68.73.79.95.51.95.50.95.76.69.86.69.76
-- absolute OID	: 1.3.6.1.4.1.7995.2.6.1.1.XX.29.73.78.80.85.84.95.49.95.69.77.66.69.68.95.65.85.68.73.79.95.51.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_3_2_STATE
--
-- MIB ref		: swCardEventLogSlotXX       .29.73.78.80.85.84.95.49.95.69.77.66.69.68.95.65.85.68.73.79.95.51.95.50.95.83.84.65.84.69
-- absolute OID	: 1.3.6.1.4.1.7995.2.6.1.1.XX.29.73.78.80.85.84.95.49.95.69.77.66.69.68.95.65.85.68.73.79.95.51.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_4_1_LEVEL
--
-- MIB ref		: swCardEventLogSlotXX       .29.73.78.80.85.84.95.49.95.69.77.66.69.68.95.65.85.68.73.79.95.52.95.49.95.76.69.86.69.76
-- absolute OID	: 1.3.6.1.4.1.7995.2.6.1.1.XX.29.73.78.80.85.84.95.49.95.69.77.66.69.68.95.65.85.68.73.79.95.52.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_4_1_STATE
--
-- MIB ref		: swCardEventLogSlotXX       .29.73.78.80.85.84.95.49.95.69.77.66.69.68.95.65.85.68.73.79.95.52.95.49.95.83.84.65.84.69
-- absolute OID	: 1.3.6.1.4.1.7995.2.6.1.1.XX.29.73.78.80.85.84.95.49.95.69.77.66.69.68.95.65.85.68.73.79.95.52.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_4_2_LEVEL
--
-- MIB ref		: swCardEventLogSlotXX       .29.73.78.80.85.84.95.49.95.69.77.66.69.68.95.65.85.68.73.79.95.52.95.50.95.76.69.86.69.76
-- absolute OID	: 1.3.6.1.4.1.7995.2.6.1.1.XX.29.73.78.80.85.84.95.49.95.69.77.66.69.68.95.65.85.68.73.79.95.52.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_4_2_STATE
--
-- MIB ref		: swCardEventLogSlotXX       .29.73.78.80.85.84.95.49.95.69.77.66.69.68.95.65.85.68.73.79.95.52.95.50.95.83.84.65.84.69
-- absolute OID	: 1.3.6.1.4.1.7995.2.6.1.1.XX.29.73.78.80.85.84.95.49.95.69.77.66.69.68.95.65.85.68.73.79.95.52.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_5_1_LEVEL
--
-- MIB ref		: swCardEventLogSlotXX       .29.73.78.80.85.84.95.49.95.69.77.66.69.68.95.65.85.68.73.79.95.53.95.49.95.76.69.86.69.76
-- absolute OID	: 1.3.6.1.4.1.7995.2.6.1.1.XX.29.73.78.80.85.84.95.49.95.69.77.66.69.68.95.65.85.68.73.79.95.53.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_5_1_STATE
--
-- MIB ref		: swCardEventLogSlotXX       .29.73.78.80.85.84.95.49.95.69.77.66.69.68.95.65.85.68.73.79.95.53.95.49.95.83.84.65.84.69
-- absolute OID	: 1.3.6.1.4.1.7995.2.6.1.1.XX.29.73.78.80.85.84.95.49.95.69.77.66.69.68.95.65.85.68.73.79.95.53.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_5_2_LEVEL
--
-- MIB ref		: swCardEventLogSlotXX       .29.73.78.80.85.84.95.49.95.69.77.66.69.68.95.65.85.68.73.79.95.53.95.50.95.76.69.86.69.76
-- absolute OID	: 1.3.6.1.4.1.7995.2.6.1.1.XX.29.73.78.80.85.84.95.49.95.69.77.66.69.68.95.65.85.68.73.79.95.53.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_5_2_STATE
--
-- MIB ref		: swCardEventLogSlotXX       .29.73.78.80.85.84.95.49.95.69.77.66.69.68.95.65.85.68.73.79.95.53.95.50.95.83.84.65.84.69
-- absolute OID	: 1.3.6.1.4.1.7995.2.6.1.1.XX.29.73.78.80.85.84.95.49.95.69.77.66.69.68.95.65.85.68.73.79.95.53.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_6_1_LEVEL
--
-- MIB ref		: swCardEventLogSlotXX       .29.73.78.80.85.84.95.49.95.69.77.66.69.68.95.65.85.68.73.79.95.54.95.49.95.76.69.86.69.76
-- absolute OID	: 1.3.6.1.4.1.7995.2.6.1.1.XX.29.73.78.80.85.84.95.49.95.69.77.66.69.68.95.65.85.68.73.79.95.54.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_6_1_STATE
--
-- MIB ref		: swCardEventLogSlotXX       .29.73.78.80.85.84.95.49.95.69.77.66.69.68.95.65.85.68.73.79.95.54.95.49.95.83.84.65.84.69
-- absolute OID	: 1.3.6.1.4.1.7995.2.6.1.1.XX.29.73.78.80.85.84.95.49.95.69.77.66.69.68.95.65.85.68.73.79.95.54.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_6_2_LEVEL
--
-- MIB ref		: swCardEventLogSlotXX       .29.73.78.80.85.84.95.49.95.69.77.66.69.68.95.65.85.68.73.79.95.54.95.50.95.76.69.86.69.76
-- absolute OID	: 1.3.6.1.4.1.7995.2.6.1.1.XX.29.73.78.80.85.84.95.49.95.69.77.66.69.68.95.65.85.68.73.79.95.54.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_6_2_STATE
--
-- MIB ref		: swCardEventLogSlotXX       .29.73.78.80.85.84.95.49.95.69.77.66.69.68.95.65.85.68.73.79.95.54.95.50.95.83.84.65.84.69
-- absolute OID	: 1.3.6.1.4.1.7995.2.6.1.1.XX.29.73.78.80.85.84.95.49.95.69.77.66.69.68.95.65.85.68.73.79.95.54.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_7_1_LEVEL
--
-- MIB ref		: swCardEventLogSlotXX       .29.73.78.80.85.84.95.49.95.69.77.66.69.68.95.65.85.68.73.79.95.55.95.49.95.76.69.86.69.76
-- absolute OID	: 1.3.6.1.4.1.7995.2.6.1.1.XX.29.73.78.80.85.84.95.49.95.69.77.66.69.68.95.65.85.68.73.79.95.55.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_7_1_STATE
--
-- MIB ref		: swCardEventLogSlotXX       .29.73.78.80.85.84.95.49.95.69.77.66.69.68.95.65.85.68.73.79.95.55.95.49.95.83.84.65.84.69
-- absolute OID	: 1.3.6.1.4.1.7995.2.6.1.1.XX.29.73.78.80.85.84.95.49.95.69.77.66.69.68.95.65.85.68.73.79.95.55.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_7_2_LEVEL
--
-- MIB ref		: swCardEventLogSlotXX       .29.73.78.80.85.84.95.49.95.69.77.66.69.68.95.65.85.68.73.79.95.55.95.50.95.76.69.86.69.76
-- absolute OID	: 1.3.6.1.4.1.7995.2.6.1.1.XX.29.73.78.80.85.84.95.49.95.69.77.66.69.68.95.65.85.68.73.79.95.55.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_7_2_STATE
--
-- MIB ref		: swCardEventLogSlotXX       .29.73.78.80.85.84.95.49.95.69.77.66.69.68.95.65.85.68.73.79.95.55.95.50.95.83.84.65.84.69
-- absolute OID	: 1.3.6.1.4.1.7995.2.6.1.1.XX.29.73.78.80.85.84.95.49.95.69.77.66.69.68.95.65.85.68.73.79.95.55.95.50.95.83.84.65.84.69
-- Vary			: YES
--
-- Value(s)		: OK
--				: WARN:No Input
--				: Info:OK
--				: Info:No Input
--				:
-- Comments		:
--
---------------------------------------------------------------------------------------------------
-- Header		: INPUT_1_EMBED_AUDIO_8_1_LEVEL
--
-- MIB ref		: swCardEventLogSlotXX       .29.73.78.80.85.84.95.49.95.69.77.66.69.68.95.65.85.68.73.79.95.56.95.49.95.76.69.86.69.76
-- absolute OID	: 1.3.6.1.4.1.7995.2.6.1.1.XX.29.73.78.80.85.84.95.49.95.69.77.66.69.68.95.65.85.68.73.79.95.56.95.49.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--

---------------------------------------------------------------------------------------------------
-- Header		: INPUT_1_EMBED_AUDIO_8_1_STATE
--
-- MIB ref		: swCardEventLogSlotXX       .29.73.78.80.85.84.95.49.95.69.77.66.69.68.95.65.85.68.73.79.95.56.95.49.95.83.84.65.84.69
-- absolute OID	: 1.3.6.1.4.1.7995.2.6.1.1.XX.29.73.78.80.85.84.95.49.95.69.77.66.69.68.95.65.85.68.73.79.95.56.95.49.95.83.84.65.84.69
-- Vary			: YES
--
-- Value(s)		: OK
--				: WARN:No Input
--				: Info:OK
--				: Info:No Input
--				:
-- Comments		:
--
---------------------------------------------------------------------------------------------------
-- Header		: INPUT_1_EMBED_AUDIO_8_2_LEVEL
--
-- MIB ref		: swCardEventLogSlotXX       .29.73.78.80.85.84.95.49.95.69.77.66.69.68.95.65.85.68.73.79.95.56.95.50.95.76.69.86.69.76
-- absolute OID	: 1.3.6.1.4.1.7995.2.6.1.1.XX.29.73.78.80.85.84.95.49.95.69.77.66.69.68.95.65.85.68.73.79.95.56.95.50.95.76.69.86.69.76
-- Vary			: YES
--
-- Value(s)		: OK
--				: WARN:No Input
--				: WARN:NON PCM
--				: WARN:Overload
--				: WARN:Loud
--				: WARN:Quiet
--				: WARN:Silent
--				: FAIL:Overload
--				: FAIL:Loud
--				: FAIL:Quiet
--				: FAIL:Silent
--				: Info:OK
--				: Info:No Input
--				: Info:NON PCM
--				: Info:Overload
--				: Info:Loud
--				: Info:Quiet
--				: Info:Silent
--				:
-- Comments		:
--
---------------------------------------------------------------------------------------------------
-- Header		: INPUT_1_EMBED_AUDIO_8_2_STATE
--
-- MIB ref		: swCardEventLogSlotXX       .29.73.78.80.85.84.95.49.95.69.77.66.69.68.95.65.85.68.73.79.95.56.95.50.95.83.84.65.84.69
-- absolute OID	: 1.3.6.1.4.1.7995.2.6.1.1.XX.29.73.78.80.85.84.95.49.95.69.77.66.69.68.95.65.85.68.73.79.95.56.95.50.95.83.84.65.84.69
-- Vary			: YES
--
-- Value(s)		: OK
--				: WARN:No Input
--				: Info:OK
--				: Info:No Input
--				:
-- Comments		:
--
---------------------------------------------------------------------------------------------------
-- Header		: INPUT_1_PID_PREVIOUS_DURATION
--
-- MIB ref		: swCardEventLogSlotXX       .29.73.78.80.85.84.95.49.95.80.73.68.95.80.82.69.86.73.79.85.83.95.68.85.82.65.84.73.79.78
-- absolute OID	: 1.3.6.1.4.1.7995.2.6.1.1.XX.29.73.78.80.85.84.95.49.95.80.73.68.95.80.82.69.86.73.79.85.83.95.68.85.82.65.84.73.79.78
-- Vary			: YES
--
-- Value(s)		: <0 to 9999999999999999999>
-- Value(s)		: WARN:No PID
-- Value(s)		: Info:No PID
--				:
-- Comments		:
--
---------------------------------------------------------------------------------------------------
-- Header		: INPUT_1_PID_PREVIOUS_HOUSE_ID
--
-- MIB ref		: swCardEventLogSlotXX       .29.73.78.80.85.84.95.49.95.80.73.68.95.80.82.69.86.73.79.85.83.95.72.79.85.83.69.95.73.68
-- absolute OID	: 1.3.6.1.4.1.7995.2.6.1.1.XX.29.73.78.80.85.84.95.49.95.80.73.68.95.80.82.69.86.73.79.85.83.95.72.79.85.83.69.95.73.68
-- Vary			: YES
--
-- Value(s)		: <19 Characters>
--				: WARN:No PID
--				: Info:No PID
--				:
-- Comments		:
--
---------------------------------------------------------------------------------------------------
-- Header		: INPUT_1_USER1_ANC_PACKET_NAME
--
-- MIB ref		: swCardEventLogSlotXX       .29.73.78.80.85.84.95.49.95.85.83.69.82.49.95.65.78.67.95.80.65.67.75.69.84.95.78.65.77.69
-- absolute OID	: 1.3.6.1.4.1.7995.2.6.1.1.XX.29.73.78.80.85.84.95.49.95.85.83.69.82.49.95.65.78.67.95.80.65.67.75.69.84.95.78.65.77.69
-- Vary			: YES
--
-- Value(s)		: <19 Characters>
--				:
-- Comments		: default: User Anc 1
--
---------------------------------------------------------------------------------------------------
-- Header		: INPUT_1_USER2_ANC_PACKET_NAME
--
-- MIB ref		: swCardEventLogSlotXX       .29.73.78.80.85.84.95.49.95.85.83.69.82.50.95.65.78.67.95.80.65.67.75.69.84.95.78.65.77.69
-- absolute OID	: 1.3.6.1.4.1.7995.2.6.1.1.XX.29.73.78.80.85.84.95.49.95.85.83.69.82.50.95.65.78.67.95.80.65.67.75.69.84.95.78.65.77.69
-- Vary			: YES
--
-- Value(s)		: <19 Characters>
--				:
-- Comments		: default: User Anc 2
--
---------------------------------------------------------------------------------------------------
-- Header		: INPUT_1_CONTENT_ADVISORY_STATE
--
-- MIB ref		: swCardEventLogSlotXX       .30.73.78.80.85.84.95.49.95.67.79.78.84.69.78.84.95.65.68.86.73.83.79.82.89.95.83.84.65.84.69
-- absolute OID	: 1.3.6.1.4.1.7995.2.6.1.1.XX.30.73.78.80.85.84.95.49.95.67.79.78.84.69.78.84.95.65.68.86.73.83.79.82.89.95.83.84.65.84.69
-- Vary			: YES
--
-- Value(s)		: OK
--				: FAIL:No CA
--				: Info:OK
--				: Info:No CA
--				:
-- Comments		:
--
---------------------------------------------------------------------------------------------------
-- Header		: INPUT_1_USER1_ANC_PACKET_STATE
--
-- MIB ref		: swCardEventLogSlotXX       .30.73.78.80.85.84.95.49.95.85.83.69.82.49.95.65.78.67.95.80.65.67.75.69.84.95.83.84.65.84.69
-- absolute OID	: 1.3.6.1.4.1.7995.2.6.1.1.XX.30.73.78.80.85.84.95.49.95.85.83.69.82.49.95.65.78.67.95.80.65.67.75.69.84.95.83.84.65.84.69
-- Vary			: YES
--
-- Value(s)		: OK
--				: FAIL:No User1 ANC
--				: Info:OK
--				: Info:No User1 ANC
-- Comments		:
--
---------------------------------------------------------------------------------------------------
-- Header		: INPUT_1_USER2_ANC_PACKET_STATE
--
-- MIB ref		: swCardEventLogSlotXX       .30.73.78.80.85.84.95.49.95.85.83.69.82.50.95.65.78.67.95.80.65.67.75.69.84.95.83.84.65.84.69
-- absolute OID	: 1.3.6.1.4.1.7995.2.6.1.1.XX.30.73.78.80.85.84.95.49.95.85.83.69.82.50.95.65.78.67.95.80.65.67.75.69.84.95.83.84.65.84.69
-- Vary			: YES
--
-- Value(s)		: OK
--				: FAIL:No User2 ANC
--				: Info:OK
--				: Info:No User2 ANC
-- Comments		:
--
---------------------------------------------------------------------------------------------------
-- Header		: INPUT_1_CONTENT_ADVISORY_SYSTEM
--
-- MIB ref		: swCardEventLogSlotXX       .31.73.78.80.85.84.95.49.95.67.79.78.84.69.78.84.95.65.68.86.73.83.79.82.89.95.83.89.83.84.69.77
-- absolute OID	: 1.3.6.1.4.1.7995.2.6.1.1.XX.31.73.78.80.85.84.95.49.95.67.79.78.84.69.78.84.95.65.68.86.73.83.79.82.89.95.83.89.83.84.69.77
-- Vary			: YES
--
-- Value(s)		: -
--				: 0-MPA
--				: 1-US TV PG
--				: 2-MPA
--				: 3-Canadian Eng
--				: 4-Canadian Fr
--				: 5-Reserved
--				: 6-Reserved
--				:
-- Comments		:
--
---------------------------------------------------------------------------------------------------
-- Header		: INPUT_1_EMBED_DOLBY_E_PR1_STATE
--
-- MIB ref		: swCardEventLogSlotXX       .31.73.78.80.85.84.95.49.95.69.77.66.69.68.95.68.79.76.66.89.95.69.95.80.82.49.95.83.84.65.84.69
-- absolute OID	: 1.3.6.1.4.1.7995.2.6.1.1.XX.31.73.78.80.85.84.95.49.95.69.77.66.69.68.95.68.79.76.66.89.95.69.95.80.82.49.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR2_STATE
--
-- MIB ref		: swCardEventLogSlotXX       .31.73.78.80.85.84.95.49.95.69.77.66.69.68.95.68.79.76.66.89.95.69.95.80.82.50.95.83.84.65.84.69
-- absolute OID	: 1.3.6.1.4.1.7995.2.6.1.1.XX.31.73.78.80.85.84.95.49.95.69.77.66.69.68.95.68.79.76.66.89.95.69.95.80.82.50.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR3_STATE
--
-- MIB ref		: swCardEventLogSlotXX       .31.73.78.80.85.84.95.49.95.69.77.66.69.68.95.68.79.76.66.89.95.69.95.80.82.51.95.83.84.65.84.69
-- absolute OID	: 1.3.6.1.4.1.7995.2.6.1.1.XX.31.73.78.80.85.84.95.49.95.69.77.66.69.68.95.68.79.76.66.89.95.69.95.80.82.51.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR4_STATE
--
-- MIB ref		: swCardEventLogSlotXX       .31.73.78.80.85.84.95.49.95.69.77.66.69.68.95.68.79.76.66.89.95.69.95.80.82.52.95.83.84.65.84.69
-- absolute OID	: 1.3.6.1.4.1.7995.2.6.1.1.XX.31.73.78.80.85.84.95.49.95.69.77.66.69.68.95.68.79.76.66.89.95.69.95.80.82.52.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR5_STATE
--
-- MIB ref		: swCardEventLogSlotXX       .31.73.78.80.85.84.95.49.95.69.77.66.69.68.95.68.79.76.66.89.95.69.95.80.82.53.95.83.84.65.84.69
-- absolute OID	: 1.3.6.1.4.1.7995.2.6.1.1.XX.31.73.78.80.85.84.95.49.95.69.77.66.69.68.95.68.79.76.66.89.95.69.95.80.82.53.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR6_STATE
--
-- MIB ref		: swCardEventLogSlotXX       .31.73.78.80.85.84.95.49.95.69.77.66.69.68.95.68.79.76.66.89.95.69.95.80.82.54.95.83.84.65.84.69
-- absolute OID	: 1.3.6.1.4.1.7995.2.6.1.1.XX.31.73.78.80.85.84.95.49.95.69.77.66.69.68.95.68.79.76.66.89.95.69.95.80.82.54.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR7_STATE
--
-- MIB ref		: swCardEventLogSlotXX       .31.73.78.80.85.84.95.49.95.69.77.66.69.68.95.68.79.76.66.89.95.69.95.80.82.55.95.83.84.65.84.69
-- absolute OID	: 1.3.6.1.4.1.7995.2.6.1.1.XX.31.73.78.80.85.84.95.49.95.69.77.66.69.68.95.68.79.76.66.89.95.69.95.80.82.55.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_EMBED_DOLBY_E_PR8_STATE
--
-- MIB ref		: swCardEventLogSlotXX       .31.73.78.80.85.84.95.49.95.69.77.66.69.68.95.68.79.76.66.89.95.69.95.80.82.56.95.83.84.65.84.69
-- absolute OID	: 1.3.6.1.4.1.7995.2.6.1.1.XX.31.73.78.80.85.84.95.49.95.69.77.66.69.68.95.68.79.76.66.89.95.69.95.80.82.56.95.83.84.65.84.69
-- Vary			: YES
--
-- Value(s)		: OK
--				: WARN:Early
--				: WARN:Late
--				: WARN:Error
--				: FAIL:Not Dolby E
--				: Info:OK
--				: Info:Early
--				: Info:Late
--				: Info:Error
--				: Info:Not Dolby E
-- Comments		:
--
---------------------------------------------------------------------------------------------------
-- Header		: INPUT_1_PID_PREVIOUS_FRAME_RATE
--
-- MIB ref		: swCardEventLogSlotXX       .31.73.78.80.85.84.95.49.95.80.73.68.95.80.82.69.86.73.79.85.83.95.70.82.65.77.69.95.82.65.84.69
-- absolute OID	: 1.3.6.1.4.1.7995.2.6.1.1.XX.31.73.78.80.85.84.95.49.95.80.73.68.95.80.82.69.86.73.79.85.83.95.70.82.65.77.69.95.82.65.84.69
-- Vary			: YES
--
-- Value(s)		: 23.976
--				: 24.000
--				: 25.000
--				: 29.970
--				: 30.000
--				: 50.000
--				: 59.940
--				: 60.000
--				: WARN:No PID
--				: Info:No PID
--				:
-- Comments		:
--
---------------------------------------------------------------------------------------------------
-- Header		: INPUT_1_ANCILLARY_TIMECODE_STATE
--
-- MIB ref		: swCardEventLogSlotXX       .32.73.78.80.85.84.95.49.95.65.78.67.73.76.76.65.82.89.95.84.73.77.69.67.79.68.69.95.83.84.65.84.69
-- absolute OID	: 1.3.6.1.4.1.7995.2.6.1.1.XX.32.73.78.80.85.84.95.49.95.65.78.67.73.76.76.65.82.89.95.84.73.77.69.67.79.68.69.95.83.84.65.84.69
-- Vary			: YES
--
-- Value(s)		: Info:No ANC TC
--          Detector not enabled
--              : Info:OK
--              : Info:Checksum Error
--              : Info:No ANC TC Field 1
--              : Info:No ANC TC Field 2
--              : Info:No ANC TC
--
--          Detector enabled
--              : OK
--              : WARN:Checksum Error
--              : WARN:No ANC TC Field 1
--              : WARN:No ANC TC Field 2
--              : FAIL:No ANC TC
-- Comments		:
--
---------------------------------------------------------------------------------------------------
-- Header		: INPUT_1_EMBED_AUDIO_1_1_CLIPPING
--
-- MIB ref		: swCardEventLogSlotXX       .32.73.78.80.85.84.95.49.95.69.77.66.69.68.95.65.85.68.73.79.95.49.95.49.95.67.76.73.80.80.73.78.71
-- absolute OID	: 1.3.6.1.4.1.7995.2.6.1.1.XX.32.73.78.80.85.84.95.49.95.69.77.66.69.68.95.65.85.68.73.79.95.49.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_1_2_CLIPPING
--
-- MIB ref		: swCardEventLogSlotXX       .32.73.78.80.85.84.95.49.95.69.77.66.69.68.95.65.85.68.73.79.95.49.95.50.95.67.76.73.80.80.73.78.71
-- absolute OID	: 1.3.6.1.4.1.7995.2.6.1.1.XX.32.73.78.80.85.84.95.49.95.69.77.66.69.68.95.65.85.68.73.79.95.49.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_2_1_CLIPPING
--
-- MIB ref		: swCardEventLogSlotXX       .32.73.78.80.85.84.95.49.95.69.77.66.69.68.95.65.85.68.73.79.95.50.95.49.95.67.76.73.80.80.73.78.71
-- absolute OID	: 1.3.6.1.4.1.7995.2.6.1.1.XX.32.73.78.80.85.84.95.49.95.69.77.66.69.68.95.65.85.68.73.79.95.50.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_2_2_CLIPPING
--
-- MIB ref		: swCardEventLogSlotXX       .32.73.78.80.85.84.95.49.95.69.77.66.69.68.95.65.85.68.73.79.95.50.95.50.95.67.76.73.80.80.73.78.71
-- absolute OID	: 1.3.6.1.4.1.7995.2.6.1.1.XX.32.73.78.80.85.84.95.49.95.69.77.66.69.68.95.65.85.68.73.79.95.50.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_3_1_CLIPPING
--
-- MIB ref		: swCardEventLogSlotXX       .32.73.78.80.85.84.95.49.95.69.77.66.69.68.95.65.85.68.73.79.95.51.95.49.95.67.76.73.80.80.73.78.71
-- absolute OID	: 1.3.6.1.4.1.7995.2.6.1.1.XX.32.73.78.80.85.84.95.49.95.69.77.66.69.68.95.65.85.68.73.79.95.51.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_3_2_CLIPPING
--
-- MIB ref		: swCardEventLogSlotXX       .32.73.78.80.85.84.95.49.95.69.77.66.69.68.95.65.85.68.73.79.95.51.95.50.95.67.76.73.80.80.73.78.71
-- absolute OID	: 1.3.6.1.4.1.7995.2.6.1.1.XX.32.73.78.80.85.84.95.49.95.69.77.66.69.68.95.65.85.68.73.79.95.51.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_4_1_CLIPPING
--
-- MIB ref		: swCardEventLogSlotXX       .32.73.78.80.85.84.95.49.95.69.77.66.69.68.95.65.85.68.73.79.95.52.95.49.95.67.76.73.80.80.73.78.71
-- absolute OID	: 1.3.6.1.4.1.7995.2.6.1.1.XX.32.73.78.80.85.84.95.49.95.69.77.66.69.68.95.65.85.68.73.79.95.52.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_4_2_CLIPPING
--
-- MIB ref		: swCardEventLogSlotXX       .32.73.78.80.85.84.95.49.95.69.77.66.69.68.95.65.85.68.73.79.95.52.95.50.95.67.76.73.80.80.73.78.71
-- absolute OID	: 1.3.6.1.4.1.7995.2.6.1.1.XX.32.73.78.80.85.84.95.49.95.69.77.66.69.68.95.65.85.68.73.79.95.52.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_5_1_CLIPPING
--
-- MIB ref		: swCardEventLogSlotXX       .32.73.78.80.85.84.95.49.95.69.77.66.69.68.95.65.85.68.73.79.95.53.95.49.95.67.76.73.80.80.73.78.71
-- absolute OID	: 1.3.6.1.4.1.7995.2.6.1.1.XX.32.73.78.80.85.84.95.49.95.69.77.66.69.68.95.65.85.68.73.79.95.53.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_5_2_CLIPPING
--
-- MIB ref		: swCardEventLogSlotXX       .32.73.78.80.85.84.95.49.95.69.77.66.69.68.95.65.85.68.73.79.95.53.95.50.95.67.76.73.80.80.73.78.71
-- absolute OID	: 1.3.6.1.4.1.7995.2.6.1.1.XX.32.73.78.80.85.84.95.49.95.69.77.66.69.68.95.65.85.68.73.79.95.53.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_6_1_CLIPPING
--
-- MIB ref		: swCardEventLogSlotXX       .32.73.78.80.85.84.95.49.95.69.77.66.69.68.95.65.85.68.73.79.95.54.95.49.95.67.76.73.80.80.73.78.71
-- absolute OID	: 1.3.6.1.4.1.7995.2.6.1.1.XX.32.73.78.80.85.84.95.49.95.69.77.66.69.68.95.65.85.68.73.79.95.54.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_6_2_CLIPPING
--
-- MIB ref		: swCardEventLogSlotXX       .32.73.78.80.85.84.95.49.95.69.77.66.69.68.95.65.85.68.73.79.95.54.95.50.95.67.76.73.80.80.73.78.71
-- absolute OID	: 1.3.6.1.4.1.7995.2.6.1.1.XX.32.73.78.80.85.84.95.49.95.69.77.66.69.68.95.65.85.68.73.79.95.54.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_7_1_CLIPPING
--
-- MIB ref		: swCardEventLogSlotXX       .32.73.78.80.85.84.95.49.95.69.77.66.69.68.95.65.85.68.73.79.95.55.95.49.95.67.76.73.80.80.73.78.71
-- absolute OID	: 1.3.6.1.4.1.7995.2.6.1.1.XX.32.73.78.80.85.84.95.49.95.69.77.66.69.68.95.65.85.68.73.79.95.55.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_7_2_CLIPPING
--
-- MIB ref		: swCardEventLogSlotXX       .32.73.78.80.85.84.95.49.95.69.77.66.69.68.95.65.85.68.73.79.95.55.95.50.95.67.76.73.80.80.73.78.71
-- absolute OID	: 1.3.6.1.4.1.7995.2.6.1.1.XX.32.73.78.80.85.84.95.49.95.69.77.66.69.68.95.65.85.68.73.79.95.55.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_8_1_CLIPPING
--
-- MIB ref		: swCardEventLogSlotXX       .32.73.78.80.85.84.95.49.95.69.77.66.69.68.95.65.85.68.73.79.95.56.95.49.95.67.76.73.80.80.73.78.71
-- absolute OID	: 1.3.6.1.4.1.7995.2.6.1.1.XX.32.73.78.80.85.84.95.49.95.69.77.66.69.68.95.65.85.68.73.79.95.56.95.49.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_8_2_CLIPPING
--
-- MIB ref		: swCardEventLogSlotXX       .32.73.78.80.85.84.95.49.95.69.77.66.69.68.95.65.85.68.73.79.95.56.95.50.95.67.76.73.80.80.73.78.71
-- absolute OID	: 1.3.6.1.4.1.7995.2.6.1.1.XX.32.73.78.80.85.84.95.49.95.69.77.66.69.68.95.65.85.68.73.79.95.56.95.50.95.67.76.73.80.80.73.78.71
-- Vary			: YES
--
-- Value(s)		:
--				: OK
--              : WARN:No Input
--              : WARN:NON PCM
--              : WARN:Clipping
--              : Info:OK
--              : Info:No Input
--              : Info:NON PCM
--              : Info:Clipping
-- Comments		:
--
---------------------------------------------------------------------------------------------------
-- Header		: INPUT_1_EMBED_AUDIO_1_1_BIT_DEPTH
--
-- MIB ref		: swCardEventLogSlotXX       .33.73.78.80.85.84.95.49.95.69.77.66.69.68.95.65.85.68.73.79.95.49.95.49.95.66.73.84.95.68.69.80.84.72
-- absolute OID	: 1.3.6.1.4.1.7995.2.6.1.1.XX.33.73.78.80.85.84.95.49.95.69.77.66.69.68.95.65.85.68.73.79.95.49.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_1_2_BIT_DEPTH
--
-- MIB ref		: swCardEventLogSlotXX       .33.73.78.80.85.84.95.49.95.69.77.66.69.68.95.65.85.68.73.79.95.49.95.50.95.66.73.84.95.68.69.80.84.72
-- absolute OID	: 1.3.6.1.4.1.7995.2.6.1.1.XX.33.73.78.80.85.84.95.49.95.69.77.66.69.68.95.65.85.68.73.79.95.49.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_2_1_BIT_DEPTH
--
-- MIB ref		: swCardEventLogSlotXX       .33.73.78.80.85.84.95.49.95.69.77.66.69.68.95.65.85.68.73.79.95.50.95.49.95.66.73.84.95.68.69.80.84.72
-- absolute OID	: 1.3.6.1.4.1.7995.2.6.1.1.XX.33.73.78.80.85.84.95.49.95.69.77.66.69.68.95.65.85.68.73.79.95.50.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_2_2_BIT_DEPTH
--
-- MIB ref		: swCardEventLogSlotXX       .33.73.78.80.85.84.95.49.95.69.77.66.69.68.95.65.85.68.73.79.95.50.95.50.95.66.73.84.95.68.69.80.84.72
-- absolute OID	: 1.3.6.1.4.1.7995.2.6.1.1.XX.33.73.78.80.85.84.95.49.95.69.77.66.69.68.95.65.85.68.73.79.95.50.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_3_1_BIT_DEPTH
--
-- MIB ref		: swCardEventLogSlotXX       .33.73.78.80.85.84.95.49.95.69.77.66.69.68.95.65.85.68.73.79.95.51.95.49.95.66.73.84.95.68.69.80.84.72
-- absolute OID	: 1.3.6.1.4.1.7995.2.6.1.1.XX.33.73.78.80.85.84.95.49.95.69.77.66.69.68.95.65.85.68.73.79.95.51.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_3_2_BIT_DEPTH
--
-- MIB ref		: swCardEventLogSlotXX       .33.73.78.80.85.84.95.49.95.69.77.66.69.68.95.65.85.68.73.79.95.51.95.50.95.66.73.84.95.68.69.80.84.72
-- absolute OID	: 1.3.6.1.4.1.7995.2.6.1.1.XX.33.73.78.80.85.84.95.49.95.69.77.66.69.68.95.65.85.68.73.79.95.51.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_4_1_BIT_DEPTH
--
-- MIB ref		: swCardEventLogSlotXX       .33.73.78.80.85.84.95.49.95.69.77.66.69.68.95.65.85.68.73.79.95.52.95.49.95.66.73.84.95.68.69.80.84.72
-- absolute OID	: 1.3.6.1.4.1.7995.2.6.1.1.XX.33.73.78.80.85.84.95.49.95.69.77.66.69.68.95.65.85.68.73.79.95.52.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_4_2_BIT_DEPTH
--
-- MIB ref		: swCardEventLogSlotXX       .33.73.78.80.85.84.95.49.95.69.77.66.69.68.95.65.85.68.73.79.95.52.95.50.95.66.73.84.95.68.69.80.84.72
-- absolute OID	: 1.3.6.1.4.1.7995.2.6.1.1.XX.33.73.78.80.85.84.95.49.95.69.77.66.69.68.95.65.85.68.73.79.95.52.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_5_1_BIT_DEPTH
--
-- MIB ref		: swCardEventLogSlotXX       .33.73.78.80.85.84.95.49.95.69.77.66.69.68.95.65.85.68.73.79.95.53.95.49.95.66.73.84.95.68.69.80.84.72
-- absolute OID	: 1.3.6.1.4.1.7995.2.6.1.1.XX.33.73.78.80.85.84.95.49.95.69.77.66.69.68.95.65.85.68.73.79.95.53.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_5_2_BIT_DEPTH
--
-- MIB ref		: swCardEventLogSlotXX       .33.73.78.80.85.84.95.49.95.69.77.66.69.68.95.65.85.68.73.79.95.53.95.50.95.66.73.84.95.68.69.80.84.72
-- absolute OID	: 1.3.6.1.4.1.7995.2.6.1.1.XX.33.73.78.80.85.84.95.49.95.69.77.66.69.68.95.65.85.68.73.79.95.53.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_6_1_BIT_DEPTH
--
-- MIB ref		: swCardEventLogSlotXX       .33.73.78.80.85.84.95.49.95.69.77.66.69.68.95.65.85.68.73.79.95.54.95.49.95.66.73.84.95.68.69.80.84.72
-- absolute OID	: 1.3.6.1.4.1.7995.2.6.1.1.XX.33.73.78.80.85.84.95.49.95.69.77.66.69.68.95.65.85.68.73.79.95.54.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_6_2_BIT_DEPTH
--
-- MIB ref		: swCardEventLogSlotXX       .33.73.78.80.85.84.95.49.95.69.77.66.69.68.95.65.85.68.73.79.95.54.95.50.95.66.73.84.95.68.69.80.84.72
-- absolute OID	: 1.3.6.1.4.1.7995.2.6.1.1.XX.33.73.78.80.85.84.95.49.95.69.77.66.69.68.95.65.85.68.73.79.95.54.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_7_1_BIT_DEPTH
--
-- MIB ref		: swCardEventLogSlotXX       .33.73.78.80.85.84.95.49.95.69.77.66.69.68.95.65.85.68.73.79.95.55.95.49.95.66.73.84.95.68.69.80.84.72
-- absolute OID	: 1.3.6.1.4.1.7995.2.6.1.1.XX.33.73.78.80.85.84.95.49.95.69.77.66.69.68.95.65.85.68.73.79.95.55.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_7_2_BIT_DEPTH
--
-- MIB ref		: swCardEventLogSlotXX       .33.73.78.80.85.84.95.49.95.69.77.66.69.68.95.65.85.68.73.79.95.55.95.50.95.66.73.84.95.68.69.80.84.72
-- absolute OID	: 1.3.6.1.4.1.7995.2.6.1.1.XX.33.73.78.80.85.84.95.49.95.69.77.66.69.68.95.65.85.68.73.79.95.55.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_8_1_BIT_DEPTH
--
-- MIB ref		: swCardEventLogSlotXX       .33.73.78.80.85.84.95.49.95.69.77.66.69.68.95.65.85.68.73.79.95.56.95.49.95.66.73.84.95.68.69.80.84.72
-- absolute OID	: 1.3.6.1.4.1.7995.2.6.1.1.XX.33.73.78.80.85.84.95.49.95.69.77.66.69.68.95.65.85.68.73.79.95.56.95.49.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_EMBED_AUDIO_8_2_BIT_DEPTH
--
-- MIB ref		: swCardEventLogSlotXX       .33.73.78.80.85.84.95.49.95.69.77.66.69.68.95.65.85.68.73.79.95.56.95.50.95.66.73.84.95.68.69.80.84.72
-- absolute OID	: 1.3.6.1.4.1.7995.2.6.1.1.XX.33.73.78.80.85.84.95.49.95.69.77.66.69.68.95.65.85.68.73.79.95.56.95.50.95.66.73.84.95.68.69.80.84.72
-- Vary			: YES
--
-- Value(s)		: 16
--				: 18
--				: 20
--				: 24
--				: UNKNOWN
--				: WARN:No Input
--				: Info:16
--				: Info:18
--				: Info:20
--				: Info:24
--				: Info:UNKNOWN
--				: Info:No Input
--				:
-- Comments		:
--
---------------------------------------------------------------------------------------------------
-- Header		: INPUT_1_UMID_PREVIOUS_FRAME_COUNT
--
-- MIB ref		: swCardEventLogSlotXX       .33.73.78.80.85.84.95.49.95.85.77.73.68.95.80.82.69.86.73.79.85.83.95.70.82.65.77.69.95.67.79.85.78.84
-- absolute OID	: 1.3.6.1.4.1.7995.2.6.1.1.XX.33.73.78.80.85.84.95.49.95.85.77.73.68.95.80.82.69.86.73.79.85.83.95.70.82.65.77.69.95.67.79.85.78.84
-- Vary			: YES
--
-- Value(s)		: -
--				: <100 to 4294967295>
--				:
-- Comments		:
--
---------------------------------------------------------------------------------------------------
-- Header		: INPUT_1_CONTENT_ADVISORY_AGE_RATING
--
-- MIB ref		: swCardEventLogSlotXX       .35.73.78.80.85.84.95.49.95.67.79.78.84.69.78.84.95.65.68.86.73.83.79.82.89.95.65.71.69.95.82.65.84.73.78.71
-- absolute OID	: 1.3.6.1.4.1.7995.2.6.1.1.XX.35.73.78.80.85.84.95.49.95.67.79.78.84.69.78.84.95.65.68.86.73.83.79.82.89.95.65.71.69.95.82.65.84.73.78.71
-- Vary			: YES
--
-- Value(s)		: -
-- Comments		:   For  INPUT_1_CONTENT_ADVISORY_SYSTEM=0-MP
--				:   or   INPUT_1_CONTENT_ADVISORY_SYSTEM=2-MP
--
--				: N/A
--				: G
--				: PG
--				: PG-13
--				: R
--				: NC-17
--				: X
--				: Not Rated
--
-- Comments		:   For INPUT_1_CONTENT_ADVISORY_SYSTEM=1-US TV PG
--				:   (If there is one or more Letters in brackets,
--				:         this shows addition Guidance.)
--
--				: None
--				: TV-Y
--				: TV-Y7 ( FV)
--				: TV-G
--				: TV-PG ( V S L D}
--				: TV-14 ( V S L D}
--				: TV-MA ( L S V}
--				: None
--
--				:   where:
--				:       FV = Fantasy Violence
--				:       V  = Violence
--				:       S  = Sexual Situations
--				:       L  = Adult Language
--				:       D  = Sexually Suggestive Dialog
--
-- Comments		:   For INPUT_1_CONTENT_ADVISORY_SYSTEM=3-Canadian Eng
--				: E
--				: C
--				: C8+
--				: G
--				: PG
--				: 14+
--				: 18+
--
-- Comments		:   For INPUT_1_CONTENT_ADVISORY_SYSTEM=4-Canadian Fr
--				: E
--				: G
--				: 8ans+
--				: 13ans+
--				: 16ans+
--				: 18ans+
--				:
--

---------------------------------------------------------------------------------------------------
-- Header		: INPUT_1_EMBEDDED_AUDIO_LIKE_1_CHANS
--
-- MIB ref		: swCardEventLogSlotXX       .35.73.78.80.85.84.95.49.95.69.77.66.69.68.68.69.68.95.65.85.68.73.79.95.76.73.75.69.95.49.95.67.72.65.78.83
-- absolute OID	: 1.3.6.1.4.1.7995.2.6.1.1.XX.35.73.78.80.85.84.95.49.95.69.77.66.69.68.68.69.68.95.65.85.68.73.79.95.76.73.75.69.95.49.95.67.72.65.78.83
-- Vary			: YES
--
-- Value(s)		: ChX+Y
--				:
-- Comments		: Where X and Y are the channel numbers being compared in the range 1 to 16
--              : Default- Ch1+2
---------------------------------------------------------------------------------------------------
-- Header		: INPUT_1_EMBEDDED_AUDIO_LIKE_1_STATE
--
-- MIB ref		: swCardEventLogSlotXX       .35.73.78.80.85.84.95.49.95.69.77.66.69.68.68.69.68.95.65.85.68.73.79.95.76.73.75.69.95.49.95.83.84.65.84.69
-- absolute OID	: 1.3.6.1.4.1.7995.2.6.1.1.XX.35.73.78.80.85.84.95.49.95.69.77.66.69.68.68.69.68.95.65.85.68.73.79.95.76.73.75.69.95.49.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
-- Header		: INPUT_1_EMBEDDED_AUDIO_LIKE_2_CHANS
--
-- MIB ref		: swCardEventLogSlotXX       .35.73.78.80.85.84.95.49.95.69.77.66.69.68.68.69.68.95.65.85.68.73.79.95.76.73.75.69.95.50.95.67.72.65.78.83
-- absolute OID	: 1.3.6.1.4.1.7995.2.6.1.1.XX.35.73.78.80.85.84.95.49.95.69.77.66.69.68.68.69.68.95.65.85.68.73.79.95.76.73.75.69.95.50.95.67.72.65.78.83
-- Vary			: YES
--
-- Value(s)		: ChX+Y
--				:
-- Comments		: Where X and Y are the channel numbers being compared in the range 1 to 16
--              : Default- Ch3+4
---------------------------------------------------------------------------------------------------
-- Header		: INPUT_1_EMBEDDED_AUDIO_LIKE_2_STATE
--
-- MIB ref		: swCardEventLogSlotXX       .35.73.78.80.85.84.95.49.95.69.77.66.69.68.68.69.68.95.65.85.68.73.79.95.76.73.75.69.95.50.95.83.84.65.84.69
-- absolute OID	: 1.3.6.1.4.1.7995.2.6.1.1.XX.35.73.78.80.85.84.95.49.95.69.77.66.69.68.68.69.68.95.65.85.68.73.79.95.76.73.75.69.95.50.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
-- Header		: INPUT_1_EMBEDDED_AUDIO_LIKE_3_CHANS
--
-- MIB ref		: swCardEventLogSlotXX       .35.73.78.80.85.84.95.49.95.69.77.66.69.68.68.69.68.95.65.85.68.73.79.95.76.73.75.69.95.51.95.67.72.65.78.83
-- absolute OID	: 1.3.6.1.4.1.7995.2.6.1.1.XX.35.73.78.80.85.84.95.49.95.69.77.66.69.68.68.69.68.95.65.85.68.73.79.95.76.73.75.69.95.51.95.67.72.65.78.83
-- Vary			: YES
--
-- Value(s)		: ChX+Y
--				:
-- Comments		: Where X and Y are the channel numbers being compared in the range 1 to 16
--              : Default- Ch5+6
---------------------------------------------------------------------------------------------------
-- Header		: INPUT_1_EMBEDDED_AUDIO_LIKE_3_STATE
--
-- MIB ref		: swCardEventLogSlotXX       .35.73.78.80.85.84.95.49.95.69.77.66.69.68.68.69.68.95.65.85.68.73.79.95.76.73.75.69.95.51.95.83.84.65.84.69
-- absolute OID	: 1.3.6.1.4.1.7995.2.6.1.1.XX.35.73.78.80.85.84.95.49.95.69.77.66.69.68.68.69.68.95.65.85.68.73.79.95.76.73.75.69.95.51.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
-- Header		: INPUT_1_EMBEDDED_AUDIO_LIKE_4_CHANS
--
-- MIB ref		: swCardEventLogSlotXX       .35.73.78.80.85.84.95.49.95.69.77.66.69.68.68.69.68.95.65.85.68.73.79.95.76.73.75.69.95.52.95.67.72.65.78.83
-- absolute OID	: 1.3.6.1.4.1.7995.2.6.1.1.XX.35.73.78.80.85.84.95.49.95.69.77.66.69.68.68.69.68.95.65.85.68.73.79.95.76.73.75.69.95.52.95.67.72.65.78.83
-- Vary			: YES
--
-- Value(s)		: ChX+Y
--				:
-- Comments		: Where X and Y are the channel numbers being compared in the range 1 to 16
--              : Default- Ch7+8

---------------------------------------------------------------------------------------------------
-- Header		: INPUT_1_EMBEDDED_AUDIO_LIKE_4_STATE
--
-- MIB ref		: swCardEventLogSlotXX       .35.73.78.80.85.84.95.49.95.69.77.66.69.68.68.69.68.95.65.85.68.73.79.95.76.73.75.69.95.52.95.83.84.65.84.69
-- absolute OID	: 1.3.6.1.4.1.7995.2.6.1.1.XX.35.73.78.80.85.84.95.49.95.69.77.66.69.68.68.69.68.95.65.85.68.73.79.95.76.73.75.69.95.52.95.83.84.65.84.69
-- Vary			: YES
--
-- Value(s)		: WARN:Low/Lost
--				: Mono
--				: Stereo
--				: Wide
--				: Inv_Mono
--				: Inv_Stereo
--				: Inv_Wide
--				: Info:Low/Lost
--				: Info:Mono
--				: Info:Stereo
--				: Info:Wide
--				: Info:Inv_Mono
--				: Info:Inv_Stereo
--				: Info:Inv_Wide
--				:
-- Comments		:
--
---------------------------------------------------------------------------------------------------
