-- ************************************************************************************
--        Snell Card:IQSYN21
--        Module Id#:387
--       Command Set:24
--          Filename:SNELL-IQSYN21-CMD-MIB.mib
--       Source File:syncombined.xml
--        Source Ver:10.5.24
--    Logging Source:logsyn21.csv
--            Author:robinbrown
--              Date:14/03/2011
--              Time:15:56
--
-- Copyright (c) 2010 Snell Ltd
-- All rights reserved.
--
-- ************************************************************************************

SNELL-IQSYN21-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQSYN21,
    moduleIQSYN21MIB
        FROM SNELL-WILCOX-PRODUCT-REG;

moduleIQSYN21CmdMi MODULE-IDENTITY
    LAST-UPDATED "1103141556Z"
    ORGANIZATION "Snell Ltd"
    CONTACT-INFO
        "Primary Author:robinbrown

         postal:    Hartman House
                    Danehill
                    Lower Earley,
                    Reading, Berks
                    RG6 4PB
         phone:     +44 (0)118 9866123
         email:     support.uk@snellgroup.com"
    DESCRIPTION
        "This file defines the Snell card, command set translations."
    ::= { moduleIQSYN21MIB 1 }




--********************************************************************************
--*
--*  Snell Card:
--*  command set:
--*  list commands/menus:
--*
--******************************************************************************
    iqsyn21CmdTable OBJECT-TYPE
        SYNTAX          SEQUENCE OF Iqsyn21CmdEntry
        MAX-ACCESS      not-accessible
        STATUS          current
        DESCRIPTION
                "Note the instance of this table is relected in the command set Version"
        ::= { moduleIQSYN21 1 }

    iqsyn21CmdEntry OBJECT-TYPE
        SYNTAX          Iqsyn21CmdEntry
        MAX-ACCESS      not-accessible
        STATUS          current
        DESCRIPTION
                "Entry in command table."
        INDEX   { iqsyn21SlotIndex }
        ::= { iqsyn21CmdTable 1 }

    Iqsyn21CmdEntry ::=
        SEQUENCE {
            iqsyn21SlotIndex
                Unsigned32,
            iqsyn21InputIPSelect
                INTEGER,
            iqsyn21InputIPLoss
                INTEGER,
            iqsyn21InputValidStandardsAllValid
                INTEGER,
            iqsyn21InputValidStandardsAllInvalid
                INTEGER,
            iqsyn21InputValidStandards108023sF
                INTEGER,
            iqsyn21InputValidStandards108023p
                INTEGER,
            iqsyn21InputValidStandards108024sF
                INTEGER,
            iqsyn21InputValidStandards108024p
                INTEGER,
            iqsyn21InputValidStandards108025i
                INTEGER,
            iqsyn21InputValidStandards108025p
                INTEGER,
            iqsyn21InputValidStandards103529i
                INTEGER,
            iqsyn21InputValidStandards108029i
                INTEGER,
            iqsyn21InputValidStandards108029p
                INTEGER,
            iqsyn21InputValidStandards103530i
                INTEGER,
            iqsyn21InputValidStandards108030i
                INTEGER,
            iqsyn21InputValidStandards108030p
                INTEGER,
            iqsyn21InputValidStandards72050p
                INTEGER,
            iqsyn21InputValidStandards72059p
                INTEGER,
            iqsyn21InputValidStandards72060p
                INTEGER,
            iqsyn21InputValidStandards62525i
                INTEGER,
            iqsyn21InputValidStandards52529i
                INTEGER,
            iqsyn21InputAgileVLock
                INTEGER,
            iqsyn21InputErrorsCRCErrs
                RollCallString,
            iqsyn21InputErrorsCRCErrSec
                RollCallString,
            iqsyn21InputErrorsANCErrs
                RollCallString,
            iqsyn21InputErrorsANCErrSec
                RollCallString,
            iqsyn21InputErrorsResetSec
                RollCallString,
            iqsyn21InputErrorsErrorReset
                INTEGER,
            iqsyn21OutputOPStd
                INTEGER,
            iqsyn21OutputVideoProcMasterGain
                INTEGER,
            iqsyn21OutputVideoProcYGain
                INTEGER,
            iqsyn21OutputVideoProcCGain
                INTEGER,
            iqsyn21OutputVideoProcBlackLevel
                INTEGER,
            iqsyn21OutputDefaultOutput
                INTEGER,
            iqsyn21OutputOutputStandard
                INTEGER,
            iqsyn21OutputDefaultOPStd
                INTEGER,
            iqsyn21AudioDelayADelaySourcesManual
                INTEGER,
            iqsyn21AudioDelayADelaySourcesGPIPWM
                INTEGER,
            iqsyn21AudioDelayADelaySourcesRollTrack14
                INTEGER,
            iqsyn21AudioDelayADelaySourcesRollTrack15
                INTEGER,
            iqsyn21AudioDelayADelaySourcesRollTrack16
                INTEGER,
            iqsyn21AudioDelayADelaySourcesRollTrack17
                INTEGER,
            iqsyn21AudioDelayAAdjustManualDelay
                INTEGER,
            iqsyn21AudioDelayACurrentAudioDelay
                RollCallString,
            iqsyn21AudioDelayBDelaySourcesManual
                INTEGER,
            iqsyn21AudioDelayBDelaySourcesGPIPWM
                INTEGER,
            iqsyn21AudioDelayBDelaySourcesRollTrack14
                INTEGER,
            iqsyn21AudioDelayBDelaySourcesRollTrack15
                INTEGER,
            iqsyn21AudioDelayBDelaySourcesRollTrack16
                INTEGER,
            iqsyn21AudioDelayBDelaySourcesRollTrack17
                INTEGER,
            iqsyn21AudioDelayBAdjustManualDelay
                INTEGER,
            iqsyn21AudioDelayBCurrentAudioDelay
                RollCallString,
            iqsyn21AudioDelaySelectDelay1
                INTEGER,
            iqsyn21AudDelaysEMBDelaySelectInternal1
                INTEGER,
            iqsyn21AudDelaysEMBDelaySelectAutoDolbyEPhaseBus1
                INTEGER,
            iqsyn21AudDelaysEMBDelaySelectDelayLimitBus1
                RollCallString,
            iqsyn21AudDelaysEMBDelaySelectEMB1FineDelay
                INTEGER,
            iqsyn21AudioDelaySelectDelay2
                INTEGER,
            iqsyn21AudDelaysEMBDelaySelectInternal2
                INTEGER,
            iqsyn21AudDelaysEMBDelaySelectAutoDolbyEPhaseBus2
                INTEGER,
            iqsyn21AudDelaysEMBDelaySelectDelayLimitBus2
                RollCallString,
            iqsyn21AudDelaysEMBDelaySelectEMB2FineDelay
                INTEGER,
            iqsyn21AudioDelaySelectDelay3
                INTEGER,
            iqsyn21AudDelaysEMBDelaySelectInternal3
                INTEGER,
            iqsyn21AudDelaysEMBDelaySelectAutoDolbyEPhaseBus3
                INTEGER,
            iqsyn21AudDelaysEMBDelaySelectDelayLimitBus3
                RollCallString,
            iqsyn21AudDelaysEMBDelaySelectEMB3FineDelay
                INTEGER,
            iqsyn21AudioDelaySelectDelay4
                INTEGER,
            iqsyn21AudDelaysEMBDelaySelectInternal4
                INTEGER,
            iqsyn21AudDelaysEMBDelaySelectAutoDolbyEPhaseBus4
                INTEGER,
            iqsyn21AudDelaysEMBDelaySelectDelayLimitBus4
                RollCallString,
            iqsyn21AudDelaysEMBDelaySelectEMB4FineDelay
                INTEGER,
            iqsyn21AudioDelaySelectDelay5
                INTEGER,
            iqsyn21AudDelaysEMBDelaySelectInternal5
                INTEGER,
            iqsyn21AudDelaysEMBDelaySelectAutoDolbyEPhaseBus5
                INTEGER,
            iqsyn21AudDelaysEMBDelaySelectDelayLimitBus5
                RollCallString,
            iqsyn21AudDelaysEMBDelaySelectEMB5FineDelay
                INTEGER,
            iqsyn21AudioDelaySelectDelay6
                INTEGER,
            iqsyn21AudDelaysEMBDelaySelectInternal6
                INTEGER,
            iqsyn21AudDelaysEMBDelaySelectAutoDolbyEPhaseBus6
                INTEGER,
            iqsyn21AudDelaysEMBDelaySelectDelayLimitBus6
                RollCallString,
            iqsyn21AudDelaysEMBDelaySelectEMB6FineDelay
                INTEGER,
            iqsyn21AudioDelaySelectDelay7
                INTEGER,
            iqsyn21AudDelaysEMBDelaySelectInternal7
                INTEGER,
            iqsyn21AudDelaysEMBDelaySelectAutoDolbyEPhaseBus7
                INTEGER,
            iqsyn21AudDelaysEMBDelaySelectDelayLimitBus7
                RollCallString,
            iqsyn21AudDelaysEMBDelaySelectEMB7FineDelay
                INTEGER,
            iqsyn21AudioDelaySelectDelay8
                INTEGER,
            iqsyn21AudDelaysEMBDelaySelectInternal8
                INTEGER,
            iqsyn21AudDelaysEMBDelaySelectDelayLimitBus8
                RollCallString,
            iqsyn21AudDelaysEMBDelaySelectAutoDolbyEPhaseBus8
                INTEGER,
            iqsyn21AudDelaysEMBDelaySelectEMB8FineDelay
                INTEGER,
            iqsyn21AudioDelaysRollTrack14
                RollCallString,
            iqsyn21AudioDelaysRollTrack15
                RollCallString,
            iqsyn21AudioDelaysRollTrack16
                RollCallString,
            iqsyn21AudioDelaysRollTrack17
                RollCallString,
            iqsyn21AudioAudDelaysCrashSRCLimit
                INTEGER,
            iqsyn21EmbCtrlGroupGroup1Active
                INTEGER,
            iqsyn21EmbCtrlGroupGroup2Active
                INTEGER,
            iqsyn21EmbCtrlGroupGroup3Active
                INTEGER,
            iqsyn21EmbCtrlGroupGroup4Active
                INTEGER,
            iqsyn21EmbCtrlChannelPair1LActive
                INTEGER,
            iqsyn21EmbCtrlChannelPair1RActive
                INTEGER,
            iqsyn21EmbCtrlChannelPair2LActive
                INTEGER,
            iqsyn21EmbCtrlChannelPair2RActive
                INTEGER,
            iqsyn21EmbCtrlChannelPair3LActive
                INTEGER,
            iqsyn21EmbCtrlChannelPair3RActive
                INTEGER,
            iqsyn21EmbCtrlChannelPair4LActive
                INTEGER,
            iqsyn21EmbCtrlChannelPair4RActive
                INTEGER,
            iqsyn21EmbCtrlChannelPair5LActive
                INTEGER,
            iqsyn21EmbCtrlChannelPair5RActive
                INTEGER,
            iqsyn21EmbCtrlChannelPair6LActive
                INTEGER,
            iqsyn21EmbCtrlChannelPair6RActive
                INTEGER,
            iqsyn21EmbCtrlChannelPair7LActive
                INTEGER,
            iqsyn21EmbCtrlChannelPair7RActive
                INTEGER,
            iqsyn21EmbCtrlChannelPair8LActive
                INTEGER,
            iqsyn21EmbCtrlChannelPair8RActive
                INTEGER,
            iqsyn21AudioEmbCtrlEmbedderPriority
                INTEGER,
            iqsyn21EmbGainEmbedPair1Embed1MuteL
                INTEGER,
            iqsyn21EmbGainEmbedPair1Embed1MuteR
                INTEGER,
            iqsyn21EmbGainEmbedPair1Embed1LGain
                INTEGER,
            iqsyn21EmbGainEmbedPair1Embed1RGain
                INTEGER,
            iqsyn21EmbGainEmbedPair1Stereo
                INTEGER,
            iqsyn21EmbGainEmbedPair1Embed1InvertL
                INTEGER,
            iqsyn21EmbGainEmbedPair1Embed1InvertR
                INTEGER,
            iqsyn21EmbGainEmbedPair1Embed1LClip
                RollCallString,
            iqsyn21EmbGainEmbedPair1Embed1RClip
                RollCallString,
            iqsyn21EmbGainEmbedPair2Embed2MuteL
                INTEGER,
            iqsyn21EmbGainEmbedPair2Embed2MuteR
                INTEGER,
            iqsyn21EmbGainEmbedPair2Embed2LGain
                INTEGER,
            iqsyn21EmbGainEmbedPair2Embed2RGain
                INTEGER,
            iqsyn21EmbGainEmbedPair2Stereo
                INTEGER,
            iqsyn21EmbGainEmbedPair2Embed2InvertL
                INTEGER,
            iqsyn21EmbGainEmbedPair2Embed2InvertR
                INTEGER,
            iqsyn21EmbGainEmbedPair2Embed2LClip
                RollCallString,
            iqsyn21EmbGainEmbedPair2Embed2RClip
                RollCallString,
            iqsyn21EmbGainEmbedPair3Embed3MuteL
                INTEGER,
            iqsyn21EmbGainEmbedPair3Embed3MuteR
                INTEGER,
            iqsyn21EmbGainEmbedPair3Embed3LGain
                INTEGER,
            iqsyn21EmbGainEmbedPair3Embed3RGain
                INTEGER,
            iqsyn21EmbGainEmbedPair3Stereo
                INTEGER,
            iqsyn21EmbGainEmbedPair3Embed3InvertL
                INTEGER,
            iqsyn21EmbGainEmbedPair3Embed3InvertR
                INTEGER,
            iqsyn21EmbGainEmbedPair3Embed3LClip
                RollCallString,
            iqsyn21EmbGainEmbedPair3Embed3RClip
                RollCallString,
            iqsyn21EmbGainEmbedPair4Embed4MuteL
                INTEGER,
            iqsyn21EmbGainEmbedPair4Embed4MuteR
                INTEGER,
            iqsyn21EmbGainEmbedPair4Embed4LGain
                INTEGER,
            iqsyn21EmbGainEmbedPair4Embed4RGain
                INTEGER,
            iqsyn21EmbGainEmbedPair4Stereo
                INTEGER,
            iqsyn21EmbGainEmbedPair4Embed4InvertL
                INTEGER,
            iqsyn21EmbGainEmbedPair4Embed4InvertR
                INTEGER,
            iqsyn21EmbGainEmbedPair4Embed4LClip
                RollCallString,
            iqsyn21EmbGainEmbedPair4Embed4RClip
                RollCallString,
            iqsyn21EmbGainEmbedPair5Embed5MuteL
                INTEGER,
            iqsyn21EmbGainEmbedPair5Embed5MuteR
                INTEGER,
            iqsyn21EmbGainEmbedPair5Embed5LGain
                INTEGER,
            iqsyn21EmbGainEmbedPair5Embed5RGain
                INTEGER,
            iqsyn21EmbGainEmbedPair5Stereo
                INTEGER,
            iqsyn21EmbGainEmbedPair5Embed5InvertL
                INTEGER,
            iqsyn21EmbGainEmbedPair5Embed5InvertR
                INTEGER,
            iqsyn21EmbGainEmbedPair5Embed5LClip
                RollCallString,
            iqsyn21EmbGainEmbedPair5Embed5RClip
                RollCallString,
            iqsyn21EmbGainEmbedPair6Embed6MuteL
                INTEGER,
            iqsyn21EmbGainEmbedPair6Embed6MuteR
                INTEGER,
            iqsyn21EmbGainEmbedPair6Embed6LGain
                INTEGER,
            iqsyn21EmbGainEmbedPair6Embed6RGain
                INTEGER,
            iqsyn21EmbGainEmbedPair6Stereo
                INTEGER,
            iqsyn21EmbGainEmbedPair6Embed6InvertL
                INTEGER,
            iqsyn21EmbGainEmbedPair6Embed6InvertR
                INTEGER,
            iqsyn21EmbGainEmbedPair6Embed6LClip
                RollCallString,
            iqsyn21EmbGainEmbedPair6Embed6RClip
                RollCallString,
            iqsyn21EmbGainEmbedPair7Embed7MuteL
                INTEGER,
            iqsyn21EmbGainEmbedPair7Embed7MuteR
                INTEGER,
            iqsyn21EmbGainEmbedPair7Embed7LGain
                INTEGER,
            iqsyn21EmbGainEmbedPair7Embed7RGain
                INTEGER,
            iqsyn21EmbGainEmbedPair7Stereo
                INTEGER,
            iqsyn21EmbGainEmbedPair7Embed7InvertL
                INTEGER,
            iqsyn21EmbGainEmbedPair7Embed7InvertR
                INTEGER,
            iqsyn21EmbGainEmbedPair7Embed7LClip
                RollCallString,
            iqsyn21EmbGainEmbedPair7Embed7RClip
                RollCallString,
            iqsyn21EmbGainEmbedPair8Embed8MuteL
                INTEGER,
            iqsyn21EmbGainEmbedPair8Embed8MuteR
                INTEGER,
            iqsyn21EmbGainEmbedPair8Embed8LGain
                INTEGER,
            iqsyn21EmbGainEmbedPair8Embed8RGain
                INTEGER,
            iqsyn21EmbGainEmbedPair8Stereo
                INTEGER,
            iqsyn21EmbGainEmbedPair8Embed8InvertL
                INTEGER,
            iqsyn21EmbGainEmbedPair8Embed8InvertR
                INTEGER,
            iqsyn21EmbGainEmbedPair8Embed8LClip
                RollCallString,
            iqsyn21EmbGainEmbedPair8Embed8RClip
                RollCallString,
            iqsyn21EmbOutEmbedPair1Left
                INTEGER,
            iqsyn21EmbOutEmbedPair1Right
                INTEGER,
            iqsyn21EmbOutEmbedPair1LinkLRSelection
                INTEGER,
            iqsyn21EmbOutEmbedPair2Left
                INTEGER,
            iqsyn21EmbOutEmbedPair2Right
                INTEGER,
            iqsyn21EmbOutEmbedPair2LinkLRSelection
                INTEGER,
            iqsyn21EmbOutEmbedPair3Left
                INTEGER,
            iqsyn21EmbOutEmbedPair3Right
                INTEGER,
            iqsyn21EmbOutEmbedPair3LinkLRSelection
                INTEGER,
            iqsyn21EmbOutEmbedPair4Left
                INTEGER,
            iqsyn21EmbOutEmbedPair4Right
                INTEGER,
            iqsyn21EmbOutEmbedPair4LinkLRSelection
                INTEGER,
            iqsyn21EmbOutEmbedPair5Left
                INTEGER,
            iqsyn21EmbOutEmbedPair5Right
                INTEGER,
            iqsyn21EmbOutEmbedPair5LinkLRSelection
                INTEGER,
            iqsyn21EmbOutEmbedPair6Left
                INTEGER,
            iqsyn21EmbOutEmbedPair6Right
                INTEGER,
            iqsyn21EmbOutEmbedPair6LinkLRSelection
                INTEGER,
            iqsyn21EmbOutEmbedPair7Left
                INTEGER,
            iqsyn21EmbOutEmbedPair7Right
                INTEGER,
            iqsyn21EmbOutEmbedPair7LinkLRSelection
                INTEGER,
            iqsyn21EmbOutEmbedPair8Left
                INTEGER,
            iqsyn21EmbOutEmbedPair8Right
                INTEGER,
            iqsyn21EmbOutEmbedPair8LinkLRSelection
                INTEGER,
            iqsyn21AudioEmbDataInput1
                INTEGER,
            iqsyn21AudioEmbDataInput2
                INTEGER,
            iqsyn21AudioEmbDataInput3
                INTEGER,
            iqsyn21AudioEmbDataInput4
                INTEGER,
            iqsyn21AudioEmbDataInput5
                INTEGER,
            iqsyn21AudioEmbDataInput6
                INTEGER,
            iqsyn21AudioEmbDataInput7
                INTEGER,
            iqsyn21AudioEmbDataInput8
                INTEGER,
            iqsyn21DisembedderNamesDisemb1L
                RollCallString,
            iqsyn21DisembedderNamesDisemb1R
                RollCallString,
            iqsyn21DisembedderNamesDisemb2L
                RollCallString,
            iqsyn21DisembedderNamesDisemb2R
                RollCallString,
            iqsyn21DisembedderNamesDisemb3L
                RollCallString,
            iqsyn21DisembedderNamesDisemb3R
                RollCallString,
            iqsyn21DisembedderNamesDisemb4L
                RollCallString,
            iqsyn21DisembedderNamesDisemb4R
                RollCallString,
            iqsyn21DisembedderNamesDisemb5L
                RollCallString,
            iqsyn21DisembedderNamesDisemb5R
                RollCallString,
            iqsyn21DisembedderNamesDisemb6L
                RollCallString,
            iqsyn21DisembedderNamesDisemb6R
                RollCallString,
            iqsyn21DisembedderNamesDisemb7L
                RollCallString,
            iqsyn21DisembedderNamesDisemb7R
                RollCallString,
            iqsyn21DisembedderNamesDisemb8L
                RollCallString,
            iqsyn21DisembedderNamesDisemb8R
                RollCallString,
            iqsyn21DisembedderNamesEmbeddedOPEmbed1L
                RollCallString,
            iqsyn21DisembedderNamesEmbeddedOPEmbed1R
                RollCallString,
            iqsyn21DisembedderNamesEmbeddedOPEmbed2L
                RollCallString,
            iqsyn21DisembedderNamesEmbeddedOPEmbed2R
                RollCallString,
            iqsyn21DisembedderNamesEmbeddedOPEmbed3L
                RollCallString,
            iqsyn21DisembedderNamesEmbeddedOPEmbed3R
                RollCallString,
            iqsyn21DisembedderNamesEmbeddedOPEmbed4L
                RollCallString,
            iqsyn21DisembedderNamesEmbeddedOPEmbed4R
                RollCallString,
            iqsyn21DisembedderNamesEmbeddedOPEmbed5L
                RollCallString,
            iqsyn21DisembedderNamesEmbeddedOPEmbed5R
                RollCallString,
            iqsyn21DisembedderNamesEmbeddedOPEmbed6L
                RollCallString,
            iqsyn21DisembedderNamesEmbeddedOPEmbed6R
                RollCallString,
            iqsyn21DisembedderNamesEmbeddedOPEmbed7L
                RollCallString,
            iqsyn21DisembedderNamesEmbeddedOPEmbed7R
                RollCallString,
            iqsyn21DisembedderNamesEmbeddedOPEmbed8L
                RollCallString,
            iqsyn21DisembedderNamesEmbeddedOPEmbed8R
                RollCallString,
            iqsyn21DisembedderNamesIPNamesStereoDisemb1
                INTEGER,
            iqsyn21DisembedderNamesIPNamesStereoDisemb2
                INTEGER,
            iqsyn21DisembedderNamesIPNamesStereoDisemb3
                INTEGER,
            iqsyn21DisembedderNamesIPNamesStereoDisemb4
                INTEGER,
            iqsyn21DisembedderNamesIPNamesStereoDisemb5
                INTEGER,
            iqsyn21DisembedderNamesIPNamesStereoDisemb6
                INTEGER,
            iqsyn21DisembedderNamesIPNamesStereoDisemb7
                INTEGER,
            iqsyn21DisembedderNamesIPNamesStereoDisemb8
                INTEGER,
            iqsyn21DisembedderNamesOPNamesStereoEmbed1
                INTEGER,
            iqsyn21DisembedderNamesOPNamesStereoEmbed2
                INTEGER,
            iqsyn21DisembedderNamesOPNamesStereoEmbed3
                INTEGER,
            iqsyn21DisembedderNamesOPNamesStereoEmbed4
                INTEGER,
            iqsyn21DisembedderNamesOPNamesStereoEmbed5
                INTEGER,
            iqsyn21DisembedderNamesOPNamesStereoEmbed6
                INTEGER,
            iqsyn21DisembedderNamesOPNamesStereoEmbed7
                INTEGER,
            iqsyn21DisembedderNamesOPNamesStereoEmbed8
                INTEGER,
            iqsyn21NamesMixNamesMix1
                RollCallString,
            iqsyn21NamesMixNamesMix2
                RollCallString,
            iqsyn21NamesMixNamesMix3
                RollCallString,
            iqsyn21NamesMixNamesMix4
                RollCallString,
            iqsyn21Mix1Mix1RoutingSource1
                INTEGER,
            iqsyn21Mix1Mix1RoutingInvert1
                INTEGER,
            iqsyn21Mix1Mix1RoutingSource2
                INTEGER,
            iqsyn21Mix1Mix1RoutingInvert2
                INTEGER,
            iqsyn21Mix1Mix1RoutingSource3
                INTEGER,
            iqsyn21Mix1Mix1RoutingInvert3
                INTEGER,
            iqsyn21Mix1Mix1RoutingSource4
                INTEGER,
            iqsyn21Mix1Mix1RoutingInvert4
                INTEGER,
            iqsyn21Mix1Mix1GainGain1
                INTEGER,
            iqsyn21Mix1Mix1GainMute1
                INTEGER,
            iqsyn21Mix1Mix1GainGain2
                INTEGER,
            iqsyn21Mix1Mix1GainMute2
                INTEGER,
            iqsyn21Mix1Mix1GainGain3
                INTEGER,
            iqsyn21Mix1Mix1GainMute3
                INTEGER,
            iqsyn21Mix1Mix1GainGain4
                INTEGER,
            iqsyn21Mix1Mix1GainMute4
                INTEGER,
            iqsyn21Mix1Mix1GainInp1Clip
                RollCallString,
            iqsyn21Mix1Mix1GainInp2Clip
                RollCallString,
            iqsyn21Mix1Mix1GainInp3Clip
                RollCallString,
            iqsyn21Mix1Mix1GainInp4Clip
                RollCallString,
            iqsyn21Mix1Mix1GainOPClip
                RollCallString,
            iqsyn21Mix2Mix2RoutingSource1
                INTEGER,
            iqsyn21Mix2Mix2RoutingInvert1
                INTEGER,
            iqsyn21Mix2Mix2RoutingSource2
                INTEGER,
            iqsyn21Mix2Mix2RoutingInvert2
                INTEGER,
            iqsyn21Mix2Mix2RoutingSource3
                INTEGER,
            iqsyn21Mix2Mix2RoutingInvert3
                INTEGER,
            iqsyn21Mix2Mix2RoutingSource4
                INTEGER,
            iqsyn21Mix2Mix2RoutingInvert4
                INTEGER,
            iqsyn21Mix2Mix2GainGain1
                INTEGER,
            iqsyn21Mix2Mix2GainMute1
                INTEGER,
            iqsyn21Mix2Mix2GainGain2
                INTEGER,
            iqsyn21Mix2Mix2GainMute2
                INTEGER,
            iqsyn21Mix2Mix2GainGain3
                INTEGER,
            iqsyn21Mix2Mix2GainMute3
                INTEGER,
            iqsyn21Mix2Mix2GainGain4
                INTEGER,
            iqsyn21Mix2Mix2GainMute4
                INTEGER,
            iqsyn21Mix2Mix2GainInp1Clip
                RollCallString,
            iqsyn21Mix2Mix2GainInp2Clip
                RollCallString,
            iqsyn21Mix2Mix2GainInp3Clip
                RollCallString,
            iqsyn21Mix2Mix2GainInp4Clip
                RollCallString,
            iqsyn21Mix2Mix2GainOPClip
                RollCallString,
            iqsyn21Mix3Mix3RoutingSource1
                INTEGER,
            iqsyn21Mix3Mix3RoutingInvert1
                INTEGER,
            iqsyn21Mix3Mix3RoutingSource2
                INTEGER,
            iqsyn21Mix3Mix3RoutingInvert2
                INTEGER,
            iqsyn21Mix3Mix3RoutingSource3
                INTEGER,
            iqsyn21Mix3Mix3RoutingInvert3
                INTEGER,
            iqsyn21Mix3Mix3RoutingSource4
                INTEGER,
            iqsyn21Mix3Mix3RoutingInvert4
                INTEGER,
            iqsyn21Mix3Mix3GainGain1
                INTEGER,
            iqsyn21Mix3Mix3GainMute1
                INTEGER,
            iqsyn21Mix3Mix3GainGain2
                INTEGER,
            iqsyn21Mix3Mix3GainMute2
                INTEGER,
            iqsyn21Mix3Mix3GainGain3
                INTEGER,
            iqsyn21Mix3Mix3GainMute3
                INTEGER,
            iqsyn21Mix3Mix3GainGain4
                INTEGER,
            iqsyn21Mix3Mix3GainMute4
                INTEGER,
            iqsyn21Mix3Mix3GainInp1Clip
                RollCallString,
            iqsyn21Mix3Mix3GainInp2Clip
                RollCallString,
            iqsyn21Mix3Mix3GainInp3Clip
                RollCallString,
            iqsyn21Mix3Mix3GainInp4Clip
                RollCallString,
            iqsyn21Mix3Mix3GainOPClip
                RollCallString,
            iqsyn21Mix4Mix4RoutingSource1
                INTEGER,
            iqsyn21Mix4Mix4RoutingInvert1
                INTEGER,
            iqsyn21Mix4Mix4RoutingSource2
                INTEGER,
            iqsyn21Mix4Mix4RoutingInvert2
                INTEGER,
            iqsyn21Mix4Mix4RoutingSource3
                INTEGER,
            iqsyn21Mix4Mix4RoutingInvert3
                INTEGER,
            iqsyn21Mix4Mix4RoutingSource4
                INTEGER,
            iqsyn21Mix4Mix4RoutingInvert4
                INTEGER,
            iqsyn21Mix4Mix4GainGain1
                INTEGER,
            iqsyn21Mix4Mix4GainMute1
                INTEGER,
            iqsyn21Mix4Mix4GainGain2
                INTEGER,
            iqsyn21Mix4Mix4GainMute2
                INTEGER,
            iqsyn21Mix4Mix4GainGain3
                INTEGER,
            iqsyn21Mix4Mix4GainMute3
                INTEGER,
            iqsyn21Mix4Mix4GainGain4
                INTEGER,
            iqsyn21Mix4Mix4GainMute4
                INTEGER,
            iqsyn21Mix4Mix4GainInp1Clip
                RollCallString,
            iqsyn21Mix4Mix4GainInp2Clip
                RollCallString,
            iqsyn21Mix4Mix4GainInp3Clip
                RollCallString,
            iqsyn21Mix4Mix4GainInp4Clip
                RollCallString,
            iqsyn21Mix4Mix4GainOPClip
                RollCallString,
            iqsyn21AudioDolbyETimingSelAudioPair
                INTEGER,
            iqsyn21AudioDolbyETimingRelativeTiming
                RollCallString,
            iqsyn21AudioDolbyETimingStatus
                RollCallString,
            iqsyn21AudioDolbyETimingError
                RollCallString,
            iqsyn21DolbyETimingDolbyELineStandard
                INTEGER,
            iqsyn21DolbyETimingDolbyELineAutoLineNo
                INTEGER,
            iqsyn21DolbyELineUserDolbyELinePair1
                INTEGER,
            iqsyn21DolbyELineUserDolbyELinePair2
                INTEGER,
            iqsyn21DolbyELineUserDolbyELinePair3
                INTEGER,
            iqsyn21DolbyELineUserDolbyELinePair4
                INTEGER,
            iqsyn21DolbyELineUserDolbyELinePair5
                INTEGER,
            iqsyn21DolbyELineUserDolbyELinePair6
                INTEGER,
            iqsyn21DolbyELineUserDolbyELinePair7
                INTEGER,
            iqsyn21DolbyELineUserDolbyELinePair8
                INTEGER,
            iqsyn21DolbyETimingDolbyELineSmoothCapRange
                INTEGER,
            iqsyn21GenlockDelayMode
                INTEGER,
            iqsyn21GenlockRefTimeDelayFrames
                INTEGER,
            iqsyn21GenlockRefTimeVerticalTiming
                INTEGER,
            iqsyn21GenlockRefTimeHorizontalTiming
                INTEGER,
            iqsyn21GenlockSetDelayDelayms
                INTEGER,
            iqsyn21GenlockRefTimeCurrentDelay
                RollCallString,
            iqsyn21GenlockSyncAmplitude
                RollCallString,
            iqsyn21GenlockUseEmbDelayFback
                INTEGER,
            iqsyn21GenlockSampleNumber
                RollCallString,
            iqsyn21GenlockLineNumber
                RollCallString,
            iqsyn21BackupEnable
                INTEGER,
            iqsyn21BackupORInput1State
                RollCallString,
            iqsyn21BackupORInput2State
                RollCallString,
            iqsyn21BackupRevertDelay
                INTEGER,
            iqsyn21BackupPriority
                INTEGER,
            iqsyn21BackupQualifyCRCErr
                INTEGER,
            iqsyn21BackupQualifyANCErr
                INTEGER,
            iqsyn21BackupInput1SelStatInp1OK
                RollCallString,
            iqsyn21BackupInput1SelStatInp2FAIL
                RollCallString,
            iqsyn21BackupInput1SelStatInp2Err
                RollCallString,
            iqsyn21BackupInput1SelStatAUDFail2
                RollCallString,
            iqsyn21BackupInput1SelStatStd2
                RollCallString,
            iqsyn21BackupInput1SelStatGPI1
                RollCallString,
            iqsyn21BackupInput1SelStatGPI2
                RollCallString,
            iqsyn21BackupInput1SelEnblInp1OK
                INTEGER,
            iqsyn21BackupInput1SelEnblInp2FAIL
                INTEGER,
            iqsyn21BackupInput1SelEnblInp2Err
                INTEGER,
            iqsyn21BackupInput1SelEnblAudInp2Err
                INTEGER,
            iqsyn21BackupInput1SelEnblStdInp2
                INTEGER,
            iqsyn21BackupInput1SelEnblGPI1
                INTEGER,
            iqsyn21BackupInput1SelEnblGPI2
                INTEGER,
            iqsyn21BackupInput1SelDlyInp1OK
                INTEGER,
            iqsyn21BackupInput1SelDlyInp2FAIL
                INTEGER,
            iqsyn21BackupInput1SelDlyInp2Err
                INTEGER,
            iqsyn21BackupInput1SelDlyGPI1
                INTEGER,
            iqsyn21BackupInput1SelDlyGPI2
                INTEGER,
            iqsyn21BackupInput1SelDlyAud2FAIL
                INTEGER,
            iqsyn21BackupInput1SelDlyStd2
                INTEGER,
            iqsyn21BackupInput1SelGPI1State
                INTEGER,
            iqsyn21BackupInput1SelGPI2State
                INTEGER,
            iqsyn21BackupInput1SelInp12AudFailG1C1
                INTEGER,
            iqsyn21BackupInput1SelInp12AudFailG1C2
                INTEGER,
            iqsyn21BackupInput1SelInp12AudFailG2C1
                INTEGER,
            iqsyn21BackupInput1SelInp12AudFailG2C2
                INTEGER,
            iqsyn21BackupInput1SelInp12AudFailG3C1
                INTEGER,
            iqsyn21BackupInput1SelInp12AudFailG3C2
                INTEGER,
            iqsyn21BackupInput1SelInp12AudFailG4C1
                INTEGER,
            iqsyn21BackupInput1SelInp12AudFailG4C2
                INTEGER,
            iqsyn21BackupInput1SelInp12AudFailLockGrp
                INTEGER,
            iqsyn21BackupInput1SelSelAll
                INTEGER,
            iqsyn21BackupInput1SelSelNone
                INTEGER,
            iqsyn21BackupInput2SelStatInp2OK
                RollCallString,
            iqsyn21BackupInput2SelStatInp1FAIL
                RollCallString,
            iqsyn21BackupInput2SelStatInp1Err
                RollCallString,
            iqsyn21BackupInput2SelStatAUDFail1
                RollCallString,
            iqsyn21BackupInput2SelStatStd1
                RollCallString,
            iqsyn21BackupInput2SelStatGPI1
                RollCallString,
            iqsyn21BackupInput2SelStatGPI2
                RollCallString,
            iqsyn21BackupInput2SelEnblInp2OK
                INTEGER,
            iqsyn21BackupInput2SelEnblInp1FAIL
                INTEGER,
            iqsyn21BackupInput2SelEnblInp1Err
                INTEGER,
            iqsyn21BackupInput2SelEnblGPI1
                INTEGER,
            iqsyn21BackupInput2SelEnblGPI2
                INTEGER,
            iqsyn21BackupInput2SelEnblAudInp1Err
                INTEGER,
            iqsyn21BackupInput2SelEnblStdInp1
                INTEGER,
            iqsyn21BackupInput2SelDlyInp2OK
                INTEGER,
            iqsyn21BackupInput2SelDlyInp1FAIL
                INTEGER,
            iqsyn21BackupInput2SelDlyInp1Err
                INTEGER,
            iqsyn21BackupInput2SelDlyAud2FAIL
                INTEGER,
            iqsyn21BackupInput2SelDlyStd1
                INTEGER,
            iqsyn21BackupInput2SelDlyGPI1
                INTEGER,
            iqsyn21BackupInput2SelDlyGPI2
                INTEGER,
            iqsyn21BackupInput2SelGPI1State
                INTEGER,
            iqsyn21BackupInput2SelGPI2State
                INTEGER,
            iqsyn21BackupInput2SelInp21AudFailG1C1
                INTEGER,
            iqsyn21BackupInput2SelInp21AudFailG1C2
                INTEGER,
            iqsyn21BackupInput2SelInp21AudFailG2C1
                INTEGER,
            iqsyn21BackupInput2SelInp21AudFailG2C2
                INTEGER,
            iqsyn21BackupInput2SelInp21AudFailG3C1
                INTEGER,
            iqsyn21BackupInput2SelInp21AudFailG3C2
                INTEGER,
            iqsyn21BackupInput2SelInp21AudFailG4C1
                INTEGER,
            iqsyn21BackupInput2SelInp21AudFailG4C2
                INTEGER,
            iqsyn21BackupInput2SelInp21AudFailLockGrp
                INTEGER,
            iqsyn21BackupInput2SelSelAll
                INTEGER,
            iqsyn21BackupInput2SelSelNone
                INTEGER,
            iqsyn21UtilsPatternsPatternEnable
                INTEGER,
            iqsyn21UtilsPatternsScrollPattern
                INTEGER,
            iqsyn21UtilsPatternsPatternType
                INTEGER,
            iqsyn21UtilsANCblankonMismat
                INTEGER,
            iqsyn21UtilsFreezeForceFreeze
                INTEGER,
            iqsyn21UtilsFreezeFreezeType
                INTEGER,
            iqsyn21UtilsMonochrome
                INTEGER,
            iqsyn21UtilsMonochromeMonochromeType
                INTEGER,
            iqsyn21UtilsHANCVBIBlankingANCMode
                INTEGER,
            iqsyn21UtilsHANCVBIBlankingStandard
                INTEGER,
            iqsyn21UtilsHANCVBIBlankingBlankAll
                INTEGER,
            iqsyn21UtilsHANCVBIBlankingPassAll
                INTEGER,
            iqsyn21UtilsHANCVBIBlankingBlank1
                INTEGER,
            iqsyn21UtilsHANCVBIBlankingBlank2
                INTEGER,
            iqsyn21UtilsHANCVBIBlankingBlank3
                INTEGER,
            iqsyn21UtilsHANCVBIBlankingBlank4
                INTEGER,
            iqsyn21UtilsHANCVBIBlankingBlank5
                INTEGER,
            iqsyn21UtilsHANCVBIBlankingBlank6
                INTEGER,
            iqsyn21UtilsHANCVBIBlankingBlank7
                INTEGER,
            iqsyn21UtilsHANCVBIBlankingBlank8
                INTEGER,
            iqsyn21UtilsHANCVBIBlankingBlank9
                INTEGER,
            iqsyn21UtilsHANCVBIBlankingBlank10
                INTEGER,
            iqsyn21UtilsHANCVBIBlankingBlank11
                INTEGER,
            iqsyn21UtilsHANCVBIBlankingBlank12
                INTEGER,
            iqsyn21UtilsHANCVBIBlankingBlank13
                INTEGER,
            iqsyn21UtilsHANCVBIBlankingBlank14
                INTEGER,
            iqsyn21UtilsHANCVBIBlankingBlank15
                INTEGER,
            iqsyn21UtilsHANCVBIBlankingBlank16
                INTEGER,
            iqsyn21UtilsHANCVBIBlankingBlank17
                INTEGER,
            iqsyn21UtilsHANCVBIBlankingBlank18
                INTEGER,
            iqsyn21UtilsHANCVBIBlankingBlank19
                INTEGER,
            iqsyn21UtilsHANCVBIBlankingBlank20
                INTEGER,
            iqsyn21UtilsHANCVBIBlankingBlank21
                INTEGER,
            iqsyn21UtilsHANCVBIBlankingBlank22
                INTEGER,
            iqsyn21UtilsHANCVBIBlankingBlank23
                INTEGER,
            iqsyn21UtilsHANCVBIBlankingBlank24
                INTEGER,
            iqsyn21UtilsHANCVBIBlankingBlank25
                INTEGER,
            iqsyn21UtilsHANCVBIBlankingBlank26
                INTEGER,
            iqsyn21UtilsHANCVBIBlankingBlank27
                INTEGER,
            iqsyn21UtilsHANCVBIBlankingBlank28
                INTEGER,
            iqsyn21UtilsHANCVBIBlankingBlank29
                INTEGER,
            iqsyn21UtilsHANCVBIBlankingBlank30
                INTEGER,
            iqsyn21UtilsHANCVBIBlankingBlank31
                INTEGER,
            iqsyn21UtilsHANCVBIBlankingBlank32
                INTEGER,
            iqsyn21UtilsHANCVBIBlankingBlank33
                INTEGER,
            iqsyn21UtilsHANCVBIBlankingBlank34
                INTEGER,
            iqsyn21UtilsSmpte2016Line2ReadAFD
                RollCallString,
            iqsyn21UtilsSmpte2016Line2ReadAR
                RollCallString,
            iqsyn21UtilsSmpte2016Line2WriteAFD
                RollCallString,
            iqsyn21UtilsSmpte2016Line2WriteAR
                RollCallString,
            iqsyn21GPIGPI1GPIO1Mode
                INTEGER,
            iqsyn21GPIGPI1GPI1ipSelect
                INTEGER,
            iqsyn21GPIGPI1GPO1opSelect
                INTEGER,
            iqsyn21GPIGPI1InvertGPIO1
                INTEGER,
            iqsyn21GPIGPI2GPIO2Mode
                INTEGER,
            iqsyn21GPIGPI2GPI2ipSelect
                INTEGER,
            iqsyn21GPIGPI2GPO2opSelect
                INTEGER,
            iqsyn21GPIGPI2InvertGPIO2
                INTEGER,
            iqsyn21GPIGPIPWMDelayTimerTimerSource
                INTEGER,
            iqsyn21GPIGPIPWMDelayTimerActiveHigh
                INTEGER,
            iqsyn21MemoriesRecallMemory
                INTEGER,
            iqsyn21MemoriesSelMemory
                INTEGER,
            iqsyn21MemoriesSaveMemory
                INTEGER,
            iqsyn21MemoriesClearMemory
                INTEGER,
            iqsyn21MemoriesMemoryNameChangeName
                RollCallString,
            iqsyn21MemoriesLastUserMemory
                RollCallString,
            iqsyn21MemoriesMemoryName1
                RollCallString,
            iqsyn21MemoriesMemoryName2
                RollCallString,
            iqsyn21MemoriesMemoryName3
                RollCallString,
            iqsyn21MemoriesMemoryName4
                RollCallString,
            iqsyn21MemoriesMemoryName5
                RollCallString,
            iqsyn21MemoriesMemoryName6
                RollCallString,
            iqsyn21MemoriesMemoryName7
                RollCallString,
            iqsyn21MemoriesMemoryName8
                RollCallString,
            iqsyn21MemoriesMemoryName9
                RollCallString,
            iqsyn21MemoriesMemoryName10
                RollCallString,
            iqsyn21MemoriesMemoryName11
                RollCallString,
            iqsyn21MemoriesMemoryName12
                RollCallString,
            iqsyn21MemoriesMemoryName13
                RollCallString,
            iqsyn21MemoriesMemoryName14
                RollCallString,
            iqsyn21MemoriesMemoryName15
                RollCallString,
            iqsyn21MemoriesMemoryName16
                RollCallString,
            iqsyn21LoggingVideoInputLogInput1Type
                INTEGER,
            iqsyn21LoggingVideoInputInput1Type
                RollCallString,
            iqsyn21LoggingVideoInputLogInput1Status
                INTEGER,
            iqsyn21LoggingVideoInputInput1Status
                RollCallString,
            iqsyn21LoggingVideoInputLogInput1Std
                INTEGER,
            iqsyn21LoggingVideoInputInput1Std
                RollCallString,
            iqsyn21LoggingVideoInputLogInput1Errors
                INTEGER,
            iqsyn21LoggingVideoInputInput1Errors
                RollCallString,
            iqsyn21LoggingVideoInputLogInput1ErrSecs
                INTEGER,
            iqsyn21LoggingVideoInputInput1ErrSecs
                RollCallString,
            iqsyn21LoggingVideoInputLogInput1ANCErr
                INTEGER,
            iqsyn21LoggingVideoInputInput1ANCErrors
                RollCallString,
            iqsyn21LoggingVideoInputLogInput1ANCErrSecs
                INTEGER,
            iqsyn21LoggingVideoInputInput1ANCErrSecs
                RollCallString,
            iqsyn21LoggingVideoInputLogInput2Type
                INTEGER,
            iqsyn21LoggingVideoInputInput2Type
                RollCallString,
            iqsyn21LoggingVideoInputLogInput2Status
                INTEGER,
            iqsyn21LoggingVideoInputInput2Status
                RollCallString,
            iqsyn21LoggingVideoInputLogInput2Std
                INTEGER,
            iqsyn21LoggingVideoInputInput2Std
                RollCallString,
            iqsyn21LoggingVideoInputLogInput2Errors
                INTEGER,
            iqsyn21LoggingVideoInputInput2Errors
                RollCallString,
            iqsyn21LoggingVideoInputLogInput2ErrSecs
                INTEGER,
            iqsyn21LoggingVideoInputInput2ErrSecs
                RollCallString,
            iqsyn21LoggingVideoInputLogInput2ANCErr
                INTEGER,
            iqsyn21LoggingVideoInputInput2ANCErrors
                RollCallString,
            iqsyn21LoggingVideoInputLogInput2ANCErrSecs
                INTEGER,
            iqsyn21LoggingVideoInputInput2ANCErrSecs
                RollCallString,
            iqsyn21LoggingRefOutputLogOutputState
                INTEGER,
            iqsyn21LoggingRefOutputOutputState
                RollCallString,
            iqsyn21LoggingRefOutputLogOutputType
                INTEGER,
            iqsyn21LoggingRefOutputOutputType
                RollCallString,
            iqsyn21LoggingRefOutputLogOutputStandard
                INTEGER,
            iqsyn21LoggingRefOutputOutputStandard
                RollCallString,
            iqsyn21LoggingVideoOutLoggingLogoutputANCstate
                INTEGER,
            iqsyn21LoggingVideoOutLoggingOutputANCstate
                RollCallString,
            iqsyn21LoggingRefOutputLogOutputSource
                INTEGER,
            iqsyn21LoggingRefOutputOutputSource
                RollCallString,
            iqsyn21LoggingIn1AudStateLogInp1Emb1stat
                INTEGER,
            iqsyn21LoggingIn1AudStateInp1Emb1state
                RollCallString,
            iqsyn21LoggingIn1AudStateLogInp1Emb2stat
                INTEGER,
            iqsyn21LoggingIn1AudStateInp1Emb2state
                RollCallString,
            iqsyn21LoggingIn1AudStateLogInp1Emb3stat
                INTEGER,
            iqsyn21LoggingIn1AudStateInp1Emb3state
                RollCallString,
            iqsyn21LoggingIn1AudStateLogInp1Emb4stat
                INTEGER,
            iqsyn21LoggingIn1AudStateInp1Emb4state
                RollCallString,
            iqsyn21LoggingIn1AudStateLogInp1Emb5stat
                INTEGER,
            iqsyn21LoggingIn1AudStateInp1Emb5state
                RollCallString,
            iqsyn21LoggingIn1AudStateLogInp1Emb6stat
                INTEGER,
            iqsyn21LoggingIn1AudStateInp1Emb6state
                RollCallString,
            iqsyn21LoggingIn1AudStateLogInp1Emb7stat
                INTEGER,
            iqsyn21LoggingIn1AudStateInp1Emb7state
                RollCallString,
            iqsyn21LoggingIn1AudStateLogInp1Emb8stat
                INTEGER,
            iqsyn21LoggingIn1AudStateInp1Emb8state
                RollCallString,
            iqsyn21LoggingIn1AudTypeLogInp1Emb1type
                INTEGER,
            iqsyn21LoggingIn1AudTypeInp1Emb1type
                RollCallString,
            iqsyn21LoggingIn1AudTypeLogInp1Emb2type
                INTEGER,
            iqsyn21LoggingIn1AudTypeInp1Emb2type
                RollCallString,
            iqsyn21LoggingIn1AudTypeLogInp1Emb3type
                INTEGER,
            iqsyn21LoggingIn1AudTypeInp1Emb3type
                RollCallString,
            iqsyn21LoggingIn1AudTypeLogInp1Emb4type
                INTEGER,
            iqsyn21LoggingIn1AudTypeInp1Emb4type
                RollCallString,
            iqsyn21LoggingIn1AudTypeLogInp1Emb5type
                INTEGER,
            iqsyn21LoggingIn1AudTypeInp1Emb5type
                RollCallString,
            iqsyn21LoggingIn1AudTypeLogInp1Emb6type
                INTEGER,
            iqsyn21LoggingIn1AudTypeInp1Emb6type
                RollCallString,
            iqsyn21LoggingIn1AudTypeLogInp1Emb7type
                INTEGER,
            iqsyn21LoggingIn1AudTypeInp1Emb7type
                RollCallString,
            iqsyn21LoggingIn1AudTypeLogInp1Emb8type
                INTEGER,
            iqsyn21LoggingIn1AudTypeInp1Emb8type
                RollCallString,
            iqsyn21LoggingIn2AudStateLogInp2Emb1stat
                INTEGER,
            iqsyn21LoggingIn2AudStateInp2Emb1state
                RollCallString,
            iqsyn21LoggingIn2AudStateLogInp2Emb2stat
                INTEGER,
            iqsyn21LoggingIn2AudStateInp2Emb2state
                RollCallString,
            iqsyn21LoggingIn2AudStateLogInp2Emb3stat
                INTEGER,
            iqsyn21LoggingIn2AudStateInp2Emb3state
                RollCallString,
            iqsyn21LoggingIn2AudStateLogInp2Emb4stat
                INTEGER,
            iqsyn21LoggingIn2AudStateInp2Emb4state
                RollCallString,
            iqsyn21LoggingIn2AudStateLogInp2Emb5stat
                INTEGER,
            iqsyn21LoggingIn2AudStateInp2Emb5state
                RollCallString,
            iqsyn21LoggingIn2AudStateLogInp2Emb6stat
                INTEGER,
            iqsyn21LoggingIn2AudStateInp2Emb6state
                RollCallString,
            iqsyn21LoggingIn2AudStateLogInp2Emb7stat
                INTEGER,
            iqsyn21LoggingIn2AudStateInp2Emb7state
                RollCallString,
            iqsyn21LoggingIn2AudStateLogInp2Emb8stat
                INTEGER,
            iqsyn21LoggingIn2AudStateInp2Emb8state
                RollCallString,
            iqsyn21LoggingIn1AudTypeLogInp2Emb1type
                INTEGER,
            iqsyn21LoggingIn1AudTypeInp2Emb1type
                RollCallString,
            iqsyn21LoggingIn1AudTypeLogInp2Emb2type
                INTEGER,
            iqsyn21LoggingIn1AudTypeInp2Emb2type
                RollCallString,
            iqsyn21LoggingIn1AudTypeLogInp2Emb3type
                INTEGER,
            iqsyn21LoggingIn1AudTypeInp2Emb3type
                RollCallString,
            iqsyn21LoggingIn1AudTypeLogInp2Emb4type
                INTEGER,
            iqsyn21LoggingIn1AudTypeInp2Emb4type
                RollCallString,
            iqsyn21LoggingIn1AudTypeLogInp2Emb5type
                INTEGER,
            iqsyn21LoggingIn1AudTypeInp2Emb5type
                RollCallString,
            iqsyn21LoggingIn1AudTypeLogInp2Emb6type
                INTEGER,
            iqsyn21LoggingIn1AudTypeInp2Emb6type
                RollCallString,
            iqsyn21LoggingIn1AudTypeLogInp2Emb7type
                INTEGER,
            iqsyn21LoggingIn1AudTypeInp2Emb7type
                RollCallString,
            iqsyn21LoggingIn1AudTypeLogInp2Emb8type
                INTEGER,
            iqsyn21LoggingIn1AudTypeInp2Emb8type
                RollCallString,
            iqsyn21LoggingOPAudStateLogOutEmb1state
                INTEGER,
            iqsyn21LoggingOPAudStateOutEmb1state
                RollCallString,
            iqsyn21LoggingOPAudStateLogOutEmb2state
                INTEGER,
            iqsyn21LoggingOPAudStateOutEmb2state
                RollCallString,
            iqsyn21LoggingOPAudStateLogOutEmb3state
                INTEGER,
            iqsyn21LoggingOPAudStateOutEmb3state
                RollCallString,
            iqsyn21LoggingOPAudStateLogOutEmb4state
                INTEGER,
            iqsyn21LoggingOPAudStateOutEmb4state
                RollCallString,
            iqsyn21LoggingOPAudStateLogOutEmb5state
                INTEGER,
            iqsyn21LoggingOPAudStateOutEmb5state
                RollCallString,
            iqsyn21LoggingOPAudStateLogOutEmb6state
                INTEGER,
            iqsyn21LoggingOPAudStateOutEmb6state
                RollCallString,
            iqsyn21LoggingOPAudStateLogOutEmb7state
                INTEGER,
            iqsyn21LoggingOPAudStateOutEmb7state
                RollCallString,
            iqsyn21LoggingOPAudStateLogOutEmb8state
                INTEGER,
            iqsyn21LoggingOPAudStateOutEmb8state
                RollCallString,
            iqsyn21LoggingOPAudTypeLogOutEmb1type
                INTEGER,
            iqsyn21LoggingOPAudTypeOutEmb1type
                RollCallString,
            iqsyn21LoggingOPAudTypeLogOutEmb2type
                INTEGER,
            iqsyn21LoggingOPAudTypeOutEmb2type
                RollCallString,
            iqsyn21LoggingOPAudTypeLogOutEmb3type
                INTEGER,
            iqsyn21LoggingOPAudTypeOutEmb3type
                RollCallString,
            iqsyn21LoggingOPAudTypeLogOutEmb4type
                INTEGER,
            iqsyn21LoggingOPAudTypeOutEmb4type
                RollCallString,
            iqsyn21LoggingOPAudTypeLogOutEmb5type
                INTEGER,
            iqsyn21LoggingOPAudTypeOutEmb5type
                RollCallString,
            iqsyn21LoggingOPAudTypeLogOutEmb6type
                INTEGER,
            iqsyn21LoggingOPAudTypeOutEmb6type
                RollCallString,
            iqsyn21LoggingOPAudTypeLogOutEmb7type
                INTEGER,
            iqsyn21LoggingOPAudTypeOutEmb7type
                RollCallString,
            iqsyn21LoggingOPAudTypeLogOutEmb8type
                INTEGER,
            iqsyn21LoggingOPAudTypeOutEmb8type
                RollCallString,
            iqsyn21LoggingOPAudLevelLogOutEmb1LLev
                INTEGER,
            iqsyn21LoggingOPAudLevelOutEmb1LLevel
                RollCallString,
            iqsyn21LoggingOPAudLevelLogOutEmb1RLev
                INTEGER,
            iqsyn21LoggingOPAudLevelOutEmb1RLevel
                RollCallString,
            iqsyn21LoggingOPAudLevelLogOutEmb2LLev
                INTEGER,
            iqsyn21LoggingOPAudLevelOutEmb2LLevel
                RollCallString,
            iqsyn21LoggingOPAudLevelLogOutEmb2RLev
                INTEGER,
            iqsyn21LoggingOPAudLevelOutEmb2RLevel
                RollCallString,
            iqsyn21LoggingOPAudLevelLogOutEmb3LLev
                INTEGER,
            iqsyn21LoggingOPAudLevelOutEmb3LLevel
                RollCallString,
            iqsyn21LoggingOPAudLevelLogOutEmb3RLev
                INTEGER,
            iqsyn21LoggingOPAudLevelOutEmb3RLevel
                RollCallString,
            iqsyn21LoggingOPAudLevelLogOutEmb4LLev
                INTEGER,
            iqsyn21LoggingOPAudLevelOutEmb4LLevel
                RollCallString,
            iqsyn21LoggingOPAudLevelLogOutEmb4RLev
                INTEGER,
            iqsyn21LoggingOPAudLevelOutEmb4RLevel
                RollCallString,
            iqsyn21LoggingOPAudLevelLogOutEmb5LLev
                INTEGER,
            iqsyn21LoggingOPAudLevelOutEmb5LLevel
                RollCallString,
            iqsyn21LoggingOPAudLevelLogOutEmb5RLev
                INTEGER,
            iqsyn21LoggingOPAudLevelOutEmb5RLevel
                RollCallString,
            iqsyn21LoggingOPAudLevelLogOutEmb6LLev
                INTEGER,
            iqsyn21LoggingOPAudLevelOutEmb6LLevel
                RollCallString,
            iqsyn21LoggingOPAudLevelLogOutEmb6RLev
                INTEGER,
            iqsyn21LoggingOPAudLevelOutEmb6RLevel
                RollCallString,
            iqsyn21LoggingOPAudLevelLogOutEmb7LLev
                INTEGER,
            iqsyn21LoggingOPAudLevelOutEmb7LLevel
                RollCallString,
            iqsyn21LoggingOPAudLevelLogOutEmb7RLev
                INTEGER,
            iqsyn21LoggingOPAudLevelOutEmb7RLevel
                RollCallString,
            iqsyn21LoggingOPAudLevelLogOutEmb8LLev
                INTEGER,
            iqsyn21LoggingOPAudLevelOutEmb8LLevel
                RollCallString,
            iqsyn21LoggingOPAudLevelLogOutEmb8RLev
                INTEGER,
            iqsyn21LoggingOPAudLevelOutEmb8RLevel
                RollCallString,
            iqsyn21LoggingOPDolbyELoggingLogEmbDolbyE1
                INTEGER,
            iqsyn21LoggingOPDolbyELoggingEmbDolbyE1
                RollCallString,
            iqsyn21LoggingOPDolbyELoggingLogEmbDolbyE2
                INTEGER,
            iqsyn21LoggingOPDolbyELoggingEmbDolbyE2
                RollCallString,
            iqsyn21LoggingOPDolbyELoggingLogEmbDolbyE3
                INTEGER,
            iqsyn21LoggingOPDolbyELoggingEmbDolbyE3
                RollCallString,
            iqsyn21LoggingOPDolbyELoggingLogEmbDolbyE4
                INTEGER,
            iqsyn21LoggingOPDolbyELoggingEmbDolbyE4
                RollCallString,
            iqsyn21LoggingOPDolbyELoggingLogEmbDolbyE5
                INTEGER,
            iqsyn21LoggingOPDolbyELoggingEmbDolbyE5
                RollCallString,
            iqsyn21LoggingOPDolbyELoggingLogEmbDolbyE6
                INTEGER,
            iqsyn21LoggingOPDolbyELoggingEmbDolbyE6
                RollCallString,
            iqsyn21LoggingOPDolbyELoggingLogEmbDolbyE7
                INTEGER,
            iqsyn21LoggingOPDolbyELoggingEmbDolbyE7
                RollCallString,
            iqsyn21LoggingOPDolbyELoggingLogEmbDolbyE8
                INTEGER,
            iqsyn21LoggingOPDolbyELoggingEmbDolbyE8
                RollCallString,
            iqsyn21LoggingMiscLogSerialNo
                INTEGER,
            iqsyn21LoggingMiscSerialNo
                RollCallString,
            iqsyn21LoggingMiscLogOSVersion
                INTEGER,
            iqsyn21LoggingMiscOSVersion
                RollCallString,
            iqsyn21LoggingMiscLogBuildNo
                INTEGER,
            iqsyn21LoggingMiscBuildNo
                RollCallString,
            iqsyn21LoggingMiscLogHardwareVer
                INTEGER,
            iqsyn21LoggingMiscHardwareVer
                RollCallString,
            iqsyn21LoggingMiscLogFirmwareVer
                INTEGER,
            iqsyn21LoggingMiscFirmwareVer
                RollCallString,
            iqsyn21LoggingMiscLogUpTime
                INTEGER,
            iqsyn21LoggingMiscUpTime
                RollCallString,
            iqsyn21LoggingRefOutputLogReferenceType
                INTEGER,
            iqsyn21LoggingRefOutputReferenceType
                RollCallString,
            iqsyn21LoggingRefOutputLogReferenceState
                INTEGER,
            iqsyn21LoggingRefOutputReferenceState
                RollCallString,
            iqsyn21LoggingRefOutputLogReferenceStand
                INTEGER,
            iqsyn21LoggingRefOutputReferenceStandard
                RollCallString,
            iqsyn21RollCallRollTrackDisableAll
                INTEGER,
            iqsyn21RollCallRollTrackIndex
                INTEGER,
            iqsyn21RollCallRollTrackSource
                INTEGER,
            iqsyn21RollCallRollTrackAddress
                RollCallString,
            iqsyn21RollCallRollTrackCommand
                RollCallString,
            iqsyn21RollCallRollTrackStatus
                RollCallString,
            iqsyn21RollCallRollTrackSending
                RollCallString,
            iqsyn21SetupProduct
                RollCallString,
            iqsyn21SetupRelease
                RollCallString,
            iqsyn21SetupBuild
                RollCallString,
            iqsyn21SetupKOS
                RollCallString,
            iqsyn21SetupSerial
                RollCallString,
            iqsyn21SetupFirmware
                RollCallString,
            iqsyn21SetupPCB
                RollCallString,
            iqsyn21SetupFactoryDefault
                INTEGER,
            iqsyn21SetupRestart
                INTEGER,
            iqsyn21MemoriesMemorySave
                INTEGER,
            iqsyn21SetupDisplay
                INTEGER,
            iqsyn21SetupSerialNumber
                RollCallString,
            iqsyn21SetupBoardID
                INTEGER,
            iqsyn21SetupSaveID
                INTEGER,
            iqsyn21EngineerPassword
                RollCallString,
            iqsyn21EngineerShowEngineer
                INTEGER,
            iqsyn21EngineerPageUndoChanges
                INTEGER,
            iqsyn21EngineerShowEngineer2
                INTEGER,
            iqsyn21EngineerShowEngineer3
                INTEGER
        }

    iqsyn21SlotIndex OBJECT-TYPE
        SYNTAX            Unsigned32
        MAX-ACCESS        not-accessible
        STATUS            current
        DESCRIPTION
                "The unique Index value for each slot.  Its value
                ranges between 1 and the value of slotNumber."
        ::= { iqsyn21CmdEntry 99999 }


    iqsyn21InputIPSelect OBJECT-TYPE
        SYNTAX            INTEGER {
                            valInput1(1),
                            valInput2(2),
                            valInputAnalog(2)
                            }
        MAX-ACCESS        read-write
        STATUS            current
        DESCRIPTION
                "CMNT: - Select video input
                 TYPE: - RadiobuttonList
                 PAGE: - Input
                    I/P Select  cmdID= 32930
                    Input 1  value= 1
                    Input 2  value= 2
                    Input Analog  value= 2  "
        ::= { iqsyn21CmdEntry 32930 }


    iqsyn21InputIPLoss OBJECT-TYPE
        SYNTAX            INTEGER {
                            valNoInput(0),
                            valInOutStdMismatch(1)
                            }
        MAX-ACCESS        read-write
        STATUS            current
        DESCRIPTION
                "CMNT: - Input loss on standard mismatch enable
                 TYPE: - RadiobuttonList
                 PAGE: - Input
                    I/P Loss  cmdID= 33030
                    No Input  value= 0
                    In/Out Std.Mismatch  value= 1  "
        ::= { iqsyn21CmdEntry 33030 }


    iqsyn21InputValidStandardsAllValid OBJECT-TYPE
        SYNTAX            INTEGER { noAction(0),valAllValid(1) }
        MAX-ACCESS        read-write
        STATUS            current
        DESCRIPTION
                "CMNT: - All input standards valid
                 TYPE: - Button
                 PAGE: - Input
                    All Valid  cmdID= 32900
                    value= 1  "
        ::= { iqsyn21CmdEntry 32900 }


    iqsyn21InputValidStandardsAllInvalid OBJECT-TYPE
        SYNTAX            INTEGER { noAction(0),valAllInvalid(1) }
        MAX-ACCESS        read-write
        STATUS            current
        DESCRIPTION
                "CMNT: - NO input standards valid
                 TYPE: - Button
                 PAGE: - Input
                    AllInvalid  cmdID= 32901
                    value= 1  "
        ::= { iqsyn21CmdEntry 32901 }


    iqsyn21InputValidStandards108023sF OBJECT-TYPE
        SYNTAX            INTEGER { disable(0), enable(1)  }
        MAX-ACCESS        read-write
        STATUS            current
        DESCRIPTION
                "CMNT: - Select valid input standards
                 TYPE: - Checkbox
                 PAGE: - Input
                    1080/23sF  cmdID= 32916  "
        ::= { iqsyn21CmdEntry 32916 }


    iqsyn21InputValidStandards108023p OBJECT-TYPE
        SYNTAX            INTEGER { disable(0), enable(1)  }
        MAX-ACCESS        read-write
        STATUS            current
        DESCRIPTION
                "CMNT: - Select valid input standards
                 TYPE: - Checkbox
                 PAGE: - Input
                    1080/23p  cmdID= 32915  "
        ::= { iqsyn21CmdEntry 32915 }


    iqsyn21InputValidStandards108024sF OBJECT-TYPE
        SYNTAX            INTEGER { disable(0), enable(1)  }
        MAX-ACCESS        read-write
        STATUS            current
        DESCRIPTION
                "CMNT: - Select valid input standards
                 TYPE: - Checkbox
                 PAGE: - Input
                    1080/24sF  cmdID= 32917  "
        ::= { iqsyn21CmdEntry 32917 }


    iqsyn21InputValidStandards108024p OBJECT-TYPE
        SYNTAX            INTEGER { disable(0), enable(1)  }
        MAX-ACCESS        read-write
        STATUS            current
        DESCRIPTION
                "CMNT: - Select valid input standards
                 TYPE: - Checkbox
                 PAGE: - Input
                    1080/24p  cmdID= 32914  "
        ::= { iqsyn21CmdEntry 32914 }


    iqsyn21InputValidStandards108025i OBJECT-TYPE
        SYNTAX            INTEGER { disable(0), enable(1)  }
        MAX-ACCESS        read-write
        STATUS            current
        DESCRIPTION
                "CMNT: - Select valid input standards
                 TYPE: - Checkbox
                 PAGE: - Input
                    1080/25i  cmdID= 32910  "
        ::= { iqsyn21CmdEntry 32910 }


    iqsyn21InputValidStandards108025p OBJECT-TYPE
        SYNTAX            INTEGER { disable(0), enable(1)  }
        MAX-ACCESS        read-write
        STATUS            current
        DESCRIPTION
                "CMNT: - Select valid input standards
                 TYPE: - Checkbox
                 PAGE: - Input
                    1080/25p  cmdID= 32911  "
        ::= { iqsyn21CmdEntry 32911 }


    iqsyn21InputValidStandards103529i OBJECT-TYPE
        SYNTAX            INTEGER { disable(0), enable(1)  }
        MAX-ACCESS        read-write
        STATUS            current
        DESCRIPTION
                "CMNT: - Select valid input standards
                 TYPE: - Checkbox
                 PAGE: - Input
                    1035/29i  cmdID= 32921  "
        ::= { iqsyn21CmdEntry 32921 }


    iqsyn21InputValidStandards108029i OBJECT-TYPE
        SYNTAX            INTEGER { disable(0), enable(1)  }
        MAX-ACCESS        read-write
        STATUS            current
        DESCRIPTION
                "CMNT: - Select valid input standards
                 TYPE: - Checkbox
                 PAGE: - Input
                    1080/29i  cmdID= 32919  "
        ::= { iqsyn21CmdEntry 32919 }


    iqsyn21InputValidStandards108029p OBJECT-TYPE
        SYNTAX            INTEGER { disable(0), enable(1)  }
        MAX-ACCESS        read-write
        STATUS            current
        DESCRIPTION
                "CMNT: - Select valid input standards
                 TYPE: - Checkbox
                 PAGE: - Input
                    1080/29p  cmdID= 32918  "
        ::= { iqsyn21CmdEntry 32918 }


    iqsyn21InputValidStandards103530i OBJECT-TYPE
        SYNTAX            INTEGER { disable(0), enable(1)  }
        MAX-ACCESS        read-write
        STATUS            current
        DESCRIPTION
                "CMNT: - Select valid input standards
                 TYPE: - Checkbox
                 PAGE: - Input
                    1035/30i  cmdID= 32920  "
        ::= { iqsyn21CmdEntry 32920 }


    iqsyn21InputValidStandards108030i OBJECT-TYPE
        SYNTAX            INTEGER { disable(0), enable(1)  }
        MAX-ACCESS        read-write
        STATUS            current
        DESCRIPTION
                "CMNT: - Select valid input standards
                 TYPE: - Checkbox
                 PAGE: - Input
                    1080/30i  cmdID= 32912  "
        ::= { iqsyn21CmdEntry 32912 }


    iqsyn21InputValidStandards108030p OBJECT-TYPE
        SYNTAX            INTEGER { disable(0), enable(1)  }
        MAX-ACCESS        read-write
        STATUS            current
        DESCRIPTION
                "CMNT: - Select valid input standards
                 TYPE: - Checkbox
                 PAGE: - Input
                    1080/30p  cmdID= 32913  "
        ::= { iqsyn21CmdEntry 32913 }


    iqsyn21InputValidStandards72050p OBJECT-TYPE
        SYNTAX            INTEGER { disable(0), enable(1)  }
        MAX-ACCESS        read-write
        STATUS            current
        DESCRIPTION
                "CMNT: - Select valid input standards
                 TYPE: - Checkbox
                 PAGE: - Input
                    720/50p  cmdID= 32922  "
        ::= { iqsyn21CmdEntry 32922 }


    iqsyn21InputValidStandards72059p OBJECT-TYPE
        SYNTAX            INTEGER { disable(0), enable(1)  }
        MAX-ACCESS        read-write
        STATUS            current
        DESCRIPTION
                "CMNT: - Select valid input standards
                 TYPE: - Checkbox
                 PAGE: - Input
                    720/59p  cmdID= 32924  "
        ::= { iqsyn21CmdEntry 32924 }


    iqsyn21InputValidStandards72060p OBJECT-TYPE
        SYNTAX            INTEGER { disable(0), enable(1)  }
        MAX-ACCESS        read-write
        STATUS            current
        DESCRIPTION
                "CMNT: - Select valid input standards
                 TYPE: - Checkbox
                 PAGE: - Input
                    720/60p  cmdID= 32923  "
        ::= { iqsyn21CmdEntry 32923 }


    iqsyn21InputValidStandards62525i OBJECT-TYPE
        SYNTAX            INTEGER { disable(0), enable(1)  }
        MAX-ACCESS        read-write
        STATUS            current
        DESCRIPTION
                "CMNT: - Select valid input standards
                 TYPE: - Checkbox
                 PAGE: - Input
                    625/25i  cmdID= 32925  "
        ::= { iqsyn21CmdEntry 32925 }


    iqsyn21InputValidStandards52529i OBJECT-TYPE
        SYNTAX            INTEGER { disable(0), enable(1)  }
        MAX-ACCESS        read-write
        STATUS            current
        DESCRIPTION
                "CMNT: - Select valid input standards
                 TYPE: - Checkbox
                 PAGE: - Input
                    525/29i  cmdID= 32926  "
        ::= { iqsyn21CmdEntry 32926 }


    iqsyn21InputAgileVLock OBJECT-TYPE
        SYNTAX            INTEGER { disable(0), enable(1)  }
        MAX-ACCESS        read-write
        STATUS            current
        DESCRIPTION
                "CMNT: - Select Agile V-Lock for an input
                 TYPE: - Checkbox
                 PAGE: - Input
                    Agile V-Lock  cmdID= 32932  "
        ::= { iqsyn21CmdEntry 32932 }


    iqsyn21InputErrorsCRCErrs OBJECT-TYPE
        SYNTAX            RollCallString
        MAX-ACCESS        read-only
        STATUS            current
        DESCRIPTION
                "CMNT: - 
                 TYPE: - Display
                 PAGE: - Input
                    CRC Errs  cmdID= 33050  "
        ::= { iqsyn21CmdEntry 33050 }


    iqsyn21InputErrorsCRCErrSec OBJECT-TYPE
        SYNTAX            RollCallString
        MAX-ACCESS        read-only
        STATUS            current
        DESCRIPTION
                "CMNT: - 
                 TYPE: - Display
                 PAGE: - Input
                    CRC ErrSec  cmdID= 33051  "
        ::= { iqsyn21CmdEntry 33051 }


    iqsyn21InputErrorsANCErrs OBJECT-TYPE
        SYNTAX            RollCallString
        MAX-ACCESS        read-only
        STATUS            current
        DESCRIPTION
                "CMNT: - 
                 TYPE: - Display
                 PAGE: - Input
                    ANC Errs  cmdID= 33053  "
        ::= { iqsyn21CmdEntry 33053 }


    iqsyn21InputErrorsANCErrSec OBJECT-TYPE
        SYNTAX            RollCallString
        MAX-ACCESS        read-only
        STATUS            current
        DESCRIPTION
                "CMNT: - 
                 TYPE: - Display
                 PAGE: - Input
                    ANC ErrSec  cmdID= 33054  "
        ::= { iqsyn21CmdEntry 33054 }


    iqsyn21InputErrorsResetSec OBJECT-TYPE
        SYNTAX            RollCallString
        MAX-ACCESS        read-only
        STATUS            current
        DESCRIPTION
                "CMNT: - 
                 TYPE: - Display
                 PAGE: - Input
                    ResetSec  cmdID= 33055  "
        ::= { iqsyn21CmdEntry 33055 }


    iqsyn21InputErrorsErrorReset OBJECT-TYPE
        SYNTAX            INTEGER { noAction(0),valErrorReset(1) }
        MAX-ACCESS        read-write
        STATUS            current
        DESCRIPTION
                "CMNT: - 
                 TYPE: - Button
                 PAGE: - Input
                    Error Reset  cmdID= 33052
                    value= 1  "
        ::= { iqsyn21CmdEntry 33052 }


    iqsyn21OutputOPStd OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select output standard
                 TYPE: - RadiobuttonList
                 PAGE: - Output
                    O/P Std.  cmdID= 33010
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn21CmdEntry 33010 }


    iqsyn21OutputVideoProcMasterGain OBJECT-TYPE
        SYNTAX            INTEGER
        MAX-ACCESS        read-write
        STATUS            current
        DESCRIPTION
                "CMNT: - Video Master Gain
                 TYPE: - Number
                 PAGE: - Output
                    Master Gain  cmdID= 33000
                    min= -600  max= 600  step= 10  format= %0.1f dB  div_scale= 100  preset= 0
                    Min = -6.0 dB  Max = 6.0 dB  Step = 0.1 dB  Preset = 0.0 dB  "
        ::= { iqsyn21CmdEntry 33000 }


    iqsyn21OutputVideoProcYGain OBJECT-TYPE
        SYNTAX            INTEGER
        MAX-ACCESS        read-write
        STATUS            current
        DESCRIPTION
                "CMNT: - Video Luminance gain
                 TYPE: - Number
                 PAGE: - Output
                    Y Gain  cmdID= 33001
                    min= -600  max= 600  step= 10  format= %0.1f dB  div_scale= 100  preset= 0
                    Min = -6.0 dB  Max = 6.0 dB  Step = 0.1 dB  Preset = 0.0 dB  "
        ::= { iqsyn21CmdEntry 33001 }


    iqsyn21OutputVideoProcCGain OBJECT-TYPE
        SYNTAX            INTEGER
        MAX-ACCESS        read-write
        STATUS            current
        DESCRIPTION
                "CMNT: - Video CbCr Gain
                 TYPE: - Number
                 PAGE: - Output
                    C Gain  cmdID= 33003
                    min= -600  max= 600  step= 10  format= %0.1f dB  div_scale= 100  preset= 0
                    Min = -6.0 dB  Max = 6.0 dB  Step = 0.1 dB  Preset = 0.0 dB  "
        ::= { iqsyn21CmdEntry 33003 }


    iqsyn21OutputVideoProcBlackLevel OBJECT-TYPE
        SYNTAX            INTEGER
        MAX-ACCESS        read-write
        STATUS            current
        DESCRIPTION
                "CMNT: - Video Black Level
                 TYPE: - Number
                 PAGE: - Output
                    Black Level  cmdID= 33002
                    min= -200  max= 200  step= 1  format= %0.0f mV  div_scale= 1  preset= 0
                    Min = -200 mV  Max = 200 mV  Step = 1 mV  Preset = 0 mV  "
        ::= { iqsyn21CmdEntry 33002 }


    iqsyn21OutputDefaultOutput OBJECT-TYPE
        SYNTAX            INTEGER {
                            valFreezeFrame(1),
                            valFreezeField(5),
                            valBlack(2),
                            valInput(3),
                            valOutPattern(4)
                            }
        MAX-ACCESS        read-write
        STATUS            current
        DESCRIPTION
                "CMNT: - What to do on input loss
                 TYPE: - RadiobuttonList
                 PAGE: - Output
                    Default Output  cmdID= 33031
                    Freeze Frame  value= 1
                    Freeze Field  value= 5
                    Black  value= 2
                    Input  value= 3
                    Out Pattern  value= 4  "
        ::= { iqsyn21CmdEntry 33031 }


    iqsyn21OutputOutputStandard OBJECT-TYPE
        SYNTAX            INTEGER {
                            valManualSelection(0),
                            valFollowsInputStd(1),
                            valFollowsRefStd(2)
                            }
        MAX-ACCESS        read-write
        STATUS            current
        DESCRIPTION
                "CMNT: - Output follows std: Man/Input/Ext.Reference
                 TYPE: - RadiobuttonList
                 PAGE: - Output
                    Output Standard  cmdID= 33011
                    Manual Selection  value= 0
                    Follows Input Std.  value= 1
                    Follows Ref. Std.  value= 2  "
        ::= { iqsyn21CmdEntry 33011 }


    iqsyn21OutputDefaultOPStd OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - 
                 TYPE: - RadiobuttonList
                 PAGE: - Output
                    Default O/P Std.  cmdID= 33012
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn21CmdEntry 33012 }


    iqsyn21AudioDelayADelaySourcesManual OBJECT-TYPE
        SYNTAX            INTEGER { disable(0), enable(1)  }
        MAX-ACCESS        read-write
        STATUS            current
        DESCRIPTION
                "CMNT: - Use manual delay select
                 TYPE: - Checkbox
                 PAGE: - Audio Delay-A
                    Manual  cmdID= 38041  "
        ::= { iqsyn21CmdEntry 38041 }


    iqsyn21AudioDelayADelaySourcesGPIPWM OBJECT-TYPE
        SYNTAX            INTEGER { disable(0), enable(1)  }
        MAX-ACCESS        read-write
        STATUS            current
        DESCRIPTION
                "CMNT: - Use GPIO PWM for delay
                 TYPE: - Checkbox
                 PAGE: - Audio Delay-A
                    GPI PWM  cmdID= 38042  "
        ::= { iqsyn21CmdEntry 38042 }


    iqsyn21AudioDelayADelaySourcesRollTrack14 OBJECT-TYPE
        SYNTAX            INTEGER { disable(0), enable(1)  }
        MAX-ACCESS        read-write
        STATUS            current
        DESCRIPTION
                "CMNT: - Use rolltrack14 data for delay
                 TYPE: - Checkbox
                 PAGE: - Audio Delay-A
                    RollTrack14  cmdID= 38044  "
        ::= { iqsyn21CmdEntry 38044 }


    iqsyn21AudioDelayADelaySourcesRollTrack15 OBJECT-TYPE
        SYNTAX            INTEGER { disable(0), enable(1)  }
        MAX-ACCESS        read-write
        STATUS            current
        DESCRIPTION
                "CMNT: - Use rolltrack15 data for delay
                 TYPE: - Checkbox
                 PAGE: - Audio Delay-A
                    RollTrack15  cmdID= 38045  "
        ::= { iqsyn21CmdEntry 38045 }


    iqsyn21AudioDelayADelaySourcesRollTrack16 OBJECT-TYPE
        SYNTAX            INTEGER { disable(0), enable(1)  }
        MAX-ACCESS        read-write
        STATUS            current
        DESCRIPTION
                "CMNT: - Use rolltrack16 data for delay
                 TYPE: - Checkbox
                 PAGE: - Audio Delay-A
                    RollTrack16  cmdID= 38046  "
        ::= { iqsyn21CmdEntry 38046 }


    iqsyn21AudioDelayADelaySourcesRollTrack17 OBJECT-TYPE
        SYNTAX            INTEGER { disable(0), enable(1)  }
        MAX-ACCESS        read-write
        STATUS            current
        DESCRIPTION
                "CMNT: - Use rolltrack17 data for delay
                 TYPE: - Checkbox
                 PAGE: - Audio Delay-A
                    RollTrack17  cmdID= 38047  "
        ::= { iqsyn21CmdEntry 38047 }


    iqsyn21AudioDelayAAdjustManualDelay OBJECT-TYPE
        SYNTAX            INTEGER
        MAX-ACCESS        read-write
        STATUS            current
        DESCRIPTION
                "CMNT: - Set Manual delay
                 TYPE: - Number
                 PAGE: - Aud.Delays
                    Adjust Coarse Delay  cmdID= 38043
                    min= -4000  max= 200000  step= 25  format= %0.2f ms  div_scale= 100  preset= 0
                    Min = -40.00 ms  Max = 2000.00 ms  Step = 0.25 ms  Preset = 0.00 ms  "
        ::= { iqsyn21CmdEntry 38043 }


    iqsyn21AudioDelayACurrentAudioDelay OBJECT-TYPE
        SYNTAX            RollCallString
        MAX-ACCESS        read-only
        STATUS            current
        DESCRIPTION
                "CMNT: - Current Value for Audio Delay A
                 TYPE: - Display
                 PAGE: - Aud.Delays
                    Current Audio Delay  cmdID= 38048  "
        ::= { iqsyn21CmdEntry 38048 }


    iqsyn21AudioDelayBDelaySourcesManual OBJECT-TYPE
        SYNTAX            INTEGER { disable(0), enable(1)  }
        MAX-ACCESS        read-write
        STATUS            current
        DESCRIPTION
                "CMNT: - Use manual delay select
                 TYPE: - Checkbox
                 PAGE: - Audio Delay-B
                    Manual  cmdID= 38061  "
        ::= { iqsyn21CmdEntry 38061 }


    iqsyn21AudioDelayBDelaySourcesGPIPWM OBJECT-TYPE
        SYNTAX            INTEGER { disable(0), enable(1)  }
        MAX-ACCESS        read-write
        STATUS            current
        DESCRIPTION
                "CMNT: - Use GPIO PWM for delay
                 TYPE: - Checkbox
                 PAGE: - Audio Delay-B
                    GPI PWM  cmdID= 38062  "
        ::= { iqsyn21CmdEntry 38062 }


    iqsyn21AudioDelayBDelaySourcesRollTrack14 OBJECT-TYPE
        SYNTAX            INTEGER { disable(0), enable(1)  }
        MAX-ACCESS        read-write
        STATUS            current
        DESCRIPTION
                "CMNT: - Use rolltrack14 data for delay
                 TYPE: - Checkbox
                 PAGE: - Audio Delay-B
                    RollTrack14  cmdID= 38064  "
        ::= { iqsyn21CmdEntry 38064 }


    iqsyn21AudioDelayBDelaySourcesRollTrack15 OBJECT-TYPE
        SYNTAX            INTEGER { disable(0), enable(1)  }
        MAX-ACCESS        read-write
        STATUS            current
        DESCRIPTION
                "CMNT: - Use rolltrack15 data for delay
                 TYPE: - Checkbox
                 PAGE: - Audio Delay-B
                    RollTrack15  cmdID= 38065  "
        ::= { iqsyn21CmdEntry 38065 }


    iqsyn21AudioDelayBDelaySourcesRollTrack16 OBJECT-TYPE
        SYNTAX            INTEGER { disable(0), enable(1)  }
        MAX-ACCESS        read-write
        STATUS            current
        DESCRIPTION
                "CMNT: - Use rolltrack16 data for delay
                 TYPE: - Checkbox
                 PAGE: - Audio Delay-B
                    RollTrack16  cmdID= 38066  "
        ::= { iqsyn21CmdEntry 38066 }


    iqsyn21AudioDelayBDelaySourcesRollTrack17 OBJECT-TYPE
        SYNTAX            INTEGER { disable(0), enable(1)  }
        MAX-ACCESS        read-write
        STATUS            current
        DESCRIPTION
                "CMNT: - Use rolltrack17 data for delay
                 TYPE: - Checkbox
                 PAGE: - Audio Delay-B
                    RollTrack17  cmdID= 38067  "
        ::= { iqsyn21CmdEntry 38067 }


    iqsyn21AudioDelayBAdjustManualDelay OBJECT-TYPE
        SYNTAX            INTEGER
        MAX-ACCESS        read-write
        STATUS            current
        DESCRIPTION
                "CMNT: - Set Manual delay
                 TYPE: - Number
                 PAGE: - Aud.Delays
                    Adjust Coarse Delay  cmdID= 38063
                    min= -4000  max= 200000  step= 25  format= %0.2f ms  div_scale= 100  preset= 0
                    Min = -40.00 ms  Max = 2000.00 ms  Step = 0.25 ms  Preset = 0.00 ms  "
        ::= { iqsyn21CmdEntry 38063 }


    iqsyn21AudioDelayBCurrentAudioDelay OBJECT-TYPE
        SYNTAX            RollCallString
        MAX-ACCESS        read-only
        STATUS            current
        DESCRIPTION
                "CMNT: - Current Value for Audio Delay B
                 TYPE: - Display
                 PAGE: - Aud.Delays
                    Current Audio Delay  cmdID= 38068  "
        ::= { iqsyn21CmdEntry 38068 }


    iqsyn21AudioDelaySelectDelay1 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-1  cmdID= 38080
                    Min  value= 0
                    Delay A  value= 1
                    Delay B  value= 2  "
        ::= { iqsyn21CmdEntry 38080 }


    iqsyn21AudDelaysEMBDelaySelectInternal1 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-1  cmdID= 38100  "
        ::= { iqsyn21CmdEntry 38100 }


    iqsyn21AudDelaysEMBDelaySelectAutoDolbyEPhaseBus1 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38110  cmdID= 38110  "
        ::= { iqsyn21CmdEntry 38110 }


    iqsyn21AudDelaysEMBDelaySelectDelayLimitBus1 OBJECT-TYPE
        SYNTAX            RollCallString
        MAX-ACCESS        read-only
        STATUS            current
        DESCRIPTION
                "CMNT: - 
                 TYPE: - Display
                 PAGE: - Aud.Delays
                    Delay Limit38308  cmdID= 38308  "
        ::= { iqsyn21CmdEntry 38308 }


    iqsyn21AudDelaysEMBDelaySelectEMB1FineDelay OBJECT-TYPE
        SYNTAX            INTEGER
        MAX-ACCESS        read-write
        STATUS            current
        DESCRIPTION
                "CMNT: - Set Manual delay
                 TYPE: - Number
                 PAGE: - Aud.Delays
                    EMB 1 Fine Delay  cmdID= 38138
                    min= -2450  max= 2450  step= 52  format= %0.3f ms  div_scale= 10000  preset= 0
                    Min = -0.245 ms  Max = 0.245 ms  Step = 0.005 ms  Preset = 0.000 ms  "
        ::= { iqsyn21CmdEntry 38138 }


    iqsyn21AudioDelaySelectDelay2 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-2  cmdID= 38081
                    Min  value= 0
                    Delay A  value= 1
                    Delay B  value= 2  "
        ::= { iqsyn21CmdEntry 38081 }


    iqsyn21AudDelaysEMBDelaySelectInternal2 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-2  cmdID= 38101  "
        ::= { iqsyn21CmdEntry 38101 }


    iqsyn21AudDelaysEMBDelaySelectAutoDolbyEPhaseBus2 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38111  cmdID= 38111  "
        ::= { iqsyn21CmdEntry 38111 }


    iqsyn21AudDelaysEMBDelaySelectDelayLimitBus2 OBJECT-TYPE
        SYNTAX            RollCallString
        MAX-ACCESS        read-only
        STATUS            current
        DESCRIPTION
                "CMNT: - 
                 TYPE: - Display
                 PAGE: - Aud.Delays
                    Delay Limit38309  cmdID= 38309  "
        ::= { iqsyn21CmdEntry 38309 }


    iqsyn21AudDelaysEMBDelaySelectEMB2FineDelay OBJECT-TYPE
        SYNTAX            INTEGER
        MAX-ACCESS        read-write
        STATUS            current
        DESCRIPTION
                "CMNT: - Set Manual delay
                 TYPE: - Number
                 PAGE: - Aud.Delays
                    EMB 2 Fine Delay  cmdID= 38139
                    min= -2450  max= 2450  step= 52  format= %0.3f ms  div_scale= 10000  preset= 0
                    Min = -0.245 ms  Max = 0.245 ms  Step = 0.005 ms  Preset = 0.000 ms  "
        ::= { iqsyn21CmdEntry 38139 }


    iqsyn21AudioDelaySelectDelay3 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-3  cmdID= 38082
                    Min  value= 0
                    Delay A  value= 1
                    Delay B  value= 2  "
        ::= { iqsyn21CmdEntry 38082 }


    iqsyn21AudDelaysEMBDelaySelectInternal3 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-3  cmdID= 38102  "
        ::= { iqsyn21CmdEntry 38102 }


    iqsyn21AudDelaysEMBDelaySelectAutoDolbyEPhaseBus3 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38112  cmdID= 38112  "
        ::= { iqsyn21CmdEntry 38112 }


    iqsyn21AudDelaysEMBDelaySelectDelayLimitBus3 OBJECT-TYPE
        SYNTAX            RollCallString
        MAX-ACCESS        read-only
        STATUS            current
        DESCRIPTION
                "CMNT: - 
                 TYPE: - Display
                 PAGE: - Aud.Delays
                    Delay Limit38310  cmdID= 38310  "
        ::= { iqsyn21CmdEntry 38310 }


    iqsyn21AudDelaysEMBDelaySelectEMB3FineDelay OBJECT-TYPE
        SYNTAX            INTEGER
        MAX-ACCESS        read-write
        STATUS            current
        DESCRIPTION
                "CMNT: - Set Manual delay
                 TYPE: - Number
                 PAGE: - Aud.Delays
                    EMB 3 Fine Delay  cmdID= 38140
                    min= -2450  max= 2450  step= 52  format= %0.3f ms  div_scale= 10000  preset= 0
                    Min = -0.245 ms  Max = 0.245 ms  Step = 0.005 ms  Preset = 0.000 ms  "
        ::= { iqsyn21CmdEntry 38140 }


    iqsyn21AudioDelaySelectDelay4 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-4  cmdID= 38083
                    Min  value= 0
                    Delay A  value= 1
                    Delay B  value= 2  "
        ::= { iqsyn21CmdEntry 38083 }


    iqsyn21AudDelaysEMBDelaySelectInternal4 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-4  cmdID= 38103  "
        ::= { iqsyn21CmdEntry 38103 }


    iqsyn21AudDelaysEMBDelaySelectAutoDolbyEPhaseBus4 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38113  cmdID= 38113  "
        ::= { iqsyn21CmdEntry 38113 }


    iqsyn21AudDelaysEMBDelaySelectDelayLimitBus4 OBJECT-TYPE
        SYNTAX            RollCallString
        MAX-ACCESS        read-only
        STATUS            current
        DESCRIPTION
                "CMNT: - 
                 TYPE: - Display
                 PAGE: - Aud.Delays
                    Delay Limit38311  cmdID= 38311  "
        ::= { iqsyn21CmdEntry 38311 }


    iqsyn21AudDelaysEMBDelaySelectEMB4FineDelay OBJECT-TYPE
        SYNTAX            INTEGER
        MAX-ACCESS        read-write
        STATUS            current
        DESCRIPTION
                "CMNT: - Set Manual delay
                 TYPE: - Number
                 PAGE: - Aud.Delays
                    EMB 4 Fine Delay  cmdID= 38141
                    min= -2450  max= 2450  step= 52  format= %0.3f ms  div_scale= 10000  preset= 0
                    Min = -0.245 ms  Max = 0.245 ms  Step = 0.005 ms  Preset = 0.000 ms  "
        ::= { iqsyn21CmdEntry 38141 }


    iqsyn21AudioDelaySelectDelay5 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-5  cmdID= 38084
                    Min  value= 0
                    Delay A  value= 1
                    Delay B  value= 2  "
        ::= { iqsyn21CmdEntry 38084 }


    iqsyn21AudDelaysEMBDelaySelectInternal5 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-5  cmdID= 38104  "
        ::= { iqsyn21CmdEntry 38104 }


    iqsyn21AudDelaysEMBDelaySelectAutoDolbyEPhaseBus5 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38114  cmdID= 38114  "
        ::= { iqsyn21CmdEntry 38114 }


    iqsyn21AudDelaysEMBDelaySelectDelayLimitBus5 OBJECT-TYPE
        SYNTAX            RollCallString
        MAX-ACCESS        read-only
        STATUS            current
        DESCRIPTION
                "CMNT: - 
                 TYPE: - Display
                 PAGE: - Aud.Delays
                    Delay Limit38312  cmdID= 38312  "
        ::= { iqsyn21CmdEntry 38312 }


    iqsyn21AudDelaysEMBDelaySelectEMB5FineDelay OBJECT-TYPE
        SYNTAX            INTEGER
        MAX-ACCESS        read-write
        STATUS            current
        DESCRIPTION
                "CMNT: - Set Manual delay
                 TYPE: - Number
                 PAGE: - Aud.Delays
                    EMB 5 Fine Delay  cmdID= 38142
                    min= -2450  max= 2450  step= 52  format= %0.3f ms  div_scale= 10000  preset= 0
                    Min = -0.245 ms  Max = 0.245 ms  Step = 0.005 ms  Preset = 0.000 ms  "
        ::= { iqsyn21CmdEntry 38142 }


    iqsyn21AudioDelaySelectDelay6 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-6  cmdID= 38085
                    Min  value= 0
                    Delay A  value= 1
                    Delay B  value= 2  "
        ::= { iqsyn21CmdEntry 38085 }


    iqsyn21AudDelaysEMBDelaySelectInternal6 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-6  cmdID= 38105  "
        ::= { iqsyn21CmdEntry 38105 }


    iqsyn21AudDelaysEMBDelaySelectAutoDolbyEPhaseBus6 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38115  cmdID= 38115  "
        ::= { iqsyn21CmdEntry 38115 }


    iqsyn21AudDelaysEMBDelaySelectDelayLimitBus6 OBJECT-TYPE
        SYNTAX            RollCallString
        MAX-ACCESS        read-only
        STATUS            current
        DESCRIPTION
                "CMNT: - 
                 TYPE: - Display
                 PAGE: - Aud.Delays
                    Delay Limit38313  cmdID= 38313  "
        ::= { iqsyn21CmdEntry 38313 }


    iqsyn21AudDelaysEMBDelaySelectEMB6FineDelay OBJECT-TYPE
        SYNTAX            INTEGER
        MAX-ACCESS        read-write
        STATUS            current
        DESCRIPTION
                "CMNT: - Set Manual delay
                 TYPE: - Number
                 PAGE: - Aud.Delays
                    EMB 6 Fine Delay  cmdID= 38143
                    min= -2450  max= 2450  step= 52  format= %0.3f ms  div_scale= 10000  preset= 0
                    Min = -0.245 ms  Max = 0.245 ms  Step = 0.005 ms  Preset = 0.000 ms  "
        ::= { iqsyn21CmdEntry 38143 }


    iqsyn21AudioDelaySelectDelay7 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-7  cmdID= 38086
                    Min  value= 0
                    Delay A  value= 1
                    Delay B  value= 2  "
        ::= { iqsyn21CmdEntry 38086 }


    iqsyn21AudDelaysEMBDelaySelectInternal7 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-7  cmdID= 38106  "
        ::= { iqsyn21CmdEntry 38106 }


    iqsyn21AudDelaysEMBDelaySelectAutoDolbyEPhaseBus7 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38116  cmdID= 38116  "
        ::= { iqsyn21CmdEntry 38116 }


    iqsyn21AudDelaysEMBDelaySelectDelayLimitBus7 OBJECT-TYPE
        SYNTAX            RollCallString
        MAX-ACCESS        read-only
        STATUS            current
        DESCRIPTION
                "CMNT: - 
                 TYPE: - Display
                 PAGE: - Aud.Delays
                    Delay Limit38314  cmdID= 38314  "
        ::= { iqsyn21CmdEntry 38314 }


    iqsyn21AudDelaysEMBDelaySelectEMB7FineDelay OBJECT-TYPE
        SYNTAX            INTEGER
        MAX-ACCESS        read-write
        STATUS            current
        DESCRIPTION
                "CMNT: - Set Manual delay
                 TYPE: - Number
                 PAGE: - Aud.Delays
                    EMB 7 Fine Delay  cmdID= 38144
                    min= -2450  max= 2450  step= 52  format= %0.3f ms  div_scale= 10000  preset= 0
                    Min = -0.245 ms  Max = 0.245 ms  Step = 0.005 ms  Preset = 0.000 ms  "
        ::= { iqsyn21CmdEntry 38144 }


    iqsyn21AudioDelaySelectDelay8 OBJECT-TYPE
        SYNTAX            INTEGER {
                            valMin(0),
                            valDelayA(1),
                            valDelayB(2)
                            }
        MAX-ACCESS        read-write
        STATUS            current
        DESCRIPTION
                "CMNT: - Embedded Audio Delay A/B/Off
                 TYPE: - RadiobuttonList
                 PAGE: - Aud.Delays
                    Delay-8  cmdID= 38087
                    Min  value= 0
                    Delay A  value= 1
                    Delay B  value= 2  "
        ::= { iqsyn21CmdEntry 38087 }


    iqsyn21AudDelaysEMBDelaySelectInternal8 OBJECT-TYPE
        SYNTAX            INTEGER { disable(0), enable(1)  }
        MAX-ACCESS        read-write
        STATUS            current
        DESCRIPTION
                "CMNT: - Embedded Audio Delay includes video delay
                 TYPE: - Checkbox
                 PAGE: - Aud.Delays
                    Internal-8  cmdID= 38107  "
        ::= { iqsyn21CmdEntry 38107 }


    iqsyn21AudDelaysEMBDelaySelectDelayLimitBus8 OBJECT-TYPE
        SYNTAX            RollCallString
        MAX-ACCESS        read-only
        STATUS            current
        DESCRIPTION
                "CMNT: - 
                 TYPE: - Display
                 PAGE: - Aud.Delays
                    Delay Limit38315  cmdID= 38315  "
        ::= { iqsyn21CmdEntry 38315 }


    iqsyn21AudDelaysEMBDelaySelectAutoDolbyEPhaseBus8 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Aud.Delays
                    Auto Dolby-E Phase38117  cmdID= 38117  "
        ::= { iqsyn21CmdEntry 38117 }


    iqsyn21AudDelaysEMBDelaySelectEMB8FineDelay OBJECT-TYPE
        SYNTAX            INTEGER
        MAX-ACCESS        read-write
        STATUS            current
        DESCRIPTION
                "CMNT: - Set Manual delay
                 TYPE: - Number
                 PAGE: - Aud.Delays
                    EMB 8 Fine Delay  cmdID= 38145
                    min= -2450  max= 2450  step= 52  format= %0.3f ms  div_scale= 10000  preset= 0
                    Min = -0.245 ms  Max = 0.245 ms  Step = 0.005 ms  Preset = 0.000 ms  "
        ::= { iqsyn21CmdEntry 38145 }


    iqsyn21AudioDelaysRollTrack14 OBJECT-TYPE
        SYNTAX            RollCallString
        MAX-ACCESS        read-only
        STATUS            current
        DESCRIPTION
                "CMNT: - Rolltrack input command for delays
                 TYPE: - Display
                 PAGE: - Audio
                    RollTrack14  cmdID= 14  "
        ::= { iqsyn21CmdEntry 14 }


    iqsyn21AudioDelaysRollTrack15 OBJECT-TYPE
        SYNTAX            RollCallString
        MAX-ACCESS        read-only
        STATUS            current
        DESCRIPTION
                "CMNT: - Rolltrack input command for delays
                 TYPE: - Display
                 PAGE: - Audio
                    RollTrack15  cmdID= 15  "
        ::= { iqsyn21CmdEntry 15 }


    iqsyn21AudioDelaysRollTrack16 OBJECT-TYPE
        SYNTAX            RollCallString
        MAX-ACCESS        read-only
        STATUS            current
        DESCRIPTION
                "CMNT: - Rolltrack input command for delays
                 TYPE: - Display
                 PAGE: - Audio
                    RollTrack16  cmdID= 16  "
        ::= { iqsyn21CmdEntry 16 }


    iqsyn21AudioDelaysRollTrack17 OBJECT-TYPE
        SYNTAX            RollCallString
        MAX-ACCESS        read-only
        STATUS            current
        DESCRIPTION
                "CMNT: - Rolltrack input command for delays
                 TYPE: - Display
                 PAGE: - Audio
                    RollTrack17  cmdID= 17  "
        ::= { iqsyn21CmdEntry 17 }


    iqsyn21AudioAudDelaysCrashSRCLimit OBJECT-TYPE
        SYNTAX            INTEGER
        MAX-ACCESS        read-write
        STATUS            current
        DESCRIPTION
                "CMNT: - Set Audio Crash SRC limit
                 TYPE: - Number
                 PAGE: - Audio
                    Crash SRC Limit  cmdID= 38678
                    min= 0  max= 80  step= 1  format= %0.0f ms  div_scale= 1  preset= 80
                    Min = 0 ms  Max = 80 ms  Step = 1 ms  Preset = 80 ms  "
        ::= { iqsyn21CmdEntry 38678 }


    iqsyn21EmbCtrlGroupGroup1Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 1 Audio  cmdID= 37450
                    Pass  value= 0
                    Blank  value= 2
                    Embed  value= 1  "
        ::= { iqsyn21CmdEntry 37450 }


    iqsyn21EmbCtrlGroupGroup2Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 2 Audio  cmdID= 37451
                    Pass  value= 0
                    Blank  value= 2
                    Embed  value= 1  "
        ::= { iqsyn21CmdEntry 37451 }


    iqsyn21EmbCtrlGroupGroup3Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 3 Audio  cmdID= 37452
                    Pass  value= 0
                    Blank  value= 2
                    Embed  value= 1  "
        ::= { iqsyn21CmdEntry 37452 }


    iqsyn21EmbCtrlGroupGroup4Active OBJECT-TYPE
        SYNTAX            INTEGER {
                            valPass(0),
                            valBlank(2),
                            valEmbed(1)
                            }
        MAX-ACCESS        read-write
        STATUS            current
        DESCRIPTION
                "CMNT: - Embedded output audio group enabled
                 TYPE: - RadiobuttonList
                 PAGE: - Audio
                    Group 4 Audio  cmdID= 37453
                    Pass  value= 0
                    Blank  value= 2
                    Embed  value= 1  "
        ::= { iqsyn21CmdEntry 37453 }


    iqsyn21EmbCtrlChannelPair1LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 1-L Active  cmdID= 37431  "
        ::= { iqsyn21CmdEntry 37431 }


    iqsyn21EmbCtrlChannelPair1RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 1-R Active  cmdID= 37432  "
        ::= { iqsyn21CmdEntry 37432 }


    iqsyn21EmbCtrlChannelPair2LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 2-L Active  cmdID= 37433  "
        ::= { iqsyn21CmdEntry 37433 }


    iqsyn21EmbCtrlChannelPair2RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 2-R Active  cmdID= 37434  "
        ::= { iqsyn21CmdEntry 37434 }


    iqsyn21EmbCtrlChannelPair3LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 3-L Active  cmdID= 37435  "
        ::= { iqsyn21CmdEntry 37435 }


    iqsyn21EmbCtrlChannelPair3RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 3-R Active  cmdID= 37436  "
        ::= { iqsyn21CmdEntry 37436 }


    iqsyn21EmbCtrlChannelPair4LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 4-L Active  cmdID= 37437  "
        ::= { iqsyn21CmdEntry 37437 }


    iqsyn21EmbCtrlChannelPair4RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 4-R Active  cmdID= 37438  "
        ::= { iqsyn21CmdEntry 37438 }


    iqsyn21EmbCtrlChannelPair5LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 5-L Active  cmdID= 37439  "
        ::= { iqsyn21CmdEntry 37439 }


    iqsyn21EmbCtrlChannelPair5RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 5-R Active  cmdID= 37440  "
        ::= { iqsyn21CmdEntry 37440 }


    iqsyn21EmbCtrlChannelPair6LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 6-L Active  cmdID= 37441  "
        ::= { iqsyn21CmdEntry 37441 }


    iqsyn21EmbCtrlChannelPair6RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 6-R Active  cmdID= 37442  "
        ::= { iqsyn21CmdEntry 37442 }


    iqsyn21EmbCtrlChannelPair7LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 7-L Active  cmdID= 37443  "
        ::= { iqsyn21CmdEntry 37443 }


    iqsyn21EmbCtrlChannelPair7RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 7-R Active  cmdID= 37444  "
        ::= { iqsyn21CmdEntry 37444 }


    iqsyn21EmbCtrlChannelPair8LActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 8-L Active  cmdID= 37445  "
        ::= { iqsyn21CmdEntry 37445 }


    iqsyn21EmbCtrlChannelPair8RActive OBJECT-TYPE
        SYNTAX            INTEGER { disable(0), enable(1)  }
        MAX-ACCESS        read-write
        STATUS            current
        DESCRIPTION
                "CMNT: - Embedded output audio channel enabled
                 TYPE: - Checkbox
                 PAGE: - Emb.Ctrl
                    Pair 8-R Active  cmdID= 37446  "
        ::= { iqsyn21CmdEntry 37446 }


    iqsyn21AudioEmbCtrlEmbedderPriority OBJECT-TYPE
        SYNTAX            INTEGER {
                            valNormal(0),
                            valAudioDolbynE(1)
                            }
        MAX-ACCESS        read-write
        STATUS            current
        DESCRIPTION
                "CMNT: - Set priority of ANC embedded data
                 TYPE: - RadiobuttonList
                 PAGE: - Audio
                    Embedder Priority  cmdID= 37460
                    Normal  value= 0
                    Audio (Dolby-E)  value= 1  "
        ::= { iqsyn21CmdEntry 37460 }


    iqsyn21EmbGainEmbedPair1Embed1MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 1 Mute L  cmdID= 37340  "
        ::= { iqsyn21CmdEntry 37340 }


    iqsyn21EmbGainEmbedPair1Embed1MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 1 Mute R  cmdID= 37341  "
        ::= { iqsyn21CmdEntry 37341 }


    iqsyn21EmbGainEmbedPair1Embed1LGain OBJECT-TYPE
        SYNTAX            INTEGER
        MAX-ACCESS        read-write
        STATUS            current
        DESCRIPTION
                "CMNT: - Embedded audio gain
                 TYPE: - Number
                 PAGE: - Emb.Gain
                    Embed 1 L Gain  cmdID= 37320
                    min= -661  max= 120  step= 1  format= %0.1f dB  div_scale= 10  preset= 0
                    Min = -66.1 dB  Max = 12.0 dB  Step = 0.1 dB  Preset = 0.0 dB  "
        ::= { iqsyn21CmdEntry 37320 }


    iqsyn21EmbGainEmbedPair1Embed1RGain OBJECT-TYPE
        SYNTAX            INTEGER
        MAX-ACCESS        read-write
        STATUS            current
        DESCRIPTION
                "CMNT: - Embedded audio gain
                 TYPE: - Number
                 PAGE: - Emb.Gain
                    Embed 1 R Gain  cmdID= 37321
                    min= -661  max= 120  step= 1  format= %0.1f dB  div_scale= 10  preset= 0
                    Min = -66.1 dB  Max = 12.0 dB  Step = 0.1 dB  Preset = 0.0 dB  "
        ::= { iqsyn21CmdEntry 37321 }


    iqsyn21EmbGainEmbedPair1Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37380  "
        ::= { iqsyn21CmdEntry 37380 }


    iqsyn21EmbGainEmbedPair1Embed1InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 1 Invert L  cmdID= 37360  "
        ::= { iqsyn21CmdEntry 37360 }


    iqsyn21EmbGainEmbedPair1Embed1InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 1 Invert R  cmdID= 37361  "
        ::= { iqsyn21CmdEntry 37361 }


    iqsyn21EmbGainEmbedPair1Embed1LClip OBJECT-TYPE
        SYNTAX            RollCallString
        MAX-ACCESS        read-only
        STATUS            current
        DESCRIPTION
                "CMNT: - Embedded audio output clip
                 TYPE: - Display
                 PAGE: - Emb.Gain
                    Embed 1-L Clip  cmdID= 37540  "
        ::= { iqsyn21CmdEntry 37540 }


    iqsyn21EmbGainEmbedPair1Embed1RClip OBJECT-TYPE
        SYNTAX            RollCallString
        MAX-ACCESS        read-only
        STATUS            current
        DESCRIPTION
                "CMNT: - Embedded audio output clip
                 TYPE: - Display
                 PAGE: - Emb.Gain
                    Embed 1-R Clip  cmdID= 37541  "
        ::= { iqsyn21CmdEntry 37541 }


    iqsyn21EmbGainEmbedPair2Embed2MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 2 Mute L  cmdID= 37342  "
        ::= { iqsyn21CmdEntry 37342 }


    iqsyn21EmbGainEmbedPair2Embed2MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 2 Mute R  cmdID= 37343  "
        ::= { iqsyn21CmdEntry 37343 }


    iqsyn21EmbGainEmbedPair2Embed2LGain OBJECT-TYPE
        SYNTAX            INTEGER
        MAX-ACCESS        read-write
        STATUS            current
        DESCRIPTION
                "CMNT: - Embedded audio gain
                 TYPE: - Number
                 PAGE: - Emb.Gain
                    Embed 2 L Gain  cmdID= 37322
                    min= -661  max= 120  step= 1  format= %0.1f dB  div_scale= 10  preset= 0
                    Min = -66.1 dB  Max = 12.0 dB  Step = 0.1 dB  Preset = 0.0 dB  "
        ::= { iqsyn21CmdEntry 37322 }


    iqsyn21EmbGainEmbedPair2Embed2RGain OBJECT-TYPE
        SYNTAX            INTEGER
        MAX-ACCESS        read-write
        STATUS            current
        DESCRIPTION
                "CMNT: - Embedded audio gain
                 TYPE: - Number
                 PAGE: - Emb.Gain
                    Embed 2 R Gain  cmdID= 37323
                    min= -661  max= 120  step= 1  format= %0.1f dB  div_scale= 10  preset= 0
                    Min = -66.1 dB  Max = 12.0 dB  Step = 0.1 dB  Preset = 0.0 dB  "
        ::= { iqsyn21CmdEntry 37323 }


    iqsyn21EmbGainEmbedPair2Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37381  "
        ::= { iqsyn21CmdEntry 37381 }


    iqsyn21EmbGainEmbedPair2Embed2InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 2 Invert L  cmdID= 37362  "
        ::= { iqsyn21CmdEntry 37362 }


    iqsyn21EmbGainEmbedPair2Embed2InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 2 Invert R  cmdID= 37363  "
        ::= { iqsyn21CmdEntry 37363 }


    iqsyn21EmbGainEmbedPair2Embed2LClip OBJECT-TYPE
        SYNTAX            RollCallString
        MAX-ACCESS        read-only
        STATUS            current
        DESCRIPTION
                "CMNT: - Embedded audio output clip
                 TYPE: - Display
                 PAGE: - Emb.Gain
                    Embed 2-L Clip  cmdID= 37542  "
        ::= { iqsyn21CmdEntry 37542 }


    iqsyn21EmbGainEmbedPair2Embed2RClip OBJECT-TYPE
        SYNTAX            RollCallString
        MAX-ACCESS        read-only
        STATUS            current
        DESCRIPTION
                "CMNT: - Embedded audio output clip
                 TYPE: - Display
                 PAGE: - Emb.Gain
                    Embed 2-R Clip  cmdID= 37543  "
        ::= { iqsyn21CmdEntry 37543 }


    iqsyn21EmbGainEmbedPair3Embed3MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 3 Mute L  cmdID= 37344  "
        ::= { iqsyn21CmdEntry 37344 }


    iqsyn21EmbGainEmbedPair3Embed3MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 3 Mute R  cmdID= 37345  "
        ::= { iqsyn21CmdEntry 37345 }


    iqsyn21EmbGainEmbedPair3Embed3LGain OBJECT-TYPE
        SYNTAX            INTEGER
        MAX-ACCESS        read-write
        STATUS            current
        DESCRIPTION
                "CMNT: - Embedded audio gain
                 TYPE: - Number
                 PAGE: - Emb.Gain
                    Embed 3 L Gain  cmdID= 37324
                    min= -661  max= 120  step= 1  format= %0.1f dB  div_scale= 10  preset= 0
                    Min = -66.1 dB  Max = 12.0 dB  Step = 0.1 dB  Preset = 0.0 dB  "
        ::= { iqsyn21CmdEntry 37324 }


    iqsyn21EmbGainEmbedPair3Embed3RGain OBJECT-TYPE
        SYNTAX            INTEGER
        MAX-ACCESS        read-write
        STATUS            current
        DESCRIPTION
                "CMNT: - Embedded audio gain
                 TYPE: - Number
                 PAGE: - Emb.Gain
                    Embed 3 R Gain  cmdID= 37325
                    min= -661  max= 120  step= 1  format= %0.1f dB  div_scale= 10  preset= 0
                    Min = -66.1 dB  Max = 12.0 dB  Step = 0.1 dB  Preset = 0.0 dB  "
        ::= { iqsyn21CmdEntry 37325 }


    iqsyn21EmbGainEmbedPair3Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37382  "
        ::= { iqsyn21CmdEntry 37382 }


    iqsyn21EmbGainEmbedPair3Embed3InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 3 Invert L  cmdID= 37364  "
        ::= { iqsyn21CmdEntry 37364 }


    iqsyn21EmbGainEmbedPair3Embed3InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 3 Invert R  cmdID= 37365  "
        ::= { iqsyn21CmdEntry 37365 }


    iqsyn21EmbGainEmbedPair3Embed3LClip OBJECT-TYPE
        SYNTAX            RollCallString
        MAX-ACCESS        read-only
        STATUS            current
        DESCRIPTION
                "CMNT: - Embedded audio output clip
                 TYPE: - Display
                 PAGE: - Emb.Gain
                    Embed 3-L Clip  cmdID= 37544  "
        ::= { iqsyn21CmdEntry 37544 }


    iqsyn21EmbGainEmbedPair3Embed3RClip OBJECT-TYPE
        SYNTAX            RollCallString
        MAX-ACCESS        read-only
        STATUS            current
        DESCRIPTION
                "CMNT: - Embedded audio output clip
                 TYPE: - Display
                 PAGE: - Emb.Gain
                    Embed 3-R Clip  cmdID= 37545  "
        ::= { iqsyn21CmdEntry 37545 }


    iqsyn21EmbGainEmbedPair4Embed4MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 4 Mute L  cmdID= 37346  "
        ::= { iqsyn21CmdEntry 37346 }


    iqsyn21EmbGainEmbedPair4Embed4MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 4 Mute R  cmdID= 37347  "
        ::= { iqsyn21CmdEntry 37347 }


    iqsyn21EmbGainEmbedPair4Embed4LGain OBJECT-TYPE
        SYNTAX            INTEGER
        MAX-ACCESS        read-write
        STATUS            current
        DESCRIPTION
                "CMNT: - Embedded audio gain
                 TYPE: - Number
                 PAGE: - Emb.Gain
                    Embed 4 L Gain  cmdID= 37326
                    min= -661  max= 120  step= 1  format= %0.1f dB  div_scale= 10  preset= 0
                    Min = -66.1 dB  Max = 12.0 dB  Step = 0.1 dB  Preset = 0.0 dB  "
        ::= { iqsyn21CmdEntry 37326 }


    iqsyn21EmbGainEmbedPair4Embed4RGain OBJECT-TYPE
        SYNTAX            INTEGER
        MAX-ACCESS        read-write
        STATUS            current
        DESCRIPTION
                "CMNT: - Embedded audio gain
                 TYPE: - Number
                 PAGE: - Emb.Gain
                    Embed 4 R Gain  cmdID= 37327
                    min= -661  max= 120  step= 1  format= %0.1f dB  div_scale= 10  preset= 0
                    Min = -66.1 dB  Max = 12.0 dB  Step = 0.1 dB  Preset = 0.0 dB  "
        ::= { iqsyn21CmdEntry 37327 }


    iqsyn21EmbGainEmbedPair4Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37383  "
        ::= { iqsyn21CmdEntry 37383 }


    iqsyn21EmbGainEmbedPair4Embed4InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 4 Invert L  cmdID= 37366  "
        ::= { iqsyn21CmdEntry 37366 }


    iqsyn21EmbGainEmbedPair4Embed4InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 4 Invert R  cmdID= 37367  "
        ::= { iqsyn21CmdEntry 37367 }


    iqsyn21EmbGainEmbedPair4Embed4LClip OBJECT-TYPE
        SYNTAX            RollCallString
        MAX-ACCESS        read-only
        STATUS            current
        DESCRIPTION
                "CMNT: - Embedded audio output clip
                 TYPE: - Display
                 PAGE: - Emb.Gain
                    Embed 4-L Clip  cmdID= 37546  "
        ::= { iqsyn21CmdEntry 37546 }


    iqsyn21EmbGainEmbedPair4Embed4RClip OBJECT-TYPE
        SYNTAX            RollCallString
        MAX-ACCESS        read-only
        STATUS            current
        DESCRIPTION
                "CMNT: - Embedded audio output clip
                 TYPE: - Display
                 PAGE: - Emb.Gain
                    Embed 4-R Clip  cmdID= 37547  "
        ::= { iqsyn21CmdEntry 37547 }


    iqsyn21EmbGainEmbedPair5Embed5MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 5 Mute L  cmdID= 37348  "
        ::= { iqsyn21CmdEntry 37348 }


    iqsyn21EmbGainEmbedPair5Embed5MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 5 Mute R  cmdID= 37349  "
        ::= { iqsyn21CmdEntry 37349 }


    iqsyn21EmbGainEmbedPair5Embed5LGain OBJECT-TYPE
        SYNTAX            INTEGER
        MAX-ACCESS        read-write
        STATUS            current
        DESCRIPTION
                "CMNT: - Embedded audio gain
                 TYPE: - Number
                 PAGE: - Emb.Gain
                    Embed 5 L Gain  cmdID= 37328
                    min= -661  max= 120  step= 1  format= %0.1f dB  div_scale= 10  preset= 0
                    Min = -66.1 dB  Max = 12.0 dB  Step = 0.1 dB  Preset = 0.0 dB  "
        ::= { iqsyn21CmdEntry 37328 }


    iqsyn21EmbGainEmbedPair5Embed5RGain OBJECT-TYPE
        SYNTAX            INTEGER
        MAX-ACCESS        read-write
        STATUS            current
        DESCRIPTION
                "CMNT: - Embedded audio gain
                 TYPE: - Number
                 PAGE: - Emb.Gain
                    Embed 5 R Gain  cmdID= 37329
                    min= -661  max= 120  step= 1  format= %0.1f dB  div_scale= 10  preset= 0
                    Min = -66.1 dB  Max = 12.0 dB  Step = 0.1 dB  Preset = 0.0 dB  "
        ::= { iqsyn21CmdEntry 37329 }


    iqsyn21EmbGainEmbedPair5Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37384  "
        ::= { iqsyn21CmdEntry 37384 }


    iqsyn21EmbGainEmbedPair5Embed5InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 5 Invert L  cmdID= 37368  "
        ::= { iqsyn21CmdEntry 37368 }


    iqsyn21EmbGainEmbedPair5Embed5InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 5 Invert R  cmdID= 37369  "
        ::= { iqsyn21CmdEntry 37369 }


    iqsyn21EmbGainEmbedPair5Embed5LClip OBJECT-TYPE
        SYNTAX            RollCallString
        MAX-ACCESS        read-only
        STATUS            current
        DESCRIPTION
                "CMNT: - Embedded audio output clip
                 TYPE: - Display
                 PAGE: - Emb.Gain
                    Embed 5-L Clip  cmdID= 37548  "
        ::= { iqsyn21CmdEntry 37548 }


    iqsyn21EmbGainEmbedPair5Embed5RClip OBJECT-TYPE
        SYNTAX            RollCallString
        MAX-ACCESS        read-only
        STATUS            current
        DESCRIPTION
                "CMNT: - Embedded audio output clip
                 TYPE: - Display
                 PAGE: - Emb.Gain
                    Embed 5-R Clip  cmdID= 37549  "
        ::= { iqsyn21CmdEntry 37549 }


    iqsyn21EmbGainEmbedPair6Embed6MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 6 Mute L  cmdID= 37350  "
        ::= { iqsyn21CmdEntry 37350 }


    iqsyn21EmbGainEmbedPair6Embed6MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 6 Mute R  cmdID= 37351  "
        ::= { iqsyn21CmdEntry 37351 }


    iqsyn21EmbGainEmbedPair6Embed6LGain OBJECT-TYPE
        SYNTAX            INTEGER
        MAX-ACCESS        read-write
        STATUS            current
        DESCRIPTION
                "CMNT: - Embedded audio gain
                 TYPE: - Number
                 PAGE: - Emb.Gain
                    Embed 6 L Gain  cmdID= 37330
                    min= -661  max= 120  step= 1  format= %0.1f dB  div_scale= 10  preset= 0
                    Min = -66.1 dB  Max = 12.0 dB  Step = 0.1 dB  Preset = 0.0 dB  "
        ::= { iqsyn21CmdEntry 37330 }


    iqsyn21EmbGainEmbedPair6Embed6RGain OBJECT-TYPE
        SYNTAX            INTEGER
        MAX-ACCESS        read-write
        STATUS            current
        DESCRIPTION
                "CMNT: - Embedded audio gain
                 TYPE: - Number
                 PAGE: - Emb.Gain
                    Embed 6 R Gain  cmdID= 37331
                    min= -661  max= 120  step= 1  format= %0.1f dB  div_scale= 10  preset= 0
                    Min = -66.1 dB  Max = 12.0 dB  Step = 0.1 dB  Preset = 0.0 dB  "
        ::= { iqsyn21CmdEntry 37331 }


    iqsyn21EmbGainEmbedPair6Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37385  "
        ::= { iqsyn21CmdEntry 37385 }


    iqsyn21EmbGainEmbedPair6Embed6InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 6 Invert L  cmdID= 37370  "
        ::= { iqsyn21CmdEntry 37370 }


    iqsyn21EmbGainEmbedPair6Embed6InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 6 Invert R  cmdID= 37371  "
        ::= { iqsyn21CmdEntry 37371 }


    iqsyn21EmbGainEmbedPair6Embed6LClip OBJECT-TYPE
        SYNTAX            RollCallString
        MAX-ACCESS        read-only
        STATUS            current
        DESCRIPTION
                "CMNT: - Embedded audio output clip
                 TYPE: - Display
                 PAGE: - Emb.Gain
                    Embed 6-L Clip  cmdID= 37550  "
        ::= { iqsyn21CmdEntry 37550 }


    iqsyn21EmbGainEmbedPair6Embed6RClip OBJECT-TYPE
        SYNTAX            RollCallString
        MAX-ACCESS        read-only
        STATUS            current
        DESCRIPTION
                "CMNT: - Embedded audio output clip
                 TYPE: - Display
                 PAGE: - Emb.Gain
                    Embed 6-R Clip  cmdID= 37551  "
        ::= { iqsyn21CmdEntry 37551 }


    iqsyn21EmbGainEmbedPair7Embed7MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 7 Mute L  cmdID= 37352  "
        ::= { iqsyn21CmdEntry 37352 }


    iqsyn21EmbGainEmbedPair7Embed7MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 7 Mute R  cmdID= 37353  "
        ::= { iqsyn21CmdEntry 37353 }


    iqsyn21EmbGainEmbedPair7Embed7LGain OBJECT-TYPE
        SYNTAX            INTEGER
        MAX-ACCESS        read-write
        STATUS            current
        DESCRIPTION
                "CMNT: - Embedded audio gain
                 TYPE: - Number
                 PAGE: - Emb.Gain
                    Embed 7 L Gain  cmdID= 37332
                    min= -661  max= 120  step= 1  format= %0.1f dB  div_scale= 10  preset= 0
                    Min = -66.1 dB  Max = 12.0 dB  Step = 0.1 dB  Preset = 0.0 dB  "
        ::= { iqsyn21CmdEntry 37332 }


    iqsyn21EmbGainEmbedPair7Embed7RGain OBJECT-TYPE
        SYNTAX            INTEGER
        MAX-ACCESS        read-write
        STATUS            current
        DESCRIPTION
                "CMNT: - Embedded audio gain
                 TYPE: - Number
                 PAGE: - Emb.Gain
                    Embed 7 R Gain  cmdID= 37333
                    min= -661  max= 120  step= 1  format= %0.1f dB  div_scale= 10  preset= 0
                    Min = -66.1 dB  Max = 12.0 dB  Step = 0.1 dB  Preset = 0.0 dB  "
        ::= { iqsyn21CmdEntry 37333 }


    iqsyn21EmbGainEmbedPair7Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37386  "
        ::= { iqsyn21CmdEntry 37386 }


    iqsyn21EmbGainEmbedPair7Embed7InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 7 Invert L  cmdID= 37372  "
        ::= { iqsyn21CmdEntry 37372 }


    iqsyn21EmbGainEmbedPair7Embed7InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 7 Invert R  cmdID= 37373  "
        ::= { iqsyn21CmdEntry 37373 }


    iqsyn21EmbGainEmbedPair7Embed7LClip OBJECT-TYPE
        SYNTAX            RollCallString
        MAX-ACCESS        read-only
        STATUS            current
        DESCRIPTION
                "CMNT: - Embedded audio output clip
                 TYPE: - Display
                 PAGE: - Emb.Gain
                    Embed 7-L Clip  cmdID= 37552  "
        ::= { iqsyn21CmdEntry 37552 }


    iqsyn21EmbGainEmbedPair7Embed7RClip OBJECT-TYPE
        SYNTAX            RollCallString
        MAX-ACCESS        read-only
        STATUS            current
        DESCRIPTION
                "CMNT: - Embedded audio output clip
                 TYPE: - Display
                 PAGE: - Emb.Gain
                    Embed 7-R Clip  cmdID= 37553  "
        ::= { iqsyn21CmdEntry 37553 }


    iqsyn21EmbGainEmbedPair8Embed8MuteL OBJECT-TYPE
        SYNTAX            INTEGER { disable(0), enable(1)  }
        MAX-ACCESS        read-write
        STATUS            current
        DESCRIPTION
                "CMNT: - Embedded audio mute
                 TYPE: - Checkbox
                 PAGE: - Emb.Gain
                    Embed 8 Mute L  cmdID= 37354  "
        ::= { iqsyn21CmdEntry 37354 }


    iqsyn21EmbGainEmbedPair8Embed8MuteR OBJECT-TYPE
        SYNTAX            INTEGER { disable(0), enable(1)  }
        MAX-ACCESS        read-write
        STATUS            current
        DESCRIPTION
                "CMNT: - Embedded audio mute
                 TYPE: - Checkbox
                 PAGE: - Emb.Gain
                    Embed 8 Mute R  cmdID= 37355  "
        ::= { iqsyn21CmdEntry 37355 }


    iqsyn21EmbGainEmbedPair8Embed8LGain OBJECT-TYPE
        SYNTAX            INTEGER
        MAX-ACCESS        read-write
        STATUS            current
        DESCRIPTION
                "CMNT: - Embedded audio gain
                 TYPE: - Number
                 PAGE: - Emb.Gain
                    Embed 8 L Gain  cmdID= 37334
                    min= -661  max= 120  step= 1  format= %0.1f dB  div_scale= 10  preset= 0
                    Min = -66.1 dB  Max = 12.0 dB  Step = 0.1 dB  Preset = 0.0 dB  "
        ::= { iqsyn21CmdEntry 37334 }


    iqsyn21EmbGainEmbedPair8Embed8RGain OBJECT-TYPE
        SYNTAX            INTEGER
        MAX-ACCESS        read-write
        STATUS            current
        DESCRIPTION
                "CMNT: - Embedded audio gain
                 TYPE: - Number
                 PAGE: - Emb.Gain
                    Embed 8 R Gain  cmdID= 37335
                    min= -661  max= 120  step= 1  format= %0.1f dB  div_scale= 10  preset= 0
                    Min = -66.1 dB  Max = 12.0 dB  Step = 0.1 dB  Preset = 0.0 dB  "
        ::= { iqsyn21CmdEntry 37335 }


    iqsyn21EmbGainEmbedPair8Stereo OBJECT-TYPE
        SYNTAX            INTEGER { disable(0), enable(1)  }
        MAX-ACCESS        read-write
        STATUS            current
        DESCRIPTION
                "CMNT: - Embedded audio stereo link gain controls
                 TYPE: - Checkbox
                 PAGE: - Emb.Gain
                    Stereo  cmdID= 37387  "
        ::= { iqsyn21CmdEntry 37387 }


    iqsyn21EmbGainEmbedPair8Embed8InvertL OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 8 Invert L  cmdID= 37374  "
        ::= { iqsyn21CmdEntry 37374 }


    iqsyn21EmbGainEmbedPair8Embed8InvertR OBJECT-TYPE
        SYNTAX            INTEGER { disable(0), enable(1)  }
        MAX-ACCESS        read-write
        STATUS            current
        DESCRIPTION
                "CMNT: - Embedded audio phase invert
                 TYPE: - Checkbox
                 PAGE: - Emb.Gain
                    Embed 8 Invert R  cmdID= 37375  "
        ::= { iqsyn21CmdEntry 37375 }


    iqsyn21EmbGainEmbedPair8Embed8LClip OBJECT-TYPE
        SYNTAX            RollCallString
        MAX-ACCESS        read-only
        STATUS            current
        DESCRIPTION
                "CMNT: - Embedded audio output clip
                 TYPE: - Display
                 PAGE: - Emb.Gain
                    Embed 8-L Clip  cmdID= 37554  "
        ::= { iqsyn21CmdEntry 37554 }


    iqsyn21EmbGainEmbedPair8Embed8RClip OBJECT-TYPE
        SYNTAX            RollCallString
        MAX-ACCESS        read-only
        STATUS            current
        DESCRIPTION
                "CMNT: - Embedded audio output clip
                 TYPE: - Display
                 PAGE: - Emb.Gain
                    Embed 8-R Clip  cmdID= 37555  "
        ::= { iqsyn21CmdEntry 37555 }


    iqsyn21EmbOutEmbedPair1Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37300
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37300 }


    iqsyn21EmbOutEmbedPair1Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37301
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37301 }


    iqsyn21EmbOutEmbedPair1LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37390  "
        ::= { iqsyn21CmdEntry 37390 }


    iqsyn21EmbOutEmbedPair2Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37302
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37302 }


    iqsyn21EmbOutEmbedPair2Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37303
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37303 }


    iqsyn21EmbOutEmbedPair2LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37391  "
        ::= { iqsyn21CmdEntry 37391 }


    iqsyn21EmbOutEmbedPair3Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37304
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37304 }


    iqsyn21EmbOutEmbedPair3Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37305
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37305 }


    iqsyn21EmbOutEmbedPair3LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37392  "
        ::= { iqsyn21CmdEntry 37392 }


    iqsyn21EmbOutEmbedPair4Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37306
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37306 }


    iqsyn21EmbOutEmbedPair4Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37307
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37307 }


    iqsyn21EmbOutEmbedPair4LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37393  "
        ::= { iqsyn21CmdEntry 37393 }


    iqsyn21EmbOutEmbedPair5Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37308
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37308 }


    iqsyn21EmbOutEmbedPair5Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37309
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37309 }


    iqsyn21EmbOutEmbedPair5LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37394  "
        ::= { iqsyn21CmdEntry 37394 }


    iqsyn21EmbOutEmbedPair6Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37310
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37310 }


    iqsyn21EmbOutEmbedPair6Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37311
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37311 }


    iqsyn21EmbOutEmbedPair6LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37395  "
        ::= { iqsyn21CmdEntry 37395 }


    iqsyn21EmbOutEmbedPair7Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37312
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37312 }


    iqsyn21EmbOutEmbedPair7Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37313
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37313 }


    iqsyn21EmbOutEmbedPair7LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37396  "
        ::= { iqsyn21CmdEntry 37396 }


    iqsyn21EmbOutEmbedPair8Left OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Left  cmdID= 37314
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37314 }


    iqsyn21EmbOutEmbedPair8Right OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            valMix1(23),
                            valMix2(24),
                            valMix3(25),
                            valMix4(26),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Embedded audio source select
                 TYPE: - RadiobuttonList
                 PAGE: - Emb.Out
                    Right  cmdID= 37315
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    Mix 1  value= 23
                    Mix 2  value= 24
                    Mix 3  value= 25
                    Mix 4  value= 26
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37315 }


    iqsyn21EmbOutEmbedPair8LinkLRSelection OBJECT-TYPE
        SYNTAX            INTEGER { disable(0), enable(1)  }
        MAX-ACCESS        read-write
        STATUS            current
        DESCRIPTION
                "CMNT: - Embedded audio stereo link source selectors
                 TYPE: - Checkbox
                 PAGE: - Emb.Out
                    Link L+R Selection  cmdID= 37397  "
        ::= { iqsyn21CmdEntry 37397 }


    iqsyn21AudioEmbDataInput1 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 1  cmdID= 37420
                    PCM  value= 0
                    Data  value= 1
                    Mixed  value= 2  "
        ::= { iqsyn21CmdEntry 37420 }


    iqsyn21AudioEmbDataInput2 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 2  cmdID= 37421
                    PCM  value= 0
                    Data  value= 1
                    Mixed  value= 2  "
        ::= { iqsyn21CmdEntry 37421 }


    iqsyn21AudioEmbDataInput3 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 3  cmdID= 37422
                    PCM  value= 0
                    Data  value= 1
                    Mixed  value= 2  "
        ::= { iqsyn21CmdEntry 37422 }


    iqsyn21AudioEmbDataInput4 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 4  cmdID= 37423
                    PCM  value= 0
                    Data  value= 1
                    Mixed  value= 2  "
        ::= { iqsyn21CmdEntry 37423 }


    iqsyn21AudioEmbDataInput5 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 5  cmdID= 37424
                    PCM  value= 0
                    Data  value= 1
                    Mixed  value= 2  "
        ::= { iqsyn21CmdEntry 37424 }


    iqsyn21AudioEmbDataInput6 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 6  cmdID= 37425
                    PCM  value= 0
                    Data  value= 1
                    Mixed  value= 2  "
        ::= { iqsyn21CmdEntry 37425 }


    iqsyn21AudioEmbDataInput7 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 7  cmdID= 37426
                    PCM  value= 0
                    Data  value= 1
                    Mixed  value= 2  "
        ::= { iqsyn21CmdEntry 37426 }


    iqsyn21AudioEmbDataInput8 OBJECT-TYPE
        SYNTAX            INTEGER {
                            valPCM(0),
                            valData(1),
                            valMixed(2)
                            }
        MAX-ACCESS        read-write
        STATUS            current
        DESCRIPTION
                "CMNT: - Sample rate converter bypass (Data mode)
                 TYPE: - RadiobuttonList
                 PAGE: - Audio
                    Input 8  cmdID= 37427
                    PCM  value= 0
                    Data  value= 1
                    Mixed  value= 2  "
        ::= { iqsyn21CmdEntry 37427 }


    iqsyn21DisembedderNamesDisemb1L OBJECT-TYPE
        SYNTAX            RollCallString
        MAX-ACCESS        read-write
        STATUS            current
        DESCRIPTION
                "CMNT: - Embedded audio input name
                 TYPE: - Editstring
                 PAGE: - Disembedder Names
                    Disembed 1  cmdID= 37500
                    preset= Disembed 1"
        ::= { iqsyn21CmdEntry 37500 }


    iqsyn21DisembedderNamesDisemb1R OBJECT-TYPE
        SYNTAX            RollCallString
        MAX-ACCESS        read-write
        STATUS            current
        DESCRIPTION
                "CMNT: - Embedded audio input name
                 TYPE: - Editstring
                 PAGE: - Disembedder Names
                    Disembed 1-R  cmdID= 37501
                    preset= Disembed 1-R"
        ::= { iqsyn21CmdEntry 37501 }


    iqsyn21DisembedderNamesDisemb2L OBJECT-TYPE
        SYNTAX            RollCallString
        MAX-ACCESS        read-write
        STATUS            current
        DESCRIPTION
                "CMNT: - Embedded audio input name
                 TYPE: - Editstring
                 PAGE: - Disembedder Names
                    Disembed 2  cmdID= 37502
                    preset= Disembed 2"
        ::= { iqsyn21CmdEntry 37502 }


    iqsyn21DisembedderNamesDisemb2R OBJECT-TYPE
        SYNTAX            RollCallString
        MAX-ACCESS        read-write
        STATUS            current
        DESCRIPTION
                "CMNT: - Embedded audio input name
                 TYPE: - Editstring
                 PAGE: - Disembedder Names
                    Disembed 2-R  cmdID= 37503
                    preset= Disembed 2-R"
        ::= { iqsyn21CmdEntry 37503 }


    iqsyn21DisembedderNamesDisemb3L OBJECT-TYPE
        SYNTAX            RollCallString
        MAX-ACCESS        read-write
        STATUS            current
        DESCRIPTION
                "CMNT: - Embedded audio input name
                 TYPE: - Editstring
                 PAGE: - Disembedder Names
                    Disembed 3  cmdID= 37504
                    preset= Disembed 3"
        ::= { iqsyn21CmdEntry 37504 }


    iqsyn21DisembedderNamesDisemb3R OBJECT-TYPE
        SYNTAX            RollCallString
        MAX-ACCESS        read-write
        STATUS            current
        DESCRIPTION
                "CMNT: - Embedded audio input name
                 TYPE: - Editstring
                 PAGE: - Disembedder Names
                    Disembed 3-R  cmdID= 37505
                    preset= Disembed 3-R"
        ::= { iqsyn21CmdEntry 37505 }


    iqsyn21DisembedderNamesDisemb4L OBJECT-TYPE
        SYNTAX            RollCallString
        MAX-ACCESS        read-write
        STATUS            current
        DESCRIPTION
                "CMNT: - Embedded audio input name
                 TYPE: - Editstring
                 PAGE: - Disembedder Names
                    Disembed 4  cmdID= 37506
                    preset= Disembed 4"
        ::= { iqsyn21CmdEntry 37506 }


    iqsyn21DisembedderNamesDisemb4R OBJECT-TYPE
        SYNTAX            RollCallString
        MAX-ACCESS        read-write
        STATUS            current
        DESCRIPTION
                "CMNT: - Embedded audio input name
                 TYPE: - Editstring
                 PAGE: - Disembedder Names
                    Disembed 4-R  cmdID= 37507
                    preset= Disembed 4-R"
        ::= { iqsyn21CmdEntry 37507 }


    iqsyn21DisembedderNamesDisemb5L OBJECT-TYPE
        SYNTAX            RollCallString
        MAX-ACCESS        read-write
        STATUS            current
        DESCRIPTION
                "CMNT: - Embedded audio input name
                 TYPE: - Editstring
                 PAGE: - Disembedder Names
                    Disembed 5  cmdID= 37508
                    preset= Disembed 5"
        ::= { iqsyn21CmdEntry 37508 }


    iqsyn21DisembedderNamesDisemb5R OBJECT-TYPE
        SYNTAX            RollCallString
        MAX-ACCESS        read-write
        STATUS            current
        DESCRIPTION
                "CMNT: - Embedded audio input name
                 TYPE: - Editstring
                 PAGE: - Disembedder Names
                    Disembed 5-R  cmdID= 37509
                    preset= Disembed 5-R"
        ::= { iqsyn21CmdEntry 37509 }


    iqsyn21DisembedderNamesDisemb6L OBJECT-TYPE
        SYNTAX            RollCallString
        MAX-ACCESS        read-write
        STATUS            current
        DESCRIPTION
                "CMNT: - Embedded audio input name
                 TYPE: - Editstring
                 PAGE: - Disembedder Names
                    Disembed 6  cmdID= 37510
                    preset= Disembed 6"
        ::= { iqsyn21CmdEntry 37510 }


    iqsyn21DisembedderNamesDisemb6R OBJECT-TYPE
        SYNTAX            RollCallString
        MAX-ACCESS        read-write
        STATUS            current
        DESCRIPTION
                "CMNT: - Embedded audio input name
                 TYPE: - Editstring
                 PAGE: - Disembedder Names
                    Disembed 6-R  cmdID= 37511
                    preset= Disembed 6-R"
        ::= { iqsyn21CmdEntry 37511 }


    iqsyn21DisembedderNamesDisemb7L OBJECT-TYPE
        SYNTAX            RollCallString
        MAX-ACCESS        read-write
        STATUS            current
        DESCRIPTION
                "CMNT: - Embedded audio input name
                 TYPE: - Editstring
                 PAGE: - Disembedder Names
                    Disembed 7  cmdID= 37512
                    preset= Disembed 7"
        ::= { iqsyn21CmdEntry 37512 }


    iqsyn21DisembedderNamesDisemb7R OBJECT-TYPE
        SYNTAX            RollCallString
        MAX-ACCESS        read-write
        STATUS            current
        DESCRIPTION
                "CMNT: - Embedded audio input name
                 TYPE: - Editstring
                 PAGE: - Disembedder Names
                    Disembed 7-R  cmdID= 37513
                    preset= Disembed 7-R"
        ::= { iqsyn21CmdEntry 37513 }


    iqsyn21DisembedderNamesDisemb8L OBJECT-TYPE
        SYNTAX            RollCallString
        MAX-ACCESS        read-write
        STATUS            current
        DESCRIPTION
                "CMNT: - Embedded audio input name
                 TYPE: - Editstring
                 PAGE: - Disembedder Names
                    Disembed 8  cmdID= 37514
                    preset= Disembed 8"
        ::= { iqsyn21CmdEntry 37514 }


    iqsyn21DisembedderNamesDisemb8R OBJECT-TYPE
        SYNTAX            RollCallString
        MAX-ACCESS        read-write
        STATUS            current
        DESCRIPTION
                "CMNT: - Embedded audio input name
                 TYPE: - Editstring
                 PAGE: - Disembedder Names
                    Disembed 8-R  cmdID= 37515
                    preset= Disembed 8-R"
        ::= { iqsyn21CmdEntry 37515 }


    iqsyn21DisembedderNamesEmbeddedOPEmbed1L OBJECT-TYPE
        SYNTAX            RollCallString
        MAX-ACCESS        read-write
        STATUS            current
        DESCRIPTION
                "CMNT: - Embedded audio output name
                 TYPE: - Editstring
                 PAGE: - Disembedder Names
                    Embed 1  cmdID= 37520
                    preset= Embed 1"
        ::= { iqsyn21CmdEntry 37520 }


    iqsyn21DisembedderNamesEmbeddedOPEmbed1R OBJECT-TYPE
        SYNTAX            RollCallString
        MAX-ACCESS        read-write
        STATUS            current
        DESCRIPTION
                "CMNT: - Embedded audio output name
                 TYPE: - Editstring
                 PAGE: - Disembedder Names
                    Embed 1-R  cmdID= 37521
                    preset= Embed 1-R"
        ::= { iqsyn21CmdEntry 37521 }


    iqsyn21DisembedderNamesEmbeddedOPEmbed2L OBJECT-TYPE
        SYNTAX            RollCallString
        MAX-ACCESS        read-write
        STATUS            current
        DESCRIPTION
                "CMNT: - Embedded audio output name
                 TYPE: - Editstring
                 PAGE: - Disembedder Names
                    Embed 2  cmdID= 37522
                    preset= Embed 2"
        ::= { iqsyn21CmdEntry 37522 }


    iqsyn21DisembedderNamesEmbeddedOPEmbed2R OBJECT-TYPE
        SYNTAX            RollCallString
        MAX-ACCESS        read-write
        STATUS            current
        DESCRIPTION
                "CMNT: - Embedded audio output name
                 TYPE: - Editstring
                 PAGE: - Disembedder Names
                    Embed 2-R  cmdID= 37523
                    preset= Embed 2-R"
        ::= { iqsyn21CmdEntry 37523 }


    iqsyn21DisembedderNamesEmbeddedOPEmbed3L OBJECT-TYPE
        SYNTAX            RollCallString
        MAX-ACCESS        read-write
        STATUS            current
        DESCRIPTION
                "CMNT: - Embedded audio output name
                 TYPE: - Editstring
                 PAGE: - Disembedder Names
                    Embed 3  cmdID= 37524
                    preset= Embed 3"
        ::= { iqsyn21CmdEntry 37524 }


    iqsyn21DisembedderNamesEmbeddedOPEmbed3R OBJECT-TYPE
        SYNTAX            RollCallString
        MAX-ACCESS        read-write
        STATUS            current
        DESCRIPTION
                "CMNT: - Embedded audio output name
                 TYPE: - Editstring
                 PAGE: - Disembedder Names
                    Embed 3-R  cmdID= 37525
                    preset= Embed 3-R"
        ::= { iqsyn21CmdEntry 37525 }


    iqsyn21DisembedderNamesEmbeddedOPEmbed4L OBJECT-TYPE
        SYNTAX            RollCallString
        MAX-ACCESS        read-write
        STATUS            current
        DESCRIPTION
                "CMNT: - Embedded audio output name
                 TYPE: - Editstring
                 PAGE: - Disembedder Names
                    Embed 4  cmdID= 37526
                    preset= Embed 4"
        ::= { iqsyn21CmdEntry 37526 }


    iqsyn21DisembedderNamesEmbeddedOPEmbed4R OBJECT-TYPE
        SYNTAX            RollCallString
        MAX-ACCESS        read-write
        STATUS            current
        DESCRIPTION
                "CMNT: - Embedded audio output name
                 TYPE: - Editstring
                 PAGE: - Disembedder Names
                    Embed 4-R  cmdID= 37527
                    preset= Embed 4-R"
        ::= { iqsyn21CmdEntry 37527 }


    iqsyn21DisembedderNamesEmbeddedOPEmbed5L OBJECT-TYPE
        SYNTAX            RollCallString
        MAX-ACCESS        read-write
        STATUS            current
        DESCRIPTION
                "CMNT: - Embedded audio output name
                 TYPE: - Editstring
                 PAGE: - Disembedder Names
                    Embed 5  cmdID= 37528
                    preset= Embed 5"
        ::= { iqsyn21CmdEntry 37528 }


    iqsyn21DisembedderNamesEmbeddedOPEmbed5R OBJECT-TYPE
        SYNTAX            RollCallString
        MAX-ACCESS        read-write
        STATUS            current
        DESCRIPTION
                "CMNT: - Embedded audio output name
                 TYPE: - Editstring
                 PAGE: - Disembedder Names
                    Embed 5-R  cmdID= 37529
                    preset= Embed 5-R"
        ::= { iqsyn21CmdEntry 37529 }


    iqsyn21DisembedderNamesEmbeddedOPEmbed6L OBJECT-TYPE
        SYNTAX            RollCallString
        MAX-ACCESS        read-write
        STATUS            current
        DESCRIPTION
                "CMNT: - Embedded audio output name
                 TYPE: - Editstring
                 PAGE: - Disembedder Names
                    Embed 6  cmdID= 37530
                    preset= Embed 6"
        ::= { iqsyn21CmdEntry 37530 }


    iqsyn21DisembedderNamesEmbeddedOPEmbed6R OBJECT-TYPE
        SYNTAX            RollCallString
        MAX-ACCESS        read-write
        STATUS            current
        DESCRIPTION
                "CMNT: - Embedded audio output name
                 TYPE: - Editstring
                 PAGE: - Disembedder Names
                    Embed 6-R  cmdID= 37531
                    preset= Embed 6-R"
        ::= { iqsyn21CmdEntry 37531 }


    iqsyn21DisembedderNamesEmbeddedOPEmbed7L OBJECT-TYPE
        SYNTAX            RollCallString
        MAX-ACCESS        read-write
        STATUS            current
        DESCRIPTION
                "CMNT: - Embedded audio output name
                 TYPE: - Editstring
                 PAGE: - Disembedder Names
                    Embed 7  cmdID= 37532
                    preset= Embed 7"
        ::= { iqsyn21CmdEntry 37532 }


    iqsyn21DisembedderNamesEmbeddedOPEmbed7R OBJECT-TYPE
        SYNTAX            RollCallString
        MAX-ACCESS        read-write
        STATUS            current
        DESCRIPTION
                "CMNT: - Embedded audio output name
                 TYPE: - Editstring
                 PAGE: - Disembedder Names
                    Embed 7-R  cmdID= 37533
                    preset= Embed 7-R"
        ::= { iqsyn21CmdEntry 37533 }


    iqsyn21DisembedderNamesEmbeddedOPEmbed8L OBJECT-TYPE
        SYNTAX            RollCallString
        MAX-ACCESS        read-write
        STATUS            current
        DESCRIPTION
                "CMNT: - Embedded audio output name
                 TYPE: - Editstring
                 PAGE: - Disembedder Names
                    Embed 8  cmdID= 37534
                    preset= Embed 8"
        ::= { iqsyn21CmdEntry 37534 }


    iqsyn21DisembedderNamesEmbeddedOPEmbed8R OBJECT-TYPE
        SYNTAX            RollCallString
        MAX-ACCESS        read-write
        STATUS            current
        DESCRIPTION
                "CMNT: - Embedded audio output name
                 TYPE: - Editstring
                 PAGE: - Disembedder Names
                    Embed 8-R  cmdID= 37535
                    preset= Embed 8-R"
        ::= { iqsyn21CmdEntry 37535 }


    iqsyn21DisembedderNamesIPNamesStereoDisemb1 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 1  cmdID= 37400  "
        ::= { iqsyn21CmdEntry 37400 }


    iqsyn21DisembedderNamesIPNamesStereoDisemb2 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 2  cmdID= 37401  "
        ::= { iqsyn21CmdEntry 37401 }


    iqsyn21DisembedderNamesIPNamesStereoDisemb3 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 3  cmdID= 37402  "
        ::= { iqsyn21CmdEntry 37402 }


    iqsyn21DisembedderNamesIPNamesStereoDisemb4 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 4  cmdID= 37403  "
        ::= { iqsyn21CmdEntry 37403 }


    iqsyn21DisembedderNamesIPNamesStereoDisemb5 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 5  cmdID= 37404  "
        ::= { iqsyn21CmdEntry 37404 }


    iqsyn21DisembedderNamesIPNamesStereoDisemb6 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 6  cmdID= 37405  "
        ::= { iqsyn21CmdEntry 37405 }


    iqsyn21DisembedderNamesIPNamesStereoDisemb7 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 7  cmdID= 37406  "
        ::= { iqsyn21CmdEntry 37406 }


    iqsyn21DisembedderNamesIPNamesStereoDisemb8 OBJECT-TYPE
        SYNTAX            INTEGER { disable(0), enable(1)  }
        MAX-ACCESS        read-write
        STATUS            current
        DESCRIPTION
                "CMNT: - Embedded input pair names are stereo
                 TYPE: - Checkbox
                 PAGE: - Disembedder Names
                    Disemb 8  cmdID= 37407  "
        ::= { iqsyn21CmdEntry 37407 }


    iqsyn21DisembedderNamesOPNamesStereoEmbed1 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 1  cmdID= 37410  "
        ::= { iqsyn21CmdEntry 37410 }


    iqsyn21DisembedderNamesOPNamesStereoEmbed2 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 2  cmdID= 37411  "
        ::= { iqsyn21CmdEntry 37411 }


    iqsyn21DisembedderNamesOPNamesStereoEmbed3 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 3  cmdID= 37412  "
        ::= { iqsyn21CmdEntry 37412 }


    iqsyn21DisembedderNamesOPNamesStereoEmbed4 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 4  cmdID= 37413  "
        ::= { iqsyn21CmdEntry 37413 }


    iqsyn21DisembedderNamesOPNamesStereoEmbed5 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 5  cmdID= 37414  "
        ::= { iqsyn21CmdEntry 37414 }


    iqsyn21DisembedderNamesOPNamesStereoEmbed6 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 6  cmdID= 37415  "
        ::= { iqsyn21CmdEntry 37415 }


    iqsyn21DisembedderNamesOPNamesStereoEmbed7 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 7  cmdID= 37416  "
        ::= { iqsyn21CmdEntry 37416 }


    iqsyn21DisembedderNamesOPNamesStereoEmbed8 OBJECT-TYPE
        SYNTAX            INTEGER { disable(0), enable(1)  }
        MAX-ACCESS        read-write
        STATUS            current
        DESCRIPTION
                "CMNT: - Embedded output pair names are stereo
                 TYPE: - Checkbox
                 PAGE: - Disembedder Names
                    Embed 8  cmdID= 37417  "
        ::= { iqsyn21CmdEntry 37417 }


    iqsyn21NamesMixNamesMix1 OBJECT-TYPE
        SYNTAX            RollCallString
        MAX-ACCESS        read-write
        STATUS            current
        DESCRIPTION
                "CMNT: - Mixer names
                 TYPE: - Editstring
                 PAGE: - Names
                    Mix 1  cmdID= 37810
                    preset= Mixer 1"
        ::= { iqsyn21CmdEntry 37810 }


    iqsyn21NamesMixNamesMix2 OBJECT-TYPE
        SYNTAX            RollCallString
        MAX-ACCESS        read-write
        STATUS            current
        DESCRIPTION
                "CMNT: - Mixer names
                 TYPE: - Editstring
                 PAGE: - Names
                    Mix 2  cmdID= 37811
                    preset= Mixer 2"
        ::= { iqsyn21CmdEntry 37811 }


    iqsyn21NamesMixNamesMix3 OBJECT-TYPE
        SYNTAX            RollCallString
        MAX-ACCESS        read-write
        STATUS            current
        DESCRIPTION
                "CMNT: - Mixer names
                 TYPE: - Editstring
                 PAGE: - Names
                    Mix 3  cmdID= 37812
                    preset= Mixer 3"
        ::= { iqsyn21CmdEntry 37812 }


    iqsyn21NamesMixNamesMix4 OBJECT-TYPE
        SYNTAX            RollCallString
        MAX-ACCESS        read-write
        STATUS            current
        DESCRIPTION
                "CMNT: - Mixer names
                 TYPE: - Editstring
                 PAGE: - Names
                    Mix 4  cmdID= 37813
                    preset= Mixer 4"
        ::= { iqsyn21CmdEntry 37813 }


    iqsyn21Mix1Mix1RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37600
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37600 }


    iqsyn21Mix1Mix1RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37720  "
        ::= { iqsyn21CmdEntry 37720 }


    iqsyn21Mix1Mix1RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37601
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37601 }


    iqsyn21Mix1Mix1RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37721  "
        ::= { iqsyn21CmdEntry 37721 }


    iqsyn21Mix1Mix1RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37602
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37602 }


    iqsyn21Mix1Mix1RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37722  "
        ::= { iqsyn21CmdEntry 37722 }


    iqsyn21Mix1Mix1RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37603
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37603 }


    iqsyn21Mix1Mix1RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37723  "
        ::= { iqsyn21CmdEntry 37723 }


    iqsyn21Mix1Mix1GainGain1 OBJECT-TYPE
        SYNTAX            INTEGER
        MAX-ACCESS        read-write
        STATUS            current
        DESCRIPTION
                "CMNT: - Mixer source gain
                 TYPE: - Number
                 PAGE: - Audio
                    Gain 1  cmdID= 37640
                    min= -360  max= 120  step= 1  format= %0.1f dB  div_scale= 10  preset= 0
                    Min = -36.0 dB  Max = 12.0 dB  Step = 0.1 dB  Preset = 0.0 dB  "
        ::= { iqsyn21CmdEntry 37640 }


    iqsyn21Mix1Mix1GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37680  "
        ::= { iqsyn21CmdEntry 37680 }


    iqsyn21Mix1Mix1GainGain2 OBJECT-TYPE
        SYNTAX            INTEGER
        MAX-ACCESS        read-write
        STATUS            current
        DESCRIPTION
                "CMNT: - Mixer source gain
                 TYPE: - Number
                 PAGE: - Audio
                    Gain 2  cmdID= 37641
                    min= -360  max= 120  step= 1  format= %0.1f dB  div_scale= 10  preset= 0
                    Min = -36.0 dB  Max = 12.0 dB  Step = 0.1 dB  Preset = 0.0 dB  "
        ::= { iqsyn21CmdEntry 37641 }


    iqsyn21Mix1Mix1GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37681  "
        ::= { iqsyn21CmdEntry 37681 }


    iqsyn21Mix1Mix1GainGain3 OBJECT-TYPE
        SYNTAX            INTEGER
        MAX-ACCESS        read-write
        STATUS            current
        DESCRIPTION
                "CMNT: - Mixer source gain
                 TYPE: - Number
                 PAGE: - Audio
                    Gain 3  cmdID= 37642
                    min= -360  max= 120  step= 1  format= %0.1f dB  div_scale= 10  preset= 0
                    Min = -36.0 dB  Max = 12.0 dB  Step = 0.1 dB  Preset = 0.0 dB  "
        ::= { iqsyn21CmdEntry 37642 }


    iqsyn21Mix1Mix1GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37682  "
        ::= { iqsyn21CmdEntry 37682 }


    iqsyn21Mix1Mix1GainGain4 OBJECT-TYPE
        SYNTAX            INTEGER
        MAX-ACCESS        read-write
        STATUS            current
        DESCRIPTION
                "CMNT: - Mixer source gain
                 TYPE: - Number
                 PAGE: - Audio
                    Gain 4  cmdID= 37643
                    min= -360  max= 120  step= 1  format= %0.1f dB  div_scale= 10  preset= 0
                    Min = -36.0 dB  Max = 12.0 dB  Step = 0.1 dB  Preset = 0.0 dB  "
        ::= { iqsyn21CmdEntry 37643 }


    iqsyn21Mix1Mix1GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37683  "
        ::= { iqsyn21CmdEntry 37683 }


    iqsyn21Mix1Mix1GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37760  "
        ::= { iqsyn21CmdEntry 37760 }


    iqsyn21Mix1Mix1GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37761  "
        ::= { iqsyn21CmdEntry 37761 }


    iqsyn21Mix1Mix1GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37762  "
        ::= { iqsyn21CmdEntry 37762 }


    iqsyn21Mix1Mix1GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37763  "
        ::= { iqsyn21CmdEntry 37763 }


    iqsyn21Mix1Mix1GainOPClip OBJECT-TYPE
        SYNTAX            RollCallString
        MAX-ACCESS        read-only
        STATUS            current
        DESCRIPTION
                "CMNT: - Audio Mixer output clipped
                 TYPE: - Display
                 PAGE: - Audio
                    O/P Clip  cmdID= 37800  "
        ::= { iqsyn21CmdEntry 37800 }


    iqsyn21Mix2Mix2RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37604
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37604 }


    iqsyn21Mix2Mix2RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37724  "
        ::= { iqsyn21CmdEntry 37724 }


    iqsyn21Mix2Mix2RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37605
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37605 }


    iqsyn21Mix2Mix2RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37725  "
        ::= { iqsyn21CmdEntry 37725 }


    iqsyn21Mix2Mix2RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37606
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37606 }


    iqsyn21Mix2Mix2RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37726  "
        ::= { iqsyn21CmdEntry 37726 }


    iqsyn21Mix2Mix2RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37607
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37607 }


    iqsyn21Mix2Mix2RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37727  "
        ::= { iqsyn21CmdEntry 37727 }


    iqsyn21Mix2Mix2GainGain1 OBJECT-TYPE
        SYNTAX            INTEGER
        MAX-ACCESS        read-write
        STATUS            current
        DESCRIPTION
                "CMNT: - Mixer source gain
                 TYPE: - Number
                 PAGE: - Audio
                    Gain 1  cmdID= 37644
                    min= -360  max= 120  step= 1  format= %0.1f dB  div_scale= 10  preset= 0
                    Min = -36.0 dB  Max = 12.0 dB  Step = 0.1 dB  Preset = 0.0 dB  "
        ::= { iqsyn21CmdEntry 37644 }


    iqsyn21Mix2Mix2GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37684  "
        ::= { iqsyn21CmdEntry 37684 }


    iqsyn21Mix2Mix2GainGain2 OBJECT-TYPE
        SYNTAX            INTEGER
        MAX-ACCESS        read-write
        STATUS            current
        DESCRIPTION
                "CMNT: - Mixer source gain
                 TYPE: - Number
                 PAGE: - Audio
                    Gain 2  cmdID= 37645
                    min= -360  max= 120  step= 1  format= %0.1f dB  div_scale= 10  preset= 0
                    Min = -36.0 dB  Max = 12.0 dB  Step = 0.1 dB  Preset = 0.0 dB  "
        ::= { iqsyn21CmdEntry 37645 }


    iqsyn21Mix2Mix2GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37685  "
        ::= { iqsyn21CmdEntry 37685 }


    iqsyn21Mix2Mix2GainGain3 OBJECT-TYPE
        SYNTAX            INTEGER
        MAX-ACCESS        read-write
        STATUS            current
        DESCRIPTION
                "CMNT: - Mixer source gain
                 TYPE: - Number
                 PAGE: - Audio
                    Gain 3  cmdID= 37646
                    min= -360  max= 120  step= 1  format= %0.1f dB  div_scale= 10  preset= 0
                    Min = -36.0 dB  Max = 12.0 dB  Step = 0.1 dB  Preset = 0.0 dB  "
        ::= { iqsyn21CmdEntry 37646 }


    iqsyn21Mix2Mix2GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37686  "
        ::= { iqsyn21CmdEntry 37686 }


    iqsyn21Mix2Mix2GainGain4 OBJECT-TYPE
        SYNTAX            INTEGER
        MAX-ACCESS        read-write
        STATUS            current
        DESCRIPTION
                "CMNT: - Mixer source gain
                 TYPE: - Number
                 PAGE: - Audio
                    Gain 4  cmdID= 37647
                    min= -360  max= 120  step= 1  format= %0.1f dB  div_scale= 10  preset= 0
                    Min = -36.0 dB  Max = 12.0 dB  Step = 0.1 dB  Preset = 0.0 dB  "
        ::= { iqsyn21CmdEntry 37647 }


    iqsyn21Mix2Mix2GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37687  "
        ::= { iqsyn21CmdEntry 37687 }


    iqsyn21Mix2Mix2GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37764  "
        ::= { iqsyn21CmdEntry 37764 }


    iqsyn21Mix2Mix2GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37765  "
        ::= { iqsyn21CmdEntry 37765 }


    iqsyn21Mix2Mix2GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37766  "
        ::= { iqsyn21CmdEntry 37766 }


    iqsyn21Mix2Mix2GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37767  "
        ::= { iqsyn21CmdEntry 37767 }


    iqsyn21Mix2Mix2GainOPClip OBJECT-TYPE
        SYNTAX            RollCallString
        MAX-ACCESS        read-only
        STATUS            current
        DESCRIPTION
                "CMNT: - Audio Mixer output clipped
                 TYPE: - Display
                 PAGE: - Audio
                    O/P Clip  cmdID= 37801  "
        ::= { iqsyn21CmdEntry 37801 }


    iqsyn21Mix3Mix3RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37608
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37608 }


    iqsyn21Mix3Mix3RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37728  "
        ::= { iqsyn21CmdEntry 37728 }


    iqsyn21Mix3Mix3RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37609
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37609 }


    iqsyn21Mix3Mix3RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37729  "
        ::= { iqsyn21CmdEntry 37729 }


    iqsyn21Mix3Mix3RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37610
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37610 }


    iqsyn21Mix3Mix3RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37730  "
        ::= { iqsyn21CmdEntry 37730 }


    iqsyn21Mix3Mix3RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37611
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37611 }


    iqsyn21Mix3Mix3RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37731  "
        ::= { iqsyn21CmdEntry 37731 }


    iqsyn21Mix3Mix3GainGain1 OBJECT-TYPE
        SYNTAX            INTEGER
        MAX-ACCESS        read-write
        STATUS            current
        DESCRIPTION
                "CMNT: - Mixer source gain
                 TYPE: - Number
                 PAGE: - Audio
                    Gain 1  cmdID= 37648
                    min= -360  max= 120  step= 1  format= %0.1f dB  div_scale= 10  preset= 0
                    Min = -36.0 dB  Max = 12.0 dB  Step = 0.1 dB  Preset = 0.0 dB  "
        ::= { iqsyn21CmdEntry 37648 }


    iqsyn21Mix3Mix3GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37688  "
        ::= { iqsyn21CmdEntry 37688 }


    iqsyn21Mix3Mix3GainGain2 OBJECT-TYPE
        SYNTAX            INTEGER
        MAX-ACCESS        read-write
        STATUS            current
        DESCRIPTION
                "CMNT: - Mixer source gain
                 TYPE: - Number
                 PAGE: - Audio
                    Gain 2  cmdID= 37649
                    min= -360  max= 120  step= 1  format= %0.1f dB  div_scale= 10  preset= 0
                    Min = -36.0 dB  Max = 12.0 dB  Step = 0.1 dB  Preset = 0.0 dB  "
        ::= { iqsyn21CmdEntry 37649 }


    iqsyn21Mix3Mix3GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37689  "
        ::= { iqsyn21CmdEntry 37689 }


    iqsyn21Mix3Mix3GainGain3 OBJECT-TYPE
        SYNTAX            INTEGER
        MAX-ACCESS        read-write
        STATUS            current
        DESCRIPTION
                "CMNT: - Mixer source gain
                 TYPE: - Number
                 PAGE: - Audio
                    Gain 3  cmdID= 37650
                    min= -360  max= 120  step= 1  format= %0.1f dB  div_scale= 10  preset= 0
                    Min = -36.0 dB  Max = 12.0 dB  Step = 0.1 dB  Preset = 0.0 dB  "
        ::= { iqsyn21CmdEntry 37650 }


    iqsyn21Mix3Mix3GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37690  "
        ::= { iqsyn21CmdEntry 37690 }


    iqsyn21Mix3Mix3GainGain4 OBJECT-TYPE
        SYNTAX            INTEGER
        MAX-ACCESS        read-write
        STATUS            current
        DESCRIPTION
                "CMNT: - Mixer source gain
                 TYPE: - Number
                 PAGE: - Audio
                    Gain 4  cmdID= 37651
                    min= -360  max= 120  step= 1  format= %0.1f dB  div_scale= 10  preset= 0
                    Min = -36.0 dB  Max = 12.0 dB  Step = 0.1 dB  Preset = 0.0 dB  "
        ::= { iqsyn21CmdEntry 37651 }


    iqsyn21Mix3Mix3GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37691  "
        ::= { iqsyn21CmdEntry 37691 }


    iqsyn21Mix3Mix3GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37768  "
        ::= { iqsyn21CmdEntry 37768 }


    iqsyn21Mix3Mix3GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37769  "
        ::= { iqsyn21CmdEntry 37769 }


    iqsyn21Mix3Mix3GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37770  "
        ::= { iqsyn21CmdEntry 37770 }


    iqsyn21Mix3Mix3GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37771  "
        ::= { iqsyn21CmdEntry 37771 }


    iqsyn21Mix3Mix3GainOPClip OBJECT-TYPE
        SYNTAX            RollCallString
        MAX-ACCESS        read-only
        STATUS            current
        DESCRIPTION
                "CMNT: - Audio Mixer output clipped
                 TYPE: - Display
                 PAGE: - Audio
                    O/P Clip  cmdID= 37802  "
        ::= { iqsyn21CmdEntry 37802 }


    iqsyn21Mix4Mix4RoutingSource1 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 1  cmdID= 37612
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37612 }


    iqsyn21Mix4Mix4RoutingInvert1 OBJECT-TYPE
        SYNTAX            INTEGER { disable(0), enable(1)  }
        MAX-ACCESS        read-write
        STATUS            current
        DESCRIPTION
                "CMNT: - Mixer source phase invert
                 TYPE: - Checkbox
                 PAGE: - Audio
                    Invert 1  cmdID= 37732  "
        ::= { iqsyn21CmdEntry 37732 }


    iqsyn21Mix4Mix4RoutingSource2 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 2  cmdID= 37613
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37613 }


    iqsyn21Mix4Mix4RoutingInvert2 OBJECT-TYPE
        SYNTAX            INTEGER { disable(0), enable(1)  }
        MAX-ACCESS        read-write
        STATUS            current
        DESCRIPTION
                "CMNT: - Mixer source phase invert
                 TYPE: - Checkbox
                 PAGE: - Audio
                    Invert 2  cmdID= 37733  "
        ::= { iqsyn21CmdEntry 37733 }


    iqsyn21Mix4Mix4RoutingSource3 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 3  cmdID= 37614
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37614 }


    iqsyn21Mix4Mix4RoutingInvert3 OBJECT-TYPE
        SYNTAX            INTEGER { disable(0), enable(1)  }
        MAX-ACCESS        read-write
        STATUS            current
        DESCRIPTION
                "CMNT: - Mixer source phase invert
                 TYPE: - Checkbox
                 PAGE: - Audio
                    Invert 3  cmdID= 37734  "
        ::= { iqsyn21CmdEntry 37734 }


    iqsyn21Mix4Mix4RoutingSource4 OBJECT-TYPE
        SYNTAX            INTEGER {
                            valMute(-1),
                            valDisembed1nL(1),
                            valDisembed1nR(2),
                            valDisembed2nL(3),
                            valDisembed2nR(4),
                            valDisembed3nL(5),
                            valDisembed3nR(6),
                            valDisembed4nL(7),
                            valDisembed4nR(8),
                            valDisembed5nL(9),
                            valDisembed5nR(10),
                            valDisembed6nL(11),
                            valDisembed6nR(12),
                            valDisembed7nL(13),
                            valDisembed7nR(14),
                            valDisembed8nL(15),
                            valDisembed8nR(16),
                            val1kHzn20dBFSTone(17),
                            val2kHzn20dBFSTone(18),
                            val4kHzn20dBFSTone(19),
                            val1kHzn18dBFSTone(20),
                            val2kHzn18dBFSTone(21),
                            val4kHzn18dBFSTone(22)
                            }
        MAX-ACCESS        read-write
        STATUS            current
        DESCRIPTION
                "CMNT: - Mixer sources
                 TYPE: - RadiobuttonList
                 PAGE: - Audio
                    Source 4  cmdID= 37615
                    Mute  value= -1
                    Disembed 1-L  value= 1
                    Disembed 1-R  value= 2
                    Disembed 2-L  value= 3
                    Disembed 2-R  value= 4
                    Disembed 3-L  value= 5
                    Disembed 3-R  value= 6
                    Disembed 4-L  value= 7
                    Disembed 4-R  value= 8
                    Disembed 5-L  value= 9
                    Disembed 5-R  value= 10
                    Disembed 6-L  value= 11
                    Disembed 6-R  value= 12
                    Disembed 7-L  value= 13
                    Disembed 7-R  value= 14
                    Disembed 8-L  value= 15
                    Disembed 8-R  value= 16
                    1kHz -20dBFS Tone  value= 17
                    2kHz -20dBFS Tone  value= 18
                    4kHz -20dBFS Tone  value= 19
                    1kHz -18dBFS Tone  value= 20
                    2kHz -18dBFS Tone  value= 21
                    4kHz -18dBFS Tone  value= 22  "
        ::= { iqsyn21CmdEntry 37615 }


    iqsyn21Mix4Mix4RoutingInvert4 OBJECT-TYPE
        SYNTAX            INTEGER { disable(0), enable(1)  }
        MAX-ACCESS        read-write
        STATUS            current
        DESCRIPTION
                "CMNT: - Mixer source phase invert
                 TYPE: - Checkbox
                 PAGE: - Audio
                    Invert 4  cmdID= 37735  "
        ::= { iqsyn21CmdEntry 37735 }


    iqsyn21Mix4Mix4GainGain1 OBJECT-TYPE
        SYNTAX            INTEGER
        MAX-ACCESS        read-write
        STATUS            current
        DESCRIPTION
                "CMNT: - Mixer source gain
                 TYPE: - Number
                 PAGE: - Audio
                    Gain 1  cmdID= 37652
                    min= -360  max= 120  step= 1  format= %0.1f dB  div_scale= 10  preset= 0
                    Min = -36.0 dB  Max = 12.0 dB  Step = 0.1 dB  Preset = 0.0 dB  "
        ::= { iqsyn21CmdEntry 37652 }


    iqsyn21Mix4Mix4GainMute1 OBJECT-TYPE
        SYNTAX            INTEGER { disable(0), enable(1)  }
        MAX-ACCESS        read-write
        STATUS            current
        DESCRIPTION
                "CMNT: - Mixer source mutes
                 TYPE: - Checkbox
                 PAGE: - Audio
                    Mute 1  cmdID= 37692  "
        ::= { iqsyn21CmdEntry 37692 }


    iqsyn21Mix4Mix4GainGain2 OBJECT-TYPE
        SYNTAX            INTEGER
        MAX-ACCESS        read-write
        STATUS            current
        DESCRIPTION
                "CMNT: - Mixer source gain
                 TYPE: - Number
                 PAGE: - Audio
                    Gain 2  cmdID= 37653
                    min= -360  max= 120  step= 1  format= %0.1f dB  div_scale= 10  preset= 0
                    Min = -36.0 dB  Max = 12.0 dB  Step = 0.1 dB  Preset = 0.0 dB  "
        ::= { iqsyn21CmdEntry 37653 }


    iqsyn21Mix4Mix4GainMute2 OBJECT-TYPE
        SYNTAX            INTEGER { disable(0), enable(1)  }
        MAX-ACCESS        read-write
        STATUS            current
        DESCRIPTION
                "CMNT: - Mixer source mutes
                 TYPE: - Checkbox
                 PAGE: - Audio
                    Mute 2  cmdID= 37693  "
        ::= { iqsyn21CmdEntry 37693 }


    iqsyn21Mix4Mix4GainGain3 OBJECT-TYPE
        SYNTAX            INTEGER
        MAX-ACCESS        read-write
        STATUS            current
        DESCRIPTION
                "CMNT: - Mixer source gain
                 TYPE: - Number
                 PAGE: - Audio
                    Gain 3  cmdID= 37654
                    min= -360  max= 120  step= 1  format= %0.1f dB  div_scale= 10  preset= 0
                    Min = -36.0 dB  Max = 12.0 dB  Step = 0.1 dB  Preset = 0.0 dB  "
        ::= { iqsyn21CmdEntry 37654 }


    iqsyn21Mix4Mix4GainMute3 OBJECT-TYPE
        SYNTAX            INTEGER { disable(0), enable(1)  }
        MAX-ACCESS        read-write
        STATUS            current
        DESCRIPTION
                "CMNT: - Mixer source mutes
                 TYPE: - Checkbox
                 PAGE: - Audio
                    Mute 3  cmdID= 37694  "
        ::= { iqsyn21CmdEntry 37694 }


    iqsyn21Mix4Mix4GainGain4 OBJECT-TYPE
        SYNTAX            INTEGER
        MAX-ACCESS        read-write
        STATUS            current
        DESCRIPTION
                "CMNT: - Mixer source gain
                 TYPE: - Number
                 PAGE: - Audio
                    Gain 4  cmdID= 37655
                    min= -360  max= 120  step= 1  format= %0.1f dB  div_scale= 10  preset= 0
                    Min = -36.0 dB  Max = 12.0 dB  Step = 0.1 dB  Preset = 0.0 dB  "
        ::= { iqsyn21CmdEntry 37655 }


    iqsyn21Mix4Mix4GainMute4 OBJECT-TYPE
        SYNTAX            INTEGER { disable(0), enable(1)  }
        MAX-ACCESS        read-write
        STATUS            current
        DESCRIPTION
                "CMNT: - Mixer source mutes
                 TYPE: - Checkbox
                 PAGE: - Audio
                    Mute 4  cmdID= 37695  "
        ::= { iqsyn21CmdEntry 37695 }


    iqsyn21Mix4Mix4GainInp1Clip OBJECT-TYPE
        SYNTAX            RollCallString
        MAX-ACCESS        read-only
        STATUS            current
        DESCRIPTION
                "CMNT: - Audio Mixer source clipped
                 TYPE: - Display
                 PAGE: - Audio
                    Inp1 Clip  cmdID= 37772  "
        ::= { iqsyn21CmdEntry 37772 }


    iqsyn21Mix4Mix4GainInp2Clip OBJECT-TYPE
        SYNTAX            RollCallString
        MAX-ACCESS        read-only
        STATUS            current
        DESCRIPTION
                "CMNT: - Audio Mixer source clipped
                 TYPE: - Display
                 PAGE: - Audio
                    Inp2 Clip  cmdID= 37773  "
        ::= { iqsyn21CmdEntry 37773 }


    iqsyn21Mix4Mix4GainInp3Clip OBJECT-TYPE
        SYNTAX            RollCallString
        MAX-ACCESS        read-only
        STATUS            current
        DESCRIPTION
                "CMNT: - Audio Mixer source clipped
                 TYPE: - Display
                 PAGE: - Audio
                    Inp3 Clip  cmdID= 37774  "
        ::= { iqsyn21CmdEntry 37774 }


    iqsyn21Mix4Mix4GainInp4Clip OBJECT-TYPE
        SYNTAX            RollCallString
        MAX-ACCESS        read-only
        STATUS            current
        DESCRIPTION
                "CMNT: - Audio Mixer source clipped
                 TYPE: - Display
                 PAGE: - Audio
                    Inp4 Clip  cmdID= 37775  "
        ::= { iqsyn21CmdEntry 37775 }


    iqsyn21Mix4Mix4GainOPClip OBJECT-TYPE
        SYNTAX            RollCallString
        MAX-ACCESS        read-only
        STATUS            current
        DESCRIPTION
                "CMNT: - Audio Mixer output clipped
                 TYPE: - Display
                 PAGE: - Audio
                    O/P Clip  cmdID= 37803  "
        ::= { iqsyn21CmdEntry 37803 }


    iqsyn21AudioDolbyETimingSelAudioPair OBJECT-TYPE
        SYNTAX            INTEGER
        MAX-ACCESS        read-write
        STATUS            current
        DESCRIPTION
                "CMNT: - 
                 TYPE: - Number
                 PAGE: - Audio
                    Sel Audio Pair  cmdID= 38650
                    min= 1  max= 8  step= 1  format= %0.0f  div_scale= 1  preset= 1
                    Min = 1  Max = 8  Step = 1  Preset = 1  "
        ::= { iqsyn21CmdEntry 38650 }


    iqsyn21AudioDolbyETimingRelativeTiming OBJECT-TYPE
        SYNTAX            RollCallString
        MAX-ACCESS        read-only
        STATUS            current
        DESCRIPTION
                "CMNT: - 
                 TYPE: - Display
                 PAGE: - Audio
                    Relative Timing  cmdID= 38653  "
        ::= { iqsyn21CmdEntry 38653 }


    iqsyn21AudioDolbyETimingStatus OBJECT-TYPE
        SYNTAX            RollCallString
        MAX-ACCESS        read-only
        STATUS            current
        DESCRIPTION
                "CMNT: - 
                 TYPE: - Display
                 PAGE: - Audio
                    Status  cmdID= 38652  "
        ::= { iqsyn21CmdEntry 38652 }


    iqsyn21AudioDolbyETimingError OBJECT-TYPE
        SYNTAX            RollCallString
        MAX-ACCESS        read-only
        STATUS            current
        DESCRIPTION
                "CMNT: - 
                 TYPE: - Display
                 PAGE: - Audio
                    Error  cmdID= 38654  "
        ::= { iqsyn21CmdEntry 38654 }


    iqsyn21DolbyETimingDolbyELineStandard OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select standard to display Dolby E Auto-Line for
                 TYPE: - RadiobuttonList
                 PAGE: - Dolby E Timing
                    Standard  cmdID= 38655
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn21CmdEntry 38655 }


    iqsyn21DolbyETimingDolbyELineAutoLineNo OBJECT-TYPE
        SYNTAX            INTEGER
        MAX-ACCESS        read-write
        STATUS            current
        DESCRIPTION
                "CMNT: - Select standard to display Dolby E Auto-Line for
                 TYPE: - Number
                 PAGE: - Dolby E Timing
                    Auto Line No.  cmdID= 38656
                    min= 1  max= 10000  step= 1  format= %0.0f  div_scale= 1  preset= 1
                    Min = 1  Max = 10000  Step = 1  Preset = 1  "
        ::= { iqsyn21CmdEntry 38656 }


    iqsyn21DolbyELineUserDolbyELinePair1 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 1  cmdID= 38670
                    User Line  value= 1
                    Standard Line  value= 0  "
        ::= { iqsyn21CmdEntry 38670 }


    iqsyn21DolbyELineUserDolbyELinePair2 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 2  cmdID= 38671
                    User Line  value= 1
                    Standard Line  value= 0  "
        ::= { iqsyn21CmdEntry 38671 }


    iqsyn21DolbyELineUserDolbyELinePair3 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 3  cmdID= 38672
                    User Line  value= 1
                    Standard Line  value= 0  "
        ::= { iqsyn21CmdEntry 38672 }


    iqsyn21DolbyELineUserDolbyELinePair4 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 4  cmdID= 38673
                    User Line  value= 1
                    Standard Line  value= 0  "
        ::= { iqsyn21CmdEntry 38673 }


    iqsyn21DolbyELineUserDolbyELinePair5 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 5  cmdID= 38674
                    User Line  value= 1
                    Standard Line  value= 0  "
        ::= { iqsyn21CmdEntry 38674 }


    iqsyn21DolbyELineUserDolbyELinePair6 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 6  cmdID= 38675
                    User Line  value= 1
                    Standard Line  value= 0  "
        ::= { iqsyn21CmdEntry 38675 }


    iqsyn21DolbyELineUserDolbyELinePair7 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 7  cmdID= 38676
                    User Line  value= 1
                    Standard Line  value= 0  "
        ::= { iqsyn21CmdEntry 38676 }


    iqsyn21DolbyELineUserDolbyELinePair8 OBJECT-TYPE
        SYNTAX            INTEGER {
                            valUserLine(1),
                            valStandardLine(0)
                            }
        MAX-ACCESS        read-write
        STATUS            current
        DESCRIPTION
                "CMNT: - 
                 TYPE: - RadiobuttonList
                 PAGE: - Dolby E Line
                    Pair 8  cmdID= 38677
                    User Line  value= 1
                    Standard Line  value= 0  "
        ::= { iqsyn21CmdEntry 38677 }


    iqsyn21DolbyETimingDolbyELineSmoothCapRange OBJECT-TYPE
        SYNTAX            INTEGER {
                            valpn1Sample(1),
                            valpn60Samples(60)
                            }
        MAX-ACCESS        read-write
        STATUS            current
        DESCRIPTION
                "CMNT: - Dolby E Select Smooth Capture Range
                 TYPE: - RadiobuttonList
                 PAGE: - Dolby E Timing
                    Smooth Cap Range  cmdID= 38658
                    +/- 1 Sample  value= 1
                    +/- 60 Samples  value= 60  "
        ::= { iqsyn21CmdEntry 38658 }


    iqsyn21GenlockDelayMode OBJECT-TYPE
        SYNTAX            INTEGER {
                            valFreeRun(0),
                            valLocktoReference(1),
                            valMinimumAudio(3),
                            valFrames(4),
                            valManualHV(5),
                            valManualms(6)
                            }
        MAX-ACCESS        read-write
        STATUS            current
        DESCRIPTION
                "CMNT: - Video Reference Mode source: Free Run/LockRef/LockRef(Delay Mismatch)/Minimum/Frames/Manual/Manual ms
                 TYPE: - RadiobuttonList
                 PAGE: - Genlock
                    Delay Mode  cmdID= 33026
                    Free Run  value= 0
                    Lock to Reference  value= 1
                    Minimum Audio  value= 3
                    Frames  value= 4
                    Manual H/V  value= 5
                    Manual ms  value= 6  "
        ::= { iqsyn21CmdEntry 33026 }


    iqsyn21GenlockRefTimeDelayFrames OBJECT-TYPE
        SYNTAX            INTEGER
        MAX-ACCESS        read-write
        STATUS            current
        DESCRIPTION
                "CMNT: - Set video delay in frames
                 TYPE: - Number
                 PAGE: - Genlock
                    Delay Frames  cmdID= 33024
                    min= 0  max= 11  step= 1  format= %0.0f frames  div_scale= 1  preset= 0
                    Min = 0 frames  Max = 11 frames  Step = 1 frames  Preset = 0 frames  "
        ::= { iqsyn21CmdEntry 33024 }


    iqsyn21GenlockRefTimeVerticalTiming OBJECT-TYPE
        SYNTAX            INTEGER
        MAX-ACCESS        read-write
        STATUS            current
        DESCRIPTION
                "CMNT: - Reference vertical timing
                 TYPE: - Number
                 PAGE: - Genlock
                    Vertical Timing  cmdID= 33022
                    min= -1500  max= 1500  step= 1  format= %0.0f lines  div_scale= 1  preset= 0
                    Min = -1500 lines  Max = 1500 lines  Step = 1 lines  Preset = 0 lines  "
        ::= { iqsyn21CmdEntry 33022 }


    iqsyn21GenlockRefTimeHorizontalTiming OBJECT-TYPE
        SYNTAX            INTEGER
        MAX-ACCESS        read-write
        STATUS            current
        DESCRIPTION
                "CMNT: - Reference horizontal timing
                 TYPE: - Number
                 PAGE: - Genlock
                    Horizontal Timing  cmdID= 33021
                    min= -3000  max= 3000  step= 1  format= %0.0f pixels  div_scale= 1  preset= 0
                    Min = -3000 pixels  Max = 3000 pixels  Step = 1 pixels  Preset = 0 pixels  "
        ::= { iqsyn21CmdEntry 33021 }


    iqsyn21GenlockSetDelayDelayms OBJECT-TYPE
        SYNTAX            INTEGER
        MAX-ACCESS        read-write
        STATUS            current
        DESCRIPTION
                "CMNT: - Video delay set in 0.01 ms
                 TYPE: - Number
                 PAGE: - Genlock
                    Delay ms  cmdID= 33027
                    min= -48000  max= 48000  step= 5  format= %0.2f ms  div_scale= 100  preset= 0
                    Min = -480.00 ms  Max = 480.00 ms  Step = 0.05 ms  Preset = 0.00 ms  "
        ::= { iqsyn21CmdEntry 33027 }


    iqsyn21GenlockRefTimeCurrentDelay OBJECT-TYPE
        SYNTAX            RollCallString
        MAX-ACCESS        read-only
        STATUS            current
        DESCRIPTION
                "CMNT: - 
                 TYPE: - Display
                 PAGE: - Genlock
                    Internal Delay  cmdID= 33025  "
        ::= { iqsyn21CmdEntry 33025 }


    iqsyn21GenlockSyncAmplitude OBJECT-TYPE
        SYNTAX            RollCallString
        MAX-ACCESS        read-only
        STATUS            current
        DESCRIPTION
                "CMNT: - External reference amplitude
                 TYPE: - Display
                 PAGE: - Genlock
                    Sync Amplitude  cmdID= 33023  "
        ::= { iqsyn21CmdEntry 33023 }


    iqsyn21GenlockUseEmbDelayFback OBJECT-TYPE
        SYNTAX            INTEGER { disable(0), enable(1)  }
        MAX-ACCESS        read-write
        STATUS            current
        DESCRIPTION
                "CMNT: - 
                 TYPE: - Checkbox
                 PAGE: - Genlock
                    Use Emb Delay F/back  cmdID= 34049  "
        ::= { iqsyn21CmdEntry 34049 }


    iqsyn21GenlockSampleNumber OBJECT-TYPE
        SYNTAX            RollCallString
        MAX-ACCESS        read-only
        STATUS            current
        DESCRIPTION
                "CMNT: - Displays sample value for Dolby-E Timing
                 TYPE: - Display
                 PAGE: - Genlock
                    Sample Number  cmdID= 38657  "
        ::= { iqsyn21CmdEntry 38657 }


    iqsyn21GenlockLineNumber OBJECT-TYPE
        SYNTAX            RollCallString
        MAX-ACCESS        read-only
        STATUS            current
        DESCRIPTION
                "CMNT: - 
                 TYPE: - Display
                 PAGE: - Genlock
                    Line Number  cmdID= 38651  "
        ::= { iqsyn21CmdEntry 38651 }


    iqsyn21BackupEnable OBJECT-TYPE
        SYNTAX            INTEGER { disable(0), enable(1)  }
        MAX-ACCESS        read-write
        STATUS            current
        DESCRIPTION
                "CMNT: - Input Backup Enable
                 TYPE: - Checkbox
                 PAGE: - Backup
                    Backup Enable  cmdID= 39100  "
        ::= { iqsyn21CmdEntry 39100 }


    iqsyn21BackupORInput1State OBJECT-TYPE
        SYNTAX            RollCallString
        MAX-ACCESS        read-only
        STATUS            current
        DESCRIPTION
                "CMNT: - Input 1 OR State
                 TYPE: - Display
                 PAGE: - Backup
                    OR Input1 State  cmdID= 39101  "
        ::= { iqsyn21CmdEntry 39101 }


    iqsyn21BackupORInput2State OBJECT-TYPE
        SYNTAX            RollCallString
        MAX-ACCESS        read-only
        STATUS            current
        DESCRIPTION
                "CMNT: - Input 2 OR State
                 TYPE: - Display
                 PAGE: - Backup
                    OR Input2 State  cmdID= 39102  "
        ::= { iqsyn21CmdEntry 39102 }


    iqsyn21BackupRevertDelay OBJECT-TYPE
        SYNTAX            INTEGER
        MAX-ACCESS        read-write
        STATUS            current
        DESCRIPTION
                "CMNT: - Backup Reversion Delay
                 TYPE: - Number
                 PAGE: - Backup
                    Revert Delay  cmdID= 39141
                    min= 0  max= 1000  step= 10  format= %0.0f s  div_scale= 10  preset= 0
                    Min = 0 s  Max = 100 s  Step = 1 s  Preset = 0 s  "
        ::= { iqsyn21CmdEntry 39141 }


    iqsyn21BackupPriority OBJECT-TYPE
        SYNTAX            INTEGER {
                            valNone(0),
                            valPriority1(1),
                            valPriority2(2)
                            }
        MAX-ACCESS        read-write
        STATUS            current
        DESCRIPTION
                "CMNT: - Input Backup Priority
                 TYPE: - RadiobuttonList
                 PAGE: - Backup
                    Priority  cmdID= 39103
                    None  value= 0
                    Priority 1  value= 1
                    Priority 2  value= 2  "
        ::= { iqsyn21CmdEntry 39103 }


    iqsyn21BackupQualifyCRCErr OBJECT-TYPE
        SYNTAX            INTEGER { disable(0), enable(1)  }
        MAX-ACCESS        read-write
        STATUS            current
        DESCRIPTION
                "CMNT: - Backup CRC Error
                 TYPE: - Checkbox
                 PAGE: - Backup
                    Qualify CRC Err  cmdID= 39105  "
        ::= { iqsyn21CmdEntry 39105 }


    iqsyn21BackupQualifyANCErr OBJECT-TYPE
        SYNTAX            INTEGER { disable(0), enable(1)  }
        MAX-ACCESS        read-write
        STATUS            current
        DESCRIPTION
                "CMNT: - Backup ANC Error
                 TYPE: - Checkbox
                 PAGE: - Backup
                    Qualify ANC Err  cmdID= 39106  "
        ::= { iqsyn21CmdEntry 39106 }


    iqsyn21BackupInput1SelStatInp1OK OBJECT-TYPE
        SYNTAX            RollCallString
        MAX-ACCESS        read-only
        STATUS            current
        DESCRIPTION
                "CMNT: - Backup Sel 1 Inp 1 OK Status
                 TYPE: - Display
                 PAGE: - Backup
                    Stat Inp1 OK  cmdID= 39127  "
        ::= { iqsyn21CmdEntry 39127 }


    iqsyn21BackupInput1SelStatInp2FAIL OBJECT-TYPE
        SYNTAX            RollCallString
        MAX-ACCESS        read-only
        STATUS            current
        DESCRIPTION
                "CMNT: - Backup Sel 1 Inp 2 FAIL Status
                 TYPE: - Display
                 PAGE: - Backup
                    Stat Inp2 FAIL  cmdID= 39128  "
        ::= { iqsyn21CmdEntry 39128 }


    iqsyn21BackupInput1SelStatInp2Err OBJECT-TYPE
        SYNTAX            RollCallString
        MAX-ACCESS        read-only
        STATUS            current
        DESCRIPTION
                "CMNT: - Backup Sel 1 Inp 2 ERR Status
                 TYPE: - Display
                 PAGE: - Backup
                    Stat Inp2 Err  cmdID= 39139  "
        ::= { iqsyn21CmdEntry 39139 }


    iqsyn21BackupInput1SelStatAUDFail2 OBJECT-TYPE
        SYNTAX            RollCallString
        MAX-ACCESS        read-only
        STATUS            current
        DESCRIPTION
                "CMNT: - Backup Reversion Delay
                 TYPE: - Display
                 PAGE: - Backup
                    Stat AUD Fail 2  cmdID= 39144  "
        ::= { iqsyn21CmdEntry 39144 }


    iqsyn21BackupInput1SelStatStd2 OBJECT-TYPE
        SYNTAX            RollCallString
        MAX-ACCESS        read-only
        STATUS            current
        DESCRIPTION
                "CMNT: - Backup Inp2 1 Aud Fail G4C2
                 TYPE: - Display
                 PAGE: - Backup
                    Stat Std 2  cmdID= 39172  "
        ::= { iqsyn21CmdEntry 39172 }


    iqsyn21BackupInput1SelStatGPI1 OBJECT-TYPE
        SYNTAX            RollCallString
        MAX-ACCESS        read-only
        STATUS            current
        DESCRIPTION
                "CMNT: - Backup Sel 1 GPI 1 Status
                 TYPE: - Display
                 PAGE: - Backup
                    Stat GPI 1  cmdID= 39129  "
        ::= { iqsyn21CmdEntry 39129 }


    iqsyn21BackupInput1SelStatGPI2 OBJECT-TYPE
        SYNTAX            RollCallString
        MAX-ACCESS        read-only
        STATUS            current
        DESCRIPTION
                "CMNT: - Backup Sel 1 GPI 2 Status
                 TYPE: - Display
                 PAGE: - Backup
                    Stat GPI 2  cmdID= 39130  "
        ::= { iqsyn21CmdEntry 39130 }


    iqsyn21BackupInput1SelEnblInp1OK OBJECT-TYPE
        SYNTAX            INTEGER { disable(0), enable(1)  }
        MAX-ACCESS        read-write
        STATUS            current
        DESCRIPTION
                "CMNT: - Backup Sel 1 Inp 1 OK
                 TYPE: - Checkbox
                 PAGE: - Backup
                    Enbl Inp1 OK  cmdID= 39107  "
        ::= { iqsyn21CmdEntry 39107 }


    iqsyn21BackupInput1SelEnblInp2FAIL OBJECT-TYPE
        SYNTAX            INTEGER { disable(0), enable(1)  }
        MAX-ACCESS        read-write
        STATUS            current
        DESCRIPTION
                "CMNT: - Backup Sel 1 Inp 2 FAIL
                 TYPE: - Checkbox
                 PAGE: - Backup
                    Enbl Inp2 FAIL  cmdID= 39108  "
        ::= { iqsyn21CmdEntry 39108 }


    iqsyn21BackupInput1SelEnblInp2Err OBJECT-TYPE
        SYNTAX            INTEGER { disable(0), enable(1)  }
        MAX-ACCESS        read-write
        STATUS            current
        DESCRIPTION
                "CMNT: - Backup Sel 1 Inp 2 ERR
                 TYPE: - Checkbox
                 PAGE: - Backup
                    Enbl Inp2 Err  cmdID= 39135  "
        ::= { iqsyn21CmdEntry 39135 }


    iqsyn21BackupInput1SelEnblAudInp2Err OBJECT-TYPE
        SYNTAX            INTEGER { disable(0), enable(1)  }
        MAX-ACCESS        read-write
        STATUS            current
        DESCRIPTION
                "CMNT: - Backup Inp1 2 Aud Fail Enable
                 TYPE: - Checkbox
                 PAGE: - Backup
                    Enbl Aud Inp2 Err  cmdID= 39143  "
        ::= { iqsyn21CmdEntry 39143 }


    iqsyn21BackupInput1SelEnblStdInp2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Enbl Std Inp 2  cmdID= 39171  "
        ::= { iqsyn21CmdEntry 39171 }


    iqsyn21BackupInput1SelEnblGPI1 OBJECT-TYPE
        SYNTAX            INTEGER { disable(0), enable(1)  }
        MAX-ACCESS        read-write
        STATUS            current
        DESCRIPTION
                "CMNT: - Backup Sel 1 GPI 1
                 TYPE: - Checkbox
                 PAGE: - Backup
                    Enbl GPI 1  cmdID= 39109  "
        ::= { iqsyn21CmdEntry 39109 }


    iqsyn21BackupInput1SelEnblGPI2 OBJECT-TYPE
        SYNTAX            INTEGER { disable(0), enable(1)  }
        MAX-ACCESS        read-write
        STATUS            current
        DESCRIPTION
                "CMNT: - Backup Sel 1 GPI 2
                 TYPE: - Checkbox
                 PAGE: - Backup
                    Enbl GPI 2  cmdID= 39110  "
        ::= { iqsyn21CmdEntry 39110 }


    iqsyn21BackupInput1SelDlyInp1OK OBJECT-TYPE
        SYNTAX            INTEGER
        MAX-ACCESS        read-write
        STATUS            current
        DESCRIPTION
                "CMNT: - Backup Sel 1 Inp 1 OK Delay
                 TYPE: - Number
                 PAGE: - Backup
                    Dly Inp1 OK  cmdID= 39115
                    min= 10  max= 100  step= 1  format= %0.1f s  div_scale= 10  preset= 10
                    Min = 1.0 s  Max = 10.0 s  Step = 0.1 s  Preset = 1.0 s  "
        ::= { iqsyn21CmdEntry 39115 }


    iqsyn21BackupInput1SelDlyInp2FAIL OBJECT-TYPE
        SYNTAX            INTEGER
        MAX-ACCESS        read-write
        STATUS            current
        DESCRIPTION
                "CMNT: - Backup Sel 1 Inp 2 FAIL Delay
                 TYPE: - Number
                 PAGE: - Backup
                    Dly Inp2 FAIL  cmdID= 39116
                    min= 5  max= 100  step= 1  format= %0.1f s  div_scale= 10  preset= 5
                    Min = 0.5 s  Max = 10.0 s  Step = 0.1 s  Preset = 0.5 s  "
        ::= { iqsyn21CmdEntry 39116 }


    iqsyn21BackupInput1SelDlyInp2Err OBJECT-TYPE
        SYNTAX            INTEGER
        MAX-ACCESS        read-write
        STATUS            current
        DESCRIPTION
                "CMNT: - Backup Sel 1 Inp 2 ERR Delay
                 TYPE: - Number
                 PAGE: - Backup
                    Dly Inp2 Err  cmdID= 39137
                    min= 10  max= 100  step= 10  format= %0.0f s  div_scale= 10  preset= 50
                    Min = 1 s  Max = 10 s  Step = 1 s  Preset = 5 s  "
        ::= { iqsyn21CmdEntry 39137 }


    iqsyn21BackupInput1SelDlyGPI1 OBJECT-TYPE
        SYNTAX            INTEGER
        MAX-ACCESS        read-write
        STATUS            current
        DESCRIPTION
                "CMNT: - Backup Sel 1 GPI 1 Delay
                 TYPE: - Number
                 PAGE: - Backup
                    Dly GPI 1  cmdID= 39117
                    min= 0  max= 100  step= 1  format= %0.1f s  div_scale= 10  preset= 0
                    Min = 0.0 s  Max = 10.0 s  Step = 0.1 s  Preset = 0.0 s  "
        ::= { iqsyn21CmdEntry 39117 }


    iqsyn21BackupInput1SelDlyGPI2 OBJECT-TYPE
        SYNTAX            INTEGER
        MAX-ACCESS        read-write
        STATUS            current
        DESCRIPTION
                "CMNT: - Backup Sel 1 GPI 2 Delay
                 TYPE: - Number
                 PAGE: - Backup
                    Dly GPI 2  cmdID= 39118
                    min= 0  max= 100  step= 1  format= %0.1f s  div_scale= 10  preset= 0
                    Min = 0.0 s  Max = 10.0 s  Step = 0.1 s  Preset = 0.0 s  "
        ::= { iqsyn21CmdEntry 39118 }


    iqsyn21BackupInput1SelDlyAud2FAIL OBJECT-TYPE
        SYNTAX            INTEGER
        MAX-ACCESS        read-write
        STATUS            current
        DESCRIPTION
                "CMNT: - Backup Inp1 2 aud Fail Delay
                 TYPE: - Number
                 PAGE: - Backup
                    Dly Aud2 FAIL  cmdID= 39145
                    min= 10  max= 100  step= 1  format= %0.1f s  div_scale= 10  preset= 10
                    Min = 1.0 s  Max = 10.0 s  Step = 0.1 s  Preset = 1.0 s  "
        ::= { iqsyn21CmdEntry 39145 }


    iqsyn21BackupInput1SelDlyStd2 OBJECT-TYPE
        SYNTAX            INTEGER
        MAX-ACCESS        read-write
        STATUS            current
        DESCRIPTION
                "CMNT: - Backup Inp2 1 Aud Fail G4C2
                 TYPE: - Number
                 PAGE: - Backup
                    Dly Std 2  cmdID= 39173
                    min= 10  max= 100  step= 1  format= %0.1f s  div_scale= 10  preset= 10
                    Min = 1.0 s  Max = 10.0 s  Step = 0.1 s  Preset = 1.0 s  "
        ::= { iqsyn21CmdEntry 39173 }


    iqsyn21BackupInput1SelGPI1State OBJECT-TYPE
        SYNTAX            INTEGER {
                            valHigh(1),
                            valLow(0)
                            }
        MAX-ACCESS        read-write
        STATUS            current
        DESCRIPTION
                "CMNT: - Backup Sel 1 GPI 1 val
                 TYPE: - RadiobuttonList
                 PAGE: - Backup
                    GPI 1 State  cmdID= 39123
                    High  value= 1
                    Low  value= 0  "
        ::= { iqsyn21CmdEntry 39123 }


    iqsyn21BackupInput1SelGPI2State OBJECT-TYPE
        SYNTAX            INTEGER {
                            valHigh(1),
                            valLow(0)
                            }
        MAX-ACCESS        read-write
        STATUS            current
        DESCRIPTION
                "CMNT: - Backup Sel 1 GPI 2 val
                 TYPE: - RadiobuttonList
                 PAGE: - Backup
                    GPI 2 State  cmdID= 39124
                    High  value= 1
                    Low  value= 0  "
        ::= { iqsyn21CmdEntry 39124 }


    iqsyn21BackupInput1SelInp12AudFailG1C1 OBJECT-TYPE
        SYNTAX            INTEGER { disable(0), enable(1)  }
        MAX-ACCESS        read-write
        STATUS            current
        DESCRIPTION
                "CMNT: - Backup Inp1 2 Aud Fail G1C1
                 TYPE: - Checkbox
                 PAGE: - Backup
                    Inp1 2 Aud Fail G1C1  cmdID= 39149  "
        ::= { iqsyn21CmdEntry 39149 }


    iqsyn21BackupInput1SelInp12AudFailG1C2 OBJECT-TYPE
        SYNTAX            INTEGER { disable(0), enable(1)  }
        MAX-ACCESS        read-write
        STATUS            current
        DESCRIPTION
                "CMNT: - Backup Inp1 2 Aud Fail G1C2
                 TYPE: - Checkbox
                 PAGE: - Backup
                    Inp1 2 Aud Fail G1C2  cmdID= 39150  "
        ::= { iqsyn21CmdEntry 39150 }


    iqsyn21BackupInput1SelInp12AudFailG2C1 OBJECT-TYPE
        SYNTAX            INTEGER { disable(0), enable(1)  }
        MAX-ACCESS        read-write
        STATUS            current
        DESCRIPTION
                "CMNT: - Backup Inp1 2 Aud Fail G2C1
                 TYPE: - Checkbox
                 PAGE: - Backup
                    Inp1 2 Aud Fail G2C1  cmdID= 39151  "
        ::= { iqsyn21CmdEntry 39151 }


    iqsyn21BackupInput1SelInp12AudFailG2C2 OBJECT-TYPE
        SYNTAX            INTEGER { disable(0), enable(1)  }
        MAX-ACCESS        read-write
        STATUS            current
        DESCRIPTION
                "CMNT: - Backup Inp1 2 Aud Fail G2C2
                 TYPE: - Checkbox
                 PAGE: - Backup
                    Inp1 2 Aud Fail G2C2  cmdID= 39152  "
        ::= { iqsyn21CmdEntry 39152 }


    iqsyn21BackupInput1SelInp12AudFailG3C1 OBJECT-TYPE
        SYNTAX            INTEGER { disable(0), enable(1)  }
        MAX-ACCESS        read-write
        STATUS            current
        DESCRIPTION
                "CMNT: - Backup Inp1 2 Aud Fail G3C1
                 TYPE: - Checkbox
                 PAGE: - Backup
                    Inp1 2 Aud Fail G3C1  cmdID= 39153  "
        ::= { iqsyn21CmdEntry 39153 }


    iqsyn21BackupInput1SelInp12AudFailG3C2 OBJECT-TYPE
        SYNTAX            INTEGER { disable(0), enable(1)  }
        MAX-ACCESS        read-write
        STATUS            current
        DESCRIPTION
                "CMNT: - Backup Inp1 2 Aud Fail G3C2
                 TYPE: - Checkbox
                 PAGE: - Backup
                    Inp1 2 Aud Fail G3C2  cmdID= 39154  "
        ::= { iqsyn21CmdEntry 39154 }


    iqsyn21BackupInput1SelInp12AudFailG4C1 OBJECT-TYPE
        SYNTAX            INTEGER { disable(0), enable(1)  }
        MAX-ACCESS        read-write
        STATUS            current
        DESCRIPTION
                "CMNT: - Backup Inp1 2 Aud Fail G4C1
                 TYPE: - Checkbox
                 PAGE: - Backup
                    Inp1 2 Aud Fail G4C1  cmdID= 39155  "
        ::= { iqsyn21CmdEntry 39155 }


    iqsyn21BackupInput1SelInp12AudFailG4C2 OBJECT-TYPE
        SYNTAX            INTEGER { disable(0), enable(1)  }
        MAX-ACCESS        read-write
        STATUS            current
        DESCRIPTION
                "CMNT: - Backup Inp1 2 Aud Fail G4C2
                 TYPE: - Checkbox
                 PAGE: - Backup
                    Inp1 2 Aud Fail G4C2  cmdID= 39156  "
        ::= { iqsyn21CmdEntry 39156 }


    iqsyn21BackupInput1SelInp12AudFailLockGrp OBJECT-TYPE
        SYNTAX            INTEGER { disable(0), enable(1)  }
        MAX-ACCESS        read-write
        STATUS            current
        DESCRIPTION
                "CMNT: - Backup Inp1 2 Aud Fail Lock Grp
                 TYPE: - Checkbox
                 PAGE: - Backup
                    Inp1 2 Aud Fail Lock Grp  cmdID= 39148  "
        ::= { iqsyn21CmdEntry 39148 }


    iqsyn21BackupInput1SelSelAll OBJECT-TYPE
        SYNTAX            INTEGER { noAction(0),valSelAll(1) }
        MAX-ACCESS        read-write
        STATUS            current
        DESCRIPTION
                "CMNT: - Backup Inp1 2 Aud Fail Sel All
                 TYPE: - Button
                 PAGE: - Backup
                    Sel All  cmdID= 39146
                    value= 1  "
        ::= { iqsyn21CmdEntry 39146 }


    iqsyn21BackupInput1SelSelNone OBJECT-TYPE
        SYNTAX            INTEGER { noAction(0),valSelNone(1) }
        MAX-ACCESS        read-write
        STATUS            current
        DESCRIPTION
                "CMNT: - Backup Inp1 2 Aud Fail Sel None
                 TYPE: - Button
                 PAGE: - Backup
                    Sel None  cmdID= 39147
                    value= 1  "
        ::= { iqsyn21CmdEntry 39147 }


    iqsyn21BackupInput2SelStatInp2OK OBJECT-TYPE
        SYNTAX            RollCallString
        MAX-ACCESS        read-only
        STATUS            current
        DESCRIPTION
                "CMNT: - Backup Sel 2 Inp 2 OK Status
                 TYPE: - Display
                 PAGE: - Backup
                    Stat Inp2 OK  cmdID= 39131  "
        ::= { iqsyn21CmdEntry 39131 }


    iqsyn21BackupInput2SelStatInp1FAIL OBJECT-TYPE
        SYNTAX            RollCallString
        MAX-ACCESS        read-only
        STATUS            current
        DESCRIPTION
                "CMNT: - Backup Sel 2 Inp 1 FAIL Status
                 TYPE: - Display
                 PAGE: - Backup
                    Stat Inp1 FAIL  cmdID= 39132  "
        ::= { iqsyn21CmdEntry 39132 }


    iqsyn21BackupInput2SelStatInp1Err OBJECT-TYPE
        SYNTAX            RollCallString
        MAX-ACCESS        read-only
        STATUS            current
        DESCRIPTION
                "CMNT: - Backup Sel 2 Inp 1 ERR Status
                 TYPE: - Display
                 PAGE: - Backup
                    Stat Inp1 Err  cmdID= 39140  "
        ::= { iqsyn21CmdEntry 39140 }


    iqsyn21BackupInput2SelStatAUDFail1 OBJECT-TYPE
        SYNTAX            RollCallString
        MAX-ACCESS        read-only
        STATUS            current
        DESCRIPTION
                "CMNT: - Backup Reversion Delay
                 TYPE: - Display
                 PAGE: - Backup
                    Stat AUD Fail 1  cmdID= 39158  "
        ::= { iqsyn21CmdEntry 39158 }


    iqsyn21BackupInput2SelStatStd1 OBJECT-TYPE
        SYNTAX            RollCallString
        MAX-ACCESS        read-only
        STATUS            current
        DESCRIPTION
                "CMNT: - Backup Inp2 1 Aud Fail G4C2
                 TYPE: - Display
                 PAGE: - Backup
                    Stat Std 1  cmdID= 39175  "
        ::= { iqsyn21CmdEntry 39175 }


    iqsyn21BackupInput2SelStatGPI1 OBJECT-TYPE
        SYNTAX            RollCallString
        MAX-ACCESS        read-only
        STATUS            current
        DESCRIPTION
                "CMNT: - Backup Sel 2 GPI 1 Status
                 TYPE: - Display
                 PAGE: - Backup
                    Stat GPI 1  cmdID= 39133  "
        ::= { iqsyn21CmdEntry 39133 }


    iqsyn21BackupInput2SelStatGPI2 OBJECT-TYPE
        SYNTAX            RollCallString
        MAX-ACCESS        read-only
        STATUS            current
        DESCRIPTION
                "CMNT: - Backup Sel 2 GPI 2 Status
                 TYPE: - Display
                 PAGE: - Backup
                    Stat GPI 2  cmdID= 39134  "
        ::= { iqsyn21CmdEntry 39134 }


    iqsyn21BackupInput2SelEnblInp2OK OBJECT-TYPE
        SYNTAX            INTEGER { disable(0), enable(1)  }
        MAX-ACCESS        read-write
        STATUS            current
        DESCRIPTION
                "CMNT: - Backup Sel 2 Inp 2 OK
                 TYPE: - Checkbox
                 PAGE: - Backup
                    Enbl Inp2 OK  cmdID= 39111  "
        ::= { iqsyn21CmdEntry 39111 }


    iqsyn21BackupInput2SelEnblInp1FAIL OBJECT-TYPE
        SYNTAX            INTEGER { disable(0), enable(1)  }
        MAX-ACCESS        read-write
        STATUS            current
        DESCRIPTION
                "CMNT: - Backup Sel 2 Inp 1 FAIL
                 TYPE: - Checkbox
                 PAGE: - Backup
                    Enbl Inp1 FAIL  cmdID= 39112  "
        ::= { iqsyn21CmdEntry 39112 }


    iqsyn21BackupInput2SelEnblInp1Err OBJECT-TYPE
        SYNTAX            INTEGER { disable(0), enable(1)  }
        MAX-ACCESS        read-write
        STATUS            current
        DESCRIPTION
                "CMNT: - Backup Sel 2 Inp 1 ERR
                 TYPE: - Checkbox
                 PAGE: - Backup
                    Enbl Inp1 Err  cmdID= 39136  "
        ::= { iqsyn21CmdEntry 39136 }


    iqsyn21BackupInput2SelEnblGPI1 OBJECT-TYPE
        SYNTAX            INTEGER { disable(0), enable(1)  }
        MAX-ACCESS        read-write
        STATUS            current
        DESCRIPTION
                "CMNT: - Backup Sel 2 GPI 1
                 TYPE: - Checkbox
                 PAGE: - Backup
                    Enbl GPI 1  cmdID= 39113  "
        ::= { iqsyn21CmdEntry 39113 }


    iqsyn21BackupInput2SelEnblGPI2 OBJECT-TYPE
        SYNTAX            INTEGER { disable(0), enable(1)  }
        MAX-ACCESS        read-write
        STATUS            current
        DESCRIPTION
                "CMNT: - Backup Sel 2 GPI 2
                 TYPE: - Checkbox
                 PAGE: - Backup
                    Enbl GPI 2  cmdID= 39114  "
        ::= { iqsyn21CmdEntry 39114 }


    iqsyn21BackupInput2SelEnblAudInp1Err OBJECT-TYPE
        SYNTAX            INTEGER { disable(0), enable(1)  }
        MAX-ACCESS        read-write
        STATUS            current
        DESCRIPTION
                "CMNT: - Backup Inp2 1 Aud Fail Enable
                 TYPE: - Checkbox
                 PAGE: - Backup
                    Enbl Aud Inp1 Err  cmdID= 39157  "
        ::= { iqsyn21CmdEntry 39157 }


    iqsyn21BackupInput2SelEnblStdInp1 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Enbl Std Inp 1  cmdID= 39174  "
        ::= { iqsyn21CmdEntry 39174 }


    iqsyn21BackupInput2SelDlyInp2OK OBJECT-TYPE
        SYNTAX            INTEGER
        MAX-ACCESS        read-write
        STATUS            current
        DESCRIPTION
                "CMNT: - Backup Sel 2 Inp 2 OK Delay
                 TYPE: - Number
                 PAGE: - Backup
                    Dly Inp2 OK  cmdID= 39119
                    min= 10  max= 100  step= 1  format= %0.1f s  div_scale= 10  preset= 10
                    Min = 1.0 s  Max = 10.0 s  Step = 0.1 s  Preset = 1.0 s  "
        ::= { iqsyn21CmdEntry 39119 }


    iqsyn21BackupInput2SelDlyInp1FAIL OBJECT-TYPE
        SYNTAX            INTEGER
        MAX-ACCESS        read-write
        STATUS            current
        DESCRIPTION
                "CMNT: - Backup Sel 2 Inp 1 FAIL Delay
                 TYPE: - Number
                 PAGE: - Backup
                    Dly Inp1 FAIL  cmdID= 39120
                    min= 5  max= 100  step= 1  format= %0.1f s  div_scale= 10  preset= 5
                    Min = 0.5 s  Max = 10.0 s  Step = 0.1 s  Preset = 0.5 s  "
        ::= { iqsyn21CmdEntry 39120 }


    iqsyn21BackupInput2SelDlyInp1Err OBJECT-TYPE
        SYNTAX            INTEGER
        MAX-ACCESS        read-write
        STATUS            current
        DESCRIPTION
                "CMNT: - Backup Sel 2 Inp 1 ERR Delay
                 TYPE: - Number
                 PAGE: - Backup
                    Dly Inp1 Err  cmdID= 39138
                    min= 10  max= 100  step= 10  format= %0.0f s  div_scale= 10  preset= 50
                    Min = 1 s  Max = 10 s  Step = 1 s  Preset = 5 s  "
        ::= { iqsyn21CmdEntry 39138 }


    iqsyn21BackupInput2SelDlyAud2FAIL OBJECT-TYPE
        SYNTAX            INTEGER
        MAX-ACCESS        read-write
        STATUS            current
        DESCRIPTION
                "CMNT: - Backup Inp2 1 Aud Fail Delay
                 TYPE: - Number
                 PAGE: - Backup
                    Dly Aud2 FAIL  cmdID= 39159
                    min= 10  max= 100  step= 1  format= %0.1f s  div_scale= 10  preset= 10
                    Min = 1.0 s  Max = 10.0 s  Step = 0.1 s  Preset = 1.0 s  "
        ::= { iqsyn21CmdEntry 39159 }


    iqsyn21BackupInput2SelDlyStd1 OBJECT-TYPE
        SYNTAX            INTEGER
        MAX-ACCESS        read-write
        STATUS            current
        DESCRIPTION
                "CMNT: - Backup Inp2 1 Aud Fail G4C2
                 TYPE: - Number
                 PAGE: - Backup
                    Dly Std 1  cmdID= 39176
                    min= 10  max= 100  step= 1  format= %0.1f s  div_scale= 10  preset= 10
                    Min = 1.0 s  Max = 10.0 s  Step = 0.1 s  Preset = 1.0 s  "
        ::= { iqsyn21CmdEntry 39176 }


    iqsyn21BackupInput2SelDlyGPI1 OBJECT-TYPE
        SYNTAX            INTEGER
        MAX-ACCESS        read-write
        STATUS            current
        DESCRIPTION
                "CMNT: - Backup Sel 2 GPI 1 Delay
                 TYPE: - Number
                 PAGE: - Backup
                    Dly GPI 1  cmdID= 39121
                    min= 0  max= 100  step= 1  format= %0.1f s  div_scale= 10  preset= 0
                    Min = 0.0 s  Max = 10.0 s  Step = 0.1 s  Preset = 0.0 s  "
        ::= { iqsyn21CmdEntry 39121 }


    iqsyn21BackupInput2SelDlyGPI2 OBJECT-TYPE
        SYNTAX            INTEGER
        MAX-ACCESS        read-write
        STATUS            current
        DESCRIPTION
                "CMNT: - Backup Sel 2 GPI 2 Delay
                 TYPE: - Number
                 PAGE: - Backup
                    Dly GPI 2  cmdID= 39122
                    min= 0  max= 100  step= 1  format= %0.1f s  div_scale= 10  preset= 0
                    Min = 0.0 s  Max = 10.0 s  Step = 0.1 s  Preset = 0.0 s  "
        ::= { iqsyn21CmdEntry 39122 }


    iqsyn21BackupInput2SelGPI1State OBJECT-TYPE
        SYNTAX            INTEGER {
                            valOn(0),
                            valOff(1)
                            }
        MAX-ACCESS        read-write
        STATUS            current
        DESCRIPTION
                "CMNT: - Backup Sel 2 GPI 1 val
                 TYPE: - RadiobuttonList
                 PAGE: - Backup
                    GPI 1 State  cmdID= 39125
                    On  value= 0
                    Off  value= 1  "
        ::= { iqsyn21CmdEntry 39125 }


    iqsyn21BackupInput2SelGPI2State OBJECT-TYPE
        SYNTAX            INTEGER {
                            valOn(0),
                            valOff(1)
                            }
        MAX-ACCESS        read-write
        STATUS            current
        DESCRIPTION
                "CMNT: - Backup Sel 2 GPI 2 val
                 TYPE: - RadiobuttonList
                 PAGE: - Backup
                    GPI 2 State  cmdID= 39126
                    On  value= 0
                    Off  value= 1  "
        ::= { iqsyn21CmdEntry 39126 }


    iqsyn21BackupInput2SelInp21AudFailG1C1 OBJECT-TYPE
        SYNTAX            INTEGER { disable(0), enable(1)  }
        MAX-ACCESS        read-write
        STATUS            current
        DESCRIPTION
                "CMNT: - Backup Inp2 1 Aud Fail G1C1
                 TYPE: - Checkbox
                 PAGE: - Backup
                    Inp2 1 Aud Fail G1C1  cmdID= 39163  "
        ::= { iqsyn21CmdEntry 39163 }


    iqsyn21BackupInput2SelInp21AudFailG1C2 OBJECT-TYPE
        SYNTAX            INTEGER { disable(0), enable(1)  }
        MAX-ACCESS        read-write
        STATUS            current
        DESCRIPTION
                "CMNT: - Backup Inp2 1 Aud Fail G1C2
                 TYPE: - Checkbox
                 PAGE: - Backup
                    Inp2 1 Aud Fail G1C2  cmdID= 39164  "
        ::= { iqsyn21CmdEntry 39164 }


    iqsyn21BackupInput2SelInp21AudFailG2C1 OBJECT-TYPE
        SYNTAX            INTEGER { disable(0), enable(1)  }
        MAX-ACCESS        read-write
        STATUS            current
        DESCRIPTION
                "CMNT: - Backup Inp2 1 Aud Fail G2C1
                 TYPE: - Checkbox
                 PAGE: - Backup
                    Inp2 1 Aud Fail G2C1  cmdID= 39165  "
        ::= { iqsyn21CmdEntry 39165 }


    iqsyn21BackupInput2SelInp21AudFailG2C2 OBJECT-TYPE
        SYNTAX            INTEGER { disable(0), enable(1)  }
        MAX-ACCESS        read-write
        STATUS            current
        DESCRIPTION
                "CMNT: - Backup Inp2 1 Aud Fail G2C2
                 TYPE: - Checkbox
                 PAGE: - Backup
                    Inp2 1 Aud Fail G2C2  cmdID= 39166  "
        ::= { iqsyn21CmdEntry 39166 }


    iqsyn21BackupInput2SelInp21AudFailG3C1 OBJECT-TYPE
        SYNTAX            INTEGER { disable(0), enable(1)  }
        MAX-ACCESS        read-write
        STATUS            current
        DESCRIPTION
                "CMNT: - Backup Inp2 1 Aud Fail G3C1
                 TYPE: - Checkbox
                 PAGE: - Backup
                    Inp2 1 Aud Fail G3C1  cmdID= 39167  "
        ::= { iqsyn21CmdEntry 39167 }


    iqsyn21BackupInput2SelInp21AudFailG3C2 OBJECT-TYPE
        SYNTAX            INTEGER { disable(0), enable(1)  }
        MAX-ACCESS        read-write
        STATUS            current
        DESCRIPTION
                "CMNT: - Backup Inp2 1 Aud Fail G3C2
                 TYPE: - Checkbox
                 PAGE: - Backup
                    Inp2 1 Aud Fail G3C2  cmdID= 39168  "
        ::= { iqsyn21CmdEntry 39168 }


    iqsyn21BackupInput2SelInp21AudFailG4C1 OBJECT-TYPE
        SYNTAX            INTEGER { disable(0), enable(1)  }
        MAX-ACCESS        read-write
        STATUS            current
        DESCRIPTION
                "CMNT: - Backup Inp2 1 Aud Fail G4C1
                 TYPE: - Checkbox
                 PAGE: - Backup
                    Inp2 1 Aud Fail G4C1  cmdID= 39169  "
        ::= { iqsyn21CmdEntry 39169 }


    iqsyn21BackupInput2SelInp21AudFailG4C2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Inp2 1 Aud Fail G4C2  cmdID= 39170  "
        ::= { iqsyn21CmdEntry 39170 }


    iqsyn21BackupInput2SelInp21AudFailLockGrp OBJECT-TYPE
        SYNTAX            INTEGER { disable(0), enable(1)  }
        MAX-ACCESS        read-write
        STATUS            current
        DESCRIPTION
                "CMNT: - Backup Inp2 1 Aud Fail Lock Grp
                 TYPE: - Checkbox
                 PAGE: - Backup
                    Inp2 1 Aud Fail Lock Grp  cmdID= 39162  "
        ::= { iqsyn21CmdEntry 39162 }


    iqsyn21BackupInput2SelSelAll OBJECT-TYPE
        SYNTAX            INTEGER { noAction(0),valSelAll(1) }
        MAX-ACCESS        read-write
        STATUS            current
        DESCRIPTION
                "CMNT: - Backup Inp2 1 Aud Fail Sel All
                 TYPE: - Button
                 PAGE: - Backup
                    Sel All  cmdID= 39160
                    value= 1  "
        ::= { iqsyn21CmdEntry 39160 }


    iqsyn21BackupInput2SelSelNone OBJECT-TYPE
        SYNTAX            INTEGER { noAction(0),valSelNone(1) }
        MAX-ACCESS        read-write
        STATUS            current
        DESCRIPTION
                "CMNT: - Backup Inp2 1 Aud Fail Sel None
                 TYPE: - Button
                 PAGE: - Backup
                    Sel None  cmdID= 39161
                    value= 1  "
        ::= { iqsyn21CmdEntry 39161 }


    iqsyn21UtilsPatternsPatternEnable OBJECT-TYPE
        SYNTAX            INTEGER { disable(0), enable(1)  }
        MAX-ACCESS        read-write
        STATUS            current
        DESCRIPTION
                "CMNT: - TPG pattern enable
                 TYPE: - Checkbox
                 PAGE: - Utils
                    Pattern Enable  cmdID= 33038  "
        ::= { iqsyn21CmdEntry 33038 }


    iqsyn21UtilsPatternsScrollPattern OBJECT-TYPE
        SYNTAX            INTEGER { disable(0), enable(1)  }
        MAX-ACCESS        read-write
        STATUS            current
        DESCRIPTION
                "CMNT: - Scroll test pattern horizontally
                 TYPE: - Checkbox
                 PAGE: - Utils
                    Scroll Pattern  cmdID= 33040  "
        ::= { iqsyn21CmdEntry 33040 }


    iqsyn21UtilsPatternsPatternType OBJECT-TYPE
        SYNTAX            INTEGER {
                            val100ColorBars(1),
                            val75ColorBars(2),
                            valSMPTEBars(3),
                            valTartanBars(4),
                            valPluge(5),
                            valRamp(6),
                            valSweep(7),
                            valPulseBar(8),
                            valBurst(9),
                            valBlack(10)
                            }
        MAX-ACCESS        read-write
        STATUS            current
        DESCRIPTION
                "CMNT: - TPG pattern type
                 TYPE: - RadiobuttonList
                 PAGE: - Utils
                    Pattern Type  cmdID= 33039
                    100% Color Bars  value= 1
                    75% Color Bars  value= 2
                    SMPTE Bars  value= 3
                    Tartan Bars  value= 4
                    Pluge  value= 5
                    Ramp  value= 6
                    Sweep  value= 7
                    Pulse & Bar  value= 8
                    Burst  value= 9
                    Black  value= 10  "
        ::= { iqsyn21CmdEntry 33039 }


    iqsyn21UtilsANCblankonMismat OBJECT-TYPE
        SYNTAX            INTEGER { disable(0), enable(1)  }
        MAX-ACCESS        read-write
        STATUS            current
        DESCRIPTION
                "CMNT: - Blank all ANC if standard mismatch
                 TYPE: - Checkbox
                 PAGE: - Utils
                    ANC blank on Mismatch  cmdID= 33036  "
        ::= { iqsyn21CmdEntry 33036 }


    iqsyn21UtilsFreezeForceFreeze OBJECT-TYPE
        SYNTAX            INTEGER { disable(0), enable(1)  }
        MAX-ACCESS        read-write
        STATUS            current
        DESCRIPTION
                "CMNT: - Freeze output picture
                 TYPE: - Checkbox
                 PAGE: - Utils
                    Force Freeze  cmdID= 33032  "
        ::= { iqsyn21CmdEntry 33032 }


    iqsyn21UtilsFreezeFreezeType OBJECT-TYPE
        SYNTAX            INTEGER {
                            valFrame(0),
                            valField(1)
                            }
        MAX-ACCESS        read-write
        STATUS            current
        DESCRIPTION
                "CMNT: - Type of Frozen output: Frame/Field
                 TYPE: - RadiobuttonList
                 PAGE: - Utils
                    Freeze Type  cmdID= 33033
                    Frame  value= 0
                    Field  value= 1  "
        ::= { iqsyn21CmdEntry 33033 }


    iqsyn21UtilsMonochrome OBJECT-TYPE
        SYNTAX            INTEGER { disable(0), enable(1)  }
        MAX-ACCESS        read-write
        STATUS            current
        DESCRIPTION
                "CMNT: - Monochrome enable
                 TYPE: - Checkbox
                 PAGE: - Utils
                    Monochrome  cmdID= 33034  "
        ::= { iqsyn21CmdEntry 33034 }


    iqsyn21UtilsMonochromeMonochromeType OBJECT-TYPE
        SYNTAX            INTEGER {
                            valYonly(0),
                            valConly(1)
                            }
        MAX-ACCESS        read-write
        STATUS            current
        DESCRIPTION
                "CMNT: - Type of Monochrome output
                 TYPE: - RadiobuttonList
                 PAGE: - Utils
                    Monochrome Type  cmdID= 33035
                    Y only  value= 0
                    C only  value= 1  "
        ::= { iqsyn21CmdEntry 33035 }


    iqsyn21UtilsHANCVBIBlankingANCMode OBJECT-TYPE
        SYNTAX            INTEGER {
                            valPassInputANC(0),
                            valBlankHANC(2),
                            valBlankAllANC(1)
                            }
        MAX-ACCESS        read-write
        STATUS            current
        DESCRIPTION
                "CMNT: - Blank ANC on output (All/HANC/Pass)
                 TYPE: - RadiobuttonList
                 PAGE: - Utils
                    ANC Mode  cmdID= 33037
                    Pass Input ANC  value= 0
                    Blank HANC  value= 2
                    Blank All ANC  value= 1  "
        ::= { iqsyn21CmdEntry 33037 }


    iqsyn21UtilsHANCVBIBlankingStandard OBJECT-TYPE
        SYNTAX            INTEGER {
                            val1125108030i(6),
                            val1125108030p(9),
                            val1125108029i(7),
                            val1125108029p(10),
                            val1125108025i(8),
                            val1125108025p(11),
                            val1125108024p(12),
                            val1125108024sf(23),
                            val1125108023p(13),
                            val1125108023sf(24),
                            val1125103530i(1),
                            val1125103529i(2),
                            val75072060p(16),
                            val75072059p(17),
                            val75072050p(30),
                            val52548029i(19),
                            val62557625i(20)
                            }
        MAX-ACCESS        read-write
        STATUS            current
        DESCRIPTION
                "CMNT: - Select std for VBI blank display/set
                 TYPE: - RadiobuttonList
                 PAGE: - Utils
                    Standard  cmdID= 37200
                    1125(1080)/30i  value= 6
                    1125(1080)/30p  value= 9
                    1125(1080)/29i  value= 7
                    1125(1080)/29p  value= 10
                    1125(1080)/25i  value= 8
                    1125(1080)/25p  value= 11
                    1125(1080)/24p  value= 12
                    1125(1080)/24sf  value= 23
                    1125(1080)/23p  value= 13
                    1125(1080)/23sf  value= 24
                    1125(1035)/30i  value= 1
                    1125(1035)/29i  value= 2
                    750(720)/60p  value= 16
                    750(720)/59p  value= 17
                    750(720)/50p  value= 30
                    525(480)/29i  value= 19
                    625(576)/25i  value= 20  "
        ::= { iqsyn21CmdEntry 37200 }


    iqsyn21UtilsHANCVBIBlankingBlankAll OBJECT-TYPE
        SYNTAX            INTEGER { noAction(0),valBlankAll(1) }
        MAX-ACCESS        read-write
        STATUS            current
        DESCRIPTION
                "CMNT: - Blank all valid lines
                 TYPE: - Button
                 PAGE: - Utils
                    Blank All  cmdID= 37201
                    value= 1  "
        ::= { iqsyn21CmdEntry 37201 }


    iqsyn21UtilsHANCVBIBlankingPassAll OBJECT-TYPE
        SYNTAX            INTEGER { noAction(0),valPassAll(1) }
        MAX-ACCESS        read-write
        STATUS            current
        DESCRIPTION
                "CMNT: - Blank no lines
                 TYPE: - Button
                 PAGE: - Utils
                    Pass All  cmdID= 37202
                    value= 1  "
        ::= { iqsyn21CmdEntry 37202 }


    iqsyn21UtilsHANCVBIBlankingBlank1 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 1  cmdID= 37210  "
        ::= { iqsyn21CmdEntry 37210 }


    iqsyn21UtilsHANCVBIBlankingBlank2 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 2  cmdID= 37211  "
        ::= { iqsyn21CmdEntry 37211 }


    iqsyn21UtilsHANCVBIBlankingBlank3 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 3  cmdID= 37212  "
        ::= { iqsyn21CmdEntry 37212 }


    iqsyn21UtilsHANCVBIBlankingBlank4 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 4  cmdID= 37213  "
        ::= { iqsyn21CmdEntry 37213 }


    iqsyn21UtilsHANCVBIBlankingBlank5 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 5  cmdID= 37214  "
        ::= { iqsyn21CmdEntry 37214 }


    iqsyn21UtilsHANCVBIBlankingBlank6 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 6  cmdID= 37215  "
        ::= { iqsyn21CmdEntry 37215 }


    iqsyn21UtilsHANCVBIBlankingBlank7 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 7  cmdID= 37216  "
        ::= { iqsyn21CmdEntry 37216 }


    iqsyn21UtilsHANCVBIBlankingBlank8 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 8  cmdID= 37217  "
        ::= { iqsyn21CmdEntry 37217 }


    iqsyn21UtilsHANCVBIBlankingBlank9 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 9  cmdID= 37218  "
        ::= { iqsyn21CmdEntry 37218 }


    iqsyn21UtilsHANCVBIBlankingBlank10 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 10  cmdID= 37219  "
        ::= { iqsyn21CmdEntry 37219 }


    iqsyn21UtilsHANCVBIBlankingBlank11 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 11  cmdID= 37220  "
        ::= { iqsyn21CmdEntry 37220 }


    iqsyn21UtilsHANCVBIBlankingBlank12 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 12  cmdID= 37221  "
        ::= { iqsyn21CmdEntry 37221 }


    iqsyn21UtilsHANCVBIBlankingBlank13 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 13  cmdID= 37222  "
        ::= { iqsyn21CmdEntry 37222 }


    iqsyn21UtilsHANCVBIBlankingBlank14 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 14  cmdID= 37223  "
        ::= { iqsyn21CmdEntry 37223 }


    iqsyn21UtilsHANCVBIBlankingBlank15 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 15  cmdID= 37224  "
        ::= { iqsyn21CmdEntry 37224 }


    iqsyn21UtilsHANCVBIBlankingBlank16 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 16  cmdID= 37225  "
        ::= { iqsyn21CmdEntry 37225 }


    iqsyn21UtilsHANCVBIBlankingBlank17 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 17  cmdID= 37226  "
        ::= { iqsyn21CmdEntry 37226 }


    iqsyn21UtilsHANCVBIBlankingBlank18 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 18  cmdID= 37227  "
        ::= { iqsyn21CmdEntry 37227 }


    iqsyn21UtilsHANCVBIBlankingBlank19 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 19  cmdID= 37228  "
        ::= { iqsyn21CmdEntry 37228 }


    iqsyn21UtilsHANCVBIBlankingBlank20 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 20  cmdID= 37229  "
        ::= { iqsyn21CmdEntry 37229 }


    iqsyn21UtilsHANCVBIBlankingBlank21 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 21  cmdID= 37230  "
        ::= { iqsyn21CmdEntry 37230 }


    iqsyn21UtilsHANCVBIBlankingBlank22 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 22  cmdID= 37231  "
        ::= { iqsyn21CmdEntry 37231 }


    iqsyn21UtilsHANCVBIBlankingBlank23 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 23  cmdID= 37232  "
        ::= { iqsyn21CmdEntry 37232 }


    iqsyn21UtilsHANCVBIBlankingBlank24 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 24  cmdID= 37233  "
        ::= { iqsyn21CmdEntry 37233 }


    iqsyn21UtilsHANCVBIBlankingBlank25 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 25  cmdID= 37234  "
        ::= { iqsyn21CmdEntry 37234 }


    iqsyn21UtilsHANCVBIBlankingBlank26 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 26  cmdID= 37235  "
        ::= { iqsyn21CmdEntry 37235 }


    iqsyn21UtilsHANCVBIBlankingBlank27 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 27  cmdID= 37236  "
        ::= { iqsyn21CmdEntry 37236 }


    iqsyn21UtilsHANCVBIBlankingBlank28 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 28  cmdID= 37237  "
        ::= { iqsyn21CmdEntry 37237 }


    iqsyn21UtilsHANCVBIBlankingBlank29 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 29  cmdID= 37238  "
        ::= { iqsyn21CmdEntry 37238 }


    iqsyn21UtilsHANCVBIBlankingBlank30 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 30  cmdID= 37239  "
        ::= { iqsyn21CmdEntry 37239 }


    iqsyn21UtilsHANCVBIBlankingBlank31 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 31  cmdID= 37240  "
        ::= { iqsyn21CmdEntry 37240 }


    iqsyn21UtilsHANCVBIBlankingBlank32 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 32  cmdID= 37241  "
        ::= { iqsyn21CmdEntry 37241 }


    iqsyn21UtilsHANCVBIBlankingBlank33 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 33  cmdID= 37242  "
        ::= { iqsyn21CmdEntry 37242 }


    iqsyn21UtilsHANCVBIBlankingBlank34 OBJECT-TYPE
        SYNTAX            INTEGER { disable(0), enable(1)  }
        MAX-ACCESS        read-write
        STATUS            current
        DESCRIPTION
                "CMNT: - VBI Blank checkbox - depends on standard selected
                 TYPE: - Checkbox
                 PAGE: - Utils
                    Blank 34  cmdID= 37243  "
        ::= { iqsyn21CmdEntry 37243 }


    iqsyn21UtilsSmpte2016Line2ReadAFD OBJECT-TYPE
        SYNTAX            RollCallString
        MAX-ACCESS        read-only
        STATUS            current
        DESCRIPTION
                "CMNT: - SMTPE2016 Reader Line 2 AFD
                 TYPE: - Display
                 PAGE: - Utils
                    Line2 Read AFD  cmdID= 39006  "
        ::= { iqsyn21CmdEntry 39006 }


    iqsyn21UtilsSmpte2016Line2ReadAR OBJECT-TYPE
        SYNTAX            RollCallString
        MAX-ACCESS        read-only
        STATUS            current
        DESCRIPTION
                "CMNT: - SMTPE2016 Reader Line 2 AR
                 TYPE: - Display
                 PAGE: - Utils
                    Line2 Read AR  cmdID= 39007  "
        ::= { iqsyn21CmdEntry 39007 }


    iqsyn21UtilsSmpte2016Line2WriteAFD OBJECT-TYPE
        SYNTAX            RollCallString
        MAX-ACCESS        read-only
        STATUS            current
        DESCRIPTION
                "CMNT: - SMTPE2016 Writer Line 2 AFD
                 TYPE: - Display
                 PAGE: - Utils
                    Line2 Write AFD  cmdID= 39013  "
        ::= { iqsyn21CmdEntry 39013 }


    iqsyn21UtilsSmpte2016Line2WriteAR OBJECT-TYPE
        SYNTAX            RollCallString
        MAX-ACCESS        read-only
        STATUS            current
        DESCRIPTION
                "CMNT: - SMTPE2016 Writer Line 2 AR
                 TYPE: - Display
                 PAGE: - Utils
                    Line2 Write AR  cmdID= 39014  "
        ::= { iqsyn21CmdEntry 39014 }


    iqsyn21GPIGPI1GPIO1Mode OBJECT-TYPE
        SYNTAX            INTEGER {
                            valUnused(0),
                            valInputGPI1(1),
                            valOutputGPO1(2)
                            }
        MAX-ACCESS        read-write
        STATUS            current
        DESCRIPTION
                "CMNT: - GPIO-1 Input/Output
                 TYPE: - RadiobuttonList
                 PAGE: - GPI
                    GPI/O 1 Mode  cmdID= 36120
                    Unused  value= 0
                    Input (GPI1)  value= 1
                    Output (GPO1)  value= 2  "
        ::= { iqsyn21CmdEntry 36120 }


    iqsyn21GPIGPI1GPI1ipSelect OBJECT-TYPE
        SYNTAX            INTEGER {
                            valUnused(-1),
                            valFreeze(0),
                            valPattern(1),
                            valBlack(2),
                            valBlankAncillary(3),
                            valMonoChrmYOnly(4),
                            valMonoChrmCbCrOnly(5),
                            valUseIPRef(6),
                            valUseExtRef(7),
                            valSelectInp1(50),
                            valSelectInp2(51),
                            valSelectInput(8),
                            valSelectBackup(9),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115)
                            }
        MAX-ACCESS        read-write
        STATUS            current
        DESCRIPTION
                "CMNT: - GPI-1 Input action
                 TYPE: - RadiobuttonList
                 PAGE: - GPI
                    GPI 1-i/p Select  cmdID= 36121
                    Unused  value= -1
                    Freeze  value= 0
                    Pattern  value= 1
                    Black  value= 2
                    Blank Ancillary  value= 3
                    MonoChrm Y Only  value= 4
                    MonoChrm CbCr Only  value= 5
                    Use I/P Ref  value= 6
                    Use Ext Ref  value= 7
                    Select Inp 1  value= 50
                    Select Inp 2  value= 51
                    Select Input  value= 8
                    Select Backup  value= 9
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115  "
        ::= { iqsyn21CmdEntry 36121 }


    iqsyn21GPIGPI1GPO1opSelect OBJECT-TYPE
        SYNTAX            INTEGER {
                            valInput1OK(50),
                            valInput2OK(51),
                            valReferenceOK(0),
                            valFreeze(1),
                            valPattern(2),
                            valBlack(3),
                            valMonochrome(4),
                            valInput2Selected(52)
                            }
        MAX-ACCESS        read-write
        STATUS            current
        DESCRIPTION
                "CMNT: - GPI-1 Output action
                 TYPE: - RadiobuttonList
                 PAGE: - GPI
                    GPO 1-o/p Select  cmdID= 36122
                    Input 1 OK  value= 50
                    Input 2 OK  value= 51
                    Reference OK  value= 0
                    Freeze  value= 1
                    Pattern  value= 2
                    Black  value= 3
                    Monochrome  value= 4
                    Input 2 Selected  value= 52  "
        ::= { iqsyn21CmdEntry 36122 }


    iqsyn21GPIGPI1InvertGPIO1 OBJECT-TYPE
        SYNTAX            INTEGER { disable(0), enable(1)  }
        MAX-ACCESS        read-write
        STATUS            current
        DESCRIPTION
                "CMNT: - GPI-1 Port Invert
                 TYPE: - Checkbox
                 PAGE: - GPI
                    Invert GPIO 1  cmdID= 36123  "
        ::= { iqsyn21CmdEntry 36123 }


    iqsyn21GPIGPI2GPIO2Mode OBJECT-TYPE
        SYNTAX            INTEGER {
                            valUnused(0),
                            valInputGPI2(1),
                            valOutputGPO2(2)
                            }
        MAX-ACCESS        read-write
        STATUS            current
        DESCRIPTION
                "CMNT: - GPIO-2 Input/Output
                 TYPE: - RadiobuttonList
                 PAGE: - GPI
                    GPI/O 2 Mode  cmdID= 36130
                    Unused  value= 0
                    Input (GPI2)  value= 1
                    Output (GPO2)  value= 2  "
        ::= { iqsyn21CmdEntry 36130 }


    iqsyn21GPIGPI2GPI2ipSelect OBJECT-TYPE
        SYNTAX            INTEGER {
                            valUnused(-1),
                            valFreeze(0),
                            valPattern(1),
                            valBlack(2),
                            valBlankAncillary(3),
                            valMonoChrmYOnly(4),
                            valMonoChrmCbCrOnly(5),
                            valUseIPRef(6),
                            valUseExtRef(7),
                            valSelectInp1(50),
                            valSelectInp2(51),
                            valSelectInput(8),
                            valSelectBackup(9),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115)
                            }
        MAX-ACCESS        read-write
        STATUS            current
        DESCRIPTION
                "CMNT: - GPI-2 Input action
                 TYPE: - RadiobuttonList
                 PAGE: - GPI
                    GPI 2-i/p Select  cmdID= 36131
                    Unused  value= -1
                    Freeze  value= 0
                    Pattern  value= 1
                    Black  value= 2
                    Blank Ancillary  value= 3
                    MonoChrm Y Only  value= 4
                    MonoChrm CbCr Only  value= 5
                    Use I/P Ref  value= 6
                    Use Ext Ref  value= 7
                    Select Inp 1  value= 50
                    Select Inp 2  value= 51
                    Select Input  value= 8
                    Select Backup  value= 9
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115  "
        ::= { iqsyn21CmdEntry 36131 }


    iqsyn21GPIGPI2GPO2opSelect OBJECT-TYPE
        SYNTAX            INTEGER {
                            valInput1OK(50),
                            valInput2OK(51),
                            valReferenceOK(0),
                            valFreeze(1),
                            valPattern(2),
                            valBlack(3),
                            valMonochrome(4),
                            valInput2Selected(52)
                            }
        MAX-ACCESS        read-write
        STATUS            current
        DESCRIPTION
                "CMNT: - GPI-2 Output action
                 TYPE: - RadiobuttonList
                 PAGE: - GPI
                    GPO 2-o/p Select  cmdID= 36132
                    Input 1 OK  value= 50
                    Input 2 OK  value= 51
                    Reference OK  value= 0
                    Freeze  value= 1
                    Pattern  value= 2
                    Black  value= 3
                    Monochrome  value= 4
                    Input 2 Selected  value= 52  "
        ::= { iqsyn21CmdEntry 36132 }


    iqsyn21GPIGPI2InvertGPIO2 OBJECT-TYPE
        SYNTAX            INTEGER { disable(0), enable(1)  }
        MAX-ACCESS        read-write
        STATUS            current
        DESCRIPTION
                "CMNT: - GPI-2 Port Invert
                 TYPE: - Checkbox
                 PAGE: - GPI
                    Invert GPIO 2  cmdID= 36133  "
        ::= { iqsyn21CmdEntry 36133 }


    iqsyn21GPIGPIPWMDelayTimerTimerSource OBJECT-TYPE
        SYNTAX            INTEGER {
                            valOff(0),
                            valGPI1(1),
                            valGPI2(2)
                            }
        MAX-ACCESS        read-write
        STATUS            current
        DESCRIPTION
                "CMNT: - 
                 TYPE: - RadiobuttonList
                 PAGE: - GPI
                    Timer Source  cmdID= 36124
                    Off  value= 0
                    GPI 1  value= 1
                    GPI 2  value= 2  "
        ::= { iqsyn21CmdEntry 36124 }


    iqsyn21GPIGPIPWMDelayTimerActiveHigh OBJECT-TYPE
        SYNTAX            INTEGER { disable(0), enable(1)  }
        MAX-ACCESS        read-write
        STATUS            current
        DESCRIPTION
                "CMNT: - 
                 TYPE: - Checkbox
                 PAGE: - GPI
                    Active High  cmdID= 36125  "
        ::= { iqsyn21CmdEntry 36125 }


    iqsyn21MemoriesRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Recall Memory  cmdID= 37100
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqsyn21CmdEntry 37100 }


    iqsyn21MemoriesSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqsyn21CmdEntry 37101 }


    iqsyn21MemoriesSaveMemory OBJECT-TYPE
        SYNTAX            INTEGER { noAction(0),valSaveMemory(1) }
        MAX-ACCESS        read-write
        STATUS            current
        DESCRIPTION
                "CMNT: - 
                 TYPE: - Button
                 PAGE: - Memories
                    Save Memory  cmdID= 37102
                    value= 1  "
        ::= { iqsyn21CmdEntry 37102 }


    iqsyn21MemoriesClearMemory OBJECT-TYPE
        SYNTAX            INTEGER { noAction(0),valClearMemory(1) }
        MAX-ACCESS        read-write
        STATUS            current
        DESCRIPTION
                "CMNT: - Delete User Memory
                 TYPE: - Button
                 PAGE: - Memories
                    Clear Memory  cmdID= 37105
                    value= 1  "
        ::= { iqsyn21CmdEntry 37105 }


    iqsyn21MemoriesMemoryNameChangeName OBJECT-TYPE
        SYNTAX            RollCallString
        MAX-ACCESS        read-write
        STATUS            current
        DESCRIPTION
                "CMNT: - 
                 TYPE: - Editstring
                 PAGE: - Memories
                    Change Name  cmdID= 37103
                    preset= Display Memory"
        ::= { iqsyn21CmdEntry 37103 }


    iqsyn21MemoriesLastUserMemory OBJECT-TYPE
        SYNTAX            RollCallString
        MAX-ACCESS        read-only
        STATUS            current
        DESCRIPTION
                "CMNT: - 
                 TYPE: - Display
                 PAGE: - Memories
                    Last User Memory  cmdID= 37104  "
        ::= { iqsyn21CmdEntry 37104 }


    iqsyn21MemoriesMemoryName1 OBJECT-TYPE
        SYNTAX            RollCallString
        MAX-ACCESS        read-only
        STATUS            current
        DESCRIPTION
                "CMNT: - 
                 TYPE: - Display
                 PAGE: - Memories
                    Memory Name1  cmdID= 37106  "
        ::= { iqsyn21CmdEntry 37106 }


    iqsyn21MemoriesMemoryName2 OBJECT-TYPE
        SYNTAX            RollCallString
        MAX-ACCESS        read-only
        STATUS            current
        DESCRIPTION
                "CMNT: - 
                 TYPE: - Display
                 PAGE: - Memories
                    Memory Name2  cmdID= 37107  "
        ::= { iqsyn21CmdEntry 37107 }


    iqsyn21MemoriesMemoryName3 OBJECT-TYPE
        SYNTAX            RollCallString
        MAX-ACCESS        read-only
        STATUS            current
        DESCRIPTION
                "CMNT: - 
                 TYPE: - Display
                 PAGE: - Memories
                    Memory Name3  cmdID= 37108  "
        ::= { iqsyn21CmdEntry 37108 }


    iqsyn21MemoriesMemoryName4 OBJECT-TYPE
        SYNTAX            RollCallString
        MAX-ACCESS        read-only
        STATUS            current
        DESCRIPTION
                "CMNT: - 
                 TYPE: - Display
                 PAGE: - Memories
                    Memory Name4  cmdID= 37109  "
        ::= { iqsyn21CmdEntry 37109 }


    iqsyn21MemoriesMemoryName5 OBJECT-TYPE
        SYNTAX            RollCallString
        MAX-ACCESS        read-only
        STATUS            current
        DESCRIPTION
                "CMNT: - 
                 TYPE: - Display
                 PAGE: - Memories
                    Memory Name5  cmdID= 37110  "
        ::= { iqsyn21CmdEntry 37110 }


    iqsyn21MemoriesMemoryName6 OBJECT-TYPE
        SYNTAX            RollCallString
        MAX-ACCESS        read-only
        STATUS            current
        DESCRIPTION
                "CMNT: - 
                 TYPE: - Display
                 PAGE: - Memories
                    Memory Name6  cmdID= 37111  "
        ::= { iqsyn21CmdEntry 37111 }


    iqsyn21MemoriesMemoryName7 OBJECT-TYPE
        SYNTAX            RollCallString
        MAX-ACCESS        read-only
        STATUS            current
        DESCRIPTION
                "CMNT: - 
                 TYPE: - Display
                 PAGE: - Memories
                    Memory Name7  cmdID= 37112  "
        ::= { iqsyn21CmdEntry 37112 }


    iqsyn21MemoriesMemoryName8 OBJECT-TYPE
        SYNTAX            RollCallString
        MAX-ACCESS        read-only
        STATUS            current
        DESCRIPTION
                "CMNT: - 
                 TYPE: - Display
                 PAGE: - Memories
                    Memory Name8  cmdID= 37113  "
        ::= { iqsyn21CmdEntry 37113 }


    iqsyn21MemoriesMemoryName9 OBJECT-TYPE
        SYNTAX            RollCallString
        MAX-ACCESS        read-only
        STATUS            current
        DESCRIPTION
                "CMNT: - 
                 TYPE: - Display
                 PAGE: - Memories
                    Memory Name9  cmdID= 37114  "
        ::= { iqsyn21CmdEntry 37114 }


    iqsyn21MemoriesMemoryName10 OBJECT-TYPE
        SYNTAX            RollCallString
        MAX-ACCESS        read-only
        STATUS            current
        DESCRIPTION
                "CMNT: - 
                 TYPE: - Display
                 PAGE: - Memories
                    Memory Name10  cmdID= 37115  "
        ::= { iqsyn21CmdEntry 37115 }


    iqsyn21MemoriesMemoryName11 OBJECT-TYPE
        SYNTAX            RollCallString
        MAX-ACCESS        read-only
        STATUS            current
        DESCRIPTION
                "CMNT: - 
                 TYPE: - Display
                 PAGE: - Memories
                    Memory Name11  cmdID= 37116  "
        ::= { iqsyn21CmdEntry 37116 }


    iqsyn21MemoriesMemoryName12 OBJECT-TYPE
        SYNTAX            RollCallString
        MAX-ACCESS        read-only
        STATUS            current
        DESCRIPTION
                "CMNT: - 
                 TYPE: - Display
                 PAGE: - Memories
                    Memory Name12  cmdID= 37117  "
        ::= { iqsyn21CmdEntry 37117 }


    iqsyn21MemoriesMemoryName13 OBJECT-TYPE
        SYNTAX            RollCallString
        MAX-ACCESS        read-only
        STATUS            current
        DESCRIPTION
                "CMNT: - 
                 TYPE: - Display
                 PAGE: - Memories
                    Memory Name13  cmdID= 37118  "
        ::= { iqsyn21CmdEntry 37118 }


    iqsyn21MemoriesMemoryName14 OBJECT-TYPE
        SYNTAX            RollCallString
        MAX-ACCESS        read-only
        STATUS            current
        DESCRIPTION
                "CMNT: - 
                 TYPE: - Display
                 PAGE: - Memories
                    Memory Name14  cmdID= 37119  "
        ::= { iqsyn21CmdEntry 37119 }


    iqsyn21MemoriesMemoryName15 OBJECT-TYPE
        SYNTAX            RollCallString
        MAX-ACCESS        read-only
        STATUS            current
        DESCRIPTION
                "CMNT: - 
                 TYPE: - Display
                 PAGE: - Memories
                    Memory Name15  cmdID= 37120  "
        ::= { iqsyn21CmdEntry 37120 }


    iqsyn21MemoriesMemoryName16 OBJECT-TYPE
        SYNTAX            RollCallString
        MAX-ACCESS        read-only
        STATUS            current
        DESCRIPTION
                "CMNT: - 
                 TYPE: - Display
                 PAGE: - Memories
                    Memory Name16  cmdID= 37121  "
        ::= { iqsyn21CmdEntry 37121 }


    iqsyn21LoggingVideoInputLogInput1Type OBJECT-TYPE
        SYNTAX            INTEGER { disable(0), enable(1)  }
        MAX-ACCESS        read-write
        STATUS            current
        DESCRIPTION
                "CMNT: - Enable/Disable logging for Input 1 Type
                 TYPE: - Checkbox
                 PAGE: - Logging
                    Log Input 1 Type  cmdID= 35017  "
        ::= { iqsyn21CmdEntry 35017 }


    iqsyn21LoggingVideoInputInput1Type OBJECT-TYPE
        SYNTAX            RollCallString
        MAX-ACCESS        read-only
        STATUS            current
        DESCRIPTION
                "CMNT: - Logging state for Input 1 Type
                 TYPE: - Display
                 PAGE: - Logging
                    Input 1 Type=  cmdID= 36017  "
        ::= { iqsyn21CmdEntry 36017 }


    iqsyn21LoggingVideoInputLogInput1Status OBJECT-TYPE
        SYNTAX            INTEGER { disable(0), enable(1)  }
        MAX-ACCESS        read-write
        STATUS            current
        DESCRIPTION
                "CMNT: - Enable/Disable logging for Input 1 Status
                 TYPE: - Checkbox
                 PAGE: - Logging
                    Log Input 1 Status  cmdID= 35005  "
        ::= { iqsyn21CmdEntry 35005 }


    iqsyn21LoggingVideoInputInput1Status OBJECT-TYPE
        SYNTAX            RollCallString
        MAX-ACCESS        read-only
        STATUS            current
        DESCRIPTION
                "CMNT: - Logging state for Input 1 Status
                 TYPE: - Display
                 PAGE: - Logging
                    Input 1 Status=  cmdID= 36005  "
        ::= { iqsyn21CmdEntry 36005 }


    iqsyn21LoggingVideoInputLogInput1Std OBJECT-TYPE
        SYNTAX            INTEGER { disable(0), enable(1)  }
        MAX-ACCESS        read-write
        STATUS            current
        DESCRIPTION
                "CMNT: - Enable/Disable logging for Input 1 Std.
                 TYPE: - Checkbox
                 PAGE: - Logging
                    Log Input 1 Std.  cmdID= 35016  "
        ::= { iqsyn21CmdEntry 35016 }


    iqsyn21LoggingVideoInputInput1Std OBJECT-TYPE
        SYNTAX            RollCallString
        MAX-ACCESS        read-only
        STATUS            current
        DESCRIPTION
                "CMNT: - Logging state for Input 1 Std.
                 TYPE: - Display
                 PAGE: - Logging
                    Input 1 Std.=  cmdID= 36016  "
        ::= { iqsyn21CmdEntry 36016 }


    iqsyn21LoggingVideoInputLogInput1Errors OBJECT-TYPE
        SYNTAX            INTEGER { disable(0), enable(1)  }
        MAX-ACCESS        read-write
        STATUS            current
        DESCRIPTION
                "CMNT: - Enable/Disable logging for Input 1 Errors
                 TYPE: - Checkbox
                 PAGE: - Logging
                    Log Input 1 Errors  cmdID= 35002  "
        ::= { iqsyn21CmdEntry 35002 }


    iqsyn21LoggingVideoInputInput1Errors OBJECT-TYPE
        SYNTAX            RollCallString
        MAX-ACCESS        read-only
        STATUS            current
        DESCRIPTION
                "CMNT: - Logging state for Input 1 Errors
                 TYPE: - Display
                 PAGE: - Logging
                    Input 1 Errors=  cmdID= 36002  "
        ::= { iqsyn21CmdEntry 36002 }


    iqsyn21LoggingVideoInputLogInput1ErrSecs OBJECT-TYPE
        SYNTAX            INTEGER { disable(0), enable(1)  }
        MAX-ACCESS        read-write
        STATUS            current
        DESCRIPTION
                "CMNT: - Enable/Disable logging for Input 1 ErrSecs
                 TYPE: - Checkbox
                 PAGE: - Logging
                    Log Input 1 ErrSecs  cmdID= 35003  "
        ::= { iqsyn21CmdEntry 35003 }


    iqsyn21LoggingVideoInputInput1ErrSecs OBJECT-TYPE
        SYNTAX            RollCallString
        MAX-ACCESS        read-only
        STATUS            current
        DESCRIPTION
                "CMNT: - Logging state for Input 1 ErrSecs
                 TYPE: - Display
                 PAGE: - Logging
                    Input 1 ErrSecs=  cmdID= 36003  "
        ::= { iqsyn21CmdEntry 36003 }


    iqsyn21LoggingVideoInputLogInput1ANCErr OBJECT-TYPE
        SYNTAX            INTEGER { disable(0), enable(1)  }
        MAX-ACCESS        read-write
        STATUS            current
        DESCRIPTION
                "CMNT: - Enable/Disable logging for Input 1 ANC Errors
                 TYPE: - Checkbox
                 PAGE: - Logging
                    Log Input 1 ANC Errors  cmdID= 35000  "
        ::= { iqsyn21CmdEntry 35000 }


    iqsyn21LoggingVideoInputInput1ANCErrors OBJECT-TYPE
        SYNTAX            RollCallString
        MAX-ACCESS        read-only
        STATUS            current
        DESCRIPTION
                "CMNT: - Logging state for Input 1 ANC Errors
                 TYPE: - Display
                 PAGE: - Logging
                    Input 1 ANC Errors=  cmdID= 36000  "
        ::= { iqsyn21CmdEntry 36000 }


    iqsyn21LoggingVideoInputLogInput1ANCErrSecs OBJECT-TYPE
        SYNTAX            INTEGER { disable(0), enable(1)  }
        MAX-ACCESS        read-write
        STATUS            current
        DESCRIPTION
                "CMNT: - Enable/Disable logging for Input 1 ANC ErrSecs
                 TYPE: - Checkbox
                 PAGE: - Logging
                    Log Input 1 ANC ErrSecs  cmdID= 35001  "
        ::= { iqsyn21CmdEntry 35001 }


    iqsyn21LoggingVideoInputInput1ANCErrSecs OBJECT-TYPE
        SYNTAX            RollCallString
        MAX-ACCESS        read-only
        STATUS            current
        DESCRIPTION
                "CMNT: - Logging state for Input 1 ANC ErrSecs
                 TYPE: - Display
                 PAGE: - Logging
                    Input 1 ANC ErrSecs=  cmdID= 36001  "
        ::= { iqsyn21CmdEntry 36001 }


    iqsyn21LoggingVideoInputLogInput2Type OBJECT-TYPE
        SYNTAX            INTEGER { disable(0), enable(1)  }
        MAX-ACCESS        read-write
        STATUS            current
        DESCRIPTION
                "CMNT: - Enable/Disable logging for Input 2 Type
                 TYPE: - Checkbox
                 PAGE: - Logging
                    Log Input 2 Type  cmdID= 35047  "
        ::= { iqsyn21CmdEntry 35047 }


    iqsyn21LoggingVideoInputInput2Type OBJECT-TYPE
        SYNTAX            RollCallString
        MAX-ACCESS        read-only
        STATUS            current
        DESCRIPTION
                "CMNT: - Logging state for Input 2 Type
                 TYPE: - Display
                 PAGE: - Logging
                    Input 2 Type=  cmdID= 36047  "
        ::= { iqsyn21CmdEntry 36047 }


    iqsyn21LoggingVideoInputLogInput2Status OBJECT-TYPE
        SYNTAX            INTEGER { disable(0), enable(1)  }
        MAX-ACCESS        read-write
        STATUS            current
        DESCRIPTION
                "CMNT: - Enable/Disable logging for Input 2 Status
                 TYPE: - Checkbox
                 PAGE: - Logging
                    Log Input 2 Status  cmdID= 35035  "
        ::= { iqsyn21CmdEntry 35035 }


    iqsyn21LoggingVideoInputInput2Status OBJECT-TYPE
        SYNTAX            RollCallString
        MAX-ACCESS        read-only
        STATUS            current
        DESCRIPTION
                "CMNT: - Logging state for Input 2 Status
                 TYPE: - Display
                 PAGE: - Logging
                    Input 2 Status=  cmdID= 36035  "
        ::= { iqsyn21CmdEntry 36035 }


    iqsyn21LoggingVideoInputLogInput2Std OBJECT-TYPE
        SYNTAX            INTEGER { disable(0), enable(1)  }
        MAX-ACCESS        read-write
        STATUS            current
        DESCRIPTION
                "CMNT: - Enable/Disable logging for Input 2 Std.
                 TYPE: - Checkbox
                 PAGE: - Logging
                    Log Input 2 Std.  cmdID= 35046  "
        ::= { iqsyn21CmdEntry 35046 }


    iqsyn21LoggingVideoInputInput2Std OBJECT-TYPE
        SYNTAX            RollCallString
        MAX-ACCESS        read-only
        STATUS            current
        DESCRIPTION
                "CMNT: - Logging state for Input 2 Std.
                 TYPE: - Display
                 PAGE: - Logging
                    Input 2 Std.=  cmdID= 36046  "
        ::= { iqsyn21CmdEntry 36046 }


    iqsyn21LoggingVideoInputLogInput2Errors OBJECT-TYPE
        SYNTAX            INTEGER { disable(0), enable(1)  }
        MAX-ACCESS        read-write
        STATUS            current
        DESCRIPTION
                "CMNT: - Enable/Disable logging for Input 2 Errors
                 TYPE: - Checkbox
                 PAGE: - Logging
                    Log Input 2 Errors  cmdID= 35032  "
        ::= { iqsyn21CmdEntry 35032 }


    iqsyn21LoggingVideoInputInput2Errors OBJECT-TYPE
        SYNTAX            RollCallString
        MAX-ACCESS        read-only
        STATUS            current
        DESCRIPTION
                "CMNT: - Logging state for Input 2 Errors
                 TYPE: - Display
                 PAGE: - Logging
                    Input 2 Errors=  cmdID= 36032  "
        ::= { iqsyn21CmdEntry 36032 }


    iqsyn21LoggingVideoInputLogInput2ErrSecs OBJECT-TYPE
        SYNTAX            INTEGER { disable(0), enable(1)  }
        MAX-ACCESS        read-write
        STATUS            current
        DESCRIPTION
                "CMNT: - Enable/Disable logging for Input 2 ErrSecs
                 TYPE: - Checkbox
                 PAGE: - Logging
                    Log Input 2 ErrSecs  cmdID= 35033  "
        ::= { iqsyn21CmdEntry 35033 }


    iqsyn21LoggingVideoInputInput2ErrSecs OBJECT-TYPE
        SYNTAX            RollCallString
        MAX-ACCESS        read-only
        STATUS            current
        DESCRIPTION
                "CMNT: - Logging state for Input 2 ErrSecs
                 TYPE: - Display
                 PAGE: - Logging
                    Input 2 ErrSecs=  cmdID= 36033  "
        ::= { iqsyn21CmdEntry 36033 }


    iqsyn21LoggingVideoInputLogInput2ANCErr OBJECT-TYPE
        SYNTAX            INTEGER { disable(0), enable(1)  }
        MAX-ACCESS        read-write
        STATUS            current
        DESCRIPTION
                "CMNT: - Enable/Disable logging for Input 2 ANC Errors
                 TYPE: - Checkbox
                 PAGE: - Logging
                    Log Input 2 ANC Errors  cmdID= 35030  "
        ::= { iqsyn21CmdEntry 35030 }


    iqsyn21LoggingVideoInputInput2ANCErrors OBJECT-TYPE
        SYNTAX            RollCallString
        MAX-ACCESS        read-only
        STATUS            current
        DESCRIPTION
                "CMNT: - Logging state for Input 2 ANC Errors
                 TYPE: - Display
                 PAGE: - Logging
                    Input 2 ANC Errors=  cmdID= 36030  "
        ::= { iqsyn21CmdEntry 36030 }


    iqsyn21LoggingVideoInputLogInput2ANCErrSecs OBJECT-TYPE
        SYNTAX            INTEGER { disable(0), enable(1)  }
        MAX-ACCESS        read-write
        STATUS            current
        DESCRIPTION
                "CMNT: - Enable/Disable logging for Input 2 ANC ErrSecs
                 TYPE: - Checkbox
                 PAGE: - Logging
                    Log Input 2 ANC ErrSecs  cmdID= 35031  "
        ::= { iqsyn21CmdEntry 35031 }


    iqsyn21LoggingVideoInputInput2ANCErrSecs OBJECT-TYPE
        SYNTAX            RollCallString
        MAX-ACCESS        read-only
        STATUS            current
        DESCRIPTION
                "CMNT: - Logging state for Input 2 ANC ErrSecs
                 TYPE: - Display
                 PAGE: - Logging
                    Input 2 ANC ErrSecs=  cmdID= 36031  "
        ::= { iqsyn21CmdEntry 36031 }


    iqsyn21LoggingRefOutputLogOutputState OBJECT-TYPE
        SYNTAX            INTEGER { disable(0), enable(1)  }
        MAX-ACCESS        read-write
        STATUS            current
        DESCRIPTION
                "CMNT: - Enable/Disable logging for Output State
                 TYPE: - Checkbox
                 PAGE: - Logging
                    Log Output State  cmdID= 35941  "
        ::= { iqsyn21CmdEntry 35941 }


    iqsyn21LoggingRefOutputOutputState OBJECT-TYPE
        SYNTAX            RollCallString
        MAX-ACCESS        read-only
        STATUS            current
        DESCRIPTION
                "CMNT: - Logging state for Output State
                 TYPE: - Display
                 PAGE: - Logging
                    Output State=  cmdID= 36941  "
        ::= { iqsyn21CmdEntry 36941 }


    iqsyn21LoggingRefOutputLogOutputType OBJECT-TYPE
        SYNTAX            INTEGER { disable(0), enable(1)  }
        MAX-ACCESS        read-write
        STATUS            current
        DESCRIPTION
                "CMNT: - Enable/Disable logging for Output Type
                 TYPE: - Checkbox
                 PAGE: - Logging
                    Log Output Type  cmdID= 35942  "
        ::= { iqsyn21CmdEntry 35942 }


    iqsyn21LoggingRefOutputOutputType OBJECT-TYPE
        SYNTAX            RollCallString
        MAX-ACCESS        read-only
        STATUS            current
        DESCRIPTION
                "CMNT: - Logging state for Output Type
                 TYPE: - Display
                 PAGE: - Logging
                    Output Type=  cmdID= 36942  "
        ::= { iqsyn21CmdEntry 36942 }


    iqsyn21LoggingRefOutputLogOutputStandard OBJECT-TYPE
        SYNTAX            INTEGER { disable(0), enable(1)  }
        MAX-ACCESS        read-write
        STATUS            current
        DESCRIPTION
                "CMNT: - Enable/Disable logging for Output Standard
                 TYPE: - Checkbox
                 PAGE: - Logging
                    Log Output Standard  cmdID= 35940  "
        ::= { iqsyn21CmdEntry 35940 }


    iqsyn21LoggingRefOutputOutputStandard OBJECT-TYPE
        SYNTAX            RollCallString
        MAX-ACCESS        read-only
        STATUS            current
        DESCRIPTION
                "CMNT: - Logging state for Output Standard
                 TYPE: - Display
                 PAGE: - Logging
                    Output Standard=  cmdID= 36940  "
        ::= { iqsyn21CmdEntry 36940 }


    iqsyn21LoggingVideoOutLoggingLogoutputANCstate OBJECT-TYPE
        SYNTAX            INTEGER { disable(0), enable(1)  }
        MAX-ACCESS        read-write
        STATUS            current
        DESCRIPTION
                "CMNT: - Enable/Disable logging for Output ANC embedder state
                 TYPE: - Checkbox
                 PAGE: - Logging
                    Log output ANC state  cmdID= 35946  "
        ::= { iqsyn21CmdEntry 35946 }


    iqsyn21LoggingVideoOutLoggingOutputANCstate OBJECT-TYPE
        SYNTAX            RollCallString
        MAX-ACCESS        read-only
        STATUS            current
        DESCRIPTION
                "CMNT: - Logging state for Output ANC embedder state
                 TYPE: - Display
                 PAGE: - Logging
                    Output ANC state=  cmdID= 36946  "
        ::= { iqsyn21CmdEntry 36946 }


    iqsyn21LoggingRefOutputLogOutputSource OBJECT-TYPE
        SYNTAX            INTEGER { disable(0), enable(1)  }
        MAX-ACCESS        read-write
        STATUS            current
        DESCRIPTION
                "CMNT: - Enable/Disable logging for Output Source
                 TYPE: - Checkbox
                 PAGE: - Logging
                    Log output Source  cmdID= 35943  "
        ::= { iqsyn21CmdEntry 35943 }


    iqsyn21LoggingRefOutputOutputSource OBJECT-TYPE
        SYNTAX            RollCallString
        MAX-ACCESS        read-only
        STATUS            current
        DESCRIPTION
                "CMNT: - Logging state for Output Source
                 TYPE: - Display
                 PAGE: - Logging
                    Output Source=  cmdID= 36943  "
        ::= { iqsyn21CmdEntry 36943 }


    iqsyn21LoggingIn1AudStateLogInp1Emb1stat OBJECT-TYPE
        SYNTAX            INTEGER { disable(0), enable(1)  }
        MAX-ACCESS        read-write
        STATUS            current
        DESCRIPTION
                "CMNT: - Enable/Disable logging for Input 1 Emb.Pair 1 state
                 TYPE: - Checkbox
                 PAGE: - Logging
                    Log Inp1 Emb.1 state  cmdID= 35006  "
        ::= { iqsyn21CmdEntry 35006 }


    iqsyn21LoggingIn1AudStateInp1Emb1state OBJECT-TYPE
        SYNTAX            RollCallString
        MAX-ACCESS        read-only
        STATUS            current
        DESCRIPTION
                "CMNT: - Logging state for Input 1 Emb.Pair 1 state
                 TYPE: - Display
                 PAGE: - Logging
                    Inp1 Emb.1 state=  cmdID= 36006  "
        ::= { iqsyn21CmdEntry 36006 }


    iqsyn21LoggingIn1AudStateLogInp1Emb2stat OBJECT-TYPE
        SYNTAX            INTEGER { disable(0), enable(1)  }
        MAX-ACCESS        read-write
        STATUS            current
        DESCRIPTION
                "CMNT: - Enable/Disable logging for Input 1 Emb.Pair 2 state
                 TYPE: - Checkbox
                 PAGE: - Logging
                    Log Inp1 Emb.2 state  cmdID= 35007  "
        ::= { iqsyn21CmdEntry 35007 }


    iqsyn21LoggingIn1AudStateInp1Emb2state OBJECT-TYPE
        SYNTAX            RollCallString
        MAX-ACCESS        read-only
        STATUS            current
        DESCRIPTION
                "CMNT: - Logging state for Input 1 Emb.Pair 2 state
                 TYPE: - Display
                 PAGE: - Logging
                    Inp1 Emb.2 state=  cmdID= 36007  "
        ::= { iqsyn21CmdEntry 36007 }


    iqsyn21LoggingIn1AudStateLogInp1Emb3stat OBJECT-TYPE
        SYNTAX            INTEGER { disable(0), enable(1)  }
        MAX-ACCESS        read-write
        STATUS            current
        DESCRIPTION
                "CMNT: - Enable/Disable logging for Input 1 Emb.Pair 3 state
                 TYPE: - Checkbox
                 PAGE: - Logging
                    Log Inp1 Emb.3 state  cmdID= 35008  "
        ::= { iqsyn21CmdEntry 35008 }


    iqsyn21LoggingIn1AudStateInp1Emb3state OBJECT-TYPE
        SYNTAX            RollCallString
        MAX-ACCESS        read-only
        STATUS            current
        DESCRIPTION
                "CMNT: - Logging state for Input 1 Emb.Pair 3 state
                 TYPE: - Display
                 PAGE: - Logging
                    Inp1 Emb.3 state=  cmdID= 36008  "
        ::= { iqsyn21CmdEntry 36008 }


    iqsyn21LoggingIn1AudStateLogInp1Emb4stat OBJECT-TYPE
        SYNTAX            INTEGER { disable(0), enable(1)  }
        MAX-ACCESS        read-write
        STATUS            current
        DESCRIPTION
                "CMNT: - Enable/Disable logging for Input 1 Emb.Pair 4 state
                 TYPE: - Checkbox
                 PAGE: - Logging
                    Log Inp1 Emb.4 state  cmdID= 35009  "
        ::= { iqsyn21CmdEntry 35009 }


    iqsyn21LoggingIn1AudStateInp1Emb4state OBJECT-TYPE
        SYNTAX            RollCallString
        MAX-ACCESS        read-only
        STATUS            current
        DESCRIPTION
                "CMNT: - Logging state for Input 1 Emb.Pair 4 state
                 TYPE: - Display
                 PAGE: - Logging
                    Inp1 Emb.4 state=  cmdID= 36009  "
        ::= { iqsyn21CmdEntry 36009 }


    iqsyn21LoggingIn1AudStateLogInp1Emb5stat OBJECT-TYPE
        SYNTAX            INTEGER { disable(0), enable(1)  }
        MAX-ACCESS        read-write
        STATUS            current
        DESCRIPTION
                "CMNT: - Enable/Disable logging for Input 1 Emb.Pair 5 state
                 TYPE: - Checkbox
                 PAGE: - Logging
                    Log Inp1 Emb.5 state  cmdID= 35010  "
        ::= { iqsyn21CmdEntry 35010 }


    iqsyn21LoggingIn1AudStateInp1Emb5state OBJECT-TYPE
        SYNTAX            RollCallString
        MAX-ACCESS        read-only
        STATUS            current
        DESCRIPTION
                "CMNT: - Logging state for Input 1 Emb.Pair 5 state
                 TYPE: - Display
                 PAGE: - Logging
                    Inp1 Emb.5 state=  cmdID= 36010  "
        ::= { iqsyn21CmdEntry 36010 }


    iqsyn21LoggingIn1AudStateLogInp1Emb6stat OBJECT-TYPE
        SYNTAX            INTEGER { disable(0), enable(1)  }
        MAX-ACCESS        read-write
        STATUS            current
        DESCRIPTION
                "CMNT: - Enable/Disable logging for Input 1 Emb.Pair 6 state
                 TYPE: - Checkbox
                 PAGE: - Logging
                    Log Inp1 Emb.6 state  cmdID= 35011  "
        ::= { iqsyn21CmdEntry 35011 }


    iqsyn21LoggingIn1AudStateInp1Emb6state OBJECT-TYPE
        SYNTAX            RollCallString
        MAX-ACCESS        read-only
        STATUS            current
        DESCRIPTION
                "CMNT: - Logging state for Input 1 Emb.Pair 6 state
                 TYPE: - Display
                 PAGE: - Logging
                    Inp1 Emb.6 state=  cmdID= 36011  "
        ::= { iqsyn21CmdEntry 36011 }


    iqsyn21LoggingIn1AudStateLogInp1Emb7stat OBJECT-TYPE
        SYNTAX            INTEGER { disable(0), enable(1)  }
        MAX-ACCESS        read-write
        STATUS            current
        DESCRIPTION
                "CMNT: - Enable/Disable logging for Input 1 Emb.Pair 7 state
                 TYPE: - Checkbox
                 PAGE: - Logging
                    Log Inp1 Emb.7 state  cmdID= 35012  "
        ::= { iqsyn21CmdEntry 35012 }


    iqsyn21LoggingIn1AudStateInp1Emb7state OBJECT-TYPE
        SYNTAX            RollCallString
        MAX-ACCESS        read-only
        STATUS            current
        DESCRIPTION
                "CMNT: - Logging state for Input 1 Emb.Pair 7 state
                 TYPE: - Display
                 PAGE: - Logging
                    Inp1 Emb.7 state=  cmdID= 36012  "
        ::= { iqsyn21CmdEntry 36012 }


    iqsyn21LoggingIn1AudStateLogInp1Emb8stat OBJECT-TYPE
        SYNTAX            INTEGER { disable(0), enable(1)  }
        MAX-ACCESS        read-write
        STATUS            current
        DESCRIPTION
                "CMNT: - Enable/Disable logging for Input 1 Emb.Pair 8 state
                 TYPE: - Checkbox
                 PAGE: - Logging
                    Log Inp1 Emb.8 state  cmdID= 35013  "
        ::= { iqsyn21CmdEntry 35013 }


    iqsyn21LoggingIn1AudStateInp1Emb8state OBJECT-TYPE
        SYNTAX            RollCallString
        MAX-ACCESS        read-only
        STATUS            current
        DESCRIPTION
                "CMNT: - Logging state for Input 1 Emb.Pair 8 state
                 TYPE: - Display
                 PAGE: - Logging
                    Inp1 Emb.8 state=  cmdID= 36013  "
        ::= { iqsyn21CmdEntry 36013 }


    iqsyn21LoggingIn1AudTypeLogInp1Emb1type OBJECT-TYPE
        SYNTAX            INTEGER { disable(0), enable(1)  }
        MAX-ACCESS        read-write
        STATUS            current
        DESCRIPTION
                "CMNT: - Enable/Disable logging for Input 1 Emb.Pair 1 type
                 TYPE: - Checkbox
                 PAGE: - Logging
                    Log Inp1 Emb.1 type  cmdID= 35018  "
        ::= { iqsyn21CmdEntry 35018 }


    iqsyn21LoggingIn1AudTypeInp1Emb1type OBJECT-TYPE
        SYNTAX            RollCallString
        MAX-ACCESS        read-only
        STATUS            current
        DESCRIPTION
                "CMNT: - Logging state for Input 1 Emb.Pair 1 type
                 TYPE: - Display
                 PAGE: - Logging
                    Inp1 Emb.1 type=  cmdID= 36018  "
        ::= { iqsyn21CmdEntry 36018 }


    iqsyn21LoggingIn1AudTypeLogInp1Emb2type OBJECT-TYPE
        SYNTAX            INTEGER { disable(0), enable(1)  }
        MAX-ACCESS        read-write
        STATUS            current
        DESCRIPTION
                "CMNT: - Enable/Disable logging for Input 1 Emb.Pair 2 type
                 TYPE: - Checkbox
                 PAGE: - Logging
                    Log Inp1 Emb.2 type  cmdID= 35019  "
        ::= { iqsyn21CmdEntry 35019 }


    iqsyn21LoggingIn1AudTypeInp1Emb2type OBJECT-TYPE
        SYNTAX            RollCallString
        MAX-ACCESS        read-only
        STATUS            current
        DESCRIPTION
                "CMNT: - Logging state for Input 1 Emb.Pair 2 type
                 TYPE: - Display
                 PAGE: - Logging
                    Inp1 Emb.2 type=  cmdID= 36019  "
        ::= { iqsyn21CmdEntry 36019 }


    iqsyn21LoggingIn1AudTypeLogInp1Emb3type OBJECT-TYPE
        SYNTAX            INTEGER { disable(0), enable(1)  }
        MAX-ACCESS        read-write
        STATUS            current
        DESCRIPTION
                "CMNT: - Enable/Disable logging for Input 1 Emb.Pair 3 type
                 TYPE: - Checkbox
                 PAGE: - Logging
                    Log Inp1 Emb.3 type  cmdID= 35020  "
        ::= { iqsyn21CmdEntry 35020 }


    iqsyn21LoggingIn1AudTypeInp1Emb3type OBJECT-TYPE
        SYNTAX            RollCallString
        MAX-ACCESS        read-only
        STATUS            current
        DESCRIPTION
                "CMNT: - Logging state for Input 1 Emb.Pair 3 type
                 TYPE: - Display
                 PAGE: - Logging
                    Inp1 Emb.3 type=  cmdID= 36020  "
        ::= { iqsyn21CmdEntry 36020 }


    iqsyn21LoggingIn1AudTypeLogInp1Emb4type OBJECT-TYPE
        SYNTAX            INTEGER { disable(0), enable(1)  }
        MAX-ACCESS        read-write
        STATUS            current
        DESCRIPTION
                "CMNT: - Enable/Disable logging for Input 1 Emb.Pair 4 type
                 TYPE: - Checkbox
                 PAGE: - Logging
                    Log Inp1 Emb.4 type  cmdID= 35021  "
        ::= { iqsyn21CmdEntry 35021 }


    iqsyn21LoggingIn1AudTypeInp1Emb4type OBJECT-TYPE
        SYNTAX            RollCallString
        MAX-ACCESS        read-only
        STATUS            current
        DESCRIPTION
                "CMNT: - Logging state for Input 1 Emb.Pair 4 type
                 TYPE: - Display
                 PAGE: - Logging
                    Inp1 Emb.4 type=  cmdID= 36021  "
        ::= { iqsyn21CmdEntry 36021 }


    iqsyn21LoggingIn1AudTypeLogInp1Emb5type OBJECT-TYPE
        SYNTAX            INTEGER { disable(0), enable(1)  }
        MAX-ACCESS        read-write
        STATUS            current
        DESCRIPTION
                "CMNT: - Enable/Disable logging for Input 1 Emb.Pair 4 type
                 TYPE: - Checkbox
                 PAGE: - Logging
                    Log Inp1 Emb.5 type  cmdID= 35022  "
        ::= { iqsyn21CmdEntry 35022 }


    iqsyn21LoggingIn1AudTypeInp1Emb5type OBJECT-TYPE
        SYNTAX            RollCallString
        MAX-ACCESS        read-only
        STATUS            current
        DESCRIPTION
                "CMNT: - Logging state for Input 1 Emb.Pair 5 type
                 TYPE: - Display
                 PAGE: - Logging
                    Inp1 Emb.5 type=  cmdID= 36022  "
        ::= { iqsyn21CmdEntry 36022 }


    iqsyn21LoggingIn1AudTypeLogInp1Emb6type OBJECT-TYPE
        SYNTAX            INTEGER { disable(0), enable(1)  }
        MAX-ACCESS        read-write
        STATUS            current
        DESCRIPTION
                "CMNT: - Enable/Disable logging for Input 1 Emb.Pair 6 type
                 TYPE: - Checkbox
                 PAGE: - Logging
                    Log Inp1 Emb.6 type  cmdID= 35023  "
        ::= { iqsyn21CmdEntry 35023 }


    iqsyn21LoggingIn1AudTypeInp1Emb6type OBJECT-TYPE
        SYNTAX            RollCallString
        MAX-ACCESS        read-only
        STATUS            current
        DESCRIPTION
                "CMNT: - Logging state for Input 1 Emb.Pair 6 type
                 TYPE: - Display
                 PAGE: - Logging
                    Inp1 Emb.6 type=  cmdID= 36023  "
        ::= { iqsyn21CmdEntry 36023 }


    iqsyn21LoggingIn1AudTypeLogInp1Emb7type OBJECT-TYPE
        SYNTAX            INTEGER { disable(0), enable(1)  }
        MAX-ACCESS        read-write
        STATUS            current
        DESCRIPTION
                "CMNT: - Enable/Disable logging for Input 1 Emb.Pair 7 type
                 TYPE: - Checkbox
                 PAGE: - Logging
                    Log Inp1 Emb.7 type  cmdID= 35024  "
        ::= { iqsyn21CmdEntry 35024 }


    iqsyn21LoggingIn1AudTypeInp1Emb7type OBJECT-TYPE
        SYNTAX            RollCallString
        MAX-ACCESS        read-only
        STATUS            current
        DESCRIPTION
                "CMNT: - Logging state for Input 1 Emb.Pair 7 type
                 TYPE: - Display
                 PAGE: - Logging
                    Inp1 Emb.7 type=  cmdID= 36024  "
        ::= { iqsyn21CmdEntry 36024 }


    iqsyn21LoggingIn1AudTypeLogInp1Emb8type OBJECT-TYPE
        SYNTAX            INTEGER { disable(0), enable(1)  }
        MAX-ACCESS        read-write
        STATUS            current
        DESCRIPTION
                "CMNT: - Enable/Disable logging for Input 1 Emb.Pair 8 type
                 TYPE: - Checkbox
                 PAGE: - Logging
                    Log Inp1 Emb.8 type  cmdID= 35025  "
        ::= { iqsyn21CmdEntry 35025 }


    iqsyn21LoggingIn1AudTypeInp1Emb8type OBJECT-TYPE
        SYNTAX            RollCallString
        MAX-ACCESS        read-only
        STATUS            current
        DESCRIPTION
                "CMNT: - Logging state for Input 1 Emb.Pair 8 type
                 TYPE: - Display
                 PAGE: - Logging
                    Inp1 Emb.8 type=  cmdID= 36025  "
        ::= { iqsyn21CmdEntry 36025 }


    iqsyn21LoggingIn2AudStateLogInp2Emb1stat OBJECT-TYPE
        SYNTAX            INTEGER { disable(0), enable(1)  }
        MAX-ACCESS        read-write
        STATUS            current
        DESCRIPTION
                "CMNT: - Enable/Disable logging for Input 2 Emb.Pair 1 state
                 TYPE: - Checkbox
                 PAGE: - Logging
                    Log Inp2 Emb.1 state  cmdID= 35036  "
        ::= { iqsyn21CmdEntry 35036 }


    iqsyn21LoggingIn2AudStateInp2Emb1state OBJECT-TYPE
        SYNTAX            RollCallString
        MAX-ACCESS        read-only
        STATUS            current
        DESCRIPTION
                "CMNT: - Logging state for Input 2 Emb.Pair 1 state
                 TYPE: - Display
                 PAGE: - Logging
                    Inp2 Emb.1 state=  cmdID= 36036  "
        ::= { iqsyn21CmdEntry 36036 }


    iqsyn21LoggingIn2AudStateLogInp2Emb2stat OBJECT-TYPE
        SYNTAX            INTEGER { disable(0), enable(1)  }
        MAX-ACCESS        read-write
        STATUS            current
        DESCRIPTION
                "CMNT: - Enable/Disable logging for Input 2 Emb.Pair 2 state
                 TYPE: - Checkbox
                 PAGE: - Logging
                    Log Inp2 Emb.2 state  cmdID= 35037  "
        ::= { iqsyn21CmdEntry 35037 }


    iqsyn21LoggingIn2AudStateInp2Emb2state OBJECT-TYPE
        SYNTAX            RollCallString
        MAX-ACCESS        read-only
        STATUS            current
        DESCRIPTION
                "CMNT: - Logging state for Input 2 Emb.Pair 2 state
                 TYPE: - Display
                 PAGE: - Logging
                    Inp2 Emb.2 state=  cmdID= 36037  "
        ::= { iqsyn21CmdEntry 36037 }


    iqsyn21LoggingIn2AudStateLogInp2Emb3stat OBJECT-TYPE
        SYNTAX            INTEGER { disable(0), enable(1)  }
        MAX-ACCESS        read-write
        STATUS            current
        DESCRIPTION
                "CMNT: - Enable/Disable logging for Input 2 Emb.Pair 3 state
                 TYPE: - Checkbox
                 PAGE: - Logging
                    Log Inp2 Emb.3 state  cmdID= 35038  "
        ::= { iqsyn21CmdEntry 35038 }


    iqsyn21LoggingIn2AudStateInp2Emb3state OBJECT-TYPE
        SYNTAX            RollCallString
        MAX-ACCESS        read-only
        STATUS            current
        DESCRIPTION
                "CMNT: - Logging state for Input 2 Emb.Pair 3 state
                 TYPE: - Display
                 PAGE: - Logging
                    Inp2 Emb.3 state=  cmdID= 36038  "
        ::= { iqsyn21CmdEntry 36038 }


    iqsyn21LoggingIn2AudStateLogInp2Emb4stat OBJECT-TYPE
        SYNTAX            INTEGER { disable(0), enable(1)  }
        MAX-ACCESS        read-write
        STATUS            current
        DESCRIPTION
                "CMNT: - Enable/Disable logging for Input 2 Emb.Pair 4 state
                 TYPE: - Checkbox
                 PAGE: - Logging
                    Log Inp2 Emb.4 state  cmdID= 35039  "
        ::= { iqsyn21CmdEntry 35039 }


    iqsyn21LoggingIn2AudStateInp2Emb4state OBJECT-TYPE
        SYNTAX            RollCallString
        MAX-ACCESS        read-only
        STATUS            current
        DESCRIPTION
                "CMNT: - Logging state for Input 2 Emb.Pair 4 state
                 TYPE: - Display
                 PAGE: - Logging
                    Inp2 Emb.4 state=  cmdID= 36039  "
        ::= { iqsyn21CmdEntry 36039 }


    iqsyn21LoggingIn2AudStateLogInp2Emb5stat OBJECT-TYPE
        SYNTAX            INTEGER { disable(0), enable(1)  }
        MAX-ACCESS        read-write
        STATUS            current
        DESCRIPTION
                "CMNT: - Enable/Disable logging for Input 2 Emb.Pair 5 state
                 TYPE: - Checkbox
                 PAGE: - Logging
                    Log Inp2 Emb.5 state  cmdID= 35040  "
        ::= { iqsyn21CmdEntry 35040 }


    iqsyn21LoggingIn2AudStateInp2Emb5state OBJECT-TYPE
        SYNTAX            RollCallString
        MAX-ACCESS        read-only
        STATUS            current
        DESCRIPTION
                "CMNT: - Logging state for Input 2 Emb.Pair 5 state
                 TYPE: - Display
                 PAGE: - Logging
                    Inp2 Emb.5 state=  cmdID= 36040  "
        ::= { iqsyn21CmdEntry 36040 }


    iqsyn21LoggingIn2AudStateLogInp2Emb6stat OBJECT-TYPE
        SYNTAX            INTEGER { disable(0), enable(1)  }
        MAX-ACCESS        read-write
        STATUS            current
        DESCRIPTION
                "CMNT: - Enable/Disable logging for Input 2 Emb.Pair 6 state
                 TYPE: - Checkbox
                 PAGE: - Logging
                    Log Inp2 Emb.6 state  cmdID= 35041  "
        ::= { iqsyn21CmdEntry 35041 }


    iqsyn21LoggingIn2AudStateInp2Emb6state OBJECT-TYPE
        SYNTAX            RollCallString
        MAX-ACCESS        read-only
        STATUS            current
        DESCRIPTION
                "CMNT: - Logging state for Input 2 Emb.Pair 6 state
                 TYPE: - Display
                 PAGE: - Logging
                    Inp2 Emb.6 state=  cmdID= 36041  "
        ::= { iqsyn21CmdEntry 36041 }


    iqsyn21LoggingIn2AudStateLogInp2Emb7stat OBJECT-TYPE
        SYNTAX            INTEGER { disable(0), enable(1)  }
        MAX-ACCESS        read-write
        STATUS            current
        DESCRIPTION
                "CMNT: - Enable/Disable logging for Input 2 Emb.Pair 7 state
                 TYPE: - Checkbox
                 PAGE: - Logging
                    Log Inp2 Emb.7 state  cmdID= 35042  "
        ::= { iqsyn21CmdEntry 35042 }


    iqsyn21LoggingIn2AudStateInp2Emb7state OBJECT-TYPE
        SYNTAX            RollCallString
        MAX-ACCESS        read-only
        STATUS            current
        DESCRIPTION
                "CMNT: - Logging state for Input 2 Emb.Pair 7 state
                 TYPE: - Display
                 PAGE: - Logging
                    Inp2 Emb.7 state=  cmdID= 36042  "
        ::= { iqsyn21CmdEntry 36042 }


    iqsyn21LoggingIn2AudStateLogInp2Emb8stat OBJECT-TYPE
        SYNTAX            INTEGER { disable(0), enable(1)  }
        MAX-ACCESS        read-write
        STATUS            current
        DESCRIPTION
                "CMNT: - Enable/Disable logging for Input 2 Emb.Pair 8 state
                 TYPE: - Checkbox
                 PAGE: - Logging
                    Log Inp2 Emb.8 state  cmdID= 35043  "
        ::= { iqsyn21CmdEntry 35043 }


    iqsyn21LoggingIn2AudStateInp2Emb8state OBJECT-TYPE
        SYNTAX            RollCallString
        MAX-ACCESS        read-only
        STATUS            current
        DESCRIPTION
                "CMNT: - Logging state for Input 2 Emb.Pair 8 state
                 TYPE: - Display
                 PAGE: - Logging
                    Inp2 Emb.8 state=  cmdID= 36043  "
        ::= { iqsyn21CmdEntry 36043 }


    iqsyn21LoggingIn1AudTypeLogInp2Emb1type OBJECT-TYPE
        SYNTAX            INTEGER { disable(0), enable(1)  }
        MAX-ACCESS        read-write
        STATUS            current
        DESCRIPTION
                "CMNT: - Enable/Disable logging for Input 2 Emb.Pair 1 type
                 TYPE: - Checkbox
                 PAGE: - Logging
                    Log Inp2 Emb.1 type  cmdID= 35048  "
        ::= { iqsyn21CmdEntry 35048 }


    iqsyn21LoggingIn1AudTypeInp2Emb1type OBJECT-TYPE
        SYNTAX            RollCallString
        MAX-ACCESS        read-only
        STATUS            current
        DESCRIPTION
                "CMNT: - Logging state for Input 2 Emb.Pair 1 type
                 TYPE: - Display
                 PAGE: - Logging
                    Inp2 Emb.1 type=  cmdID= 36048  "
        ::= { iqsyn21CmdEntry 36048 }


    iqsyn21LoggingIn1AudTypeLogInp2Emb2type OBJECT-TYPE
        SYNTAX            INTEGER { disable(0), enable(1)  }
        MAX-ACCESS        read-write
        STATUS            current
        DESCRIPTION
                "CMNT: - Enable/Disable logging for Input 1 Emb.Pair 2 type
                 TYPE: - Checkbox
                 PAGE: - Logging
                    Log Inp2 Emb.2 type  cmdID= 35049  "
        ::= { iqsyn21CmdEntry 35049 }


    iqsyn21LoggingIn1AudTypeInp2Emb2type OBJECT-TYPE
        SYNTAX            RollCallString
        MAX-ACCESS        read-only
        STATUS            current
        DESCRIPTION
                "CMNT: - Logging state for Input 2 Emb.Pair 2 type
                 TYPE: - Display
                 PAGE: - Logging
                    Inp2 Emb.2 type=  cmdID= 36049  "
        ::= { iqsyn21CmdEntry 36049 }


    iqsyn21LoggingIn1AudTypeLogInp2Emb3type OBJECT-TYPE
        SYNTAX            INTEGER { disable(0), enable(1)  }
        MAX-ACCESS        read-write
        STATUS            current
        DESCRIPTION
                "CMNT: - Enable/Disable logging for Input 2 Emb.Pair 3 type
                 TYPE: - Checkbox
                 PAGE: - Logging
                    Log Inp2 Emb.3 type  cmdID= 35050  "
        ::= { iqsyn21CmdEntry 35050 }


    iqsyn21LoggingIn1AudTypeInp2Emb3type OBJECT-TYPE
        SYNTAX            RollCallString
        MAX-ACCESS        read-only
        STATUS            current
        DESCRIPTION
                "CMNT: - Logging state for Input 2 Emb.Pair 3 type
                 TYPE: - Display
                 PAGE: - Logging
                    Inp2 Emb.3 type=  cmdID= 36050  "
        ::= { iqsyn21CmdEntry 36050 }


    iqsyn21LoggingIn1AudTypeLogInp2Emb4type OBJECT-TYPE
        SYNTAX            INTEGER { disable(0), enable(1)  }
        MAX-ACCESS        read-write
        STATUS            current
        DESCRIPTION
                "CMNT: - Enable/Disable logging for Input 2 Emb.Pair 4 type
                 TYPE: - Checkbox
                 PAGE: - Logging
                    Log Inp2 Emb.4 type  cmdID= 35051  "
        ::= { iqsyn21CmdEntry 35051 }


    iqsyn21LoggingIn1AudTypeInp2Emb4type OBJECT-TYPE
        SYNTAX            RollCallString
        MAX-ACCESS        read-only
        STATUS            current
        DESCRIPTION
                "CMNT: - Logging state for Input 2 Emb.Pair 4 type
                 TYPE: - Display
                 PAGE: - Logging
                    Inp2 Emb.4 type=  cmdID= 36051  "
        ::= { iqsyn21CmdEntry 36051 }


    iqsyn21LoggingIn1AudTypeLogInp2Emb5type OBJECT-TYPE
        SYNTAX            INTEGER { disable(0), enable(1)  }
        MAX-ACCESS        read-write
        STATUS            current
        DESCRIPTION
                "CMNT: - Enable/Disable logging for Input 2 Emb.Pair 5 type
                 TYPE: - Checkbox
                 PAGE: - Logging
                    Log Inp2 Emb.5 type  cmdID= 35052  "
        ::= { iqsyn21CmdEntry 35052 }


    iqsyn21LoggingIn1AudTypeInp2Emb5type OBJECT-TYPE
        SYNTAX            RollCallString
        MAX-ACCESS        read-only
        STATUS            current
        DESCRIPTION
                "CMNT: - Logging state for Input 2 Emb.Pair 5 type
                 TYPE: - Display
                 PAGE: - Logging
                    Inp2 Emb.5 type=  cmdID= 36052  "
        ::= { iqsyn21CmdEntry 36052 }


    iqsyn21LoggingIn1AudTypeLogInp2Emb6type OBJECT-TYPE
        SYNTAX            INTEGER { disable(0), enable(1)  }
        MAX-ACCESS        read-write
        STATUS            current
        DESCRIPTION
                "CMNT: - Enable/Disable logging for Input 2 Emb.Pair 6 type
                 TYPE: - Checkbox
                 PAGE: - Logging
                    Log Inp2 Emb.6 type  cmdID= 35053  "
        ::= { iqsyn21CmdEntry 35053 }


    iqsyn21LoggingIn1AudTypeInp2Emb6type OBJECT-TYPE
        SYNTAX            RollCallString
        MAX-ACCESS        read-only
        STATUS            current
        DESCRIPTION
                "CMNT: - Logging state for Input 2 Emb.Pair 6 type
                 TYPE: - Display
                 PAGE: - Logging
                    Inp2 Emb.6 type=  cmdID= 36053  "
        ::= { iqsyn21CmdEntry 36053 }


    iqsyn21LoggingIn1AudTypeLogInp2Emb7type OBJECT-TYPE
        SYNTAX            INTEGER { disable(0), enable(1)  }
        MAX-ACCESS        read-write
        STATUS            current
        DESCRIPTION
                "CMNT: - Enable/Disable logging for Input 2 Emb.Pair 7 type
                 TYPE: - Checkbox
                 PAGE: - Logging
                    Log Inp2 Emb.7 type  cmdID= 35054  "
        ::= { iqsyn21CmdEntry 35054 }


    iqsyn21LoggingIn1AudTypeInp2Emb7type OBJECT-TYPE
        SYNTAX            RollCallString
        MAX-ACCESS        read-only
        STATUS            current
        DESCRIPTION
                "CMNT: - Logging state for Input 2 Emb.Pair 7 type
                 TYPE: - Display
                 PAGE: - Logging
                    Inp2 Emb.7 type=  cmdID= 36054  "
        ::= { iqsyn21CmdEntry 36054 }


    iqsyn21LoggingIn1AudTypeLogInp2Emb8type OBJECT-TYPE
        SYNTAX            INTEGER { disable(0), enable(1)  }
        MAX-ACCESS        read-write
        STATUS            current
        DESCRIPTION
                "CMNT: - Enable/Disable logging for Input 2 Emb.Pair 8 type
                 TYPE: - Checkbox
                 PAGE: - Logging
                    Log Inp2 Emb.8 type  cmdID= 35055  "
        ::= { iqsyn21CmdEntry 35055 }


    iqsyn21LoggingIn1AudTypeInp2Emb8type OBJECT-TYPE
        SYNTAX            RollCallString
        MAX-ACCESS        read-only
        STATUS            current
        DESCRIPTION
                "CMNT: - Logging state for Input 2 Emb.Pair 8 type
                 TYPE: - Display
                 PAGE: - Logging
                    Inp2 Emb.8 type=  cmdID= 36055  "
        ::= { iqsyn21CmdEntry 36055 }


    iqsyn21LoggingOPAudStateLogOutEmb1state OBJECT-TYPE
        SYNTAX            INTEGER { disable(0), enable(1)  }
        MAX-ACCESS        read-write
        STATUS            current
        DESCRIPTION
                "CMNT: - Enable/Disable logging for Output Emb.Pair 1 state
                 TYPE: - Checkbox
                 PAGE: - Logging
                    Log Out Emb.1 state  cmdID= 35920  "
        ::= { iqsyn21CmdEntry 35920 }


    iqsyn21LoggingOPAudStateOutEmb1state OBJECT-TYPE
        SYNTAX            RollCallString
        MAX-ACCESS        read-only
        STATUS            current
        DESCRIPTION
                "CMNT: - Logging state for Output Emb.Pair 1 state
                 TYPE: - Display
                 PAGE: - Logging
                    Out Emb.1 state=  cmdID= 36920  "
        ::= { iqsyn21CmdEntry 36920 }


    iqsyn21LoggingOPAudStateLogOutEmb2state OBJECT-TYPE
        SYNTAX            INTEGER { disable(0), enable(1)  }
        MAX-ACCESS        read-write
        STATUS            current
        DESCRIPTION
                "CMNT: - Enable/Disable logging for Output Emb.Pair 2 state
                 TYPE: - Checkbox
                 PAGE: - Logging
                    Log Out Emb.2 state  cmdID= 35921  "
        ::= { iqsyn21CmdEntry 35921 }


    iqsyn21LoggingOPAudStateOutEmb2state OBJECT-TYPE
        SYNTAX            RollCallString
        MAX-ACCESS        read-only
        STATUS            current
        DESCRIPTION
                "CMNT: - Logging state for Output Emb.Pair 2 state
                 TYPE: - Display
                 PAGE: - Logging
                    Out Emb.2 state=  cmdID= 36921  "
        ::= { iqsyn21CmdEntry 36921 }


    iqsyn21LoggingOPAudStateLogOutEmb3state OBJECT-TYPE
        SYNTAX            INTEGER { disable(0), enable(1)  }
        MAX-ACCESS        read-write
        STATUS            current
        DESCRIPTION
                "CMNT: - Enable/Disable logging for Output Emb.Pair 3 state
                 TYPE: - Checkbox
                 PAGE: - Logging
                    Log Out Emb.3 state  cmdID= 35922  "
        ::= { iqsyn21CmdEntry 35922 }


    iqsyn21LoggingOPAudStateOutEmb3state OBJECT-TYPE
        SYNTAX            RollCallString
        MAX-ACCESS        read-only
        STATUS            current
        DESCRIPTION
                "CMNT: - Logging state for Output Emb.Pair 3 state
                 TYPE: - Display
                 PAGE: - Logging
                    Out Emb.3 state=  cmdID= 36922  "
        ::= { iqsyn21CmdEntry 36922 }


    iqsyn21LoggingOPAudStateLogOutEmb4state OBJECT-TYPE
        SYNTAX            INTEGER { disable(0), enable(1)  }
        MAX-ACCESS        read-write
        STATUS            current
        DESCRIPTION
                "CMNT: - Enable/Disable logging for Output Emb.Pair 4 state
                 TYPE: - Checkbox
                 PAGE: - Logging
                    Log Out Emb.4 state  cmdID= 35923  "
        ::= { iqsyn21CmdEntry 35923 }


    iqsyn21LoggingOPAudStateOutEmb4state OBJECT-TYPE
        SYNTAX            RollCallString
        MAX-ACCESS        read-only
        STATUS            current
        DESCRIPTION
                "CMNT: - Logging state for Output Emb.Pair 4 state
                 TYPE: - Display
                 PAGE: - Logging
                    Out Emb.4 state=  cmdID= 36923  "
        ::= { iqsyn21CmdEntry 36923 }


    iqsyn21LoggingOPAudStateLogOutEmb5state OBJECT-TYPE
        SYNTAX            INTEGER { disable(0), enable(1)  }
        MAX-ACCESS        read-write
        STATUS            current
        DESCRIPTION
                "CMNT: - Enable/Disable logging for Output Emb.Pair 5 state
                 TYPE: - Checkbox
                 PAGE: - Logging
                    Log Out Emb.5 state  cmdID= 35924  "
        ::= { iqsyn21CmdEntry 35924 }


    iqsyn21LoggingOPAudStateOutEmb5state OBJECT-TYPE
        SYNTAX            RollCallString
        MAX-ACCESS        read-only
        STATUS            current
        DESCRIPTION
                "CMNT: - Logging state for Output Emb.Pair 5 state
                 TYPE: - Display
                 PAGE: - Logging
                    Out Emb.5 state=  cmdID= 36924  "
        ::= { iqsyn21CmdEntry 36924 }


    iqsyn21LoggingOPAudStateLogOutEmb6state OBJECT-TYPE
        SYNTAX            INTEGER { disable(0), enable(1)  }
        MAX-ACCESS        read-write
        STATUS            current
        DESCRIPTION
                "CMNT: - Enable/Disable logging for Output Emb.Pair 6 state
                 TYPE: - Checkbox
                 PAGE: - Logging
                    Log Out Emb.6 state  cmdID= 35925  "
        ::= { iqsyn21CmdEntry 35925 }


    iqsyn21LoggingOPAudStateOutEmb6state OBJECT-TYPE
        SYNTAX            RollCallString
        MAX-ACCESS        read-only
        STATUS            current
        DESCRIPTION
                "CMNT: - Logging state for Output Emb.Pair 6 state
                 TYPE: - Display
                 PAGE: - Logging
                    Out Emb.6 state=  cmdID= 36925  "
        ::= { iqsyn21CmdEntry 36925 }


    iqsyn21LoggingOPAudStateLogOutEmb7state OBJECT-TYPE
        SYNTAX            INTEGER { disable(0), enable(1)  }
        MAX-ACCESS        read-write
        STATUS            current
        DESCRIPTION
                "CMNT: - Enable/Disable logging for Output Emb.Pair 7 state
                 TYPE: - Checkbox
                 PAGE: - Logging
                    Log Out Emb.7 state  cmdID= 35926  "
        ::= { iqsyn21CmdEntry 35926 }


    iqsyn21LoggingOPAudStateOutEmb7state OBJECT-TYPE
        SYNTAX            RollCallString
        MAX-ACCESS        read-only
        STATUS            current
        DESCRIPTION
                "CMNT: - Logging state for Output Emb.Pair 7 state
                 TYPE: - Display
                 PAGE: - Logging
                    Out Emb.7 state=  cmdID= 36926  "
        ::= { iqsyn21CmdEntry 36926 }


    iqsyn21LoggingOPAudStateLogOutEmb8state OBJECT-TYPE
        SYNTAX            INTEGER { disable(0), enable(1)  }
        MAX-ACCESS        read-write
        STATUS            current
        DESCRIPTION
                "CMNT: - Enable/Disable logging for Output Emb.Pair 8 state
                 TYPE: - Checkbox
                 PAGE: - Logging
                    Log Out Emb.8 state  cmdID= 35927  "
        ::= { iqsyn21CmdEntry 35927 }


    iqsyn21LoggingOPAudStateOutEmb8state OBJECT-TYPE
        SYNTAX            RollCallString
        MAX-ACCESS        read-only
        STATUS            current
        DESCRIPTION
                "CMNT: - Logging state for Output Emb.Pair 8 state
                 TYPE: - Display
                 PAGE: - Logging
                    Out Emb.8 state=  cmdID= 36927  "
        ::= { iqsyn21CmdEntry 36927 }


    iqsyn21LoggingOPAudTypeLogOutEmb1type OBJECT-TYPE
        SYNTAX            INTEGER { disable(0), enable(1)  }
        MAX-ACCESS        read-write
        STATUS            current
        DESCRIPTION
                "CMNT: - Enable/Disable logging for Output Emb.Pair 1 type
                 TYPE: - Checkbox
                 PAGE: - Logging
                    Log Out Emb.1 type  cmdID= 35930  "
        ::= { iqsyn21CmdEntry 35930 }


    iqsyn21LoggingOPAudTypeOutEmb1type OBJECT-TYPE
        SYNTAX            RollCallString
        MAX-ACCESS        read-only
        STATUS            current
        DESCRIPTION
                "CMNT: - Logging state for Output Emb.Pair 1 type
                 TYPE: - Display
                 PAGE: - Logging
                    Out Emb.1 type=  cmdID= 36930  "
        ::= { iqsyn21CmdEntry 36930 }


    iqsyn21LoggingOPAudTypeLogOutEmb2type OBJECT-TYPE
        SYNTAX            INTEGER { disable(0), enable(1)  }
        MAX-ACCESS        read-write
        STATUS            current
        DESCRIPTION
                "CMNT: - Enable/Disable logging for Output Emb.Pair 2 type
                 TYPE: - Checkbox
                 PAGE: - Logging
                    Log Out Emb.2 type  cmdID= 35931  "
        ::= { iqsyn21CmdEntry 35931 }


    iqsyn21LoggingOPAudTypeOutEmb2type OBJECT-TYPE
        SYNTAX            RollCallString
        MAX-ACCESS        read-only
        STATUS            current
        DESCRIPTION
                "CMNT: - Logging state for Output Emb.Pair 2 type
                 TYPE: - Display
                 PAGE: - Logging
                    Out Emb.2 type=  cmdID= 36931  "
        ::= { iqsyn21CmdEntry 36931 }


    iqsyn21LoggingOPAudTypeLogOutEmb3type OBJECT-TYPE
        SYNTAX            INTEGER { disable(0), enable(1)  }
        MAX-ACCESS        read-write
        STATUS            current
        DESCRIPTION
                "CMNT: - Enable/Disable logging for Output Emb.Pair 3 type
                 TYPE: - Checkbox
                 PAGE: - Logging
                    Log Out Emb.3 type  cmdID= 35932  "
        ::= { iqsyn21CmdEntry 35932 }


    iqsyn21LoggingOPAudTypeOutEmb3type OBJECT-TYPE
        SYNTAX            RollCallString
        MAX-ACCESS        read-only
        STATUS            current
        DESCRIPTION
                "CMNT: - Logging state for Output Emb.Pair 3 type
                 TYPE: - Display
                 PAGE: - Logging
                    Out Emb.3 type=  cmdID= 36932  "
        ::= { iqsyn21CmdEntry 36932 }


    iqsyn21LoggingOPAudTypeLogOutEmb4type OBJECT-TYPE
        SYNTAX            INTEGER { disable(0), enable(1)  }
        MAX-ACCESS        read-write
        STATUS            current
        DESCRIPTION
                "CMNT: - Enable/Disable logging for Output Emb.Pair 4 type
                 TYPE: - Checkbox
                 PAGE: - Logging
                    Log Out Emb.4 type  cmdID= 35933  "
        ::= { iqsyn21CmdEntry 35933 }


    iqsyn21LoggingOPAudTypeOutEmb4type OBJECT-TYPE
        SYNTAX            RollCallString
        MAX-ACCESS        read-only
        STATUS            current
        DESCRIPTION
                "CMNT: - Logging state for Output Emb.Pair 4 type
                 TYPE: - Display
                 PAGE: - Logging
                    Out Emb.4 type=  cmdID= 36933  "
        ::= { iqsyn21CmdEntry 36933 }


    iqsyn21LoggingOPAudTypeLogOutEmb5type OBJECT-TYPE
        SYNTAX            INTEGER { disable(0), enable(1)  }
        MAX-ACCESS        read-write
        STATUS            current
        DESCRIPTION
                "CMNT: - Enable/Disable logging for Output Emb.Pair 5 type
                 TYPE: - Checkbox
                 PAGE: - Logging
                    Log Out Emb.5 type  cmdID= 35934  "
        ::= { iqsyn21CmdEntry 35934 }


    iqsyn21LoggingOPAudTypeOutEmb5type OBJECT-TYPE
        SYNTAX            RollCallString
        MAX-ACCESS        read-only
        STATUS            current
        DESCRIPTION
                "CMNT: - Logging state for Output Emb.Pair 5 type
                 TYPE: - Display
                 PAGE: - Logging
                    Out Emb.5 type=  cmdID= 36934  "
        ::= { iqsyn21CmdEntry 36934 }


    iqsyn21LoggingOPAudTypeLogOutEmb6type OBJECT-TYPE
        SYNTAX            INTEGER { disable(0), enable(1)  }
        MAX-ACCESS        read-write
        STATUS            current
        DESCRIPTION
                "CMNT: - Enable/Disable logging for Output Emb.Pair 6 type
                 TYPE: - Checkbox
                 PAGE: - Logging
                    Log Out Emb.6 type  cmdID= 35935  "
        ::= { iqsyn21CmdEntry 35935 }


    iqsyn21LoggingOPAudTypeOutEmb6type OBJECT-TYPE
        SYNTAX            RollCallString
        MAX-ACCESS        read-only
        STATUS            current
        DESCRIPTION
                "CMNT: - Logging state for Output Emb.Pair 6 type
                 TYPE: - Display
                 PAGE: - Logging
                    Out Emb.6 type=  cmdID= 36935  "
        ::= { iqsyn21CmdEntry 36935 }


    iqsyn21LoggingOPAudTypeLogOutEmb7type OBJECT-TYPE
        SYNTAX            INTEGER { disable(0), enable(1)  }
        MAX-ACCESS        read-write
        STATUS            current
        DESCRIPTION
                "CMNT: - Enable/Disable logging for Output Emb.Pair 7 type
                 TYPE: - Checkbox
                 PAGE: - Logging
                    Log Out Emb.7 type  cmdID= 35936  "
        ::= { iqsyn21CmdEntry 35936 }


    iqsyn21LoggingOPAudTypeOutEmb7type OBJECT-TYPE
        SYNTAX            RollCallString
        MAX-ACCESS        read-only
        STATUS            current
        DESCRIPTION
                "CMNT: - Logging state for Output Emb.Pair 7 type
                 TYPE: - Display
                 PAGE: - Logging
                    Out Emb.7 type=  cmdID= 36936  "
        ::= { iqsyn21CmdEntry 36936 }


    iqsyn21LoggingOPAudTypeLogOutEmb8type OBJECT-TYPE
        SYNTAX            INTEGER { disable(0), enable(1)  }
        MAX-ACCESS        read-write
        STATUS            current
        DESCRIPTION
                "CMNT: - Enable/Disable logging for Output Emb.Pair 8 type
                 TYPE: - Checkbox
                 PAGE: - Logging
                    Log Out Emb.8 type  cmdID= 35937  "
        ::= { iqsyn21CmdEntry 35937 }


    iqsyn21LoggingOPAudTypeOutEmb8type OBJECT-TYPE
        SYNTAX            RollCallString
        MAX-ACCESS        read-only
        STATUS            current
        DESCRIPTION
                "CMNT: - Logging state for Output Emb.Pair 8 type
                 TYPE: - Display
                 PAGE: - Logging
                    Out Emb.8 type=  cmdID= 36937  "
        ::= { iqsyn21CmdEntry 36937 }


    iqsyn21LoggingOPAudLevelLogOutEmb1LLev OBJECT-TYPE
        SYNTAX            INTEGER { disable(0), enable(1)  }
        MAX-ACCESS        read-write
        STATUS            current
        DESCRIPTION
                "CMNT: - Enable/Disable logging for Output Emb.Audio 1-L Level
                 TYPE: - Checkbox
                 PAGE: - Logging
                    Log Out Emb.1-L Level  cmdID= 35900  "
        ::= { iqsyn21CmdEntry 35900 }


    iqsyn21LoggingOPAudLevelOutEmb1LLevel OBJECT-TYPE
        SYNTAX            RollCallString
        MAX-ACCESS        read-only
        STATUS            current
        DESCRIPTION
                "CMNT: - Logging state for Output Emb.Audio 1-L Level
                 TYPE: - Display
                 PAGE: - Logging
                    Out Emb.1-L Level=  cmdID= 36900  "
        ::= { iqsyn21CmdEntry 36900 }


    iqsyn21LoggingOPAudLevelLogOutEmb1RLev OBJECT-TYPE
        SYNTAX            INTEGER { disable(0), enable(1)  }
        MAX-ACCESS        read-write
        STATUS            current
        DESCRIPTION
                "CMNT: - Enable/Disable logging for Output Emb.Audio 1-R Level
                 TYPE: - Checkbox
                 PAGE: - Logging
                    Log Out Emb.1-R Level  cmdID= 35901  "
        ::= { iqsyn21CmdEntry 35901 }


    iqsyn21LoggingOPAudLevelOutEmb1RLevel OBJECT-TYPE
        SYNTAX            RollCallString
        MAX-ACCESS        read-only
        STATUS            current
        DESCRIPTION
                "CMNT: - Logging state for Output Emb.Audio 1-R Level
                 TYPE: - Display
                 PAGE: - Logging
                    Out Emb.1-R Level=  cmdID= 36901  "
        ::= { iqsyn21CmdEntry 36901 }


    iqsyn21LoggingOPAudLevelLogOutEmb2LLev OBJECT-TYPE
        SYNTAX            INTEGER { disable(0), enable(1)  }
        MAX-ACCESS        read-write
        STATUS            current
        DESCRIPTION
                "CMNT: - Enable/Disable logging for Output Emb.Audio 2-L Level
                 TYPE: - Checkbox
                 PAGE: - Logging
                    Log Out Emb.2-L Level  cmdID= 35902  "
        ::= { iqsyn21CmdEntry 35902 }


    iqsyn21LoggingOPAudLevelOutEmb2LLevel OBJECT-TYPE
        SYNTAX            RollCallString
        MAX-ACCESS        read-only
        STATUS            current
        DESCRIPTION
                "CMNT: - Logging state for Output Emb.Audio 2-L Level
                 TYPE: - Display
                 PAGE: - Logging
                    Out Emb.2-L Level=  cmdID= 36902  "
        ::= { iqsyn21CmdEntry 36902 }


    iqsyn21LoggingOPAudLevelLogOutEmb2RLev OBJECT-TYPE
        SYNTAX            INTEGER { disable(0), enable(1)  }
        MAX-ACCESS        read-write
        STATUS            current
        DESCRIPTION
                "CMNT: - Enable/Disable logging for Output Emb.Audio 2-R Level
                 TYPE: - Checkbox
                 PAGE: - Logging
                    Log Out Emb.2-R Level  cmdID= 35903  "
        ::= { iqsyn21CmdEntry 35903 }


    iqsyn21LoggingOPAudLevelOutEmb2RLevel OBJECT-TYPE
        SYNTAX            RollCallString
        MAX-ACCESS        read-only
        STATUS            current
        DESCRIPTION
                "CMNT: - Logging state for Output Emb.Audio 2-R Level
                 TYPE: - Display
                 PAGE: - Logging
                    Out Emb.2-R Level=  cmdID= 36903  "
        ::= { iqsyn21CmdEntry 36903 }


    iqsyn21LoggingOPAudLevelLogOutEmb3LLev OBJECT-TYPE
        SYNTAX            INTEGER { disable(0), enable(1)  }
        MAX-ACCESS        read-write
        STATUS            current
        DESCRIPTION
                "CMNT: - Enable/Disable logging for Output Emb.Audio 3-L Level
                 TYPE: - Checkbox
                 PAGE: - Logging
                    Log Out Emb.3-L Level  cmdID= 35904  "
        ::= { iqsyn21CmdEntry 35904 }


    iqsyn21LoggingOPAudLevelOutEmb3LLevel OBJECT-TYPE
        SYNTAX            RollCallString
        MAX-ACCESS        read-only
        STATUS            current
        DESCRIPTION
                "CMNT: - Logging state for Output Emb.Audio 3-L Level
                 TYPE: - Display
                 PAGE: - Logging
                    Out Emb.3-L Level=  cmdID= 36904  "
        ::= { iqsyn21CmdEntry 36904 }


    iqsyn21LoggingOPAudLevelLogOutEmb3RLev OBJECT-TYPE
        SYNTAX            INTEGER { disable(0), enable(1)  }
        MAX-ACCESS        read-write
        STATUS            current
        DESCRIPTION
                "CMNT: - Enable/Disable logging for Output Emb.Audio 3-R Level
                 TYPE: - Checkbox
                 PAGE: - Logging
                    Log Out Emb.3-R Level  cmdID= 35905  "
        ::= { iqsyn21CmdEntry 35905 }


    iqsyn21LoggingOPAudLevelOutEmb3RLevel OBJECT-TYPE
        SYNTAX            RollCallString
        MAX-ACCESS        read-only
        STATUS            current
        DESCRIPTION
                "CMNT: - Logging state for Output Emb.Audio 3-R Level
                 TYPE: - Display
                 PAGE: - Logging
                    Out Emb.3-R Level=  cmdID= 36905  "
        ::= { iqsyn21CmdEntry 36905 }


    iqsyn21LoggingOPAudLevelLogOutEmb4LLev OBJECT-TYPE
        SYNTAX            INTEGER { disable(0), enable(1)  }
        MAX-ACCESS        read-write
        STATUS            current
        DESCRIPTION
                "CMNT: - Enable/Disable logging for Output Emb.Audio 4-L Level
                 TYPE: - Checkbox
                 PAGE: - Logging
                    Log Out Emb.4-L Level  cmdID= 35906  "
        ::= { iqsyn21CmdEntry 35906 }


    iqsyn21LoggingOPAudLevelOutEmb4LLevel OBJECT-TYPE
        SYNTAX            RollCallString
        MAX-ACCESS        read-only
        STATUS            current
        DESCRIPTION
                "CMNT: - Logging state for Output Emb.Audio 4-L Level
                 TYPE: - Display
                 PAGE: - Logging
                    Out Emb.4-L Level=  cmdID= 36906  "
        ::= { iqsyn21CmdEntry 36906 }


    iqsyn21LoggingOPAudLevelLogOutEmb4RLev OBJECT-TYPE
        SYNTAX            INTEGER { disable(0), enable(1)  }
        MAX-ACCESS        read-write
        STATUS            current
        DESCRIPTION
                "CMNT: - Enable/Disable logging for Output Emb.Audio 4-R Level
                 TYPE: - Checkbox
                 PAGE: - Logging
                    Log Out Emb.4-R Level  cmdID= 35907  "
        ::= { iqsyn21CmdEntry 35907 }


    iqsyn21LoggingOPAudLevelOutEmb4RLevel OBJECT-TYPE
        SYNTAX            RollCallString
        MAX-ACCESS        read-only
        STATUS            current
        DESCRIPTION
                "CMNT: - Logging state for Output Emb.Audio 4-R Level
                 TYPE: - Display
                 PAGE: - Logging
                    Out Emb.4-R Level=  cmdID= 36907  "
        ::= { iqsyn21CmdEntry 36907 }


    iqsyn21LoggingOPAudLevelLogOutEmb5LLev OBJECT-TYPE
        SYNTAX            INTEGER { disable(0), enable(1)  }
        MAX-ACCESS        read-write
        STATUS            current
        DESCRIPTION
                "CMNT: - Enable/Disable logging for Output Emb.Audio 5-L Level
                 TYPE: - Checkbox
                 PAGE: - Logging
                    Log Out Emb.5-L Level  cmdID= 35908  "
        ::= { iqsyn21CmdEntry 35908 }


    iqsyn21LoggingOPAudLevelOutEmb5LLevel OBJECT-TYPE
        SYNTAX            RollCallString
        MAX-ACCESS        read-only
        STATUS            current
        DESCRIPTION
                "CMNT: - Logging state for Output Emb.Audio 5-L Level
                 TYPE: - Display
                 PAGE: - Logging
                    Out Emb.5-L Level=  cmdID= 36908  "
        ::= { iqsyn21CmdEntry 36908 }


    iqsyn21LoggingOPAudLevelLogOutEmb5RLev OBJECT-TYPE
        SYNTAX            INTEGER { disable(0), enable(1)  }
        MAX-ACCESS        read-write
        STATUS            current
        DESCRIPTION
                "CMNT: - Enable/Disable logging for Output Emb.Audio 5-R Level
                 TYPE: - Checkbox
                 PAGE: - Logging
                    Log Out Emb.5-R Level  cmdID= 35909  "
        ::= { iqsyn21CmdEntry 35909 }


    iqsyn21LoggingOPAudLevelOutEmb5RLevel OBJECT-TYPE
        SYNTAX            RollCallString
        MAX-ACCESS        read-only
        STATUS            current
        DESCRIPTION
                "CMNT: - Logging state for Output Emb.Audio 5-R Level
                 TYPE: - Display
                 PAGE: - Logging
                    Out Emb.5-R Level=  cmdID= 36909  "
        ::= { iqsyn21CmdEntry 36909 }


    iqsyn21LoggingOPAudLevelLogOutEmb6LLev OBJECT-TYPE
        SYNTAX            INTEGER { disable(0), enable(1)  }
        MAX-ACCESS        read-write
        STATUS            current
        DESCRIPTION
                "CMNT: - Enable/Disable logging for Output Emb.Audio 6-L Level
                 TYPE: - Checkbox
                 PAGE: - Logging
                    Log Out Emb.6-L Level  cmdID= 35910  "
        ::= { iqsyn21CmdEntry 35910 }


    iqsyn21LoggingOPAudLevelOutEmb6LLevel OBJECT-TYPE
        SYNTAX            RollCallString
        MAX-ACCESS        read-only
        STATUS            current
        DESCRIPTION
                "CMNT: - Logging state for Output Emb.Audio 6-L Level
                 TYPE: - Display
                 PAGE: - Logging
                    Out Emb.6-L Level=  cmdID= 36910  "
        ::= { iqsyn21CmdEntry 36910 }


    iqsyn21LoggingOPAudLevelLogOutEmb6RLev OBJECT-TYPE
        SYNTAX            INTEGER { disable(0), enable(1)  }
        MAX-ACCESS        read-write
        STATUS            current
        DESCRIPTION
                "CMNT: - Enable/Disable logging for Output Emb.Audio 6-R Level
                 TYPE: - Checkbox
                 PAGE: - Logging
                    Log Out Emb.6-R Level  cmdID= 35911  "
        ::= { iqsyn21CmdEntry 35911 }


    iqsyn21LoggingOPAudLevelOutEmb6RLevel OBJECT-TYPE
        SYNTAX            RollCallString
        MAX-ACCESS        read-only
        STATUS            current
        DESCRIPTION
                "CMNT: - Logging state for Output Emb.Audio 6-R Level
                 TYPE: - Display
                 PAGE: - Logging
                    Out Emb.6-R Level=  cmdID= 36911  "
        ::= { iqsyn21CmdEntry 36911 }


    iqsyn21LoggingOPAudLevelLogOutEmb7LLev OBJECT-TYPE
        SYNTAX            INTEGER { disable(0), enable(1)  }
        MAX-ACCESS        read-write
        STATUS            current
        DESCRIPTION
                "CMNT: - Enable/Disable logging for Output Emb.Audio 7-L Level
                 TYPE: - Checkbox
                 PAGE: - Logging
                    Log Out Emb.7-L Level  cmdID= 35912  "
        ::= { iqsyn21CmdEntry 35912 }


    iqsyn21LoggingOPAudLevelOutEmb7LLevel OBJECT-TYPE
        SYNTAX            RollCallString
        MAX-ACCESS        read-only
        STATUS            current
        DESCRIPTION
                "CMNT: - Logging state for Output Emb.Audio 7-L Level
                 TYPE: - Display
                 PAGE: - Logging
                    Out Emb.7-L Level=  cmdID= 36912  "
        ::= { iqsyn21CmdEntry 36912 }


    iqsyn21LoggingOPAudLevelLogOutEmb7RLev OBJECT-TYPE
        SYNTAX            INTEGER { disable(0), enable(1)  }
        MAX-ACCESS        read-write
        STATUS            current
        DESCRIPTION
                "CMNT: - Enable/Disable logging for Output Emb.Audio 7-R Level
                 TYPE: - Checkbox
                 PAGE: - Logging
                    Log Out Emb.7-R Level  cmdID= 35913  "
        ::= { iqsyn21CmdEntry 35913 }


    iqsyn21LoggingOPAudLevelOutEmb7RLevel OBJECT-TYPE
        SYNTAX            RollCallString
        MAX-ACCESS        read-only
        STATUS            current
        DESCRIPTION
                "CMNT: - Logging state for Output Emb.Audio 7-R Level
                 TYPE: - Display
                 PAGE: - Logging
                    Out Emb.7-R Level=  cmdID= 36913  "
        ::= { iqsyn21CmdEntry 36913 }


    iqsyn21LoggingOPAudLevelLogOutEmb8LLev OBJECT-TYPE
        SYNTAX            INTEGER { disable(0), enable(1)  }
        MAX-ACCESS        read-write
        STATUS            current
        DESCRIPTION
                "CMNT: - Enable/Disable logging for Output Emb.Audio 8-L Level
                 TYPE: - Checkbox
                 PAGE: - Logging
                    Log Out Emb.8-L Level  cmdID= 35914  "
        ::= { iqsyn21CmdEntry 35914 }


    iqsyn21LoggingOPAudLevelOutEmb8LLevel OBJECT-TYPE
        SYNTAX            RollCallString
        MAX-ACCESS        read-only
        STATUS            current
        DESCRIPTION
                "CMNT: - Logging state for Output Emb.Audio 8-L Level
                 TYPE: - Display
                 PAGE: - Logging
                    Out Emb.8-L Level=  cmdID= 36914  "
        ::= { iqsyn21CmdEntry 36914 }


    iqsyn21LoggingOPAudLevelLogOutEmb8RLev OBJECT-TYPE
        SYNTAX            INTEGER { disable(0), enable(1)  }
        MAX-ACCESS        read-write
        STATUS            current
        DESCRIPTION
                "CMNT: - Enable/Disable logging for Output Emb.Audio 8-R Level
                 TYPE: - Checkbox
                 PAGE: - Logging
                    Log Out Emb.8-R Level  cmdID= 35915  "
        ::= { iqsyn21CmdEntry 35915 }


    iqsyn21LoggingOPAudLevelOutEmb8RLevel OBJECT-TYPE
        SYNTAX            RollCallString
        MAX-ACCESS        read-only
        STATUS            current
        DESCRIPTION
                "CMNT: - Logging state for Output Emb.Audio 8-R Level
                 TYPE: - Display
                 PAGE: - Logging
                    Out Emb.8-R Level=  cmdID= 36915  "
        ::= { iqsyn21CmdEntry 36915 }


    iqsyn21LoggingOPDolbyELoggingLogEmbDolbyE1 OBJECT-TYPE
        SYNTAX            INTEGER { disable(0), enable(1)  }
        MAX-ACCESS        read-write
        STATUS            current
        DESCRIPTION
                "CMNT: - Enable/Disable logging for Emb DolbyE 1
                 TYPE: - Checkbox
                 PAGE: - Logging
                    Log Emb DolbyE 1  cmdID= 35950  "
        ::= { iqsyn21CmdEntry 35950 }


    iqsyn21LoggingOPDolbyELoggingEmbDolbyE1 OBJECT-TYPE
        SYNTAX            RollCallString
        MAX-ACCESS        read-only
        STATUS            current
        DESCRIPTION
                "CMNT: - Logging state for Emb DolbyE 1
                 TYPE: - Display
                 PAGE: - Logging
                    Emb DolbyE 1=  cmdID= 36950  "
        ::= { iqsyn21CmdEntry 36950 }


    iqsyn21LoggingOPDolbyELoggingLogEmbDolbyE2 OBJECT-TYPE
        SYNTAX            INTEGER { disable(0), enable(1)  }
        MAX-ACCESS        read-write
        STATUS            current
        DESCRIPTION
                "CMNT: - Enable/Disable logging for Emb DolbyE 2
                 TYPE: - Checkbox
                 PAGE: - Logging
                    Log Emb DolbyE 2  cmdID= 35951  "
        ::= { iqsyn21CmdEntry 35951 }


    iqsyn21LoggingOPDolbyELoggingEmbDolbyE2 OBJECT-TYPE
        SYNTAX            RollCallString
        MAX-ACCESS        read-only
        STATUS            current
        DESCRIPTION
                "CMNT: - Logging state for Emb DolbyE 2
                 TYPE: - Display
                 PAGE: - Logging
                    Emb DolbyE 2=  cmdID= 36951  "
        ::= { iqsyn21CmdEntry 36951 }


    iqsyn21LoggingOPDolbyELoggingLogEmbDolbyE3 OBJECT-TYPE
        SYNTAX            INTEGER { disable(0), enable(1)  }
        MAX-ACCESS        read-write
        STATUS            current
        DESCRIPTION
                "CMNT: - Enable/Disable logging for Emb DolbyE 3
                 TYPE: - Checkbox
                 PAGE: - Logging
                    Log Emb DolbyE 3  cmdID= 35952  "
        ::= { iqsyn21CmdEntry 35952 }


    iqsyn21LoggingOPDolbyELoggingEmbDolbyE3 OBJECT-TYPE
        SYNTAX            RollCallString
        MAX-ACCESS        read-only
        STATUS            current
        DESCRIPTION
                "CMNT: - Logging state for Emb DolbyE 3
                 TYPE: - Display
                 PAGE: - Logging
                    Emb DolbyE 3=  cmdID= 36952  "
        ::= { iqsyn21CmdEntry 36952 }


    iqsyn21LoggingOPDolbyELoggingLogEmbDolbyE4 OBJECT-TYPE
        SYNTAX            INTEGER { disable(0), enable(1)  }
        MAX-ACCESS        read-write
        STATUS            current
        DESCRIPTION
                "CMNT: - Enable/Disable logging for Emb DolbyE 4
                 TYPE: - Checkbox
                 PAGE: - Logging
                    Log Emb DolbyE 4  cmdID= 35953  "
        ::= { iqsyn21CmdEntry 35953 }


    iqsyn21LoggingOPDolbyELoggingEmbDolbyE4 OBJECT-TYPE
        SYNTAX            RollCallString
        MAX-ACCESS        read-only
        STATUS            current
        DESCRIPTION
                "CMNT: - Logging state for Emb DolbyE 4
                 TYPE: - Display
                 PAGE: - Logging
                    Emb DolbyE 4=  cmdID= 36953  "
        ::= { iqsyn21CmdEntry 36953 }


    iqsyn21LoggingOPDolbyELoggingLogEmbDolbyE5 OBJECT-TYPE
        SYNTAX            INTEGER { disable(0), enable(1)  }
        MAX-ACCESS        read-write
        STATUS            current
        DESCRIPTION
                "CMNT: - Enable/Disable logging for Emb DolbyE 5
                 TYPE: - Checkbox
                 PAGE: - Logging
                    Log Emb DolbyE 5  cmdID= 35954  "
        ::= { iqsyn21CmdEntry 35954 }


    iqsyn21LoggingOPDolbyELoggingEmbDolbyE5 OBJECT-TYPE
        SYNTAX            RollCallString
        MAX-ACCESS        read-only
        STATUS            current
        DESCRIPTION
                "CMNT: - Logging state for Emb DolbyE 5
                 TYPE: - Display
                 PAGE: - Logging
                    Emb DolbyE 5=  cmdID= 36954  "
        ::= { iqsyn21CmdEntry 36954 }


    iqsyn21LoggingOPDolbyELoggingLogEmbDolbyE6 OBJECT-TYPE
        SYNTAX            INTEGER { disable(0), enable(1)  }
        MAX-ACCESS        read-write
        STATUS            current
        DESCRIPTION
                "CMNT: - Enable/Disable logging for Emb DolbyE 6
                 TYPE: - Checkbox
                 PAGE: - Logging
                    Log Emb DolbyE 6  cmdID= 35955  "
        ::= { iqsyn21CmdEntry 35955 }


    iqsyn21LoggingOPDolbyELoggingEmbDolbyE6 OBJECT-TYPE
        SYNTAX            RollCallString
        MAX-ACCESS        read-only
        STATUS            current
        DESCRIPTION
                "CMNT: - Logging state for Emb DolbyE 6
                 TYPE: - Display
                 PAGE: - Logging
                    Emb DolbyE 6=  cmdID= 36955  "
        ::= { iqsyn21CmdEntry 36955 }


    iqsyn21LoggingOPDolbyELoggingLogEmbDolbyE7 OBJECT-TYPE
        SYNTAX            INTEGER { disable(0), enable(1)  }
        MAX-ACCESS        read-write
        STATUS            current
        DESCRIPTION
                "CMNT: - Enable/Disable logging for Emb DolbyE 7
                 TYPE: - Checkbox
                 PAGE: - Logging
                    Log Emb DolbyE 7  cmdID= 35956  "
        ::= { iqsyn21CmdEntry 35956 }


    iqsyn21LoggingOPDolbyELoggingEmbDolbyE7 OBJECT-TYPE
        SYNTAX            RollCallString
        MAX-ACCESS        read-only
        STATUS            current
        DESCRIPTION
                "CMNT: - Logging state for Emb DolbyE 7
                 TYPE: - Display
                 PAGE: - Logging
                    Emb DolbyE 7=  cmdID= 36956  "
        ::= { iqsyn21CmdEntry 36956 }


    iqsyn21LoggingOPDolbyELoggingLogEmbDolbyE8 OBJECT-TYPE
        SYNTAX            INTEGER { disable(0), enable(1)  }
        MAX-ACCESS        read-write
        STATUS            current
        DESCRIPTION
                "CMNT: - Enable/Disable logging for Emb DolbyE 8
                 TYPE: - Checkbox
                 PAGE: - Logging
                    Log Emb DolbyE 8  cmdID= 35957  "
        ::= { iqsyn21CmdEntry 35957 }


    iqsyn21LoggingOPDolbyELoggingEmbDolbyE8 OBJECT-TYPE
        SYNTAX            RollCallString
        MAX-ACCESS        read-only
        STATUS            current
        DESCRIPTION
                "CMNT: - Logging state for Emb DolbyE 8
                 TYPE: - Display
                 PAGE: - Logging
                    Emb DolbyE 8=  cmdID= 36957  "
        ::= { iqsyn21CmdEntry 36957 }


    iqsyn21LoggingMiscLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging
                    Log Serial No.  cmdID= 35015  "
        ::= { iqsyn21CmdEntry 35015 }


    iqsyn21LoggingMiscSerialNo OBJECT-TYPE
        SYNTAX            RollCallString
        MAX-ACCESS        read-only
        STATUS            current
        DESCRIPTION
                "CMNT: - Logging state for Serial No.
                 TYPE: - Display
                 PAGE: - Logging
                    Serial No.=  cmdID= 36015  "
        ::= { iqsyn21CmdEntry 36015 }


    iqsyn21LoggingMiscLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging
                    Log OS Version  cmdID= 35993  "
        ::= { iqsyn21CmdEntry 35993 }


    iqsyn21LoggingMiscOSVersion OBJECT-TYPE
        SYNTAX            RollCallString
        MAX-ACCESS        read-only
        STATUS            current
        DESCRIPTION
                "CMNT: - Logging state for OS Version
                 TYPE: - Display
                 PAGE: - Logging
                    OS Version=  cmdID= 36993  "
        ::= { iqsyn21CmdEntry 36993 }


    iqsyn21LoggingMiscLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging
                    Log Build No.  cmdID= 35990  "
        ::= { iqsyn21CmdEntry 35990 }


    iqsyn21LoggingMiscBuildNo OBJECT-TYPE
        SYNTAX            RollCallString
        MAX-ACCESS        read-only
        STATUS            current
        DESCRIPTION
                "CMNT: - Logging state for Build No.
                 TYPE: - Display
                 PAGE: - Logging
                    Build No.=  cmdID= 36990  "
        ::= { iqsyn21CmdEntry 36990 }


    iqsyn21LoggingMiscLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging
                    Log Hardware Ver.  cmdID= 35992  "
        ::= { iqsyn21CmdEntry 35992 }


    iqsyn21LoggingMiscHardwareVer OBJECT-TYPE
        SYNTAX            RollCallString
        MAX-ACCESS        read-only
        STATUS            current
        DESCRIPTION
                "CMNT: - Logging state for Hardware Ver.
                 TYPE: - Display
                 PAGE: - Logging
                    Hardware Ver.=  cmdID= 36992  "
        ::= { iqsyn21CmdEntry 36992 }


    iqsyn21LoggingMiscLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging
                    Log Firmware Ver.  cmdID= 35991  "
        ::= { iqsyn21CmdEntry 35991 }


    iqsyn21LoggingMiscFirmwareVer OBJECT-TYPE
        SYNTAX            RollCallString
        MAX-ACCESS        read-only
        STATUS            current
        DESCRIPTION
                "CMNT: - Logging state for Firmware Ver.
                 TYPE: - Display
                 PAGE: - Logging
                    Firmware Ver.=  cmdID= 36991  "
        ::= { iqsyn21CmdEntry 36991 }


    iqsyn21LoggingMiscLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging
                    Log Up Time  cmdID= 35994  "
        ::= { iqsyn21CmdEntry 35994 }


    iqsyn21LoggingMiscUpTime OBJECT-TYPE
        SYNTAX            RollCallString
        MAX-ACCESS        read-only
        STATUS            current
        DESCRIPTION
                "CMNT: - Logging state for Up Time
                 TYPE: - Display
                 PAGE: - Logging
                    Up Time=  cmdID= 36994  "
        ::= { iqsyn21CmdEntry 36994 }


    iqsyn21LoggingRefOutputLogReferenceType OBJECT-TYPE
        SYNTAX            INTEGER { disable(0), enable(1)  }
        MAX-ACCESS        read-write
        STATUS            current
        DESCRIPTION
                "CMNT: - Enable/Disable logging for Reference Type
                 TYPE: - Checkbox
                 PAGE: - Logging
                    Log Reference Type  cmdID= 35995  "
        ::= { iqsyn21CmdEntry 35995 }


    iqsyn21LoggingRefOutputReferenceType OBJECT-TYPE
        SYNTAX            RollCallString
        MAX-ACCESS        read-only
        STATUS            current
        DESCRIPTION
                "CMNT: - Logging state for Reference Type
                 TYPE: - Display
                 PAGE: - Logging
                    Reference Type=  cmdID= 36995  "
        ::= { iqsyn21CmdEntry 36995 }


    iqsyn21LoggingRefOutputLogReferenceState OBJECT-TYPE
        SYNTAX            INTEGER { disable(0), enable(1)  }
        MAX-ACCESS        read-write
        STATUS            current
        DESCRIPTION
                "CMNT: - Enable/Disable logging for Reference State
                 TYPE: - Checkbox
                 PAGE: - Logging
                    Log Reference State  cmdID= 35004  "
        ::= { iqsyn21CmdEntry 35004 }


    iqsyn21LoggingRefOutputReferenceState OBJECT-TYPE
        SYNTAX            RollCallString
        MAX-ACCESS        read-only
        STATUS            current
        DESCRIPTION
                "CMNT: - Logging state for Reference State
                 TYPE: - Display
                 PAGE: - Logging
                    Reference State=  cmdID= 36004  "
        ::= { iqsyn21CmdEntry 36004 }


    iqsyn21LoggingRefOutputLogReferenceStand OBJECT-TYPE
        SYNTAX            INTEGER { disable(0), enable(1)  }
        MAX-ACCESS        read-write
        STATUS            current
        DESCRIPTION
                "CMNT: - Enable/Disable logging for Reference Standard
                 TYPE: - Checkbox
                 PAGE: - Logging
                    Log Reference Standard  cmdID= 35014  "
        ::= { iqsyn21CmdEntry 35014 }


    iqsyn21LoggingRefOutputReferenceStandard OBJECT-TYPE
        SYNTAX            RollCallString
        MAX-ACCESS        read-only
        STATUS            current
        DESCRIPTION
                "CMNT: - Logging state for Reference Standard
                 TYPE: - Display
                 PAGE: - Logging
                    Reference Standard=  cmdID= 36014  "
        ::= { iqsyn21CmdEntry 36014 }


    iqsyn21RollCallRollTrackDisableAll OBJECT-TYPE
        SYNTAX            INTEGER { disable(0), enable(1)  }
        MAX-ACCESS        read-write
        STATUS            current
        DESCRIPTION
                "CMNT: - Disable all rolltrack outputs
                 TYPE: - Checkbox
                 PAGE: - RollTrack
                    Disable All  cmdID= 36104  "
        ::= { iqsyn21CmdEntry 36104 }


    iqsyn21RollCallRollTrackIndex OBJECT-TYPE
        SYNTAX            INTEGER
        MAX-ACCESS        read-write
        STATUS            current
        DESCRIPTION
                "CMNT: - Select rolltrack to edit
                 TYPE: - BarGraph
                 PAGE: - RollTrack
                    Index  cmdID= 36100
                    min= 1  max= 16  step= 1  format= %0.0f  div_scale= 1  preset= 1
                    Min = 1  Max = 16  Step = 1  Preset = 1  "
        ::= { iqsyn21CmdEntry 36100 }


    iqsyn21RollCallRollTrackSource OBJECT-TYPE
        SYNTAX            INTEGER {
                            valUnused(-1),
                            valVideoDelay(0),
                            valInputPresent(1),
                            valInputLoss(2),
                            valReferenceOK(3),
                            valReferenceLost(4),
                            valOpFreeze(5),
                            valOpUnFreeze(6),
                            valINP1Select(54),
                            valINP2Select(55),
                            valGPI1High(32),
                            valGPI1Low(33),
                            valGPI1InActive(31),
                            valGPI2High(35),
                            valGPI2Low(36),
                            valGPI2InActive(34),
                            valDenembed1Data(7),
                            valDenembed1Pcm(8),
                            valDenembed1Lost(9),
                            valDenembed2Data(10),
                            valDenembed2Pcm(11),
                            valDenembed2Lost(12),
                            valDenembed3Data(13),
                            valDenembed3Pcm(14),
                            valDenembed3Lost(15),
                            valDenembed4Data(16),
                            valDenembed4Pcm(17),
                            valDenembed4Lost(18),
                            valDenembed5Data(19),
                            valDenembed5Pcm(20),
                            valDenembed5Lost(21),
                            valDenembed6Data(22),
                            valDenembed6Pcm(23),
                            valDenembed6Lost(24),
                            valDenembed7Data(25),
                            valDenembed7Pcm(26),
                            valDenembed7Lost(27),
                            valDenembed8Data(28),
                            valDenembed8Pcm(29),
                            valDenembed8Lost(30),
                            valOut1125108030i(37),
                            valOut1125108030p(38),
                            valOut1125108029i(39),
                            valOut1125108029p(40),
                            valOut1125108025i(41),
                            valOut1125108025p(42),
                            valOut1125108024p(43),
                            valOut1125108024sf(44),
                            valOut1125108023p(45),
                            valOut1125108023sf(46),
                            valOut1125103530i(47),
                            valOut1125103529i(48),
                            valOut75072060p(49),
                            valOut75072059p(50),
                            valOut75072050p(51),
                            valOut52548029i(52),
                            valOut62557625i(53)
                            }
        MAX-ACCESS        read-write
        STATUS            current
        DESCRIPTION
                "CMNT: - Source for Rolltrack
                 TYPE: - RadiobuttonList
                 PAGE: - RollTrack
                    Source  cmdID= 36101
                    Unused  value= -1
                    Video Delay  value= 0
                    Input Present  value= 1
                    Input Loss  value= 2
                    Reference OK  value= 3
                    Reference Lost  value= 4
                    O/p Freeze  value= 5
                    O/p UnFreeze  value= 6
                    INP1 Select  value= 54
                    INP2 Select  value= 55
                    GPI 1 High  value= 32
                    GPI 1 Low  value= 33
                    GPI 1 InActive  value= 31
                    GPI 2 High  value= 35
                    GPI 2 Low  value= 36
                    GPI 2 InActive  value= 34
                    De-embed 1 Data  value= 7
                    De-embed 1 Pcm  value= 8
                    De-embed 1 Lost  value= 9
                    De-embed 2 Data  value= 10
                    De-embed 2 Pcm  value= 11
                    De-embed 2 Lost  value= 12
                    De-embed 3 Data  value= 13
                    De-embed 3 Pcm  value= 14
                    De-embed 3 Lost  value= 15
                    De-embed 4 Data  value= 16
                    De-embed 4 Pcm  value= 17
                    De-embed 4 Lost  value= 18
                    De-embed 5 Data  value= 19
                    De-embed 5 Pcm  value= 20
                    De-embed 5 Lost  value= 21
                    De-embed 6 Data  value= 22
                    De-embed 6 Pcm  value= 23
                    De-embed 6 Lost  value= 24
                    De-embed 7 Data  value= 25
                    De-embed 7 Pcm  value= 26
                    De-embed 7 Lost  value= 27
                    De-embed 8 Data  value= 28
                    De-embed 8 Pcm  value= 29
                    De-embed 8 Lost  value= 30
                    Out 1125(1080)/30i  value= 37
                    Out 1125(1080)/30p  value= 38
                    Out 1125(1080)/29i  value= 39
                    Out 1125(1080)/29p  value= 40
                    Out 1125(1080)/25i  value= 41
                    Out 1125(1080)/25p  value= 42
                    Out 1125(1080)/24p  value= 43
                    Out 1125(1080)/24sf  value= 44
                    Out 1125(1080)/23p  value= 45
                    Out 1125(1080)/23sf  value= 46
                    Out 1125(1035)/30i  value= 47
                    Out 1125(1035)/29i  value= 48
                    Out 750(720)/60p  value= 49
                    Out 750(720)/59p  value= 50
                    Out 750(720)/50p  value= 51
                    Out 525(480)/29i  value= 52
                    Out 625(576)/25i  value= 53  "
        ::= { iqsyn21CmdEntry 36101 }


    iqsyn21RollCallRollTrackAddress OBJECT-TYPE
        SYNTAX            RollCallString
        MAX-ACCESS        read-write
        STATUS            current
        DESCRIPTION
                "CMNT: - Unit address for Rolltrack message
                 TYPE: - Editstring
                 PAGE: - RollTrack
                    Address  cmdID= 36102
                    preset= 0000:00:00*0\0*"
        ::= { iqsyn21CmdEntry 36102 }


    iqsyn21RollCallRollTrackCommand OBJECT-TYPE
        SYNTAX            RollCallString
        MAX-ACCESS        read-write
        STATUS            current
        DESCRIPTION
                "CMNT: - Command to send for Rolltrack message
                 TYPE: - Editstring
                 PAGE: - RollTrack
                    Command  cmdID= 36103
                    preset= 000:000\0"
        ::= { iqsyn21CmdEntry 36103 }


    iqsyn21RollCallRollTrackStatus OBJECT-TYPE
        SYNTAX            RollCallString
        MAX-ACCESS        read-only
        STATUS            current
        DESCRIPTION
                "CMNT: - Rolltrack status
                 TYPE: - Display
                 PAGE: - RollTrack
                    Status  cmdID= 36105  "
        ::= { iqsyn21CmdEntry 36105 }


    iqsyn21RollCallRollTrackSending OBJECT-TYPE
        SYNTAX            RollCallString
        MAX-ACCESS        read-only
        STATUS            current
        DESCRIPTION
                "CMNT: - Rolltrack sending status: true/false
                 TYPE: - Display
                 PAGE: - RollTrack
                    Sending  cmdID= 36106  "
        ::= { iqsyn21CmdEntry 36106 }


    iqsyn21SetupProduct OBJECT-TYPE
        SYNTAX            RollCallString
        MAX-ACCESS        read-only
        STATUS            current
        DESCRIPTION
                "CMNT: - 
                 TYPE: - Display
                 PAGE: - Setup
                    Product  cmdID= 32771  "
        ::= { iqsyn21CmdEntry 32771 }


    iqsyn21SetupRelease OBJECT-TYPE
        SYNTAX            RollCallString
        MAX-ACCESS        read-only
        STATUS            current
        DESCRIPTION
                "CMNT: - Unit version number
                 TYPE: - Display
                 PAGE: - Setup
                    Release  cmdID= 2  "
        ::= { iqsyn21CmdEntry 2 }


    iqsyn21SetupBuild OBJECT-TYPE
        SYNTAX            RollCallString
        MAX-ACCESS        read-only
        STATUS            current
        DESCRIPTION
                "CMNT: - Unit build number
                 TYPE: - Display
                 PAGE: - Setup
                    Build  cmdID= 5  "
        ::= { iqsyn21CmdEntry 5 }


    iqsyn21SetupKOS OBJECT-TYPE
        SYNTAX            RollCallString
        MAX-ACCESS        read-only
        STATUS            current
        DESCRIPTION
                "CMNT: - 
                 TYPE: - Display
                 PAGE: - Setup
                    KOS  cmdID= 32772  "
        ::= { iqsyn21CmdEntry 32772 }


    iqsyn21SetupSerial OBJECT-TYPE
        SYNTAX            RollCallString
        MAX-ACCESS        read-only
        STATUS            current
        DESCRIPTION
                "CMNT: - Unit serial number
                 TYPE: - Display
                 PAGE: - Setup
                    Serial No.  cmdID= 1  "
        ::= { iqsyn21CmdEntry 1 }


    iqsyn21SetupFirmware OBJECT-TYPE
        SYNTAX            RollCallString
        MAX-ACCESS        read-only
        STATUS            current
        DESCRIPTION
                "CMNT: - Display firmware version
                 TYPE: - Display
                 PAGE: - Setup
                    Firmware  cmdID= 32769  "
        ::= { iqsyn21CmdEntry 32769 }


    iqsyn21SetupPCB OBJECT-TYPE
        SYNTAX            RollCallString
        MAX-ACCESS        read-only
        STATUS            current
        DESCRIPTION
                "CMNT: - Display PCB revision
                 TYPE: - Display
                 PAGE: - Setup
                    PCB  cmdID= 32770  "
        ::= { iqsyn21CmdEntry 32770 }


    iqsyn21SetupFactoryDefault OBJECT-TYPE
        SYNTAX            INTEGER { noAction(0),valFactoryDefault(1) }
        MAX-ACCESS        read-write
        STATUS            current
        DESCRIPTION
                "CMNT: - Recall factory defaults
                 TYPE: - Button
                 PAGE: - Setup
                    Factory Default  cmdID= 37002
                    value= 1  "
        ::= { iqsyn21CmdEntry 37002 }


    iqsyn21SetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 4
                    value= 1  "
        ::= { iqsyn21CmdEntry 4 }


    iqsyn21MemoriesMemorySave OBJECT-TYPE
        SYNTAX            INTEGER { noAction(0),valDefaultSettings(1) }
        MAX-ACCESS        read-write
        STATUS            current
        DESCRIPTION
                "CMNT: - Recall factory defaults-KeepMemories
                 TYPE: - Button
                 PAGE: - Setup
                    Default Settings  cmdID= 37001
                    value= 1  "
        ::= { iqsyn21CmdEntry 37001 }


    iqsyn21SetupDisplay OBJECT-TYPE
        SYNTAX            INTEGER {
                            valVideoStatus(0),
                            valAudioStatus(1),
                            valMetadataStatus(2)
                            }
        MAX-ACCESS        read-write
        STATUS            current
        DESCRIPTION
                "CMNT: - Select Info display to show
                 TYPE: - RadiobuttonList
                 PAGE: - Setup
                    Display  cmdID= 32773
                    Video Status  value= 0
                    Audio Status  value= 1
                    Metadata Status  value= 2  "
        ::= { iqsyn21CmdEntry 32773 }


    iqsyn21SetupSerialNumber OBJECT-TYPE
        SYNTAX            RollCallString
        MAX-ACCESS        read-write
        STATUS            current
        DESCRIPTION
                "CMNT: - Edit serial number (On Factory Test Only)
                 TYPE: - Editstring
                 PAGE: - Setup
                    Serial Number  cmdID= 32774
                    preset= unknown"
        ::= { iqsyn21CmdEntry 32774 }


    iqsyn21SetupBoardID OBJECT-TYPE
        SYNTAX            INTEGER {
                            valIQSYN20(344),
                            valIQSYN21(387),
                            valIQSYN22(538)
                            }
        MAX-ACCESS        read-write
        STATUS            current
        DESCRIPTION
                "CMNT: - Edit product type (On Factory Test Only)
                 TYPE: - RadiobuttonList
                 PAGE: - Setup
                    BoardID  cmdID= 32776
                    IQSYN20  value= 344
                    IQSYN21  value= 387
                    IQSYN22  value= 538  "
        ::= { iqsyn21CmdEntry 32776 }


    iqsyn21SetupSaveID OBJECT-TYPE
        SYNTAX            INTEGER { noAction(0),valSaveID(1) }
        MAX-ACCESS        read-write
        STATUS            current
        DESCRIPTION
                "CMNT: - Save serial number/board type (On Factory Test Only)
                 TYPE: - Button
                 PAGE: - Setup
                    Save ID  cmdID= 32775
                    value= 1  "
        ::= { iqsyn21CmdEntry 32775 }


    iqsyn21EngineerPassword OBJECT-TYPE
        SYNTAX            RollCallString
        MAX-ACCESS        read-write
        STATUS            current
        DESCRIPTION
                "CMNT: - 
                 TYPE: - Editstring
                 PAGE: - Engineer
                    Engineer Password  cmdID= 34011
                    preset= -"
        ::= { iqsyn21CmdEntry 34011 }


    iqsyn21EngineerShowEngineer OBJECT-TYPE
        SYNTAX            INTEGER { disable(0), enable(1)  }
        MAX-ACCESS        read-write
        STATUS            current
        DESCRIPTION
                "CMNT: - 
                 TYPE: - Checkbox
                 PAGE: - Engineer
                    Show Engineer  cmdID= 34012  "
        ::= { iqsyn21CmdEntry 34012 }


    iqsyn21EngineerPageUndoChanges OBJECT-TYPE
        SYNTAX            INTEGER { noAction(0),valUndoChanges(1) }
        MAX-ACCESS        read-write
        STATUS            current
        DESCRIPTION
                "CMNT: - 
                 TYPE: - Button
                 PAGE: - Engineer
                    Undo Changes  cmdID= 34013
                    value= 1  "
        ::= { iqsyn21CmdEntry 34013 }


    iqsyn21EngineerShowEngineer2 OBJECT-TYPE
        SYNTAX            INTEGER { disable(0), enable(1)  }
        MAX-ACCESS        read-write
        STATUS            current
        DESCRIPTION
                "CMNT: - 
                 TYPE: - Checkbox
                 PAGE: - Engineer
                    Show Engineer2  cmdID= 34050  "
        ::= { iqsyn21CmdEntry 34050 }


    iqsyn21EngineerShowEngineer3 OBJECT-TYPE
        SYNTAX            INTEGER { disable(0), enable(1)  }
        MAX-ACCESS        read-write
        STATUS            current
        DESCRIPTION
                "CMNT: - 
                 TYPE: - Checkbox
                 PAGE: - Engineer
                    Show Engineer3  cmdID= 34051  "
        ::= { iqsyn21CmdEntry 34051 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S34091041
-- Comments		: Runtime string Serial Number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 00-00-00 01:30Z
-- Comments		: Uptime in formated date-time string
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
--
-- Value(s)		: INP 1
--				: INP 2
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: K_OS: V115 Release
-- Comments		: String
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 0003102405
-- Comments		: String of current Software build number
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD / SD SDI
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD / SD SDI
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: FAIL:Lost
--				: OK
--				: FAIL:Error
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: FAIL:Lost
--				: OK
--				: FAIL:Error
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: HD / SD SDI
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 2.122
-- Comments		: String of current Firmware version
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: 1
-- Comments		: String of current Hardware version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: NONE
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: NONE
--				: WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: Tri/Bi-Level
--				: TriLevel
--				: BiLevel
--				: BlackBurst
--				: Analog
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: FAIL:Lost
--				: FAIL:Error
-- Comments		:
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
--
-- Value(s)		: 0
-- Comments		: Number
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
--
-- Value(s)		: 0
-- Comments		: Number
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: NONE
--				: WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: NONE
--				: WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: Unknown
--				: 1035/30i
--				: 1035/29i
--				: 1080/60p
--				: 1080/59p
--				: 1080/50p
--				: 1080/30i
--				: 1080/29i
--				: 1080/25i
--				: 1080/30p
--				: 1080/29p
--				: 1080/25p
--				: 1080/24p
--				: 1080/23p
--				: 1080/50p
--				: 1080/25i
--				: 720/60p
--				: 720/59p
--				: 525/59p
--				: 525/29i
--				: 625/25i
--				: 525/29i
--				: 625/25i
--				: 1080/24sF
--				: 1080/23sF
--				: 480/60p
--				: 480/59p
--				: 625/24sF
--				: 625/23sF
--				: 1152/25i
--				: 720/50p
--				: 576/50p
--				: 480/60p
--				: 480/59p
--				: 1080/30sF
--				: 1080/29sF
--				: 1080/25sF
--				: 720/30p
--				: 720/29p
--				: 720/25p
--				: 720/24p
--				: 720/23p
--				: Invalid
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
--
-- Value(s)		: 0
-- Comments		: Number
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
--
-- Value(s)		: 0
-- Comments		: Number
--
---------------------------------------------------------------------------------------------------
-- Header		: INPUT_1_EMBEDDED_AUDIO_1_TYPE
--
-- MIB ref		: swCardEventLogSlotXX       .29.73.78.80.85.84.95.49.95.69.77.66.69.68.68.69.68.95.65.85.68.73.79.95.49.95.84.89.80.69
-- absolute OID	: 1.3.6.1.4.1.7995.2.6.1.1.XX.29.73.78.80.85.84.95.49.95.69.77.66.69.68.68.69.68.95.65.85.68.73.79.95.49.95.84.89.80.69
--
-- Value(s)		: WARN: No Input
--				: PCM
--				: NONPCM
--				: Unknown
-- Comments		:
--
---------------------------------------------------------------------------------------------------
-- Header		: INPUT_1_EMBEDDED_AUDIO_2_TYPE
--
-- MIB ref		: swCardEventLogSlotXX       .29.73.78.80.85.84.95.49.95.69.77.66.69.68.68.69.68.95.65.85.68.73.79.95.50.95.84.89.80.69
-- absolute OID	: 1.3.6.1.4.1.7995.2.6.1.1.XX.29.73.78.80.85.84.95.49.95.69.77.66.69.68.68.69.68.95.65.85.68.73.79.95.50.95.84.89.80.69
--
-- Value(s)		: WARN: No Input
--				: PCM
--				: NONPCM
--				: Unknown
-- Comments		:
--
---------------------------------------------------------------------------------------------------
-- Header		: INPUT_1_EMBEDDED_AUDIO_3_TYPE
--
-- MIB ref		: swCardEventLogSlotXX       .29.73.78.80.85.84.95.49.95.69.77.66.69.68.68.69.68.95.65.85.68.73.79.95.51.95.84.89.80.69
-- absolute OID	: 1.3.6.1.4.1.7995.2.6.1.1.XX.29.73.78.80.85.84.95.49.95.69.77.66.69.68.68.69.68.95.65.85.68.73.79.95.51.95.84.89.80.69
--
-- Value(s)		: WARN: No Input
--				: PCM
--				: NONPCM
--				: Unknown
-- Comments		:
--
---------------------------------------------------------------------------------------------------
-- Header		: INPUT_1_EMBEDDED_AUDIO_4_TYPE
--
-- MIB ref		: swCardEventLogSlotXX       .29.73.78.80.85.84.95.49.95.69.77.66.69.68.68.69.68.95.65.85.68.73.79.95.52.95.84.89.80.69
-- absolute OID	: 1.3.6.1.4.1.7995.2.6.1.1.XX.29.73.78.80.85.84.95.49.95.69.77.66.69.68.68.69.68.95.65.85.68.73.79.95.52.95.84.89.80.69
--
-- Value(s)		: WARN: No Input
--				: PCM
--				: NONPCM
--				: Unknown
-- Comments		:
--
---------------------------------------------------------------------------------------------------
-- Header		: INPUT_1_EMBEDDED_AUDIO_5_TYPE
--
-- MIB ref		: swCardEventLogSlotXX       .29.73.78.80.85.84.95.49.95.69.77.66.69.68.68.69.68.95.65.85.68.73.79.95.53.95.84.89.80.69
-- absolute OID	: 1.3.6.1.4.1.7995.2.6.1.1.XX.29.73.78.80.85.84.95.49.95.69.77.66.69.68.68.69.68.95.65.85.68.73.79.95.53.95.84.89.80.69
--
-- Value(s)		: WARN: No Input
--				: PCM
--				: NONPCM
--				: Unknown
-- Comments		:
--
---------------------------------------------------------------------------------------------------
-- Header		: INPUT_1_EMBEDDED_AUDIO_6_TYPE
--
-- MIB ref		: swCardEventLogSlotXX       .29.73.78.80.85.84.95.49.95.69.77.66.69.68.68.69.68.95.65.85.68.73.79.95.54.95.84.89.80.69
-- absolute OID	: 1.3.6.1.4.1.7995.2.6.1.1.XX.29.73.78.80.85.84.95.49.95.69.77.66.69.68.68.69.68.95.65.85.68.73.79.95.54.95.84.89.80.69
--
-- Value(s)		: WARN: No Input
--				: PCM
--				: NONPCM
--				: Unknown
-- Comments		:
--
---------------------------------------------------------------------------------------------------
-- Header		: INPUT_1_EMBEDDED_AUDIO_7_TYPE
--
-- MIB ref		: swCardEventLogSlotXX       .29.73.78.80.85.84.95.49.95.69.77.66.69.68.68.69.68.95.65.85.68.73.79.95.55.95.84.89.80.69
-- absolute OID	: 1.3.6.1.4.1.7995.2.6.1.1.XX.29.73.78.80.85.84.95.49.95.69.77.66.69.68.68.69.68.95.65.85.68.73.79.95.55.95.84.89.80.69
--
-- Value(s)		: WARN: No Input
--				: PCM
--				: NONPCM
--				: Unknown
-- Comments		:
--
---------------------------------------------------------------------------------------------------
-- Header		: INPUT_1_EMBEDDED_AUDIO_8_TYPE
--
-- MIB ref		: swCardEventLogSlotXX       .29.73.78.80.85.84.95.49.95.69.77.66.69.68.68.69.68.95.65.85.68.73.79.95.56.95.84.89.80.69
-- absolute OID	: 1.3.6.1.4.1.7995.2.6.1.1.XX.29.73.78.80.85.84.95.49.95.69.77.66.69.68.68.69.68.95.65.85.68.73.79.95.56.95.84.89.80.69
--
-- Value(s)		: WARN: No Input
--				: PCM
--				: NONPCM
--				: Unknown
-- Comments		:
--
---------------------------------------------------------------------------------------------------
-- Header		: INPUT_2_EMBEDDED_AUDIO_1_TYPE
--
-- MIB ref		: swCardEventLogSlotXX       .29.73.78.80.85.84.95.50.95.69.77.66.69.68.68.69.68.95.65.85.68.73.79.95.49.95.84.89.80.69
-- absolute OID	: 1.3.6.1.4.1.7995.2.6.1.1.XX.29.73.78.80.85.84.95.50.95.69.77.66.69.68.68.69.68.95.65.85.68.73.79.95.49.95.84.89.80.69
--
-- Value(s)		: WARN: No Input
--				: PCM
--				: NONPCM
--				: Unknown
-- Comments		:
--
---------------------------------------------------------------------------------------------------
-- Header		: INPUT_2_EMBEDDED_AUDIO_2_TYPE
--
-- MIB ref		: swCardEventLogSlotXX       .29.73.78.80.85.84.95.50.95.69.77.66.69.68.68.69.68.95.65.85.68.73.79.95.50.95.84.89.80.69
-- absolute OID	: 1.3.6.1.4.1.7995.2.6.1.1.XX.29.73.78.80.85.84.95.50.95.69.77.66.69.68.68.69.68.95.65.85.68.73.79.95.50.95.84.89.80.69
--
-- Value(s)		: WARN: No Input
--				: PCM
--				: NONPCM
--				: Unknown
-- Comments		:
--
---------------------------------------------------------------------------------------------------
-- Header		: INPUT_2_EMBEDDED_AUDIO_3_TYPE
--
-- MIB ref		: swCardEventLogSlotXX       .29.73.78.80.85.84.95.50.95.69.77.66.69.68.68.69.68.95.65.85.68.73.79.95.51.95.84.89.80.69
-- absolute OID	: 1.3.6.1.4.1.7995.2.6.1.1.XX.29.73.78.80.85.84.95.50.95.69.77.66.69.68.68.69.68.95.65.85.68.73.79.95.51.95.84.89.80.69
--
-- Value(s)		: WARN: No Input
--				: PCM
--				: NONPCM
--				: Unknown
-- Comments		:
--
---------------------------------------------------------------------------------------------------
-- Header		: INPUT_2_EMBEDDED_AUDIO_4_TYPE
--
-- MIB ref		: swCardEventLogSlotXX       .29.73.78.80.85.84.95.50.95.69.77.66.69.68.68.69.68.95.65.85.68.73.79.95.52.95.84.89.80.69
-- absolute OID	: 1.3.6.1.4.1.7995.2.6.1.1.XX.29.73.78.80.85.84.95.50.95.69.77.66.69.68.68.69.68.95.65.85.68.73.79.95.52.95.84.89.80.69
--
-- Value(s)		: WARN: No Input
--				: PCM
--				: NONPCM
--				: Unknown
-- Comments		:
--
---------------------------------------------------------------------------------------------------
-- Header		: INPUT_2_EMBEDDED_AUDIO_5_TYPE
--
-- MIB ref		: swCardEventLogSlotXX       .29.73.78.80.85.84.95.50.95.69.77.66.69.68.68.69.68.95.65.85.68.73.79.95.53.95.84.89.80.69
-- absolute OID	: 1.3.6.1.4.1.7995.2.6.1.1.XX.29.73.78.80.85.84.95.50.95.69.77.66.69.68.68.69.68.95.65.85.68.73.79.95.53.95.84.89.80.69
--
-- Value(s)		: WARN: No Input
--				: PCM
--				: NONPCM
--				: Unknown
-- Comments		:
--
---------------------------------------------------------------------------------------------------
-- Header		: INPUT_2_EMBEDDED_AUDIO_6_TYPE
--
-- MIB ref		: swCardEventLogSlotXX       .29.73.78.80.85.84.95.50.95.69.77.66.69.68.68.69.68.95.65.85.68.73.79.95.54.95.84.89.80.69
-- absolute OID	: 1.3.6.1.4.1.7995.2.6.1.1.XX.29.73.78.80.85.84.95.50.95.69.77.66.69.68.68.69.68.95.65.85.68.73.79.95.54.95.84.89.80.69
--
-- Value(s)		: WARN: No Input
--				: PCM
--				: NONPCM
--				: Unknown
-- Comments		:
--
---------------------------------------------------------------------------------------------------
-- Header		: INPUT_2_EMBEDDED_AUDIO_7_TYPE
--
-- MIB ref		: swCardEventLogSlotXX       .29.73.78.80.85.84.95.50.95.69.77.66.69.68.68.69.68.95.65.85.68.73.79.95.55.95.84.89.80.69
-- absolute OID	: 1.3.6.1.4.1.7995.2.6.1.1.XX.29.73.78.80.85.84.95.50.95.69.77.66.69.68.68.69.68.95.65.85.68.73.79.95.55.95.84.89.80.69
--
-- Value(s)		: WARN: No Input
--				: PCM
--				: NONPCM
--				: Unknown
-- Comments		:
--
---------------------------------------------------------------------------------------------------
-- Header		: INPUT_2_EMBEDDED_AUDIO_8_TYPE
--
-- MIB ref		: swCardEventLogSlotXX       .29.73.78.80.85.84.95.50.95.69.77.66.69.68.68.69.68.95.65.85.68.73.79.95.56.95.84.89.80.69
-- absolute OID	: 1.3.6.1.4.1.7995.2.6.1.1.XX.29.73.78.80.85.84.95.50.95.69.77.66.69.68.68.69.68.95.65.85.68.73.79.95.56.95.84.89.80.69
--
-- Value(s)		: WARN: No Input
--				: PCM
--				: NONPCM
--				: Unknown
-- Comments		:
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: LOST
--				: FAIL:Lost
--				: OK
--				: Unknown
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: LOST
--				: FAIL:Lost
--				: OK
--				: Unknown
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: LOST
--				: FAIL:Lost
--				: OK
--				: Unknown
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: LOST
--				: FAIL:Lost
--				: OK
--				: Unknown
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: LOST
--				: FAIL:Lost
--				: OK
--				: Unknown
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: LOST
--				: FAIL:Lost
--				: OK
--				: Unknown
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: LOST
--				: FAIL:Lost
--				: OK
--				: Unknown
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: LOST
--				: FAIL:Lost
--				: OK
--				: Unknown
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: LOST
--				: FAIL:Lost
--				: OK
--				: Unknown
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: LOST
--				: FAIL:Lost
--				: OK
--				: Unknown
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: LOST
--				: FAIL:Lost
--				: OK
--				: Unknown
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: LOST
--				: FAIL:Lost
--				: OK
--				: Unknown
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: LOST
--				: FAIL:Lost
--				: OK
--				: Unknown
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: LOST
--				: FAIL:Lost
--				: OK
--				: Unknown
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: LOST
--				: FAIL:Lost
--				: OK
--				: Unknown
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: LOST
--				: FAIL:Lost
--				: OK
--				: Unknown
-- Comments		:
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
--
-- Value(s)		: WARN: No Input
--				: PCM
--				: NONPCM
--				: Unknown
-- Comments		:
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
--
-- Value(s)		: WARN: No Input
--				: PCM
--				: NONPCM
--				: Unknown
-- Comments		:
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
--
-- Value(s)		: WARN: No Input
--				: PCM
--				: NONPCM
--				: Unknown
-- Comments		:
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
--
-- Value(s)		: WARN: No Input
--				: PCM
--				: NONPCM
--				: Unknown
-- Comments		:
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
--
-- Value(s)		: WARN: No Input
--				: PCM
--				: NONPCM
--				: Unknown
-- Comments		:
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
--
-- Value(s)		: WARN: No Input
--				: PCM
--				: NONPCM
--				: Unknown
-- Comments		:
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
--
-- Value(s)		: WARN: No Input
--				: PCM
--				: NONPCM
--				: Unknown
-- Comments		:
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
--
-- Value(s)		: WARN: No Input
--				: PCM
--				: NONPCM
--				: Unknown
-- Comments		:
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
--
-- Value(s)		: LOST
--				: FAIL:Lost
--				: OK
--				: Unknown
-- Comments		:
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
--
-- Value(s)		: LOST
--				: FAIL:Lost
--				: OK
--				: Unknown
-- Comments		:
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
--
-- Value(s)		: LOST
--				: FAIL:Lost
--				: OK
--				: Unknown
-- Comments		:
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
--
-- Value(s)		: LOST
--				: FAIL:Lost
--				: OK
--				: Unknown
-- Comments		:
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
--
-- Value(s)		: LOST
--				: FAIL:Lost
--				: OK
--				: Unknown
-- Comments		:
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
--
-- Value(s)		: LOST
--				: FAIL:Lost
--				: OK
--				: Unknown
-- Comments		:
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
--
-- Value(s)		: LOST
--				: FAIL:Lost
--				: OK
--				: Unknown
-- Comments		:
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
--
-- Value(s)		: LOST
--				: FAIL:Lost
--				: OK
--				: Unknown
-- Comments		:
--
---------------------------------------------------------------------------------------------------
-- Header		: OUTPUT_1_EMBEDDED_AUDIO_1_1_LEVEL
--
-- MIB ref		: swCardEventLogSlotXX       .33.79.85.84.80.85.84.95.49.95.69.77.66.69.68.68.69.68.95.65.85.68.73.79.95.49.95.49.95.76.69.86.69.76
-- absolute OID	: 1.3.6.1.4.1.7995.2.6.1.1.XX.33.79.85.84.80.85.84.95.49.95.69.77.66.69.68.68.69.68.95.65.85.68.73.79.95.49.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_1_2_LEVEL
--
-- MIB ref		: swCardEventLogSlotXX       .33.79.85.84.80.85.84.95.49.95.69.77.66.69.68.68.69.68.95.65.85.68.73.79.95.49.95.50.95.76.69.86.69.76
-- absolute OID	: 1.3.6.1.4.1.7995.2.6.1.1.XX.33.79.85.84.80.85.84.95.49.95.69.77.66.69.68.68.69.68.95.65.85.68.73.79.95.49.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_2_1_LEVEL
--
-- MIB ref		: swCardEventLogSlotXX       .33.79.85.84.80.85.84.95.49.95.69.77.66.69.68.68.69.68.95.65.85.68.73.79.95.50.95.49.95.76.69.86.69.76
-- absolute OID	: 1.3.6.1.4.1.7995.2.6.1.1.XX.33.79.85.84.80.85.84.95.49.95.69.77.66.69.68.68.69.68.95.65.85.68.73.79.95.50.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_2_2_LEVEL
--
-- MIB ref		: swCardEventLogSlotXX       .33.79.85.84.80.85.84.95.49.95.69.77.66.69.68.68.69.68.95.65.85.68.73.79.95.50.95.50.95.76.69.86.69.76
-- absolute OID	: 1.3.6.1.4.1.7995.2.6.1.1.XX.33.79.85.84.80.85.84.95.49.95.69.77.66.69.68.68.69.68.95.65.85.68.73.79.95.50.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_3_1_LEVEL
--
-- MIB ref		: swCardEventLogSlotXX       .33.79.85.84.80.85.84.95.49.95.69.77.66.69.68.68.69.68.95.65.85.68.73.79.95.51.95.49.95.76.69.86.69.76
-- absolute OID	: 1.3.6.1.4.1.7995.2.6.1.1.XX.33.79.85.84.80.85.84.95.49.95.69.77.66.69.68.68.69.68.95.65.85.68.73.79.95.51.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_3_2_LEVEL
--
-- MIB ref		: swCardEventLogSlotXX       .33.79.85.84.80.85.84.95.49.95.69.77.66.69.68.68.69.68.95.65.85.68.73.79.95.51.95.50.95.76.69.86.69.76
-- absolute OID	: 1.3.6.1.4.1.7995.2.6.1.1.XX.33.79.85.84.80.85.84.95.49.95.69.77.66.69.68.68.69.68.95.65.85.68.73.79.95.51.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_4_1_LEVEL
--
-- MIB ref		: swCardEventLogSlotXX       .33.79.85.84.80.85.84.95.49.95.69.77.66.69.68.68.69.68.95.65.85.68.73.79.95.52.95.49.95.76.69.86.69.76
-- absolute OID	: 1.3.6.1.4.1.7995.2.6.1.1.XX.33.79.85.84.80.85.84.95.49.95.69.77.66.69.68.68.69.68.95.65.85.68.73.79.95.52.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_4_2_LEVEL
--
-- MIB ref		: swCardEventLogSlotXX       .33.79.85.84.80.85.84.95.49.95.69.77.66.69.68.68.69.68.95.65.85.68.73.79.95.52.95.50.95.76.69.86.69.76
-- absolute OID	: 1.3.6.1.4.1.7995.2.6.1.1.XX.33.79.85.84.80.85.84.95.49.95.69.77.66.69.68.68.69.68.95.65.85.68.73.79.95.52.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_5_1_LEVEL
--
-- MIB ref		: swCardEventLogSlotXX       .33.79.85.84.80.85.84.95.49.95.69.77.66.69.68.68.69.68.95.65.85.68.73.79.95.53.95.49.95.76.69.86.69.76
-- absolute OID	: 1.3.6.1.4.1.7995.2.6.1.1.XX.33.79.85.84.80.85.84.95.49.95.69.77.66.69.68.68.69.68.95.65.85.68.73.79.95.53.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_5_2_LEVEL
--
-- MIB ref		: swCardEventLogSlotXX       .33.79.85.84.80.85.84.95.49.95.69.77.66.69.68.68.69.68.95.65.85.68.73.79.95.53.95.50.95.76.69.86.69.76
-- absolute OID	: 1.3.6.1.4.1.7995.2.6.1.1.XX.33.79.85.84.80.85.84.95.49.95.69.77.66.69.68.68.69.68.95.65.85.68.73.79.95.53.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_6_1_LEVEL
--
-- MIB ref		: swCardEventLogSlotXX       .33.79.85.84.80.85.84.95.49.95.69.77.66.69.68.68.69.68.95.65.85.68.73.79.95.54.95.49.95.76.69.86.69.76
-- absolute OID	: 1.3.6.1.4.1.7995.2.6.1.1.XX.33.79.85.84.80.85.84.95.49.95.69.77.66.69.68.68.69.68.95.65.85.68.73.79.95.54.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_6_2_LEVEL
--
-- MIB ref		: swCardEventLogSlotXX       .33.79.85.84.80.85.84.95.49.95.69.77.66.69.68.68.69.68.95.65.85.68.73.79.95.54.95.50.95.76.69.86.69.76
-- absolute OID	: 1.3.6.1.4.1.7995.2.6.1.1.XX.33.79.85.84.80.85.84.95.49.95.69.77.66.69.68.68.69.68.95.65.85.68.73.79.95.54.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_7_1_LEVEL
--
-- MIB ref		: swCardEventLogSlotXX       .33.79.85.84.80.85.84.95.49.95.69.77.66.69.68.68.69.68.95.65.85.68.73.79.95.55.95.49.95.76.69.86.69.76
-- absolute OID	: 1.3.6.1.4.1.7995.2.6.1.1.XX.33.79.85.84.80.85.84.95.49.95.69.77.66.69.68.68.69.68.95.65.85.68.73.79.95.55.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_7_2_LEVEL
--
-- MIB ref		: swCardEventLogSlotXX       .33.79.85.84.80.85.84.95.49.95.69.77.66.69.68.68.69.68.95.65.85.68.73.79.95.55.95.50.95.76.69.86.69.76
-- absolute OID	: 1.3.6.1.4.1.7995.2.6.1.1.XX.33.79.85.84.80.85.84.95.49.95.69.77.66.69.68.68.69.68.95.65.85.68.73.79.95.55.95.50.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_8_1_LEVEL
--
-- MIB ref		: swCardEventLogSlotXX       .33.79.85.84.80.85.84.95.49.95.69.77.66.69.68.68.69.68.95.65.85.68.73.79.95.56.95.49.95.76.69.86.69.76
-- absolute OID	: 1.3.6.1.4.1.7995.2.6.1.1.XX.33.79.85.84.80.85.84.95.49.95.69.77.66.69.68.68.69.68.95.65.85.68.73.79.95.56.95.49.95.76.69.86.69.76
--
-- Value(s)		: OK
--				: WARN:Overflow
--				: WARN:Silent
--				: WARN:Quiet
--				: WARN:Loud
-- Comments		:
--
---------------------------------------------------------------------------------------------------
-- Header		: OUTPUT_1_EMBEDDED_AUDIO_8_2_LEVEL
--
-- MIB ref		: swCardEventLogSlotXX       .33.79.85.84.80.85.84.95.49.95.69.77.66.69.68.68.69.68.95.65.85.68.73.79.95.56.95.50.95.76.69.86.69.76
-- absolute OID	: 1.3.6.1.4.1.7995.2.6.1.1.XX.33.79.85.84.80.85.84.95.49.95.69.77.66.69.68.68.69.68.95.65.85.68.73.79.95.56.95.50.95.76.69.86.69.76
--
-- Value(s)		: OK
--				: WARN:Overflow
--				: WARN:Silent
--				: WARN:Quiet
--				: WARN:Loud
-- Comments		:
--
---------------------------------------------------------------------------------------------------
