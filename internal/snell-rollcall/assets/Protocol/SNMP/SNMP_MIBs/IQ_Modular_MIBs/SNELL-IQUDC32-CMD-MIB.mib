-- ************************************************************************************
--        Snell Card:IQUDC32
--        Module Id#:683
--       Command Set:7
--          Filename:SNELL-IQUDC32-CMD-MIB.mib
--            Author:n tye
--              Date:19/02/2015
--              Time:14:21
--
-- Copyright (c) 2010 Snell Ltd
-- All rights reserved.
--
-- ************************************************************************************

SNELL-IQUDC32-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUDC32,
    moduleIQUDC32MIB
        FROM SNELL-WILCOX-PRODUCT-REG;

 moduleIQUDC32CmdMi MODULE-IDENTITY
    LAST-UPDATED "1502191421Z"
    ORGANIZATION "Snell Ltd"
    CONTACT-INFO
        "Primary Author:n tye

         postal:    Southleigh Park House
                    Eastleigh Road
                    Havant, Hants
                    PO9 2PE
         phone:     +44 (0)23 92489000
         email:     snmp.support@snellgroup.com"
    DESCRIPTION
        "This file defines the Snell card, command set  translations."
    ::= { moduleIQUDC32MIB 1 }




--********************************************************************************
--*
--*  Snell Card:
--*  command set:
--*  list commands/menus:
--*
--******************************************************************************
	iqudc32CmdTable OBJECT-TYPE
		SYNTAX			SEQUENCE OF Iqudc32CmdEntry
		MAX-ACCESS		not-accessible
		STATUS			current
		DESCRIPTION
				"Note the instance of this table is relected in the command set Version"
		::= { moduleIQUDC32 1 }

	iqudc32CmdEntry OBJECT-TYPE
		SYNTAX		Iqudc32CmdEntry
		MAX-ACCESS		not-accessible
		STATUS			current
		DESCRIPTION
				"Entry in command table."
		INDEX	{ iqudc32SlotIndex }
		::= { iqudc32CmdTable 1 }

	Iqudc32CmdEntry ::=
		SEQUENCE {
			iqudc32SlotIndex
				Unsigned32,
			iqudc32InputInputSourceCh1InputSelect
				INTEGER,
			iqudc32InputSourceCh1StatusSDI1
				RollCallString,
			iqudc32InputSourceCh1StatusSDI2
				RollCallString,
			iqudc32InputSourceCh1StatusCVBS
				RollCallString,
			iqudc32InputSourceCh1StatusSFP1
				RollCallString,
			iqudc32InputSourceCh1StatusSFP2
				RollCallString,
			iqudc32InputSourceCh1StatusCurrentInputStand
				RollCallString,
			iqudc32InputInputSourceCh2InputSelect
				INTEGER,
			iqudc32InputSourceCh2StatusSDI1
				RollCallString,
			iqudc32InputSourceCh2StatusSDI2
				RollCallString,
			iqudc32InputSourceCh2StatusCVBS
				RollCallString,
			iqudc32InputSourceCh2StatusSFP1
				RollCallString,
			iqudc32InputSourceCh2StatusSFP2
				RollCallString,
			iqudc32InputSourceCh2StatusCurrentInputStand
				RollCallString,
			iqudc32CVBSDecoderSetupACC
				INTEGER,
			iqudc32CVBSDecoderSetupCTI
				INTEGER,
			iqudc32CVBSDecoderSetupPedestal
				INTEGER,
			iqudc32InputCVBSDecoderNTSCHue
				INTEGER,
			iqudc32CVBSDecoderCalibrationLumaGain
				INTEGER,
			iqudc32CVBSDecoderCalibrationSaveDecoder
				INTEGER,
			iqudc32OutputCh1OutputStandardStandard
				INTEGER,
			iqudc32MenuOutputCh1Format
				INTEGER,
			iqudc32MenuOutputCh1DefaultFieldRate
				INTEGER,
			iqudc32MenuOutputCh1CurrentOutputStan
				RollCallString,
			iqudc32OutputCh1ScrollingCaptionGCaptionEntry
				RollCallString,
			iqudc32OutputCh1ScrollingCaptionGCaptionScroll
				INTEGER,
			iqudc32OutputCh1ScrollingCaptionGCaptionEnable
				INTEGER,
			iqudc32MenuOutputCh1ForceFreeze
				INTEGER,
			iqudc32MenuOutputCh1Legalization
				INTEGER,
			iqudc32OutputCh1BlankingEmbeddedAudio
				INTEGER,
			iqudc32MenuOutputCh1SDHalfLine
				INTEGER,
			iqudc32OutputCh1LumaClipperEnable
				INTEGER,
			iqudc32OutputCh1LumaClipperWhiteMax
				INTEGER,
			iqudc32OutputCh1LumaClipperBlackMin
				INTEGER,
			iqudc32MenuOutputCh1DefaultOutput
				INTEGER,
			iqudc32MenuOutputCh1TestPatterns
				INTEGER,
			iqudc32OutputCh1LogoControlPreShaped
				INTEGER,
			iqudc32OutputCh1LogoControlTake
				INTEGER,
			iqudc32OutputCh1LogoControlHPosition
				INTEGER,
			iqudc32OutputCh1LogoControlVPosition
				INTEGER,
			iqudc32OutputCh1LogoControlTransparancy
				INTEGER,
			iqudc32OutputCh1LogoControlDelete
				INTEGER,
			iqudc32OutputCh1LogoControlCurrentSelectedLo
				RollCallString,
			iqudc32OutputCh1LogoControlLogoState
				RollCallString,
			iqudc32OutputCh1LogoControlNewLogo
				RollCallString,
			iqudc32OutputCh1LogoControlLogoStatus
				RollCallString,
			iqudc32OutputCh1LogoControlLogoSelect
				INTEGER,
			iqudc32CVBSEncoderASetupFormat
				INTEGER,
			iqudc32OutputCh1CalibrationDACGain
				INTEGER,
			iqudc32OutputCh1CalibrationSaveEncoder
				INTEGER,
			iqudc32OutputCh1SFPOutputRoutingSFP1Source
				INTEGER,
			iqudc32MenuOutputCh1SFP2Source
				INTEGER,
			iqudc32OutputCh2OutputStandardStandard
				INTEGER,
			iqudc32MenuOutputCh2Format
				INTEGER,
			iqudc32MenuOutputCh2DefaultFieldRate
				INTEGER,
			iqudc32MenuOutputCh2CurrentOutputStan
				RollCallString,
			iqudc32OutputCh2ScrollingCaptionGCaptionEntry
				RollCallString,
			iqudc32OutputCh2ScrollingCaptionGCaptionScroll
				INTEGER,
			iqudc32OutputCh2ScrollingCaptionGCaptionEnable
				INTEGER,
			iqudc32MenuOutputCh2ForceFreeze
				INTEGER,
			iqudc32MenuOutputCh2Legalization
				INTEGER,
			iqudc32OutputCh2BlankingEmbeddedAudio
				INTEGER,
			iqudc32MenuOutputCh2SDHalfLine
				INTEGER,
			iqudc32OutputCh2LumaClipperEnable
				INTEGER,
			iqudc32OutputCh2LumaClipperWhiteMax
				INTEGER,
			iqudc32OutputCh2LumaClipperBlackMin
				INTEGER,
			iqudc32MenuOutputCh2DefaultOutput
				INTEGER,
			iqudc32MenuOutputCh2TestPatterns
				INTEGER,
			iqudc32OutputCh2LogoControlPreShaped
				INTEGER,
			iqudc32OutputCh2LogoControlTake
				INTEGER,
			iqudc32OutputCh2LogoControlHPosition
				INTEGER,
			iqudc32OutputCh2LogoControlVPosition
				INTEGER,
			iqudc32OutputCh2LogoControlTransparancy
				INTEGER,
			iqudc32OutputCh2LogoControlDelete
				INTEGER,
			iqudc32OutputCh2LogoControlCurrentSelectedLo
				RollCallString,
			iqudc32OutputCh2LogoControlLogoState
				RollCallString,
			iqudc32OutputCh2LogoControlLogoSelect
				INTEGER,
			iqudc32CVBSEncoderBSetupFormat
				INTEGER,
			iqudc32OutputCh2CalibrationDACGain
				INTEGER,
			iqudc32OutputCh2CalibrationSaveEncoder
				INTEGER,
			iqudc32MenuOutputCh2NewDisplay
				RollCallString,
			iqudc32VideoCh1ProcAmpEnable
				INTEGER,
			iqudc32VideoCh1ProcAmpContrast
				INTEGER,
			iqudc32VideoCh1ProcAmpSaturation
				INTEGER,
			iqudc32VideoCh1ProcAmpBlackLevel
				INTEGER,
			iqudc32VideoCh1ProcAmpGamma
				INTEGER,
			iqudc32VideoCh1ProcAmpYCOffset
				INTEGER,
			iqudc32VideoCh1ProcAmpMasterGain
				INTEGER,
			iqudc32VideoCh1NonlinearEnhancerEnable
				INTEGER,
			iqudc32VideoCh1NonlinearEnhancerLevel
				INTEGER,
			iqudc32VideoCh1NonlinearEnhancerMode
				INTEGER,
			iqudc32MenuVideoCh1FrequencyBand20052
				INTEGER,
			iqudc32MenuVideoCh1NoiseRejection
				INTEGER,
			iqudc32VideoCh1ConversionAperturePreset
				INTEGER,
			iqudc32ConversionApertureHorizontalSharpness30100
				INTEGER,
			iqudc32MenuVideoCh1Detail
				INTEGER,
			iqudc32VideoCh1VerticalLevel
				INTEGER,
			iqudc32MenuVideoCh1FrequencyBand20060
				INTEGER,
			iqudc32VideoCh1NoiseReductionEnable
				INTEGER,
			iqudc32NoiseReductionRecursiveLuma20005
				INTEGER,
			iqudc32NoiseReductionRecursiveChroma20001
				INTEGER,
			iqudc32NoiseReductionRecursiveMode20002
				INTEGER,
			iqudc32VideoCh1NoiseReductionThreshold
				INTEGER,
			iqudc32NoiseReductionSpatialLevel20011
				INTEGER,
			iqudc32NoiseReductionSpatialMode20010
				INTEGER,
			iqudc32MenuVideoCh1Threshold
				INTEGER,
			iqudc32MenuVideoCh1SplitScreen
				INTEGER,
			iqudc32VideoCh2ProcAmpEnable
				INTEGER,
			iqudc32VideoCh2ProcAmpContrast
				INTEGER,
			iqudc32VideoCh2ProcAmpSaturation
				INTEGER,
			iqudc32VideoCh2ProcAmpBlackLevel
				INTEGER,
			iqudc32VideoCh2ProcAmpGamma
				INTEGER,
			iqudc32VideoCh2ProcAmpYCOffset
				INTEGER,
			iqudc32VideoCh2ProcAmpMasterGain
				INTEGER,
			iqudc32VideoCh2NonlinearEnhancerEnable
				INTEGER,
			iqudc32VideoCh2NonlinearEnhancerLevel
				INTEGER,
			iqudc32VideoCh2NonlinearEnhancerMode
				INTEGER,
			iqudc32MenuVideoCh2FrequencyBand20152
				INTEGER,
			iqudc32MenuVideoCh2NoiseRejection
				INTEGER,
			iqudc32VideoCh2ConversionAperturePreset
				INTEGER,
			iqudc32ConversionApertureHorizontalSharpness30200
				INTEGER,
			iqudc32MenuVideoCh2Detail
				INTEGER,
			iqudc32VideoCh2VerticalLevel
				INTEGER,
			iqudc32MenuVideoCh2FrequencyBand20160
				INTEGER,
			iqudc32VideoCh2NoiseReductionEnable
				INTEGER,
			iqudc32NoiseReductionRecursiveLuma20105
				INTEGER,
			iqudc32NoiseReductionRecursiveChroma20101
				INTEGER,
			iqudc32NoiseReductionRecursiveMode20107
				INTEGER,
			iqudc32VideoCh2NoiseReductionThreshold
				INTEGER,
			iqudc32NoiseReductionSpatialLevel20111
				INTEGER,
			iqudc32NoiseReductionSpatialMode20110
				INTEGER,
			iqudc32MenuVideoCh2Threshold
				INTEGER,
			iqudc32MenuVideoCh2SplitScreen
				INTEGER,
			iqudc32MenuVideoCh2NewDisplay
				RollCallString,
			iqudc32ConvertCh1UpConversionCleanEdgeUpconver
				INTEGER,
			iqudc32ConvertCh1MotionProcessing
				INTEGER,
			iqudc32ConvertCh1MotionProcessingEnhancedMotion
				INTEGER,
			iqudc32ConvertCh1MotionProcessingStillProcess
				INTEGER,
			iqudc32ConvertCh1MotionProcessingEnhancedStill
				INTEGER,
			iqudc32ConvertCh1MotionProcessingEnhancedFilm
				INTEGER,
			iqudc32ConvertCh1MotionProcessingEnhancedDeinterla
				INTEGER,
			iqudc32ConvertCh1MotionProcessingCleanCut
				INTEGER,
			iqudc32ConvertCh1InputCadenceFilmCadence
				INTEGER,
			iqudc32MenuConvertCh1
				INTEGER,
			iqudc32MenuConvertCh123Source30052
				INTEGER,
			iqudc32MenuConvertCh123StartHour30053
				INTEGER,
			iqudc32ConvertCh1OutputCadenceFilmCadence
				INTEGER,
			iqudc32ConvertCh1OutputCadence59Cadence
				INTEGER,
			iqudc32MenuConvertCh123Source30062
				INTEGER,
			iqudc32MenuConvertCh123StartHour30063
				INTEGER,
			iqudc32ConvertCh2UpConversionCleanEdgeUpconver
				INTEGER,
			iqudc32ConvertCh2MotionProcessing
				INTEGER,
			iqudc32ConvertCh2MotionProcessingEnhancedMotion
				INTEGER,
			iqudc32ConvertCh2MotionProcessingStillProcess
				INTEGER,
			iqudc32ConvertCh2MotionProcessingEnhancedStill
				INTEGER,
			iqudc32ConvertCh2MotionProcessingEnhancedFilm
				INTEGER,
			iqudc32ConvertCh2MotionProcessingEnhancedDeinterla
				INTEGER,
			iqudc32ConvertCh2MotionProcessingCleanCut
				INTEGER,
			iqudc32ConvertCh2InputCadenceFilmCadence
				INTEGER,
			iqudc32ConvertCh2InputCadence59Cadence
				INTEGER,
			iqudc32MenuConvertCh223Source30152
				INTEGER,
			iqudc32MenuConvertCh223StartHour30153
				INTEGER,
			iqudc32ConvertCh2OutputCadenceFilmCadence
				INTEGER,
			iqudc32ConvertCh2OutputCadence59Cadence
				INTEGER,
			iqudc32MenuConvertCh223Source30162
				INTEGER,
			iqudc32MenuConvertCh223StartHour30163
				INTEGER,
			iqudc32MenuConvertCh2NewDisplay
				RollCallString,
			iqudc32MenuARCSidebarKeyerSyncMode40007
				INTEGER,
			iqudc32MenuARCSidebarKeyerSignallingDetected64020
				RollCallString,
			iqudc32ARCSidebarKeyerSidebarKeyingOuMode40017
				INTEGER,
			iqudc32MenuARCSidebarKeyerSidebarKeySource40018
				INTEGER,
			iqudc32MenuOutputCropPositioTop
				INTEGER,
			iqudc32MenuOutputCropPositioBottom
				INTEGER,
			iqudc32MenuOutputCropPositioLeft
				INTEGER,
			iqudc32MenuOutputCropPositioRight
				INTEGER,
			iqudc32MenuPostScalingControPostScalingEnable
				INTEGER,
			iqudc32MenuPostScalingControSize
				INTEGER,
			iqudc32MenuPostScalingControAspect
				INTEGER,
			iqudc32MenuPostScalingControPan
				INTEGER,
			iqudc32MenuPostScalingControTilt
				INTEGER,
			iqudc32MenuScalerConfigUsePresets
				INTEGER,
			iqudc32ScalerConfigPresetsSDInputis70240030
				INTEGER,
			iqudc32ScalerConfigPresetsSDOutputis70240037
				INTEGER,
			iqudc32PresetsSDCrossConversionSelectStdPreset40031
				INTEGER,
			iqudc32ScalerConfigHDCrossConversionSelectStdPreset40032
				INTEGER,
			iqudc32ScalerConfigUpConversionSelectStdPreset40033
				INTEGER,
			iqudc32ScalerConfigDownConversionSelectStdPreset40035
				INTEGER,
			iqudc32ScalerConfigInputConfigInputSignallingSo40100
				INTEGER,
			iqudc32ScalerConfigIfInputSignallingForceInputFormat40135
				INTEGER,
			iqudc32ScalerConfigIfInputSignallingSDInputFormat40010
				INTEGER,
			iqudc32MenuScalerConfigHDInputFormat
				INTEGER,
			iqudc32ScalerConfigOutputConfigConversionScaling40012
				INTEGER,
			iqudc32MenuScalerConfigSDOutputFormat
				INTEGER,
			iqudc32MenuMemoriesRecallMemory
				INTEGER,
			iqudc32MenuMemoriesSelMemory
				INTEGER,
			iqudc32MenuMemoriesSaveMemory
				INTEGER,
			iqudc32MenuMemoriesClearMemory
				INTEGER,
			iqudc32MemoriesMemoryNameChangeName64003
				RollCallString,
			iqudc32MenuMemoriesLastDisplayMemory
				RollCallString,
			iqudc32OutputSignallingCSMPTE2016Mode40130
				INTEGER,
			iqudc32MenuOutputSignallingCOutputLine625
				INTEGER,
			iqudc32MenuOutputSignallingCOutputLine525
				INTEGER,
			iqudc32MenuOutputSignallingCOutputLineHD
				INTEGER,
			iqudc32MenuOutputSignallingCOutputLineStatus40141
				RollCallString,
			iqudc32OutputSignallingCVIMode40120
				INTEGER,
			iqudc32MenuOutputSignallingCOutputFormat
				INTEGER,
			iqudc32MenuOutputSignallingCVIPassData
				INTEGER,
			iqudc32OutputSignallingCL23Mode40112
				INTEGER,
			iqudc32MenuOutputSignallingC
				INTEGER,
			iqudc32MenuOutputSignallingCInputLine
				INTEGER,
			iqudc32MenuOutputSignallingCOutputLine
				INTEGER,
			iqudc32MenuOutputSignallingCOutputLineStatus20166
				RollCallString,
			iqudc32OutputSignallingCAFDUserBitsForceUserBitsVal20163
				INTEGER,
			iqudc32OutputSignallingCAFDUserBitsUserBitsValue40137
				INTEGER,
			iqudc32OutputSignallingCForceModeConfigSMPTE201640133
				INTEGER,
			iqudc32MenuOutputSignallingCSMPTERP186
				INTEGER,
			iqudc32MenuOutputSignallingCAFD
				INTEGER,
			iqudc32MenuOutputSignallingCETSI
				INTEGER,
			iqudc32MenuARCSidebarKeyerSyncMode40107
				INTEGER,
			iqudc32MenuARCSidebarKeyerSignallingDetected64220
				RollCallString,
			iqudc32ARCSidebarKeyerSidebarKeyingOuMode40023
				INTEGER,
			iqudc32MenuARCSidebarKeyerSidebarKeySource40024
				INTEGER,
			iqudc32ARCSidebarKeyerOutputCropPositioTop
				INTEGER,
			iqudc32ARCSidebarKeyerOutputCropPositioBottom
				INTEGER,
			iqudc32ARCSidebarKeyerOutputCropPositioLeft
				INTEGER,
			iqudc32ARCSidebarKeyerOutputCropPositioRight
				INTEGER,
			iqudc32ARCSidebarKeyerPostScalingControPostScalingEnable
				INTEGER,
			iqudc32ARCSidebarKeyerPostScalingControSize
				INTEGER,
			iqudc32ARCSidebarKeyerPostScalingControAspect
				INTEGER,
			iqudc32ARCSidebarKeyerPostScalingControPan
				INTEGER,
			iqudc32ARCSidebarKeyerPostScalingControTilt
				INTEGER,
			iqudc32ARCSidebarKeyerScalerConfigUsePresets
				INTEGER,
			iqudc32ScalerConfigPresetsSDInputis70240040
				INTEGER,
			iqudc32ScalerConfigPresetsSDOutputis70240047
				INTEGER,
			iqudc32PresetsSDCrossConversionSelectStdPreset40041
				INTEGER,
			iqudc32ScalerConfigHDCrossConversionSelectStdPreset40046
				INTEGER,
			iqudc32ScalerConfigUpConversionSelectStdPreset40043
				INTEGER,
			iqudc32ScalerConfigDownConversionSelectStdPreset40045
				INTEGER,
			iqudc32ScalerConfigInputConfigInputSignallingSo40202
				INTEGER,
			iqudc32ScalerConfigIfInputSignallingForceInputFormat40235
				INTEGER,
			iqudc32ScalerConfigIfInputSignallingSDInputFormat40114
				INTEGER,
			iqudc32ARCSidebarKeyerScalerConfigHDInputFormat
				INTEGER,
			iqudc32ScalerConfigOutputConfigConversionScaling40116
				INTEGER,
			iqudc32ARCSidebarKeyerScalerConfigSDOutputFormat
				INTEGER,
			iqudc32ARCSidebarKeyerMemoriesRecallMemory
				INTEGER,
			iqudc32ARCSidebarKeyerMemoriesSelMemory
				INTEGER,
			iqudc32ARCSidebarKeyerMemoriesSaveMemory
				INTEGER,
			iqudc32ARCSidebarKeyerMemoriesClearMemory
				INTEGER,
			iqudc32MemoriesMemoryNameChangeName64009
				RollCallString,
			iqudc32ARCSidebarKeyerMemoriesLastDisplayMemory
				RollCallString,
			iqudc32OutputSignallingCSMPTE2016Mode40230
				INTEGER,
			iqudc32ARCSidebarKeyerOutputSignallingCOutputLine625
				INTEGER,
			iqudc32ARCSidebarKeyerOutputSignallingCOutputLine525
				INTEGER,
			iqudc32ARCSidebarKeyerOutputSignallingCOutputLineHD
				INTEGER,
			iqudc32ARCSidebarKeyerOutputSignallingCOutputLineStatus40241
				RollCallString,
			iqudc32OutputSignallingCVIMode40220
				INTEGER,
			iqudc32ARCSidebarKeyerOutputSignallingCOutputFormat
				INTEGER,
			iqudc32ARCSidebarKeyerOutputSignallingCVIPassData
				INTEGER,
			iqudc32OutputSignallingCL23Mode40212
				INTEGER,
			iqudc32ARCSidebarKeyerOutputSignallingC
				INTEGER,
			iqudc32ARCSidebarKeyerOutputSignallingCInputLine
				INTEGER,
			iqudc32ARCSidebarKeyerOutputSignallingCOutputLine
				INTEGER,
			iqudc32ARCSidebarKeyerOutputSignallingCOutputLineStatus20176
				RollCallString,
			iqudc32OutputSignallingCAFDUserBitsForceUserBitsVal20173
				INTEGER,
			iqudc32OutputSignallingCAFDUserBitsUserBitsValue40237
				INTEGER,
			iqudc32OutputSignallingCForceModeConfigSMPTE201640233
				INTEGER,
			iqudc32ARCSidebarKeyerOutputSignallingCSMPTERP186
				INTEGER,
			iqudc32ARCSidebarKeyerOutputSignallingCAFD
				INTEGER,
			iqudc32ARCSidebarKeyerOutputSignallingCETSI
				INTEGER,
			iqudc32MenuARCSidebarKeyerNewDisplay
				RollCallString,
			iqudc32AudioRoutingCh1InputPairsStatusEmbedded1
				RollCallString,
			iqudc32AudioRoutingCh1InputPairsStatusEmbedded2
				RollCallString,
			iqudc32AudioRoutingCh1InputPairsStatusEmbedded3
				RollCallString,
			iqudc32AudioRoutingCh1InputPairsStatusEmbedded4
				RollCallString,
			iqudc32AudioRoutingCh1InputPairsStatusEmbedded5
				RollCallString,
			iqudc32AudioRoutingCh1InputPairsStatusEmbedded6
				RollCallString,
			iqudc32AudioRoutingCh1InputPairsStatusEmbedded7
				RollCallString,
			iqudc32AudioRoutingCh1InputPairsStatusEmbedded8
				RollCallString,
			iqudc32AudioRoutingCh1InputPairsStatusAES1
				RollCallString,
			iqudc32AudioRoutingCh1InputPairsStatusAES2
				RollCallString,
			iqudc32AudioRoutingCh1InputPairsStatusAES3
				RollCallString,
			iqudc32AudioRoutingCh1InputPairsStatusAES4
				RollCallString,
			iqudc32AudioRoutingCh1InputPairsStatusAES5
				RollCallString,
			iqudc32AudioRoutingCh1InputPairsStatusAES6
				RollCallString,
			iqudc32AudioRoutingCh1InputPairsStatusAES7
				RollCallString,
			iqudc32AudioRoutingCh1InputPairsStatusAES8
				RollCallString,
			iqudc32AudioRoutingCh1InputPairsStatusAnalog1
				RollCallString,
			iqudc32AudioRoutingCh1InputPairsStatusAnalog2
				RollCallString,
			iqudc32AudioRoutingCh1InputPairsStatusDolbyDecoder1
				RollCallString,
			iqudc32AudioRoutingCh1InputPairsStatusDolbyDecoder2
				RollCallString,
			iqudc32AudioRoutingCh1InputPairsStatusDolbyDecoder3
				RollCallString,
			iqudc32AudioRoutingCh1InputPairsStatusDolbyDecoder4
				RollCallString,
			iqudc32AudioRoutingCh1InputPairsStatusDolbyDownmix
				RollCallString,
			iqudc32AudioRoutingCh1InputPairsStatusDolbyEncoder
				RollCallString,
			iqudc32ProcessPairs18Pair1InputPairsSource
				INTEGER,
			iqudc32ProcessPairs18Pair2InputPairsSource
				INTEGER,
			iqudc32ProcessPairs18Pair3InputPairsSource
				INTEGER,
			iqudc32ProcessPairs18Pair4InputPairsSource
				INTEGER,
			iqudc32ProcessPairs18Pair5InputPairsSource
				INTEGER,
			iqudc32ProcessPairs18Pair6InputPairsSource
				INTEGER,
			iqudc32ProcessPairs18Pair7InputPairsSource
				INTEGER,
			iqudc32ProcessPairs18Pair8InputPairsSource
				INTEGER,
			iqudc32AudioRoutingCh1ProcessPairs18SPair1
				RollCallString,
			iqudc32AudioRoutingCh1ProcessPairs18SPair2
				RollCallString,
			iqudc32AudioRoutingCh1ProcessPairs18SPair3
				RollCallString,
			iqudc32AudioRoutingCh1ProcessPairs18SPair4
				RollCallString,
			iqudc32AudioRoutingCh1ProcessPairs18SPair5
				RollCallString,
			iqudc32AudioRoutingCh1ProcessPairs18SPair6
				RollCallString,
			iqudc32AudioRoutingCh1ProcessPairs18SPair7
				RollCallString,
			iqudc32AudioRoutingCh1ProcessPairs18SPair8
				RollCallString,
			iqudc32AudioRoutingCh2InputPairsStatusEmbedded1
				RollCallString,
			iqudc32AudioRoutingCh2InputPairsStatusEmbedded2
				RollCallString,
			iqudc32AudioRoutingCh2InputPairsStatusEmbedded3
				RollCallString,
			iqudc32AudioRoutingCh2InputPairsStatusEmbedded4
				RollCallString,
			iqudc32AudioRoutingCh2InputPairsStatusEmbedded5
				RollCallString,
			iqudc32AudioRoutingCh2InputPairsStatusEmbedded6
				RollCallString,
			iqudc32AudioRoutingCh2InputPairsStatusEmbedded7
				RollCallString,
			iqudc32AudioRoutingCh2InputPairsStatusEmbedded8
				RollCallString,
			iqudc32AudioRoutingCh2InputPairsStatusAES1
				RollCallString,
			iqudc32AudioRoutingCh2InputPairsStatusAES2
				RollCallString,
			iqudc32AudioRoutingCh2InputPairsStatusAES3
				RollCallString,
			iqudc32AudioRoutingCh2InputPairsStatusAES4
				RollCallString,
			iqudc32AudioRoutingCh2InputPairsStatusAES5
				RollCallString,
			iqudc32AudioRoutingCh2InputPairsStatusAES6
				RollCallString,
			iqudc32AudioRoutingCh2InputPairsStatusAES7
				RollCallString,
			iqudc32AudioRoutingCh2InputPairsStatusAES8
				RollCallString,
			iqudc32AudioRoutingCh2InputPairsStatusAnalog1
				RollCallString,
			iqudc32AudioRoutingCh2InputPairsStatusAnalog2
				RollCallString,
			iqudc32AudioRoutingCh2InputPairsStatusDolbyDecoder1
				RollCallString,
			iqudc32AudioRoutingCh2InputPairsStatusDolbyDecoder2
				RollCallString,
			iqudc32AudioRoutingCh2InputPairsStatusDolbyDecoder3
				RollCallString,
			iqudc32AudioRoutingCh2InputPairsStatusDolbyDecoder4
				RollCallString,
			iqudc32AudioRoutingCh2InputPairsStatusDolbyDownmix
				RollCallString,
			iqudc32AudioRoutingCh2InputPairsStatusDolbyEncoder
				RollCallString,
			iqudc32ProcessPairs18ProcessPair1InputPairsSource
				INTEGER,
			iqudc32ProcessPairs18ProcessPair2InputPairsSource
				INTEGER,
			iqudc32ProcessPairs18ProcessPair3InputPairsSource
				INTEGER,
			iqudc32ProcessPairs18ProcessPair4InputPairsSource
				INTEGER,
			iqudc32ProcessPairs18ProcessPair5InputPairsSource
				INTEGER,
			iqudc32ProcessPairs18ProcessPair6InputPairsSource
				INTEGER,
			iqudc32ProcessPairs18ProcessPair7InputPairsSource
				INTEGER,
			iqudc32ProcessPairs18ProcessPair8InputPairsSource
				INTEGER,
			iqudc32AudioRoutingCh2ProcessPairs18SPair1
				RollCallString,
			iqudc32AudioRoutingCh2ProcessPairs18SPair2
				RollCallString,
			iqudc32AudioRoutingCh2ProcessPairs18SPair3
				RollCallString,
			iqudc32AudioRoutingCh2ProcessPairs18SPair4
				RollCallString,
			iqudc32AudioRoutingCh2ProcessPairs18SPair5
				RollCallString,
			iqudc32AudioRoutingCh2ProcessPairs18SPair6
				RollCallString,
			iqudc32AudioRoutingCh2ProcessPairs18SPair7
				RollCallString,
			iqudc32AudioRoutingCh2ProcessPairs18SPair8
				RollCallString,
			iqudc32MenuAudioRoutingCh2NewDisplay
				RollCallString,
			iqudc32OutputPairs18OutputPair1LProcessPairsSourc52000
				INTEGER,
			iqudc32OutputPairs18OutputPair1LInvertPhase50700
				INTEGER,
			iqudc32OutputPairs18OutputPair1LControl50100
				INTEGER,
			iqudc32OutputPairs18OutputPair1RProcessPairsSourc52008
				INTEGER,
			iqudc32OutputPairs18OutputPair1RInvertPhase50708
				INTEGER,
			iqudc32OutputPairs18OutputPair1RControl50108
				INTEGER,
			iqudc32OutputPairs18OutputPair2LProcessPairsSourc52001
				INTEGER,
			iqudc32OutputPairs18OutputPair2LInvertPhase50701
				INTEGER,
			iqudc32OutputPairs18OutputPair2LControl50101
				INTEGER,
			iqudc32OutputPairs18OutputPair2RProcessPairsSourc52009
				INTEGER,
			iqudc32OutputPairs18OutputPair2RInvertPhase50709
				INTEGER,
			iqudc32OutputPairs18OutputPair2RControl50109
				INTEGER,
			iqudc32OutputPairs18OutputPair3LProcessPairsSourc52002
				INTEGER,
			iqudc32OutputPairs18OutputPair3LInvertPhase50702
				INTEGER,
			iqudc32OutputPairs18OutputPair3LControl50102
				INTEGER,
			iqudc32OutputPairs18OutputPair3RProcessPairsSourc52010
				INTEGER,
			iqudc32OutputPairs18OutputPair3RInvertPhase50710
				INTEGER,
			iqudc32OutputPairs18OutputPair3RControl50110
				INTEGER,
			iqudc32OutputPairs18OutputPair4LProcessPairsSourc52003
				INTEGER,
			iqudc32OutputPairs18OutputPair4LInvertPhase50703
				INTEGER,
			iqudc32OutputPairs18OutputPair4LControl50103
				INTEGER,
			iqudc32OutputPairs18OutputPair4RProcessPairsSourc52011
				INTEGER,
			iqudc32OutputPairs18OutputPair4RInvertPhase50711
				INTEGER,
			iqudc32OutputPairs18OutputPair4RControl50111
				INTEGER,
			iqudc32OutputPairs18OutputPair5LProcessPairsSourc52004
				INTEGER,
			iqudc32OutputPairs18OutputPair5LInvertPhase50704
				INTEGER,
			iqudc32OutputPairs18OutputPair5LControl50104
				INTEGER,
			iqudc32OutputPairs18OutputPair5RProcessPairsSourc52012
				INTEGER,
			iqudc32OutputPairs18OutputPair5RInvertPhase50712
				INTEGER,
			iqudc32OutputPairs18OutputPair5RControl50112
				INTEGER,
			iqudc32OutputPairs18OutputPair6LProcessPairsSourc52005
				INTEGER,
			iqudc32OutputPairs18OutputPair6LInvertPhase50705
				INTEGER,
			iqudc32OutputPairs18OutputPair6LControl50105
				INTEGER,
			iqudc32OutputPairs18OutputPair6RProcessPairsSourc52013
				INTEGER,
			iqudc32OutputPairs18OutputPair6RInvertPhase50713
				INTEGER,
			iqudc32OutputPairs18OutputPair6RControl50113
				INTEGER,
			iqudc32OutputPairs18OutputPair7LProcessPairsSourc52006
				INTEGER,
			iqudc32OutputPairs18OutputPair7LInvertPhase50706
				INTEGER,
			iqudc32OutputPairs18OutputPair7LControl50106
				INTEGER,
			iqudc32OutputPairs18OutputPair7RProcessPairsSourc52014
				INTEGER,
			iqudc32OutputPairs18OutputPair7RInvertPhase50714
				INTEGER,
			iqudc32OutputPairs18OutputPair7RControl50114
				INTEGER,
			iqudc32OutputPairs18OutputPair8LProcessPairsSourc52007
				INTEGER,
			iqudc32OutputPairs18OutputPair8LInvertPhase50707
				INTEGER,
			iqudc32OutputPairs18OutputPair8LControl50107
				INTEGER,
			iqudc32OutputPairs18OutputPair8RProcessPairsSourc52015
				INTEGER,
			iqudc32OutputPairs18OutputPair8RInvertPhase50715
				INTEGER,
			iqudc32OutputPairs18OutputPair8RControl50115
				INTEGER,
			iqudc32AudioShuffleCh1OutputPairs18StPair1
				RollCallString,
			iqudc32AudioShuffleCh1OutputPairs18StPair2
				RollCallString,
			iqudc32AudioShuffleCh1OutputPairs18StPair3
				RollCallString,
			iqudc32AudioShuffleCh1OutputPairs18StPair4
				RollCallString,
			iqudc32AudioShuffleCh1OutputPairs18StPair5
				RollCallString,
			iqudc32AudioShuffleCh1OutputPairs18StPair6
				RollCallString,
			iqudc32AudioShuffleCh1OutputPairs18StPair7
				RollCallString,
			iqudc32AudioShuffleCh1OutputPairs18StPair8
				RollCallString,
			iqudc32MenuAudioShuffleCh1NewDisplay
				RollCallString,
			iqudc32OutputPairs18OutputPair1LProcessPairsSourc50800
				INTEGER,
			iqudc32OutputPairs18OutputPair1LInvertPhase50816
				INTEGER,
			iqudc32OutputPairs18OutputPair1LControl50832
				INTEGER,
			iqudc32OutputPairs18OutputPair1RProcessPairsSourc50808
				INTEGER,
			iqudc32OutputPairs18OutputPair1RInvertPhase50824
				INTEGER,
			iqudc32OutputPairs18OutputPair1RControl50840
				INTEGER,
			iqudc32OutputPairs18OutputPair2LProcessPairsSourc50801
				INTEGER,
			iqudc32OutputPairs18OutputPair2LInvertPhase50817
				INTEGER,
			iqudc32OutputPairs18OutputPair2LControl50833
				INTEGER,
			iqudc32OutputPairs18OutputPair2RProcessPairsSourc50809
				INTEGER,
			iqudc32OutputPairs18OutputPair2RInvertPhase50825
				INTEGER,
			iqudc32OutputPairs18OutputPair2RControl50841
				INTEGER,
			iqudc32OutputPairs18OutputPair3LProcessPairsSourc50802
				INTEGER,
			iqudc32OutputPairs18OutputPair3LInvertPhase50818
				INTEGER,
			iqudc32OutputPairs18OutputPair3LControl50834
				INTEGER,
			iqudc32OutputPairs18OutputPair3RProcessPairsSourc50810
				INTEGER,
			iqudc32OutputPairs18OutputPair3RInvertPhase50826
				INTEGER,
			iqudc32OutputPairs18OutputPair3RControl50842
				INTEGER,
			iqudc32OutputPairs18OutputPair4LProcessPairsSourc50803
				INTEGER,
			iqudc32OutputPairs18OutputPair4LInvertPhase50819
				INTEGER,
			iqudc32OutputPairs18OutputPair4LControl50835
				INTEGER,
			iqudc32OutputPairs18OutputPair4RProcessPairsSourc50811
				INTEGER,
			iqudc32OutputPairs18OutputPair4RInvertPhase50827
				INTEGER,
			iqudc32OutputPairs18OutputPair4RControl50843
				INTEGER,
			iqudc32OutputPairs18OutputPair5LProcessPairsSourc50804
				INTEGER,
			iqudc32OutputPairs18OutputPair5LInvertPhase50820
				INTEGER,
			iqudc32OutputPairs18OutputPair5LControl50836
				INTEGER,
			iqudc32OutputPairs18OutputPair5RProcessPairsSourc50812
				INTEGER,
			iqudc32OutputPairs18OutputPair5RInvertPhase50828
				INTEGER,
			iqudc32OutputPairs18OutputPair5RControl50844
				INTEGER,
			iqudc32OutputPairs18OutputPair6LProcessPairsSourc50805
				INTEGER,
			iqudc32OutputPairs18OutputPair6LInvertPhase50821
				INTEGER,
			iqudc32OutputPairs18OutputPair6LControl50837
				INTEGER,
			iqudc32OutputPairs18OutputPair6RProcessPairsSourc50813
				INTEGER,
			iqudc32OutputPairs18OutputPair6RInvertPhase50829
				INTEGER,
			iqudc32OutputPairs18OutputPair6RControl50845
				INTEGER,
			iqudc32OutputPairs18OutputPair7LProcessPairsSourc50806
				INTEGER,
			iqudc32OutputPairs18OutputPair7LInvertPhase50822
				INTEGER,
			iqudc32OutputPairs18OutputPair7LControl50838
				INTEGER,
			iqudc32OutputPairs18OutputPair7RProcessPairsSourc50814
				INTEGER,
			iqudc32OutputPairs18OutputPair7RInvertPhase50830
				INTEGER,
			iqudc32OutputPairs18OutputPair7RControl50846
				INTEGER,
			iqudc32OutputPairs18OutputPair8LProcessPairsSourc50807
				INTEGER,
			iqudc32OutputPairs18OutputPair8LInvertPhase50823
				INTEGER,
			iqudc32OutputPairs18OutputPair8LControl50839
				INTEGER,
			iqudc32OutputPairs18OutputPair8RProcessPairsSourc50815
				INTEGER,
			iqudc32OutputPairs18OutputPair8RInvertPhase50831
				INTEGER,
			iqudc32OutputPairs18OutputPair8RControl50847
				INTEGER,
			iqudc32AudioShuffleCh2OutputPairs18StPair1
				RollCallString,
			iqudc32AudioShuffleCh2OutputPairs18StPair2
				RollCallString,
			iqudc32AudioShuffleCh2OutputPairs18StPair3
				RollCallString,
			iqudc32AudioShuffleCh2OutputPairs18StPair4
				RollCallString,
			iqudc32AudioShuffleCh2OutputPairs18StPair5
				RollCallString,
			iqudc32AudioShuffleCh2OutputPairs18StPair6
				RollCallString,
			iqudc32AudioShuffleCh2OutputPairs18StPair7
				RollCallString,
			iqudc32AudioShuffleCh2OutputPairs18StPair8
				RollCallString,
			iqudc32MenuAudioShuffleCh2NewDisplay
				RollCallString,
			iqudc32AudioControlCh1GainPair1L
				INTEGER,
			iqudc32AudioControlCh1GainPair1R
				INTEGER,
			iqudc32AudioControlCh1GainPair2L
				INTEGER,
			iqudc32AudioControlCh1GainPair2R
				INTEGER,
			iqudc32AudioControlCh1GainPair3L
				INTEGER,
			iqudc32AudioControlCh1GainPair3R
				INTEGER,
			iqudc32AudioControlCh1GainPair4L
				INTEGER,
			iqudc32AudioControlCh1GainPair4R
				INTEGER,
			iqudc32AudioControlCh1GainPair5L
				INTEGER,
			iqudc32AudioControlCh1GainPair5R
				INTEGER,
			iqudc32AudioControlCh1GainPair6L
				INTEGER,
			iqudc32AudioControlCh1GainPair6R
				INTEGER,
			iqudc32AudioControlCh1GainPair7L
				INTEGER,
			iqudc32AudioControlCh1GainPair7R
				INTEGER,
			iqudc32AudioControlCh1GainPair8L
				INTEGER,
			iqudc32AudioControlCh1GainPair8R
				INTEGER,
			iqudc32MenuAudioControlCh1ToneFrequency
				INTEGER,
			iqudc32MenuAudioControlCh1DolbyEAlignmentO
				INTEGER,
			iqudc32DelayGlobalDelayPairOPair150319
				INTEGER,
			iqudc32DelayGlobalDelayPairOPair1Total50327
				RollCallString,
			iqudc32DelayGlobalDelayPairOPair250320
				INTEGER,
			iqudc32DelayGlobalDelayPairOPair2Total50328
				RollCallString,
			iqudc32DelayGlobalDelayPairOPair350321
				INTEGER,
			iqudc32DelayGlobalDelayPairOPair3Total50329
				RollCallString,
			iqudc32DelayGlobalDelayPairOPair450322
				INTEGER,
			iqudc32DelayGlobalDelayPairOPair4Total50330
				RollCallString,
			iqudc32DelayGlobalDelayPairOPair550323
				INTEGER,
			iqudc32DelayGlobalDelayPairOPair5Total50331
				RollCallString,
			iqudc32DelayGlobalDelayPairOPair650324
				INTEGER,
			iqudc32DelayGlobalDelayPairOPair6Total50332
				RollCallString,
			iqudc32DelayGlobalDelayPairOPair750325
				INTEGER,
			iqudc32DelayGlobalDelayPairOPair7Total50333
				RollCallString,
			iqudc32DelayGlobalDelayPairOPair850326
				INTEGER,
			iqudc32DelayGlobalDelayPairOPair8Total50334
				RollCallString,
			iqudc32AudioControlCh1GlobalDelayAudio
				INTEGER,
			iqudc32AudioControlCh1GlobalDelayAudioTotal
				RollCallString,
			iqudc32AudioControlCh1GlobalDelayVideoTotal
				RollCallString,
			iqudc32MenuAudioControlCh1NewDisplay
				RollCallString,
			iqudc32AudioControlCh2GainPair1L
				INTEGER,
			iqudc32AudioControlCh2GainPair1R
				INTEGER,
			iqudc32AudioControlCh2GainPair2L
				INTEGER,
			iqudc32AudioControlCh2GainPair2R
				INTEGER,
			iqudc32AudioControlCh2GainPair3L
				INTEGER,
			iqudc32AudioControlCh2GainPair3R
				INTEGER,
			iqudc32AudioControlCh2GainPair4L
				INTEGER,
			iqudc32AudioControlCh2GainPair4R
				INTEGER,
			iqudc32AudioControlCh2GainPair5L
				INTEGER,
			iqudc32AudioControlCh2GainPair5R
				INTEGER,
			iqudc32AudioControlCh2GainPair6L
				INTEGER,
			iqudc32AudioControlCh2GainPair6R
				INTEGER,
			iqudc32AudioControlCh2GainPair7L
				INTEGER,
			iqudc32AudioControlCh2GainPair7R
				INTEGER,
			iqudc32AudioControlCh2GainPair8L
				INTEGER,
			iqudc32AudioControlCh2GainPair8R
				INTEGER,
			iqudc32MenuAudioControlCh2ToneFrequency
				INTEGER,
			iqudc32MenuAudioControlCh2DolbyEAlignmentO
				INTEGER,
			iqudc32DelayGlobalDelayPairOPair150505
				INTEGER,
			iqudc32DelayGlobalDelayPairOPair1Total50513
				RollCallString,
			iqudc32DelayGlobalDelayPairOPair250506
				INTEGER,
			iqudc32DelayGlobalDelayPairOPair2Total50514
				RollCallString,
			iqudc32DelayGlobalDelayPairOPair350507
				INTEGER,
			iqudc32DelayGlobalDelayPairOPair3Total50515
				RollCallString,
			iqudc32DelayGlobalDelayPairOPair450508
				INTEGER,
			iqudc32DelayGlobalDelayPairOPair4Total50516
				RollCallString,
			iqudc32DelayGlobalDelayPairOPair550509
				INTEGER,
			iqudc32DelayGlobalDelayPairOPair5Total50517
				RollCallString,
			iqudc32DelayGlobalDelayPairOPair650510
				INTEGER,
			iqudc32DelayGlobalDelayPairOPair6Total50518
				RollCallString,
			iqudc32DelayGlobalDelayPairOPair750511
				INTEGER,
			iqudc32DelayGlobalDelayPairOPair7Total50519
				RollCallString,
			iqudc32DelayGlobalDelayPairOPair850512
				INTEGER,
			iqudc32DelayGlobalDelayPairOPair8Total50520
				RollCallString,
			iqudc32AudioControlCh2GlobalDelay
				INTEGER,
			iqudc32AudioControlCh2GlobalDelayGlobalTotal
				RollCallString,
			iqudc32AudioControlCh2GlobalDelayVideoTotal
				RollCallString,
			iqudc32MenuAudioControlCh2NewDisplay
				RollCallString,
			iqudc32AudioIOAESAESOutput14AES1
				INTEGER,
			iqudc32MenuAudioIOAESAES2
				INTEGER,
			iqudc32MenuAudioIOAESAES3
				INTEGER,
			iqudc32MenuAudioIOAESAES4
				INTEGER,
			iqudc32AudioIOAESAESOutput58AES5
				INTEGER,
			iqudc32MenuAudioIOAESAES6
				INTEGER,
			iqudc32MenuAudioIOAESAES7
				INTEGER,
			iqudc32MenuAudioIOAESAES8
				INTEGER,
			iqudc32MenuAudioIOAESNewDisplay
				RollCallString,
			iqudc32AudioIOAnalogAnalogOutput12Analog1
				INTEGER,
			iqudc32MenuAudioIOAnalogAnalog2
				INTEGER,
			iqudc32InputAnalogInADCHeadrPair1
				INTEGER,
			iqudc32InputAnalogInADCHeadrPair2
				INTEGER,
			iqudc32OutputAnalogOutDACLevePair1
				INTEGER,
			iqudc32OutputAnalogOutDACLevePair2
				INTEGER,
			iqudc32MenuAudioIOAnalogNewDisplay
				RollCallString,
			iqudc32DolbySetupDolbyCh1Mode
				INTEGER,
			iqudc32DolbySetupDolbyCh1DolbyEDelayCompen
				INTEGER,
			iqudc32DolbySetupDolbyCh1MetadataSource
				INTEGER,
			iqudc32DolbyCh1SMPTE2020OutputOutputLine
				INTEGER,
			iqudc32DolbyCh1SMPTE2020OutputOutputEnable
				INTEGER,
			iqudc32DolbySetupDolbyCh1DecoderSource
				INTEGER,
			iqudc32MenuDolbySetupEncoderSource1
				INTEGER,
			iqudc32MenuDolbySetupEncoderSource2
				INTEGER,
			iqudc32MenuDolbySetupEncoderSource3
				INTEGER,
			iqudc32MenuDolbySetupEncoderSource4
				INTEGER,
			iqudc32MenuDolbySetupEncoderFormat
				INTEGER,
			iqudc32MenuDolbySetupEncoderFormatED
				INTEGER,
			iqudc32MenuDolbySetupEncoderRate
				INTEGER,
			iqudc32MenuDolbySetupEncoderBitDepth
				INTEGER,
			iqudc32MenuDolbySetupEncoderConfig
				INTEGER,
			iqudc32MenuDolbySetupInputStatus
				RollCallString,
			iqudc32MenuDolbySetupDecoderRate
				RollCallString,
			iqudc32MenuDolbySetupDecoderFormat
				RollCallString,
			iqudc32MenuDolbySetupDecoderVersion
				RollCallString,
			iqudc32MenuDolbySetupEncoderVersion
				RollCallString,
			iqudc32MenuDolbySetupNewDisplay
				RollCallString,
			iqudc32MenuGenlockSourceCh12
				INTEGER,
			iqudc32GenlockTimingCh1VerticalTiming
				INTEGER,
			iqudc32GenlockTimingCh1HorizontalTiming
				INTEGER,
			iqudc32GenlockTimingCh1Status
				RollCallString,
			iqudc32GenlockTimingCh2VerticalTiming
				INTEGER,
			iqudc32GenlockTimingCh2HorizontalTiming
				INTEGER,
			iqudc32GenlockTimingCh2Status
				RollCallString,
			iqudc32MenuTimecodeCh1SourceHD
				INTEGER,
			iqudc32MenuTimecodeCh1SourceSD
				INTEGER,
			iqudc32MenuTimecodeCh1Status
				RollCallString,
			iqudc32MenuTimecodeCh1Mode
				INTEGER,
			iqudc32MenuTimecodeCh1OnTimecodeLoss
				INTEGER,
			iqudc32MenuTimecodeCh1TimecodeEntry
				RollCallString,
			iqudc32MenuTimecodeCh1TimecodeLoad
				INTEGER,
			iqudc32MenuTimecodeCh1NondropFrame
				INTEGER,
			iqudc32MenuTimecodeCh1VITCEnable
				INTEGER,
			iqudc32MenuTimecodeCh1OutputLine525
				INTEGER,
			iqudc32MenuTimecodeCh1OutputLine625
				INTEGER,
			iqudc32MenuTimecodeCh1OutputLineStatus
				RollCallString,
			iqudc32MenuTimecodeCh1NewDisplay
				RollCallString,
			iqudc32MenuTimecodeCh2SourceHD
				INTEGER,
			iqudc32MenuTimecodeCh2SourceSD
				INTEGER,
			iqudc32MenuTimecodeCh2Status
				RollCallString,
			iqudc32MenuTimecodeCh2Mode
				INTEGER,
			iqudc32MenuTimecodeCh2OnTimecodeLoss
				INTEGER,
			iqudc32MenuTimecodeCh2TimecodeEntry
				RollCallString,
			iqudc32MenuTimecodeCh2TimecodeLoad
				INTEGER,
			iqudc32MenuTimecodeCh2NondropFrame
				INTEGER,
			iqudc32MenuTimecodeCh2VITCEnable
				INTEGER,
			iqudc32MenuTimecodeCh2OutputLine525
				INTEGER,
			iqudc32MenuTimecodeCh2OutputLine625
				INTEGER,
			iqudc32MenuTimecodeCh2OutputLineStatus
				RollCallString,
			iqudc32MenuTimecodeCh2NewDisplay
				RollCallString,
			iqudc32MetadataCh1ClosedCaptionsInputStatus
				RollCallString,
			iqudc32MetadataCh1ClosedCaptionsCEA608OutputEnab
				INTEGER,
			iqudc32MetadataCh1ClosedCaptionsCEA708OutputEnab
				INTEGER,
			iqudc32MetadataCh1ClosedCaptionsCEA708OutputLine60216
				INTEGER,
			iqudc32MetadataCh1ClosedCaptionsCEA708OutputLine60221
				RollCallString,
			iqudc32MetadataCh1Teletext625CaptionsSource
				INTEGER,
			iqudc32TeletextSDVBISetupWSTOriginLine760400
				INTEGER,
			iqudc32TeletextSDVBISetupWSTOriginLine860401
				INTEGER,
			iqudc32TeletextSDVBISetupWSTOriginLine960402
				INTEGER,
			iqudc32TeletextSDVBISetupWSTOriginLine1060403
				INTEGER,
			iqudc32TeletextSDVBISetupWSTOriginLine1160404
				INTEGER,
			iqudc32TeletextSDVBISetupWSTOriginLine1260405
				INTEGER,
			iqudc32TeletextSDVBISetupWSTOriginLine1360406
				INTEGER,
			iqudc32TeletextSDVBISetupWSTOriginLine1460407
				INTEGER,
			iqudc32TeletextSDVBISetupWSTOriginLine1560408
				INTEGER,
			iqudc32TeletextSDVBISetupWSTOriginLine1660409
				INTEGER,
			iqudc32TeletextSDVBISetupWSTOriginLine1760410
				INTEGER,
			iqudc32TeletextSDVBISetupWSTOriginLine1860411
				INTEGER,
			iqudc32TeletextSDVBISetupWSTOriginLine1960412
				INTEGER,
			iqudc32TeletextSDVBISetupWSTOriginLine2060413
				INTEGER,
			iqudc32TeletextSDVBISetupWSTOriginLine2160414
				INTEGER,
			iqudc32TeletextSDVBISetupWSTOriginLine2260415
				INTEGER,
			iqudc32TeletextSDVBISetupWSTOriginLine7S60416
				RollCallString,
			iqudc32TeletextSDVBISetupWSTOriginLine8S60417
				RollCallString,
			iqudc32TeletextSDVBISetupWSTOriginLine9S60418
				RollCallString,
			iqudc32TeletextSDVBISetupWSTOriginLine1060419
				RollCallString,
			iqudc32TeletextSDVBISetupWSTOriginLine1160420
				RollCallString,
			iqudc32TeletextSDVBISetupWSTOriginLine1260421
				RollCallString,
			iqudc32TeletextSDVBISetupWSTOriginLine1360422
				RollCallString,
			iqudc32TeletextSDVBISetupWSTOriginLine1460423
				RollCallString,
			iqudc32TeletextSDVBISetupWSTOriginLine1560424
				RollCallString,
			iqudc32TeletextSDVBISetupWSTOriginLine1660425
				RollCallString,
			iqudc32TeletextSDVBISetupWSTOriginLine1760426
				RollCallString,
			iqudc32TeletextSDVBISetupWSTOriginLine1860427
				RollCallString,
			iqudc32TeletextSDVBISetupWSTOriginLine1960428
				RollCallString,
			iqudc32TeletextSDVBISetupWSTOriginLine2060429
				RollCallString,
			iqudc32TeletextSDVBISetupWSTOriginLine2160430
				RollCallString,
			iqudc32TeletextSDVBISetupWSTOriginLine2260431
				RollCallString,
			iqudc32TeletextSDVBISetupWSTOPLine7Statu60432
				RollCallString,
			iqudc32TeletextSDVBISetupWSTOPLine8Statu60433
				RollCallString,
			iqudc32TeletextSDVBISetupWSTOPLine9Statu60434
				RollCallString,
			iqudc32TeletextSDVBISetupWSTOPLine10Stat60435
				RollCallString,
			iqudc32TeletextSDVBISetupWSTOPLine11Stat60436
				RollCallString,
			iqudc32TeletextSDVBISetupWSTOPLine12Stat60437
				RollCallString,
			iqudc32TeletextSDVBISetupWSTOPLine13Stat60438
				RollCallString,
			iqudc32TeletextSDVBISetupWSTOPLine14Stat60439
				RollCallString,
			iqudc32TeletextSDVBISetupWSTOPLine15Stat60440
				RollCallString,
			iqudc32TeletextSDVBISetupWSTOPLine16Stat60441
				RollCallString,
			iqudc32TeletextSDVBISetupWSTOPLine17Stat60442
				RollCallString,
			iqudc32TeletextSDVBISetupWSTOPLine18Stat60443
				RollCallString,
			iqudc32TeletextSDVBISetupWSTOPLine19Stat60444
				RollCallString,
			iqudc32TeletextSDVBISetupWSTOPLine20Stat60445
				RollCallString,
			iqudc32TeletextSDVBISetupWSTOPLine21Stat60446
				RollCallString,
			iqudc32TeletextSDVBISetupWSTOPLine22Stat60447
				RollCallString,
			iqudc32TeletextSDVBISetupAllowWSTRemap60466
				INTEGER,
			iqudc32TeletextSDVBISetupWSTOriginLine60467
				INTEGER,
			iqudc32TeletextSDVBISetupWSTOriginLineSta60468
				RollCallString,
			iqudc32TeletextSDVBISetupWSTOutputLine60469
				INTEGER,
			iqudc32TeletextSDVBISetupWSTOutputLineSta60470
				RollCallString,
			iqudc32TeletextSMPTERDD8SMPTERDD82031InputP60448
				INTEGER,
			iqudc32TeletextSMPTERDD8SMPTERDD82031Output60449
				INTEGER,
			iqudc32TeletextSMPTERDD8SMPTERDD82031Output60450
				INTEGER,
			iqudc32TeletextSMPTERDD8RDD8OutputLinePK60451
				INTEGER,
			iqudc32TeletextSMPTERDD8RDD8OutputLinePK60452
				INTEGER,
			iqudc32TeletextSMPTERDD8RDD8OutputLinePK60453
				INTEGER,
			iqudc32TeletextSMPTERDD8RDD8OutputLinePK60454
				RollCallString,
			iqudc32TeletextSMPTERDD8RDD8OutputLinePK60455
				RollCallString,
			iqudc32TeletextSMPTERDD8RDD8OutputLinePK60456
				RollCallString,
			iqudc32TeletextSMPTE20312031DataUnitIDP60457
				INTEGER,
			iqudc32TeletextSMPTE20312031DataUnitIDP60458
				INTEGER,
			iqudc32TeletextSMPTE20312031DataUnitIDP60459
				INTEGER,
			iqudc32TeletextSMPTE20312031DataUnitIDP60460
				INTEGER,
			iqudc32TeletextSMPTE20312031DataUnitIDP60461
				INTEGER,
			iqudc32TeletextSMPTE20312031OutputLineAl60462
				INTEGER,
			iqudc32TeletextSMPTE20312031OutputLineAl60463
				RollCallString,
			iqudc32MetadataCh1TeletextNewDisplay
				RollCallString,
			iqudc32MetadataCh2ClosedCaptionsInputStatus
				RollCallString,
			iqudc32MetadataCh2ClosedCaptionsCEA608OutputEnab
				INTEGER,
			iqudc32MetadataCh2ClosedCaptionsCEA708OutputEnab
				INTEGER,
			iqudc32MetadataCh2ClosedCaptionsCEA708OutputLine60302
				INTEGER,
			iqudc32MetadataCh2ClosedCaptionsCEA708OutputLine60222
				RollCallString,
			iqudc32MetadataCh2Teletext625CaptionsSource
				INTEGER,
			iqudc32TeletextSDVBISetupWSTOriginLine760600
				INTEGER,
			iqudc32TeletextSDVBISetupWSTOriginLine860601
				INTEGER,
			iqudc32TeletextSDVBISetupWSTOriginLine960602
				INTEGER,
			iqudc32TeletextSDVBISetupWSTOriginLine1060603
				INTEGER,
			iqudc32TeletextSDVBISetupWSTOriginLine1160604
				INTEGER,
			iqudc32TeletextSDVBISetupWSTOriginLine1260605
				INTEGER,
			iqudc32TeletextSDVBISetupWSTOriginLine1360606
				INTEGER,
			iqudc32TeletextSDVBISetupWSTOriginLine1460607
				INTEGER,
			iqudc32TeletextSDVBISetupWSTOriginLine1560608
				INTEGER,
			iqudc32TeletextSDVBISetupWSTOriginLine1660609
				INTEGER,
			iqudc32TeletextSDVBISetupWSTOriginLine1760610
				INTEGER,
			iqudc32TeletextSDVBISetupWSTOriginLine1860611
				INTEGER,
			iqudc32TeletextSDVBISetupWSTOriginLine1960612
				INTEGER,
			iqudc32TeletextSDVBISetupWSTOriginLine2060613
				INTEGER,
			iqudc32TeletextSDVBISetupWSTOriginLine2160614
				INTEGER,
			iqudc32TeletextSDVBISetupWSTOriginLine2260615
				INTEGER,
			iqudc32TeletextSDVBISetupWSTOriginLine7S60616
				RollCallString,
			iqudc32TeletextSDVBISetupWSTOriginLine8S60617
				RollCallString,
			iqudc32TeletextSDVBISetupWSTOriginLine9S60618
				RollCallString,
			iqudc32TeletextSDVBISetupWSTOriginLine1060619
				RollCallString,
			iqudc32TeletextSDVBISetupWSTOriginLine1160620
				RollCallString,
			iqudc32TeletextSDVBISetupWSTOriginLine1260621
				RollCallString,
			iqudc32TeletextSDVBISetupWSTOriginLine1360622
				RollCallString,
			iqudc32TeletextSDVBISetupWSTOriginLine1460623
				RollCallString,
			iqudc32TeletextSDVBISetupWSTOriginLine1560624
				RollCallString,
			iqudc32TeletextSDVBISetupWSTOriginLine1660625
				RollCallString,
			iqudc32TeletextSDVBISetupWSTOriginLine1760626
				RollCallString,
			iqudc32TeletextSDVBISetupWSTOriginLine1860627
				RollCallString,
			iqudc32TeletextSDVBISetupWSTOriginLine1960628
				RollCallString,
			iqudc32TeletextSDVBISetupWSTOriginLine2060629
				RollCallString,
			iqudc32TeletextSDVBISetupWSTOriginLine2160630
				RollCallString,
			iqudc32TeletextSDVBISetupWSTOriginLine2260631
				RollCallString,
			iqudc32TeletextSDVBISetupWSTOPLine7Statu60632
				RollCallString,
			iqudc32TeletextSDVBISetupWSTOPLine8Statu60633
				RollCallString,
			iqudc32TeletextSDVBISetupWSTOPLine9Statu60634
				RollCallString,
			iqudc32TeletextSDVBISetupWSTOPLine10Stat60635
				RollCallString,
			iqudc32TeletextSDVBISetupWSTOPLine11Stat60636
				RollCallString,
			iqudc32TeletextSDVBISetupWSTOPLine12Stat60637
				RollCallString,
			iqudc32TeletextSDVBISetupWSTOPLine13Stat60638
				RollCallString,
			iqudc32TeletextSDVBISetupWSTOPLine14Stat60639
				RollCallString,
			iqudc32TeletextSDVBISetupWSTOPLine15Stat60640
				RollCallString,
			iqudc32TeletextSDVBISetupWSTOPLine16Stat60641
				RollCallString,
			iqudc32TeletextSDVBISetupWSTOPLine17Stat60642
				RollCallString,
			iqudc32TeletextSDVBISetupWSTOPLine18Stat60643
				RollCallString,
			iqudc32TeletextSDVBISetupWSTOPLine19Stat60644
				RollCallString,
			iqudc32TeletextSDVBISetupWSTOPLine20Stat60645
				RollCallString,
			iqudc32TeletextSDVBISetupWSTOPLine21Stat60646
				RollCallString,
			iqudc32TeletextSDVBISetupWSTOPLine22Stat60647
				RollCallString,
			iqudc32TeletextSDVBISetupAllowWSTRemap60666
				INTEGER,
			iqudc32TeletextSDVBISetupWSTOriginLine60667
				INTEGER,
			iqudc32TeletextSDVBISetupWSTOriginLineSta60668
				RollCallString,
			iqudc32TeletextSDVBISetupWSTOutputLine60669
				INTEGER,
			iqudc32TeletextSDVBISetupWSTOutputLineSta60670
				RollCallString,
			iqudc32TeletextSMPTERDD8SMPTERDD82031InputP60648
				INTEGER,
			iqudc32TeletextSMPTERDD8SMPTERDD82031Output60649
				INTEGER,
			iqudc32TeletextSMPTERDD8SMPTERDD82031Output60650
				INTEGER,
			iqudc32TeletextSMPTERDD8RDD8OutputLinePK60651
				INTEGER,
			iqudc32TeletextSMPTERDD8RDD8OutputLinePK60652
				INTEGER,
			iqudc32TeletextSMPTERDD8RDD8OutputLinePK60653
				INTEGER,
			iqudc32TeletextSMPTERDD8RDD8OutputLinePK60654
				RollCallString,
			iqudc32TeletextSMPTERDD8RDD8OutputLinePK60655
				RollCallString,
			iqudc32TeletextSMPTERDD8RDD8OutputLinePK60656
				RollCallString,
			iqudc32TeletextSMPTE20312031DataUnitIDP60657
				INTEGER,
			iqudc32TeletextSMPTE20312031DataUnitIDP60658
				INTEGER,
			iqudc32TeletextSMPTE20312031DataUnitIDP60659
				INTEGER,
			iqudc32TeletextSMPTE20312031DataUnitIDP60660
				INTEGER,
			iqudc32TeletextSMPTE20312031DataUnitIDP60661
				INTEGER,
			iqudc32TeletextSMPTE20312031OutputLineAl60662
				INTEGER,
			iqudc32TeletextSMPTE20312031OutputLineAl60663
				RollCallString,
			iqudc32MetadataCh2TeletextNewDisplay
				RollCallString,
			iqudc32AncillaryBridgeChAncDataStoresIPBlock1DID60472
				INTEGER,
			iqudc32AncillaryBridgeChAncDataStoresIPBlock1SDID60473
				INTEGER,
			iqudc32AncillaryBridgeChAncDataStoresIPBlock2DID60474
				INTEGER,
			iqudc32AncillaryBridgeChAncDataStoresIPBlock2SDID60475
				INTEGER,
			iqudc32AncillaryBridgeChAncDataStoresIPBlock3DID60476
				INTEGER,
			iqudc32AncillaryBridgeChAncDataStoresIPBlock3SDID60477
				INTEGER,
			iqudc32AncillaryBridgeChAncDataStoresIPBlock4DID60478
				INTEGER,
			iqudc32AncillaryBridgeChAncDataStoresIPBlock4SDID60479
				INTEGER,
			iqudc32AncillaryBridgeChAncDataStoresIPBlock5DID60480
				INTEGER,
			iqudc32AncillaryBridgeChAncDataStoresIPBlock5SDID60481
				INTEGER,
			iqudc32AncillaryBridgeChAncDataStoresIPBlock6DID60482
				INTEGER,
			iqudc32AncillaryBridgeChAncDataStoresIPBlock6SDID60483
				INTEGER,
			iqudc32AncillaryBridgeChAncDataStoresIPBlock7DID60484
				INTEGER,
			iqudc32AncillaryBridgeChAncDataStoresIPBlock7SDID60485
				INTEGER,
			iqudc32AncillaryBridgeChAncDataStoresDetBlock1HANCVANC60486
				RollCallString,
			iqudc32AncillaryBridgeChAncDataStoresDetBlock1Line60487
				RollCallString,
			iqudc32AncillaryBridgeChAncDataStoresDetBlock1Status60488
				RollCallString,
			iqudc32AncillaryBridgeChAncDataStoresDetBLOCK2HANCVANC60489
				RollCallString,
			iqudc32AncillaryBridgeChAncDataStoresDetBLOCK2Line60490
				RollCallString,
			iqudc32AncillaryBridgeChAncDataStoresDetBLOCK2Status60491
				RollCallString,
			iqudc32AncillaryBridgeChAncDataStoresDetBlock3HANCVANC60492
				RollCallString,
			iqudc32AncillaryBridgeChAncDataStoresDetBlock3Line60493
				RollCallString,
			iqudc32AncillaryBridgeChAncDataStoresDetBlock3Status60494
				RollCallString,
			iqudc32AncillaryBridgeChAncDataStoresDetBlock4HANCVANC60495
				RollCallString,
			iqudc32AncillaryBridgeChAncDataStoresDetBlock4Status60497
				RollCallString,
			iqudc32AncillaryBridgeChAncDataStoresDetBlock5HANCVANC60498
				RollCallString,
			iqudc32AncillaryBridgeChAncDataStoresDetBlock5Status60500
				RollCallString,
			iqudc32AncillaryBridgeChAncDataStoresDetBlock6HANCVANC60501
				RollCallString,
			iqudc32AncillaryBridgeChAncDataStoresDetBlock6Status60503
				RollCallString,
			iqudc32AncillaryBridgeChAncDataStoresDetBlock7HANCVANC60504
				RollCallString,
			iqudc32AncillaryBridgeChAncDataStoresDetBlock7Status60506
				RollCallString,
			iqudc32AncillaryBridgeChAncDataStoresOPBlock1OPEnable60507
				INTEGER,
			iqudc32AncillaryBridgeChAncDataStoresOPBlock1OPLine60508
				INTEGER,
			iqudc32AncillaryBridgeChAncDataStoresOPBlock2OPEnable60509
				INTEGER,
			iqudc32AncillaryBridgeChAncDataStoresOPBlock2OPLine60510
				INTEGER,
			iqudc32AncillaryBridgeChAncDataStoresOPBlock3OPEnable60511
				INTEGER,
			iqudc32AncillaryBridgeChAncDataStoresOPBlock3OPLine60512
				INTEGER,
			iqudc32AncillaryBridgeChAncDataStoresOPBlock4OPEnable60513
				INTEGER,
			iqudc32AncillaryBridgeChAncDataStoresOPBlock4OPLine60514
				INTEGER,
			iqudc32AncillaryBridgeChAncDataStoresOPBlock5OPEnable60515
				INTEGER,
			iqudc32AncillaryBridgeChAncDataStoresOPBlock5OPLine60516
				INTEGER,
			iqudc32AncillaryBridgeChAncDataStoresOPBlock6OPEnable60517
				INTEGER,
			iqudc32AncillaryBridgeChAncDataStoresOPBlock6OPLine60518
				INTEGER,
			iqudc32AncillaryBridgeChAncDataStoresOPBlock7OPEnable60519
				INTEGER,
			iqudc32AncillaryBridgeChAncDataStoresOPBlock7OPLine60520
				INTEGER,
			iqudc32MetadataCh2AncillaryBridgeChNewDisplay44468
				RollCallString,
			iqudc32AncillaryBridgeChAncDataStoresIPBlock1DID60672
				INTEGER,
			iqudc32AncillaryBridgeChAncDataStoresIPBlock1SDID60673
				INTEGER,
			iqudc32AncillaryBridgeChAncDataStoresIPBlock2DID60674
				INTEGER,
			iqudc32AncillaryBridgeChAncDataStoresIPBlock2SDID60675
				INTEGER,
			iqudc32AncillaryBridgeChAncDataStoresIPBlock3DID60676
				INTEGER,
			iqudc32AncillaryBridgeChAncDataStoresIPBlock3SDID60677
				INTEGER,
			iqudc32AncillaryBridgeChAncDataStoresIPBlock4DID60678
				INTEGER,
			iqudc32AncillaryBridgeChAncDataStoresIPBlock4SDID60679
				INTEGER,
			iqudc32AncillaryBridgeChAncDataStoresIPBlock5DID60680
				INTEGER,
			iqudc32AncillaryBridgeChAncDataStoresIPBlock5SDID60681
				INTEGER,
			iqudc32AncillaryBridgeChAncDataStoresIPBlock6DID60682
				INTEGER,
			iqudc32AncillaryBridgeChAncDataStoresIPBlock6SDID60683
				INTEGER,
			iqudc32AncillaryBridgeChAncDataStoresIPBlock7DID60684
				INTEGER,
			iqudc32AncillaryBridgeChAncDataStoresIPBlock7SDID60685
				INTEGER,
			iqudc32AncillaryBridgeChAncDataStoresDetBlock1HANCVANC60686
				RollCallString,
			iqudc32AncillaryBridgeChAncDataStoresDetBlock1Line60687
				RollCallString,
			iqudc32AncillaryBridgeChAncDataStoresDetBlock1Status60688
				RollCallString,
			iqudc32AncillaryBridgeChAncDataStoresDetBLOCK2HANCVANC60689
				RollCallString,
			iqudc32AncillaryBridgeChAncDataStoresDetBLOCK2Line60690
				RollCallString,
			iqudc32AncillaryBridgeChAncDataStoresDetBLOCK2Status60691
				RollCallString,
			iqudc32AncillaryBridgeChAncDataStoresDetBlock3HANCVANC60692
				RollCallString,
			iqudc32AncillaryBridgeChAncDataStoresDetBlock3Line60693
				RollCallString,
			iqudc32AncillaryBridgeChAncDataStoresDetBlock3Status60694
				RollCallString,
			iqudc32AncillaryBridgeChAncDataStoresDetBlock4HANCVANC60695
				RollCallString,
			iqudc32AncillaryBridgeChAncDataStoresDetBlock4Status60697
				RollCallString,
			iqudc32AncillaryBridgeChAncDataStoresDetBlock5HANCVANC60698
				RollCallString,
			iqudc32AncillaryBridgeChAncDataStoresDetBlock5Status60700
				RollCallString,
			iqudc32AncillaryBridgeChAncDataStoresDetBlock6HANCVANC60701
				RollCallString,
			iqudc32AncillaryBridgeChAncDataStoresDetBlock6Status60703
				RollCallString,
			iqudc32AncillaryBridgeChAncDataStoresDetBlock7HANCVANC60704
				RollCallString,
			iqudc32AncillaryBridgeChAncDataStoresDetBlock7Status60706
				RollCallString,
			iqudc32AncillaryBridgeChAncDataStoresOPBlock1OPEnable60707
				INTEGER,
			iqudc32AncillaryBridgeChAncDataStoresOPBlock1OPLine60708
				INTEGER,
			iqudc32AncillaryBridgeChAncDataStoresOPBlock2OPEnable60709
				INTEGER,
			iqudc32AncillaryBridgeChAncDataStoresOPBlock2OPLine60710
				INTEGER,
			iqudc32AncillaryBridgeChAncDataStoresOPBlock3OPEnable60711
				INTEGER,
			iqudc32AncillaryBridgeChAncDataStoresOPBlock3OPLine60712
				INTEGER,
			iqudc32AncillaryBridgeChAncDataStoresOPBlock4OPEnable60713
				INTEGER,
			iqudc32AncillaryBridgeChAncDataStoresOPBlock4OPLine60714
				INTEGER,
			iqudc32AncillaryBridgeChAncDataStoresOPBlock5OPEnable60715
				INTEGER,
			iqudc32AncillaryBridgeChAncDataStoresOPBlock5OPLine60716
				INTEGER,
			iqudc32AncillaryBridgeChAncDataStoresOPBlock6OPEnable60717
				INTEGER,
			iqudc32AncillaryBridgeChAncDataStoresOPBlock6OPLine60718
				INTEGER,
			iqudc32AncillaryBridgeChAncDataStoresOPBlock7OPEnable60719
				INTEGER,
			iqudc32AncillaryBridgeChAncDataStoresOPBlock7OPLine60720
				INTEGER,
			iqudc32MetadataCh2AncillaryBridgeChNewDisplay44469
				RollCallString,
			iqudc32GPIOGPI1GPIO1Mode
				INTEGER,
			iqudc32MetadataCh2GPIOGPI1ipSelect
				INTEGER,
			iqudc32MetadataCh2GPIOGPO1opSelect
				INTEGER,
			iqudc32GPIOGPI2GPIO2Mode
				INTEGER,
			iqudc32MetadataCh2GPIOGPI2ipSelect
				INTEGER,
			iqudc32MetadataCh2GPIOGPO2opSelect
				INTEGER,
			iqudc32MetadataCh2GPIONewDisplay
				RollCallString,
			iqudc32MetadataCh2RollCallUnitName
				RollCallString,
			iqudc32MetadataCh2RollCallIPSharePort
				INTEGER,
			iqudc32MetadataCh2RollCallIPBridgingPort
				INTEGER,
			iqudc32MetadataCh2MemoriesRecallMemory
				INTEGER,
			iqudc32MetadataCh2MemoriesSelMemory
				INTEGER,
			iqudc32MetadataCh2MemoriesSaveMemory
				INTEGER,
			iqudc32MetadataCh2MemoriesClearMemory
				INTEGER,
			iqudc32MemoriesMemoryNameChangeName
				RollCallString,
			iqudc32MetadataCh2MemoriesLastDisplayMemory
				RollCallString,
			iqudc32MetadataCh2RollTrackDisableAll
				INTEGER,
			iqudc32MetadataCh2RollTrackIndex
				INTEGER,
			iqudc32MetadataCh2RollTrackSource
				INTEGER,
			iqudc32MetadataCh2RollTrackAddress
				RollCallString,
			iqudc32MetadataCh2RollTrackCommand
				RollCallString,
			iqudc32MetadataCh2RollTrackStatus
				RollCallString,
			iqudc32MetadataCh2RollTrackSending
				RollCallString,
			iqudc32MetadataCh2MiscLoggingSerialNumberEnabl
				INTEGER,
			iqudc32MetadataCh2MiscLoggingSerialNumberStatu
				RollCallString,
			iqudc32MetadataCh2MiscLoggingUpTimeEnable
				INTEGER,
			iqudc32MetadataCh2MiscLoggingUpTimeStatus
				RollCallString,
			iqudc32MetadataCh2MiscLoggingPowerUsageStateE
				INTEGER,
			iqudc32MetadataCh2MiscLoggingPowerUsageStateS
				RollCallString,
			iqudc32MetadataCh2MiscLoggingBuild62011
				INTEGER,
			iqudc32MetadataCh2MiscLoggingBuild62010
				RollCallString,
			iqudc32MetadataCh2MiscLoggingAESOutput14Place
				RollCallString,
			iqudc32MetadataCh2MiscLoggingAESOutput58Place
				RollCallString,
			iqudc32MetadataCh2MiscLoggingInputADCPlacehold
				RollCallString,
			iqudc32MetadataCh2MiscLoggingSourceCh1Ch2Pl
				RollCallString,
			iqudc32MetadataCh2MiscLoggingCVBSDecoderPlaceh
				RollCallString,
			iqudc32MetadataCh2MiscLoggingFanSpeedPlacehold
				RollCallString,
			iqudc32MetadataCh2VideoInputLoggingInput1Type62100
				INTEGER,
			iqudc32MetadataCh2VideoInputLoggingInput1Type62101
				RollCallString,
			iqudc32MetadataCh2VideoInputLoggingInput1State62102
				INTEGER,
			iqudc32MetadataCh2VideoInputLoggingInput1State62103
				RollCallString,
			iqudc32MetadataCh2VideoInputLoggingInput1Std62104
				INTEGER,
			iqudc32MetadataCh2VideoInputLoggingInput1Std62105
				RollCallString,
			iqudc32MetadataCh2VideoInputLoggingInput2Type62200
				INTEGER,
			iqudc32MetadataCh2VideoInputLoggingInput2Type62201
				RollCallString,
			iqudc32MetadataCh2VideoInputLoggingInput2State62202
				INTEGER,
			iqudc32MetadataCh2VideoInputLoggingInput2State62203
				RollCallString,
			iqudc32MetadataCh2VideoInputLoggingInput2Std62204
				INTEGER,
			iqudc32MetadataCh2VideoInputLoggingInput2Std62205
				RollCallString,
			iqudc32MetadataCh2VideoInputLoggingInput3Type62300
				INTEGER,
			iqudc32MetadataCh2VideoInputLoggingInput3Type62301
				RollCallString,
			iqudc32MetadataCh2VideoInputLoggingInput3State62302
				INTEGER,
			iqudc32MetadataCh2VideoInputLoggingInput3State62303
				RollCallString,
			iqudc32MetadataCh2VideoInputLoggingInput3Std62304
				INTEGER,
			iqudc32MetadataCh2VideoInputLoggingInput3Std62305
				RollCallString,
			iqudc32MetadataCh2VideoInputLoggingInput4Type62400
				INTEGER,
			iqudc32MetadataCh2VideoInputLoggingInput4Type62401
				RollCallString,
			iqudc32MetadataCh2VideoInputLoggingInput4State62402
				INTEGER,
			iqudc32MetadataCh2VideoInputLoggingInput4State62403
				RollCallString,
			iqudc32MetadataCh2VideoInputLoggingInput4Std62404
				INTEGER,
			iqudc32MetadataCh2VideoInputLoggingInput4Std62405
				RollCallString,
			iqudc32MetadataCh2VideoInputLoggingInput5Type62500
				INTEGER,
			iqudc32MetadataCh2VideoInputLoggingInput5Type62501
				RollCallString,
			iqudc32MetadataCh2VideoInputLoggingInput5State62502
				INTEGER,
			iqudc32MetadataCh2VideoInputLoggingInput5State62503
				RollCallString,
			iqudc32MetadataCh2VideoInputLoggingInput5Std62504
				INTEGER,
			iqudc32MetadataCh2VideoInputLoggingInput5Std62505
				RollCallString,
			iqudc32MetadataCh2OutputLoggingOutput1Type62600
				INTEGER,
			iqudc32MetadataCh2OutputLoggingOutput1Type62601
				RollCallString,
			iqudc32MetadataCh2OutputLoggingOutput1State62602
				INTEGER,
			iqudc32MetadataCh2OutputLoggingOutput1State62603
				RollCallString,
			iqudc32MetadataCh2OutputLoggingOutput1Std62604
				INTEGER,
			iqudc32MetadataCh2OutputLoggingOutput1Std62605
				RollCallString,
			iqudc32MetadataCh2OutputLoggingOutput2Type62612
				INTEGER,
			iqudc32MetadataCh2OutputLoggingOutput2Type62613
				RollCallString,
			iqudc32MetadataCh2OutputLoggingOutput2State62614
				INTEGER,
			iqudc32MetadataCh2OutputLoggingOutput2State62615
				RollCallString,
			iqudc32MetadataCh2OutputLoggingOutput2Std62616
				INTEGER,
			iqudc32MetadataCh2OutputLoggingOutput2Std62617
				RollCallString,
			iqudc32MetadataCh2OPAudioStateCh1OutputEmbPair1s62620
				INTEGER,
			iqudc32MetadataCh2OPAudioStateCh1OutputEmbPair1s62621
				RollCallString,
			iqudc32MetadataCh2OPAudioStateCh1OutputEmbPair2s62622
				INTEGER,
			iqudc32MetadataCh2OPAudioStateCh1OutputEmbPair2s62623
				RollCallString,
			iqudc32MetadataCh2OPAudioStateCh1OutputEmbPair3s62624
				INTEGER,
			iqudc32MetadataCh2OPAudioStateCh1OutputEmbPair3s62625
				RollCallString,
			iqudc32MetadataCh2OPAudioStateCh1OutputEmbPair4s62626
				INTEGER,
			iqudc32MetadataCh2OPAudioStateCh1OutputEmbPair4s62627
				RollCallString,
			iqudc32MetadataCh2OPAudioStateCh1OutputEmbPair5s62628
				INTEGER,
			iqudc32MetadataCh2OPAudioStateCh1OutputEmbPair5s62629
				RollCallString,
			iqudc32MetadataCh2OPAudioStateCh1OutputEmbPair6s62630
				INTEGER,
			iqudc32MetadataCh2OPAudioStateCh1OutputEmbPair6s62631
				RollCallString,
			iqudc32MetadataCh2OPAudioStateCh1OutputEmbPair7s62632
				INTEGER,
			iqudc32MetadataCh2OPAudioStateCh1OutputEmbPair7s62633
				RollCallString,
			iqudc32MetadataCh2OPAudioStateCh1OutputEmbPair8s62634
				INTEGER,
			iqudc32MetadataCh2OPAudioStateCh1OutputEmbPair8s62635
				RollCallString,
			iqudc32MetadataCh2OPAudioStateCh2OutputEmbPair1s62636
				INTEGER,
			iqudc32MetadataCh2OPAudioStateCh2OutputEmbPair1s62637
				RollCallString,
			iqudc32MetadataCh2OPAudioStateCh2OutputEmbPair2s62638
				INTEGER,
			iqudc32MetadataCh2OPAudioStateCh2OutputEmbPair2s62639
				RollCallString,
			iqudc32MetadataCh2OPAudioStateCh2OutputEmbPair3s62640
				INTEGER,
			iqudc32MetadataCh2OPAudioStateCh2OutputEmbPair3s62641
				RollCallString,
			iqudc32MetadataCh2OPAudioStateCh2OutputEmbPair4s62642
				INTEGER,
			iqudc32MetadataCh2OPAudioStateCh2OutputEmbPair4s62643
				RollCallString,
			iqudc32MetadataCh2OPAudioStateCh2OutputEmbPair5s62644
				INTEGER,
			iqudc32MetadataCh2OPAudioStateCh2OutputEmbPair5s62645
				RollCallString,
			iqudc32MetadataCh2OPAudioStateCh2OutputEmbPair6s62646
				INTEGER,
			iqudc32MetadataCh2OPAudioStateCh2OutputEmbPair6s62647
				RollCallString,
			iqudc32MetadataCh2OPAudioStateCh2OutputEmbPair7s62648
				INTEGER,
			iqudc32MetadataCh2OPAudioStateCh2OutputEmbPair7s62649
				RollCallString,
			iqudc32MetadataCh2OPAudioStateCh2OutputEmbPair8s62650
				INTEGER,
			iqudc32MetadataCh2OPAudioStateCh2OutputEmbPair8s62651
				RollCallString,
			iqudc32MetadataCh2OPAudioStateCh2NewDisplay
				RollCallString,
			iqudc32MetadataCh2OPAudioTypeCh1OutputEmbPair1t62653
				INTEGER,
			iqudc32MetadataCh2OPAudioTypeCh1OutputEmbPair1t62654
				RollCallString,
			iqudc32MetadataCh2OPAudioTypeCh1OutputEmbPair2t
				INTEGER,
			iqudc32MetadataCh2OPAudioTypeCh1OutputEmbPair2s
				RollCallString,
			iqudc32MetadataCh2OPAudioTypeCh1OutputEmbPair3t62657
				INTEGER,
			iqudc32MetadataCh2OPAudioTypeCh1OutputEmbPair3t62658
				RollCallString,
			iqudc32MetadataCh2OPAudioTypeCh1OutputEmbPair4t62659
				INTEGER,
			iqudc32MetadataCh2OPAudioTypeCh1OutputEmbPair4t62660
				RollCallString,
			iqudc32MetadataCh2OPAudioTypeCh1OutputEmbPair5t62661
				INTEGER,
			iqudc32MetadataCh2OPAudioTypeCh1OutputEmbPair5t62662
				RollCallString,
			iqudc32MetadataCh2OPAudioTypeCh1OutputEmbPair6t62663
				INTEGER,
			iqudc32MetadataCh2OPAudioTypeCh1OutputEmbPair6t62664
				RollCallString,
			iqudc32MetadataCh2OPAudioTypeCh1OutputEmbPair7t62665
				INTEGER,
			iqudc32MetadataCh2OPAudioTypeCh1OutputEmbPair7t62666
				RollCallString,
			iqudc32MetadataCh2OPAudioTypeCh1OutputEmbPair8t62667
				INTEGER,
			iqudc32MetadataCh2OPAudioTypeCh1OutputEmbPair8t62668
				RollCallString,
			iqudc32MetadataCh2OPAudioTypeCh2OutputEmbPair1t62669
				INTEGER,
			iqudc32MetadataCh2OPAudioTypeCh2OutputEmbPair1t62670
				RollCallString,
			iqudc32MetadataCh2OPAudioTypeCh2OutputEmbPair2t62671
				INTEGER,
			iqudc32MetadataCh2OPAudioTypeCh2OutputEmbPair2t62672
				RollCallString,
			iqudc32MetadataCh2OPAudioTypeCh2OutputEmbPair3t62673
				INTEGER,
			iqudc32MetadataCh2OPAudioTypeCh2OutputEmbPair3t62674
				RollCallString,
			iqudc32MetadataCh2OPAudioTypeCh2OutputEmbPair4t62675
				INTEGER,
			iqudc32MetadataCh2OPAudioTypeCh2OutputEmbPair4t62676
				RollCallString,
			iqudc32MetadataCh2OPAudioTypeCh2OutputEmbPair5t62677
				INTEGER,
			iqudc32MetadataCh2OPAudioTypeCh2OutputEmbPair5t62678
				RollCallString,
			iqudc32MetadataCh2OPAudioTypeCh2OutputEmbPair6t62679
				INTEGER,
			iqudc32MetadataCh2OPAudioTypeCh2OutputEmbPair6t62680
				RollCallString,
			iqudc32MetadataCh2OPAudioTypeCh2OutputEmbPair7t62681
				INTEGER,
			iqudc32MetadataCh2OPAudioTypeCh2OutputEmbPair7t62682
				RollCallString,
			iqudc32MetadataCh2OPAudioTypeCh2OutputEmbPair8t62683
				INTEGER,
			iqudc32MetadataCh2OPAudioTypeCh2OutputEmbPair8t62684
				RollCallString,
			iqudc32MetadataCh2OPAudioTypeCh2NewDisplay
				RollCallString,
			iqudc32MetadataCh2SetupSoftwareVersion
				RollCallString,
			iqudc32MetadataCh2SetupSerialNumber
				RollCallString,
			iqudc32MetadataCh2SetupNumberOfChannels
				RollCallString,
			iqudc32MetadataCh2SetupFrameSlotNumber
				RollCallString,
			iqudc32MetadataCh2SetupRearId
				RollCallString,
			iqudc32MetadataCh2SetupFanSpeed
				RollCallString,
			iqudc32MetadataCh2SetupIQOPTMNR
				RollCallString,
			iqudc32MetadataCh2SetupIQOPTMSBK
				RollCallString,
			iqudc32MetadataCh2SetupIQOPTMLFR
				RollCallString,
			iqudc32MetadataCh2SetupIQOPTMLOG
				RollCallString,
			iqudc32MetadataCh2SetupIQOPTMLC
				RollCallString,
			iqudc32MetadataCh2SetupIQOPTMDBD
				RollCallString,
			iqudc32MetadataCh2SetupIQOPTMDBEE
				RollCallString,
			iqudc32MetadataCh2SetupIQOPTMDBED
				RollCallString,
			iqudc32MetadataCh2SetupIQOPTMLOUDJ
				RollCallString,
			iqudc32MetadataCh2SetupIQOPTMLOUDMC
				RollCallString,
			iqudc32MetadataCh2SetupBuild
				RollCallString,
			iqudc32MetadataCh2SetupLicencedOptionsH
				RollCallString,
			iqudc32MetadataCh2SetupFactoryDefaults
				INTEGER,
			iqudc32MetadataCh2SetupDefaultSettings
				INTEGER,
			iqudc32MetadataCh2SetupRestart
				INTEGER,
			iqudc32MetadataCh2SetupUpgradeStartHide
				INTEGER,
			iqudc32MetadataCh2SetupUpgradeFinishHid
				INTEGER,
			iqudc32MetadataCh2Displaymenu
				INTEGER,
			iqudc32MetadataCh2PlaceholderCh1ScrollingCaptionG
				RollCallString,
			iqudc32MetadataCh2PlaceholderCh1SFPOutputRouting
				RollCallString,
			iqudc32MetadataCh2PlaceholderCh1CVBSEncoderPlaceh
				RollCallString,
			iqudc32MetadataCh2PlaceholderCh1LogoControlPlaceh
				RollCallString,
			iqudc32MetadataCh2PlaceholderCh1NonlinearEnhancer
				RollCallString,
			iqudc32MetadataCh2PlaceholderCh1ConversionAperture
				RollCallString,
			iqudc32MetadataCh2PlaceholderCh1NoiseReducerPlace
				RollCallString,
			iqudc32MetadataCh2PlaceholderCh1UpConversionPlace
				RollCallString,
			iqudc32MetadataCh2PlaceholderCh1GenlockTimingPlac
				RollCallString,
			iqudc32MetadataCh2PlaceholderCh1SMPTERDD8Placehol
				RollCallString,
			iqudc32MetadataCh2PlaceholderCh1SMPTE2031Placehol
				RollCallString,
			iqudc32MetadataCh2PlaceholderCh2InputSourcePlaceh
				RollCallString,
			iqudc32MetadataCh2PlaceholderCh2ScrollingCaptionG
				RollCallString,
			iqudc32MetadataCh2PlaceholderCh2SFPOutputRouting
				RollCallString,
			iqudc32MetadataCh2PlaceholderCh2CVBSEncoderPlaceh
				RollCallString,
			iqudc32MetadataCh2PlaceholderCh2LogoControlPlaceh
				RollCallString,
			iqudc32MetadataCh2PlaceholderCh2NonlinearEnhancer
				RollCallString,
			iqudc32MetadataCh2PlaceholderCh2ConversionAperture
				RollCallString,
			iqudc32MetadataCh2PlaceholderCh2NoiseReducerPlace
				RollCallString,
			iqudc32MetadataCh2PlaceholderCh2UpConversionPlace
				RollCallString,
			iqudc32MetadataCh2PlaceholderCh2GenlockTimingPlac
				RollCallString,
			iqudc32MetadataCh2PlaceholderCh2SMPTERDD8Placehol
				RollCallString,
			iqudc32MetadataCh2PlaceholderCh2SMPTE2031Placehol
				RollCallString
		}

	iqudc32SlotIndex OBJECT-TYPE
		SYNTAX		Unsigned32
		MAX-ACCESS		not-accessible
		STATUS			current
		DESCRIPTION
				"The unique Index value for each slot.  Its value
					ranges between 1 and the value of slotNumber."
		::= { iqudc32CmdEntry 0 }


	iqudc32InputInputSourceCh1InputSelect OBJECT-TYPE
		SYNTAX		INTEGER {
							val-SDI-1(0),
							val-SDI-2(1),
							val-CVBS(2),
							val-SFP-1(3),
							val-SFP-2(4)
							}
		MAX-ACCESS		read-write
		STATUS			current
		DESCRIPTION
				"TYPE: - RadiobuttonList
				 PAGE: - Input- Input Source Ch 1
					Input Select  cmdID= 10006 
					SDI 1  value= 0  
					SDI 2  value= 1  
					CVBS  value= 2  
					SFP 1  value= 3  
					SFP 2  value= 4  "
		::= { iqudc32CmdEntry 10006 }


	iqudc32InputSourceCh1StatusSDI1 OBJECT-TYPE
		SYNTAX		RollCallString
		MAX-ACCESS		read-only
		STATUS			current
		DESCRIPTION
				"TYPE: - Display
				 PAGE: - Input- Input Source Ch 1
					SDI 1  cmdID= 63000  format=   "
		::= { iqudc32CmdEntry 63000 }


	iqudc32InputSourceCh1StatusSDI2 OBJECT-TYPE
		SYNTAX		RollCallString
		MAX-ACCESS		read-only
		STATUS			current
		DESCRIPTION
				"TYPE: - Display
				 PAGE: - Input- Input Source Ch 1
					SDI 2  cmdID= 63001  format=   "
		::= { iqudc32CmdEntry 63001 }


	iqudc32InputSourceCh1StatusCVBS OBJECT-TYPE
		SYNTAX		RollCallString
		MAX-ACCESS		read-only
		STATUS			current
		DESCRIPTION
				"TYPE: - Display
				 PAGE: - Input- Input Source Ch 1
					CVBS  cmdID= 63004  format=   "
		::= { iqudc32CmdEntry 63004 }


	iqudc32InputSourceCh1StatusSFP1 OBJECT-TYPE
		SYNTAX		RollCallString
		MAX-ACCESS		read-only
		STATUS			current
		DESCRIPTION
				"TYPE: - Display
				 PAGE: - Input- Input Source Ch 1
					SFP 1  cmdID= 63008  format=   "
		::= { iqudc32CmdEntry 63008 }


	iqudc32InputSourceCh1StatusSFP2 OBJECT-TYPE
		SYNTAX		RollCallString
		MAX-ACCESS		read-only
		STATUS			current
		DESCRIPTION
				"TYPE: - Display
				 PAGE: - Input- Input Source Ch 1
					SFP 2  cmdID= 63009  format=   "
		::= { iqudc32CmdEntry 63009 }


	iqudc32InputSourceCh1StatusCurrentInputStand OBJECT-TYPE
		SYNTAX		RollCallString
		MAX-ACCESS		read-only
		STATUS			current
		DESCRIPTION
				"TYPE: - Display
				 PAGE: - Input- Input Source Ch 1
					Current Input Stand  cmdID= 64010  format=   "
		::= { iqudc32CmdEntry 64010 }


	iqudc32InputInputSourceCh2InputSelect OBJECT-TYPE
		SYNTAX		INTEGER {
							val-SDI-1(0),
							val-SDI-2(1),
							val-CVBS(2),
							val-SFP-1(3),
							val-SFP-2(4)
							}
		MAX-ACCESS		read-write
		STATUS			current
		DESCRIPTION
				"TYPE: - RadiobuttonList
				 PAGE: - Input- Input Source Ch 2
					Input Select  cmdID= 10106 
					SDI 1  value= 0  
					SDI 2  value= 1  
					CVBS  value= 2  
					SFP 1  value= 3  
					SFP 2  value= 4  "
		::= { iqudc32CmdEntry 10106 }


	iqudc32InputSourceCh2StatusSDI1 OBJECT-TYPE
		SYNTAX		RollCallString
		MAX-ACCESS		read-only
		STATUS			current
		DESCRIPTION
				"TYPE: - Display
				 PAGE: - Input- Input Source Ch 2
					SDI 1  cmdID= 63100  format=   "
		::= { iqudc32CmdEntry 63100 }


	iqudc32InputSourceCh2StatusSDI2 OBJECT-TYPE
		SYNTAX		RollCallString
		MAX-ACCESS		read-only
		STATUS			current
		DESCRIPTION
				"TYPE: - Display
				 PAGE: - Input- Input Source Ch 2
					SDI 2  cmdID= 63101  format=   "
		::= { iqudc32CmdEntry 63101 }


	iqudc32InputSourceCh2StatusCVBS OBJECT-TYPE
		SYNTAX		RollCallString
		MAX-ACCESS		read-only
		STATUS			current
		DESCRIPTION
				"TYPE: - Display
				 PAGE: - Input- Input Source Ch 2
					CVBS  cmdID= 63104  format=   "
		::= { iqudc32CmdEntry 63104 }


	iqudc32InputSourceCh2StatusSFP1 OBJECT-TYPE
		SYNTAX		RollCallString
		MAX-ACCESS		read-only
		STATUS			current
		DESCRIPTION
				"TYPE: - Display
				 PAGE: - Input- Input Source Ch 2
					SFP 1  cmdID= 63108  format=   "
		::= { iqudc32CmdEntry 63108 }


	iqudc32InputSourceCh2StatusSFP2 OBJECT-TYPE
		SYNTAX		RollCallString
		MAX-ACCESS		read-only
		STATUS			current
		DESCRIPTION
				"TYPE: - Display
				 PAGE: - Input- Input Source Ch 2
					SFP 2  cmdID= 63109  format=   "
		::= { iqudc32CmdEntry 63109 }


	iqudc32InputSourceCh2StatusCurrentInputStand OBJECT-TYPE
		SYNTAX		RollCallString
		MAX-ACCESS		read-only
		STATUS			current
		DESCRIPTION
				"TYPE: - Display
				 PAGE: - Input- Input Source Ch 2
					Current Input Stand  cmdID= 64110  format=   "
		::= { iqudc32CmdEntry 64110 }


	iqudc32CVBSDecoderSetupACC OBJECT-TYPE
		SYNTAX		INTEGER { disable(0), enable(1) }
		MAX-ACCESS		read-write
		STATUS			current
		DESCRIPTION
				"TYPE: - Checkbox
				 PAGE: - Input- CVBS Decoder
					ACC  cmdID= 20501 "
		::= { iqudc32CmdEntry 20501 }


	iqudc32CVBSDecoderSetupCTI OBJECT-TYPE
		SYNTAX		INTEGER { disable(0), enable(1) }
		MAX-ACCESS		read-write
		STATUS			current
		DESCRIPTION
				"TYPE: - Checkbox
				 PAGE: - Input- CVBS Decoder
					CTI  cmdID= 20502 "
		::= { iqudc32CmdEntry 20502 }


	iqudc32CVBSDecoderSetupPedestal OBJECT-TYPE
		SYNTAX		INTEGER {
							val-Off(0),
							val-On(1)
							}
		MAX-ACCESS		read-write
		STATUS			current
		DESCRIPTION
				"TYPE: - RadiobuttonList
				 PAGE: - Input- CVBS Decoder
					Pedestal  cmdID= 20503 
					Off  value= 0  
					On  value= 1  "
		::= { iqudc32CmdEntry 20503 }


	iqudc32InputCVBSDecoderNTSCHue OBJECT-TYPE
		SYNTAX		INTEGER
		MAX-ACCESS		read-write
		STATUS			current
		DESCRIPTION
				"TYPE: - Number
				 PAGE: - Input- CVBS Decoder
					NTSC Hue  cmdID= 20504  min= -180  max= 180  step= 1  format= %d deg  div_scale= 1 
					Min = -180 deg  Max = 180 deg  Step = 1 deg "
		::= { iqudc32CmdEntry 20504 }


	iqudc32CVBSDecoderCalibrationLumaGain OBJECT-TYPE
		SYNTAX		INTEGER
		MAX-ACCESS		read-write
		STATUS			current
		DESCRIPTION
				"TYPE: - Number
				 PAGE: - Input- CVBS Decoder
					Luma Gain  cmdID= 20505  min= 0  max= 2047  step= 1  format= %d  div_scale= 1 
					Min = 0  Max = 2047  Step = 1 "
		::= { iqudc32CmdEntry 20505 }


	iqudc32CVBSDecoderCalibrationSaveDecoder OBJECT-TYPE
		SYNTAX		INTEGER { noAction(0),val-Save-Decoder(1) }
		MAX-ACCESS		read-write
		STATUS			current
		DESCRIPTION
				"TYPE: - Button
				 PAGE: - Input- CVBS Decoder
					Save Decoder  cmdID= 20506  value= 1  "
		::= { iqudc32CmdEntry 20506 }


	iqudc32OutputCh1OutputStandardStandard OBJECT-TYPE
		SYNTAX		INTEGER {
							val-625-50i(2),
							val-525-59i(3),
							val-720-23p(4),
							val-720-24p(5),
							val-720-25p(6),
							val-720-29p(7),
							val-720-50p(9),
							val-720-59p(10),
							val-1080-23p(12),
							val-1080-24p(13),
							val-1080-25p(14),
							val-1080-29p(15),
							val-1080-50i(17),
							val-1080-59i(18),
							val-1080-23psf(20),
							val-1080-24psf(21),
							val-1080-25psf(50),
							val-1080-29psf(51),
							val-1080-50p-A(22),
							val-1080-59p-A(23),
							val-1080-50p-B(25),
							val-1080-59p-B(26)
							}
		MAX-ACCESS		read-write
		STATUS			current
		DESCRIPTION
				"TYPE: - RadiobuttonList
				 PAGE: - Output-Ch1
					Standard  cmdID= 10100 
					625 50i  value= 2  
					525 59i  value= 3  
					720 23p  value= 4  
					720 24p  value= 5  
					720 25p  value= 6  
					720 29p  value= 7  
					720 50p  value= 9  
					720 59p  value= 10  
					1080 23p  value= 12  
					1080 24p  value= 13  
					1080 25p  value= 14  
					1080 29p  value= 15  
					1080 50i  value= 17  
					1080 59i  value= 18  
					1080 23psf  value= 20  
					1080 24psf  value= 21  
					1080 25psf  value= 50  
					1080 29psf  value= 51  
					1080 50p-A  value= 22  
					1080 59p-A  value= 23  
					1080 50p-B  value= 25  
					1080 59p-B  value= 26  "
		::= { iqudc32CmdEntry 10100 }


	iqudc32MenuOutputCh1Format OBJECT-TYPE
		SYNTAX		INTEGER {
							val-525-625(0),
							val-720p(1),
							val-1080i(2),
							val-1080p-A(3),
							val-1080p-B(4)
							}
		MAX-ACCESS		read-write
		STATUS			current
		DESCRIPTION
				"TYPE: - RadiobuttonList
				 PAGE: - Output-Ch1
					Format  cmdID= 10101 
					525/625  value= 0  
					720p  value= 1  
					1080i  value= 2  
					1080p-A  value= 3  
					1080p-B  value= 4  "
		::= { iqudc32CmdEntry 10101 }


	iqudc32MenuOutputCh1DefaultFieldRate OBJECT-TYPE
		SYNTAX		INTEGER {
							val-Last-Valid-Input(0),
							val-23-Hz(1),
							val-24-Hz(2),
							val-25-Hz(3),
							val-29-Hz(4),
							val-50-Hz(6),
							val-59-Hz(7)
							}
		MAX-ACCESS		read-write
		STATUS			current
		DESCRIPTION
				"TYPE: - RadiobuttonList
				 PAGE: - Output-Ch1
					Default Field Rate  cmdID= 10102 
					Last Valid Input  value= 0  
					23 Hz  value= 1  
					24 Hz  value= 2  
					25 Hz  value= 3  
					29 Hz  value= 4  
					50 Hz  value= 6  
					59 Hz  value= 7  "
		::= { iqudc32CmdEntry 10102 }


	iqudc32MenuOutputCh1CurrentOutputStan OBJECT-TYPE
		SYNTAX		RollCallString
		MAX-ACCESS		read-only
		STATUS			current
		DESCRIPTION
				"TYPE: - Display
				 PAGE: - Output-Ch1
					Current Output Stan  cmdID= 64011  format=   "
		::= { iqudc32CmdEntry 64011 }


	iqudc32OutputCh1ScrollingCaptionGCaptionEntry OBJECT-TYPE
		SYNTAX		RollCallString
		MAX-ACCESS		read-write
		STATUS			current
		DESCRIPTION
				"TYPE: - Editstring
				 PAGE: - Output-Ch1
					Caption Entry  cmdID= 10013  "
		::= { iqudc32CmdEntry 10013 }


	iqudc32OutputCh1ScrollingCaptionGCaptionScroll OBJECT-TYPE
		SYNTAX		INTEGER { disable(0), enable(1) }
		MAX-ACCESS		read-write
		STATUS			current
		DESCRIPTION
				"TYPE: - Checkbox
				 PAGE: - Output-Ch1
					Caption Scroll  cmdID= 10015 "
		::= { iqudc32CmdEntry 10015 }


	iqudc32OutputCh1ScrollingCaptionGCaptionEnable OBJECT-TYPE
		SYNTAX		INTEGER { disable(0), enable(1) }
		MAX-ACCESS		read-write
		STATUS			current
		DESCRIPTION
				"TYPE: - Checkbox
				 PAGE: - Output-Ch1
					Caption Enable  cmdID= 10014 "
		::= { iqudc32CmdEntry 10014 }


	iqudc32MenuOutputCh1ForceFreeze OBJECT-TYPE
		SYNTAX		INTEGER { disable(0), enable(1) }
		MAX-ACCESS		read-write
		STATUS			current
		DESCRIPTION
				"TYPE: - Checkbox
				 PAGE: - Output-Ch1
					Force Freeze  cmdID= 20302 "
		::= { iqudc32CmdEntry 20302 }


	iqudc32MenuOutputCh1Legalization OBJECT-TYPE
		SYNTAX		INTEGER {
							val-Off(0),
							val-700mV(1),
							val-721mV(2),
							val-735mV(3),
							val-746mV(4)
							}
		MAX-ACCESS		read-write
		STATUS			current
		DESCRIPTION
				"TYPE: - RadiobuttonList
				 PAGE: - Output-Ch1
					Legalization  cmdID= 20205 
					Off  value= 0  
					700mV  value= 1  
					721mV  value= 2  
					735mV  value= 3  
					746mV  value= 4  "
		::= { iqudc32CmdEntry 20205 }


	iqudc32OutputCh1BlankingEmbeddedAudio OBJECT-TYPE
		SYNTAX		INTEGER {
							val-Enable(0),
							val-Blank(1)
							}
		MAX-ACCESS		read-write
		STATUS			current
		DESCRIPTION
				"TYPE: - RadiobuttonList
				 PAGE: - Output-Ch1
					Embedded Audio  cmdID= 10010 
					Enable  value= 0  
					Blank  value= 1  "
		::= { iqudc32CmdEntry 10010 }


	iqudc32MenuOutputCh1SDHalfLine OBJECT-TYPE
		SYNTAX		INTEGER {
							val-Pass(0),
							val-Blank(1)
							}
		MAX-ACCESS		read-write
		STATUS			current
		DESCRIPTION
				"TYPE: - RadiobuttonList
				 PAGE: - Output-Ch1
					SD Half Line  cmdID= 10012 
					Pass  value= 0  
					Blank  value= 1  "
		::= { iqudc32CmdEntry 10012 }


	iqudc32OutputCh1LumaClipperEnable OBJECT-TYPE
		SYNTAX		INTEGER { disable(0), enable(1) }
		MAX-ACCESS		read-write
		STATUS			current
		DESCRIPTION
				"TYPE: - Checkbox
				 PAGE: - Output-Ch1
					Enable  cmdID= 20312 "
		::= { iqudc32CmdEntry 20312 }


	iqudc32OutputCh1LumaClipperWhiteMax OBJECT-TYPE
		SYNTAX		INTEGER
		MAX-ACCESS		read-write
		STATUS			current
		DESCRIPTION
				"TYPE: - Number
				 PAGE: - Output-Ch1
					White Max  cmdID= 20313  min= 90  max= 109  step= 1  format= %0.0f%%  div_scale= 1 
					Min = 90%  Max = 109%  Step = 1% "
		::= { iqudc32CmdEntry 20313 }


	iqudc32OutputCh1LumaClipperBlackMin OBJECT-TYPE
		SYNTAX		INTEGER
		MAX-ACCESS		read-write
		STATUS			current
		DESCRIPTION
				"TYPE: - Number
				 PAGE: - Output-Ch1
					Black Min  cmdID= 20314  min= -7  max= 10  step= 1  format= %0.0f%%  div_scale= 1 
					Min = -7%  Max = 10%  Step = 1% "
		::= { iqudc32CmdEntry 20314 }


	iqudc32MenuOutputCh1DefaultOutput OBJECT-TYPE
		SYNTAX		INTEGER {
							val-Black(1),
							val-Pattern(2)
							}
		MAX-ACCESS		read-write
		STATUS			current
		DESCRIPTION
				"TYPE: - RadiobuttonList
				 PAGE: - Output-Ch1
					Default Output  cmdID= 20311 
					Black  value= 1  
					Pattern  value= 2  "
		::= { iqudc32CmdEntry 20311 }


	iqudc32MenuOutputCh1TestPatterns OBJECT-TYPE
		SYNTAX		INTEGER {
							val-Off(0),
							val-Black(1),
							val-Ramp(2),
							val-Bars(3)
							}
		MAX-ACCESS		read-write
		STATUS			current
		DESCRIPTION
				"TYPE: - RadiobuttonList
				 PAGE: - Output-Ch1
					Test Patterns  cmdID= 20301 
					Off  value= 0  
					Black  value= 1  
					Ramp  value= 2  
					Bars  value= 3  "
		::= { iqudc32CmdEntry 20301 }


	iqudc32OutputCh1LogoControlPreShaped OBJECT-TYPE
		SYNTAX		INTEGER { disable(0), enable(1) }
		MAX-ACCESS		read-write
		STATUS			current
		DESCRIPTION
				"TYPE: - Checkbox
				 PAGE: - Output-Ch1
					Pre-Shaped  cmdID= 20315 "
		::= { iqudc32CmdEntry 20315 }


	iqudc32OutputCh1LogoControlTake OBJECT-TYPE
		SYNTAX		INTEGER { disable(0), enable(1) }
		MAX-ACCESS		read-write
		STATUS			current
		DESCRIPTION
				"TYPE: - Checkbox
				 PAGE: - Output-Ch1
					Take  cmdID= 20303 "
		::= { iqudc32CmdEntry 20303 }


	iqudc32OutputCh1LogoControlHPosition OBJECT-TYPE
		SYNTAX		INTEGER
		MAX-ACCESS		read-write
		STATUS			current
		DESCRIPTION
				"TYPE: - Number
				 PAGE: - Output-Ch1
					H Position  cmdID= 20304  min= 0  max= 100  step= 1  format= %0.0f  div_scale= 1 
					Min = 0  Max = 100  Step = 1 "
		::= { iqudc32CmdEntry 20304 }


	iqudc32OutputCh1LogoControlVPosition OBJECT-TYPE
		SYNTAX		INTEGER
		MAX-ACCESS		read-write
		STATUS			current
		DESCRIPTION
				"TYPE: - Number
				 PAGE: - Output-Ch1
					V Position  cmdID= 20305  min= 0  max= 100  step= 1  format= %0.0f  div_scale= 1 
					Min = 0  Max = 100  Step = 1 "
		::= { iqudc32CmdEntry 20305 }


	iqudc32OutputCh1LogoControlTransparancy OBJECT-TYPE
		SYNTAX		INTEGER
		MAX-ACCESS		read-write
		STATUS			current
		DESCRIPTION
				"TYPE: - Number
				 PAGE: - Output-Ch1
					Transparancy  cmdID= 20306  min= 0  max= 100  step= 1  format= %0.0f  div_scale= 1 
					Min = 0  Max = 100  Step = 1 "
		::= { iqudc32CmdEntry 20306 }


	iqudc32OutputCh1LogoControlDelete OBJECT-TYPE
		SYNTAX		INTEGER { noAction(0),val-Delete(1) }
		MAX-ACCESS		read-write
		STATUS			current
		DESCRIPTION
				"TYPE: - Button
				 PAGE: - Output-Ch1
					Delete  cmdID= 20307  value= 1  "
		::= { iqudc32CmdEntry 20307 }


	iqudc32OutputCh1LogoControlCurrentSelectedLo OBJECT-TYPE
		SYNTAX		RollCallString
		MAX-ACCESS		read-only
		STATUS			current
		DESCRIPTION
				"TYPE: - Display
				 PAGE: - Output-Ch1
					Current Selected Lo  cmdID= 20309  format=   "
		::= { iqudc32CmdEntry 20309 }


	iqudc32OutputCh1LogoControlLogoState OBJECT-TYPE
		SYNTAX		RollCallString
		MAX-ACCESS		read-only
		STATUS			current
		DESCRIPTION
				"TYPE: - Display
				 PAGE: - Output-Ch1
					Logo State  cmdID= 20310  format=   "
		::= { iqudc32CmdEntry 20310 }


	iqudc32OutputCh1LogoControlNewLogo OBJECT-TYPE
		SYNTAX		RollCallString
		MAX-ACCESS		read-write
		STATUS			current
		DESCRIPTION
				"TYPE: - Editstring
				 PAGE: - Output-Ch1
					New Logo  cmdID= 15000  "
		::= { iqudc32CmdEntry 15000 }


	iqudc32OutputCh1LogoControlLogoStatus OBJECT-TYPE
		SYNTAX		RollCallString
		MAX-ACCESS		read-only
		STATUS			current
		DESCRIPTION
				"TYPE: - Display
				 PAGE: - Output-Ch1
					Logo Status  cmdID= 15001  format=   "
		::= { iqudc32CmdEntry 15001 }


	iqudc32OutputCh1LogoControlLogoSelect OBJECT-TYPE
		SYNTAX		INTEGER {
							val-None-Selected(-1),
							val-Logo-1(1),
							val-Logo-2(2),
							val-Logo-3(3),
							val-Logo-4(4),
							val-Logo-5(5),
							val-Logo-6(6),
							val-Logo-7(7),
							val-Logo-8(8),
							val-Logo-9(9),
							val-Logo-10(10),
							val-Logo-11(11),
							val-Logo-12(12),
							val-Logo-13(13),
							val-Logo-14(14),
							val-Logo-15(15),
							val-Logo-16(16),
							val-Logo-17(17),
							val-Logo-18(18),
							val-Logo-19(19),
							val-Logo-20(20),
							val-Logo-21(21),
							val-Logo-22(22),
							val-Logo-23(23),
							val-Logo-24(24),
							val-Logo-25(25),
							val-Logo-26(26),
							val-Logo-27(27),
							val-Logo-28(28),
							val-Logo-29(29),
							val-Logo-30(30),
							val-Logo-31(31),
							val-Logo-32(32),
							val-Logo-33(33),
							val-Logo-34(34),
							val-Logo-35(35),
							val-Logo-36(36),
							val-Logo-37(37),
							val-Logo-38(38),
							val-Logo-39(39),
							val-Logo-40(40),
							val-Logo-41(41),
							val-Logo-42(42),
							val-Logo-43(43),
							val-Logo-44(44),
							val-Logo-45(45),
							val-Logo-46(46),
							val-Logo-47(47),
							val-Logo-48(48),
							val-Logo-49(49),
							val-Logo-50(50),
							val-Logo-51(51),
							val-Logo-52(52),
							val-Logo-53(53),
							val-Logo-54(54),
							val-Logo-55(55),
							val-Logo-56(56),
							val-Logo-57(57),
							val-Logo-58(58),
							val-Logo-59(59),
							val-Logo-60(60),
							val-Logo-61(61),
							val-Logo-62(62),
							val-Logo-63(63),
							val-Logo-64(64)
							}
		MAX-ACCESS		read-write
		STATUS			current
		DESCRIPTION
				"TYPE: - RadiobuttonList
				 PAGE: - Output-Ch1
					Logo Select  cmdID= 20308 
					None Selected  value= -1  
					Logo 1  value= 1  
					Logo 2  value= 2  
					Logo 3  value= 3  
					Logo 4  value= 4  
					Logo 5  value= 5  
					Logo 6  value= 6  
					Logo 7  value= 7  
					Logo 8  value= 8  
					Logo 9  value= 9  
					Logo 10  value= 10  
					Logo 11  value= 11  
					Logo 12  value= 12  
					Logo 13  value= 13  
					Logo 14  value= 14  
					Logo 15  value= 15  
					Logo 16  value= 16  
					Logo 17  value= 17  
					Logo 18  value= 18  
					Logo 19  value= 19  
					Logo 20  value= 20  
					Logo 21  value= 21  
					Logo 22  value= 22  
					Logo 23  value= 23  
					Logo 24  value= 24  
					Logo 25  value= 25  
					Logo 26  value= 26  
					Logo 27  value= 27  
					Logo 28  value= 28  
					Logo 29  value= 29  
					Logo 30  value= 30  
					Logo 31  value= 31  
					Logo 32  value= 32  
					Logo 33  value= 33  
					Logo 34  value= 34  
					Logo 35  value= 35  
					Logo 36  value= 36  
					Logo 37  value= 37  
					Logo 38  value= 38  
					Logo 39  value= 39  
					Logo 40  value= 40  
					Logo 41  value= 41  
					Logo 42  value= 42  
					Logo 43  value= 43  
					Logo 44  value= 44  
					Logo 45  value= 45  
					Logo 46  value= 46  
					Logo 47  value= 47  
					Logo 48  value= 48  
					Logo 49  value= 49  
					Logo 50  value= 50  
					Logo 51  value= 51  
					Logo 52  value= 52  
					Logo 53  value= 53  
					Logo 54  value= 54  
					Logo 55  value= 55  
					Logo 56  value= 56  
					Logo 57  value= 57  
					Logo 58  value= 58  
					Logo 59  value= 59  
					Logo 60  value= 60  
					Logo 61  value= 61  
					Logo 62  value= 62  
					Logo 63  value= 63  
					Logo 64  value= 64  "
		::= { iqudc32CmdEntry 20308 }


	iqudc32CVBSEncoderASetupFormat OBJECT-TYPE
		SYNTAX		INTEGER {
							val-PAL-NTSC(0),
							val-PAL-N-PAL-M(1),
							val-PAL-NTSC-J(2)
							}
		MAX-ACCESS		read-write
		STATUS			current
		DESCRIPTION
				"TYPE: - RadiobuttonList
				 PAGE: - Output-Ch1
					Format  cmdID= 20508 
					PAL/NTSC  value= 0  
					PAL-N/PAL-M  value= 1  
					PAL/NTSC-J  value= 2  "
		::= { iqudc32CmdEntry 20508 }


	iqudc32OutputCh1CalibrationDACGain OBJECT-TYPE
		SYNTAX		INTEGER
		MAX-ACCESS		read-write
		STATUS			current
		DESCRIPTION
				"TYPE: - Number
				 PAGE: - Output-Ch1
					DAC Gain  cmdID= 20509  min= -64  max= 64  step= 1  format= %d  div_scale= 1 
					Min = -64  Max = 64  Step = 1 "
		::= { iqudc32CmdEntry 20509 }


	iqudc32OutputCh1CalibrationSaveEncoder OBJECT-TYPE
		SYNTAX		INTEGER { noAction(0),val-Save-Encoder(1) }
		MAX-ACCESS		read-write
		STATUS			current
		DESCRIPTION
				"TYPE: - Button
				 PAGE: - Output-Ch1
					Save Encoder  cmdID= 20510  value= 1  "
		::= { iqudc32CmdEntry 20510 }


	iqudc32OutputCh1SFPOutputRoutingSFP1Source OBJECT-TYPE
		SYNTAX		INTEGER {
							val-Ch-1(0),
							val-Ch-2(1)
							}
		MAX-ACCESS		read-write
		STATUS			current
		DESCRIPTION
				"TYPE: - RadiobuttonList
				 PAGE: - Output-Ch1
					SFP 1 Source  cmdID= 20519 
					Ch 1  value= 0  
					Ch 2  value= 1  "
		::= { iqudc32CmdEntry 20519 }


	iqudc32MenuOutputCh1SFP2Source OBJECT-TYPE
		SYNTAX		INTEGER {
							val-Ch-1(0),
							val-Ch-2(1)
							}
		MAX-ACCESS		read-write
		STATUS			current
		DESCRIPTION
				"TYPE: - RadiobuttonList
				 PAGE: - Output-Ch1
					SFP 2 Source  cmdID= 20520 
					Ch 1  value= 0  
					Ch 2  value= 1  "
		::= { iqudc32CmdEntry 20520 }


	iqudc32OutputCh2OutputStandardStandard OBJECT-TYPE
		SYNTAX		INTEGER {
							val-625-50i(2),
							val-525-59i(3),
							val-720-23p(4),
							val-720-24p(5),
							val-720-25p(6),
							val-720-29p(7),
							val-720-50p(9),
							val-720-59p(10),
							val-1080-23p(12),
							val-1080-24p(13),
							val-1080-25p(14),
							val-1080-29p(15),
							val-1080-50i(17),
							val-1080-59i(18),
							val-1080-23psf(20),
							val-1080-24psf(21),
							val-1080-25psf(50),
							val-1080-29psf(51),
							val-1080-50p-A(22),
							val-1080-59p-A(23),
							val-1080-50p-B(25),
							val-1080-59p-B(26)
							}
		MAX-ACCESS		read-write
		STATUS			current
		DESCRIPTION
				"TYPE: - RadiobuttonList
				 PAGE: - Output-Ch2
					Standard  cmdID= 10200 
					625 50i  value= 2  
					525 59i  value= 3  
					720 23p  value= 4  
					720 24p  value= 5  
					720 25p  value= 6  
					720 29p  value= 7  
					720 50p  value= 9  
					720 59p  value= 10  
					1080 23p  value= 12  
					1080 24p  value= 13  
					1080 25p  value= 14  
					1080 29p  value= 15  
					1080 50i  value= 17  
					1080 59i  value= 18  
					1080 23psf  value= 20  
					1080 24psf  value= 21  
					1080 25psf  value= 50  
					1080 29psf  value= 51  
					1080 50p-A  value= 22  
					1080 59p-A  value= 23  
					1080 50p-B  value= 25  
					1080 59p-B  value= 26  "
		::= { iqudc32CmdEntry 10200 }


	iqudc32MenuOutputCh2Format OBJECT-TYPE
		SYNTAX		INTEGER {
							val-525-625(0),
							val-720p(1),
							val-1080i(2),
							val-1080p-A(3),
							val-1080p-B(4)
							}
		MAX-ACCESS		read-write
		STATUS			current
		DESCRIPTION
				"TYPE: - RadiobuttonList
				 PAGE: - Output-Ch2
					Format  cmdID= 10201 
					525/625  value= 0  
					720p  value= 1  
					1080i  value= 2  
					1080p-A  value= 3  
					1080p-B  value= 4  "
		::= { iqudc32CmdEntry 10201 }


	iqudc32MenuOutputCh2DefaultFieldRate OBJECT-TYPE
		SYNTAX		INTEGER {
							val-Last-Valid-Input(0),
							val-23-Hz(1),
							val-24-Hz(2),
							val-25-Hz(3),
							val-29-Hz(4),
							val-50-Hz(6),
							val-59-Hz(7)
							}
		MAX-ACCESS		read-write
		STATUS			current
		DESCRIPTION
				"TYPE: - RadiobuttonList
				 PAGE: - Output-Ch2
					Default Field Rate  cmdID= 10202 
					Last Valid Input  value= 0  
					23 Hz  value= 1  
					24 Hz  value= 2  
					25 Hz  value= 3  
					29 Hz  value= 4  
					50 Hz  value= 6  
					59 Hz  value= 7  "
		::= { iqudc32CmdEntry 10202 }


	iqudc32MenuOutputCh2CurrentOutputStan OBJECT-TYPE
		SYNTAX		RollCallString
		MAX-ACCESS		read-only
		STATUS			current
		DESCRIPTION
				"TYPE: - Display
				 PAGE: - Output-Ch2
					Current Output Stan  cmdID= 64111  format=   "
		::= { iqudc32CmdEntry 64111 }


	iqudc32OutputCh2ScrollingCaptionGCaptionEntry OBJECT-TYPE
		SYNTAX		RollCallString
		MAX-ACCESS		read-write
		STATUS			current
		DESCRIPTION
				"TYPE: - Editstring
				 PAGE: - Output-Ch2
					Caption Entry  cmdID= 10113  "
		::= { iqudc32CmdEntry 10113 }


	iqudc32OutputCh2ScrollingCaptionGCaptionScroll OBJECT-TYPE
		SYNTAX		INTEGER { disable(0), enable(1) }
		MAX-ACCESS		read-write
		STATUS			current
		DESCRIPTION
				"TYPE: - Checkbox
				 PAGE: - Output-Ch2
					Caption Scroll  cmdID= 10115 "
		::= { iqudc32CmdEntry 10115 }


	iqudc32OutputCh2ScrollingCaptionGCaptionEnable OBJECT-TYPE
		SYNTAX		INTEGER { disable(0), enable(1) }
		MAX-ACCESS		read-write
		STATUS			current
		DESCRIPTION
				"TYPE: - Checkbox
				 PAGE: - Output-Ch2
					Caption Enable  cmdID= 10114 "
		::= { iqudc32CmdEntry 10114 }


	iqudc32MenuOutputCh2ForceFreeze OBJECT-TYPE
		SYNTAX		INTEGER { disable(0), enable(1) }
		MAX-ACCESS		read-write
		STATUS			current
		DESCRIPTION
				"TYPE: - Checkbox
				 PAGE: - Output-Ch2
					Force Freeze  cmdID= 20400 "
		::= { iqudc32CmdEntry 20400 }


	iqudc32MenuOutputCh2Legalization OBJECT-TYPE
		SYNTAX		INTEGER {
							val-Off(0),
							val-700mV(1),
							val-721mV(2),
							val-735mV(3),
							val-746mV(4)
							}
		MAX-ACCESS		read-write
		STATUS			current
		DESCRIPTION
				"TYPE: - RadiobuttonList
				 PAGE: - Output-Ch2
					Legalization  cmdID= 20300 
					Off  value= 0  
					700mV  value= 1  
					721mV  value= 2  
					735mV  value= 3  
					746mV  value= 4  "
		::= { iqudc32CmdEntry 20300 }


	iqudc32OutputCh2BlankingEmbeddedAudio OBJECT-TYPE
		SYNTAX		INTEGER {
							val-Enable(0),
							val-Blank(1)
							}
		MAX-ACCESS		read-write
		STATUS			current
		DESCRIPTION
				"TYPE: - RadiobuttonList
				 PAGE: - Output-Ch2
					Embedded Audio  cmdID= 10110 
					Enable  value= 0  
					Blank  value= 1  "
		::= { iqudc32CmdEntry 10110 }


	iqudc32MenuOutputCh2SDHalfLine OBJECT-TYPE
		SYNTAX		INTEGER {
							val-Pass(0),
							val-Blank(1)
							}
		MAX-ACCESS		read-write
		STATUS			current
		DESCRIPTION
				"TYPE: - RadiobuttonList
				 PAGE: - Output-Ch2
					SD Half Line  cmdID= 10112 
					Pass  value= 0  
					Blank  value= 1  "
		::= { iqudc32CmdEntry 10112 }


	iqudc32OutputCh2LumaClipperEnable OBJECT-TYPE
		SYNTAX		INTEGER { disable(0), enable(1) }
		MAX-ACCESS		read-write
		STATUS			current
		DESCRIPTION
				"TYPE: - Checkbox
				 PAGE: - Output-Ch2
					Enable  cmdID= 20412 "
		::= { iqudc32CmdEntry 20412 }


	iqudc32OutputCh2LumaClipperWhiteMax OBJECT-TYPE
		SYNTAX		INTEGER
		MAX-ACCESS		read-write
		STATUS			current
		DESCRIPTION
				"TYPE: - Number
				 PAGE: - Output-Ch2
					White Max  cmdID= 20413  min= 90  max= 109  step= 1  format= %0.0f%%  div_scale= 1 
					Min = 90%  Max = 109%  Step = 1% "
		::= { iqudc32CmdEntry 20413 }


	iqudc32OutputCh2LumaClipperBlackMin OBJECT-TYPE
		SYNTAX		INTEGER
		MAX-ACCESS		read-write
		STATUS			current
		DESCRIPTION
				"TYPE: - Number
				 PAGE: - Output-Ch2
					Black Min  cmdID= 20414  min= -7  max= 10  step= 1  format= %0.0f%%  div_scale= 1 
					Min = -7%  Max = 10%  Step = 1% "
		::= { iqudc32CmdEntry 20414 }


	iqudc32MenuOutputCh2DefaultOutput OBJECT-TYPE
		SYNTAX		INTEGER {
							val-Black(1),
							val-Pattern(2)
							}
		MAX-ACCESS		read-write
		STATUS			current
		DESCRIPTION
				"TYPE: - RadiobuttonList
				 PAGE: - Output-Ch2
					Default Output  cmdID= 20411 
					Black  value= 1  
					Pattern  value= 2  "
		::= { iqudc32CmdEntry 20411 }


	iqudc32MenuOutputCh2TestPatterns OBJECT-TYPE
		SYNTAX		INTEGER {
							val-Off(0),
							val-Black(1),
							val-Ramp(2),
							val-Bars(3)
							}
		MAX-ACCESS		read-write
		STATUS			current
		DESCRIPTION
				"TYPE: - RadiobuttonList
				 PAGE: - Output-Ch2
					Test Patterns  cmdID= 20401 
					Off  value= 0  
					Black  value= 1  
					Ramp  value= 2  
					Bars  value= 3  "
		::= { iqudc32CmdEntry 20401 }


	iqudc32OutputCh2LogoControlPreShaped OBJECT-TYPE
		SYNTAX		INTEGER { disable(0), enable(1) }
		MAX-ACCESS		read-write
		STATUS			current
		DESCRIPTION
				"TYPE: - Checkbox
				 PAGE: - Output-Ch2
					Pre-Shaped  cmdID= 20402 "
		::= { iqudc32CmdEntry 20402 }


	iqudc32OutputCh2LogoControlTake OBJECT-TYPE
		SYNTAX		INTEGER { disable(0), enable(1) }
		MAX-ACCESS		read-write
		STATUS			current
		DESCRIPTION
				"TYPE: - Checkbox
				 PAGE: - Output-Ch2
					Take  cmdID= 20403 "
		::= { iqudc32CmdEntry 20403 }


	iqudc32OutputCh2LogoControlHPosition OBJECT-TYPE
		SYNTAX		INTEGER
		MAX-ACCESS		read-write
		STATUS			current
		DESCRIPTION
				"TYPE: - Number
				 PAGE: - Output-Ch2
					H Position  cmdID= 20404  min= 0  max= 100  step= 1  format= %0.0f  div_scale= 1 
					Min = 0  Max = 100  Step = 1 "
		::= { iqudc32CmdEntry 20404 }


	iqudc32OutputCh2LogoControlVPosition OBJECT-TYPE
		SYNTAX		INTEGER
		MAX-ACCESS		read-write
		STATUS			current
		DESCRIPTION
				"TYPE: - Number
				 PAGE: - Output-Ch2
					V Position  cmdID= 20405  min= 0  max= 100  step= 1  format= %0.0f  div_scale= 1 
					Min = 0  Max = 100  Step = 1 "
		::= { iqudc32CmdEntry 20405 }


	iqudc32OutputCh2LogoControlTransparancy OBJECT-TYPE
		SYNTAX		INTEGER
		MAX-ACCESS		read-write
		STATUS			current
		DESCRIPTION
				"TYPE: - Number
				 PAGE: - Output-Ch2
					Transparancy  cmdID= 20406  min= 0  max= 100  step= 1  format= %0.0f  div_scale= 1 
					Min = 0  Max = 100  Step = 1 "
		::= { iqudc32CmdEntry 20406 }


	iqudc32OutputCh2LogoControlDelete OBJECT-TYPE
		SYNTAX		INTEGER { noAction(0),val-Delete(1) }
		MAX-ACCESS		read-write
		STATUS			current
		DESCRIPTION
				"TYPE: - Button
				 PAGE: - Output-Ch2
					Delete  cmdID= 20407  value= 1  "
		::= { iqudc32CmdEntry 20407 }


	iqudc32OutputCh2LogoControlCurrentSelectedLo OBJECT-TYPE
		SYNTAX		RollCallString
		MAX-ACCESS		read-only
		STATUS			current
		DESCRIPTION
				"TYPE: - Display
				 PAGE: - Output-Ch2
					Current Selected Lo  cmdID= 20409  format=   "
		::= { iqudc32CmdEntry 20409 }


	iqudc32OutputCh2LogoControlLogoState OBJECT-TYPE
		SYNTAX		RollCallString
		MAX-ACCESS		read-only
		STATUS			current
		DESCRIPTION
				"TYPE: - Display
				 PAGE: - Output-Ch2
					Logo State  cmdID= 20410  format=   "
		::= { iqudc32CmdEntry 20410 }


	iqudc32OutputCh2LogoControlLogoSelect OBJECT-TYPE
		SYNTAX		INTEGER {
							val-None-Selected(-1),
							val-Logo-1(1),
							val-Logo-2(2),
							val-Logo-3(3),
							val-Logo-4(4),
							val-Logo-5(5),
							val-Logo-6(6),
							val-Logo-7(7),
							val-Logo-8(8),
							val-Logo-9(9),
							val-Logo-10(10),
							val-Logo-11(11),
							val-Logo-12(12),
							val-Logo-13(13),
							val-Logo-14(14),
							val-Logo-15(15),
							val-Logo-16(16),
							val-Logo-17(17),
							val-Logo-18(18),
							val-Logo-19(19),
							val-Logo-20(20),
							val-Logo-21(21),
							val-Logo-22(22),
							val-Logo-23(23),
							val-Logo-24(24),
							val-Logo-25(25),
							val-Logo-26(26),
							val-Logo-27(27),
							val-Logo-28(28),
							val-Logo-29(29),
							val-Logo-30(30),
							val-Logo-31(31),
							val-Logo-32(32),
							val-Logo-33(33),
							val-Logo-34(34),
							val-Logo-35(35),
							val-Logo-36(36),
							val-Logo-37(37),
							val-Logo-38(38),
							val-Logo-39(39),
							val-Logo-40(40),
							val-Logo-41(41),
							val-Logo-42(42),
							val-Logo-43(43),
							val-Logo-44(44),
							val-Logo-45(45),
							val-Logo-46(46),
							val-Logo-47(47),
							val-Logo-48(48),
							val-Logo-49(49),
							val-Logo-50(50),
							val-Logo-51(51),
							val-Logo-52(52),
							val-Logo-53(53),
							val-Logo-54(54),
							val-Logo-55(55),
							val-Logo-56(56),
							val-Logo-57(57),
							val-Logo-58(58),
							val-Logo-59(59),
							val-Logo-60(60),
							val-Logo-61(61),
							val-Logo-62(62),
							val-Logo-63(63),
							val-Logo-64(64)
							}
		MAX-ACCESS		read-write
		STATUS			current
		DESCRIPTION
				"TYPE: - RadiobuttonList
				 PAGE: - Output-Ch2
					Logo Select  cmdID= 20408 
					None Selected  value= -1  
					Logo 1  value= 1  
					Logo 2  value= 2  
					Logo 3  value= 3  
					Logo 4  value= 4  
					Logo 5  value= 5  
					Logo 6  value= 6  
					Logo 7  value= 7  
					Logo 8  value= 8  
					Logo 9  value= 9  
					Logo 10  value= 10  
					Logo 11  value= 11  
					Logo 12  value= 12  
					Logo 13  value= 13  
					Logo 14  value= 14  
					Logo 15  value= 15  
					Logo 16  value= 16  
					Logo 17  value= 17  
					Logo 18  value= 18  
					Logo 19  value= 19  
					Logo 20  value= 20  
					Logo 21  value= 21  
					Logo 22  value= 22  
					Logo 23  value= 23  
					Logo 24  value= 24  
					Logo 25  value= 25  
					Logo 26  value= 26  
					Logo 27  value= 27  
					Logo 28  value= 28  
					Logo 29  value= 29  
					Logo 30  value= 30  
					Logo 31  value= 31  
					Logo 32  value= 32  
					Logo 33  value= 33  
					Logo 34  value= 34  
					Logo 35  value= 35  
					Logo 36  value= 36  
					Logo 37  value= 37  
					Logo 38  value= 38  
					Logo 39  value= 39  
					Logo 40  value= 40  
					Logo 41  value= 41  
					Logo 42  value= 42  
					Logo 43  value= 43  
					Logo 44  value= 44  
					Logo 45  value= 45  
					Logo 46  value= 46  
					Logo 47  value= 47  
					Logo 48  value= 48  
					Logo 49  value= 49  
					Logo 50  value= 50  
					Logo 51  value= 51  
					Logo 52  value= 52  
					Logo 53  value= 53  
					Logo 54  value= 54  
					Logo 55  value= 55  
					Logo 56  value= 56  
					Logo 57  value= 57  
					Logo 58  value= 58  
					Logo 59  value= 59  
					Logo 60  value= 60  
					Logo 61  value= 61  
					Logo 62  value= 62  
					Logo 63  value= 63  
					Logo 64  value= 64  "
		::= { iqudc32CmdEntry 20408 }


	iqudc32CVBSEncoderBSetupFormat OBJECT-TYPE
		SYNTAX		INTEGER {
							val-PAL-NTSC(0),
							val-PAL-N-PAL-M(1),
							val-PAL-NTSC-J(2)
							}
		MAX-ACCESS		read-write
		STATUS			current
		DESCRIPTION
				"TYPE: - RadiobuttonList
				 PAGE: - Output-Ch2
					Format  cmdID= 20512 
					PAL/NTSC  value= 0  
					PAL-N/PAL-M  value= 1  
					PAL/NTSC-J  value= 2  "
		::= { iqudc32CmdEntry 20512 }


	iqudc32OutputCh2CalibrationDACGain OBJECT-TYPE
		SYNTAX		INTEGER
		MAX-ACCESS		read-write
		STATUS			current
		DESCRIPTION
				"TYPE: - Number
				 PAGE: - Output-Ch2
					DAC Gain  cmdID= 20513  min= -64  max= 64  step= 1  format= %d  div_scale= 1 
					Min = -64  Max = 64  Step = 1 "
		::= { iqudc32CmdEntry 20513 }


	iqudc32OutputCh2CalibrationSaveEncoder OBJECT-TYPE
		SYNTAX		INTEGER { noAction(0),val-Save-Encoder(1) }
		MAX-ACCESS		read-write
		STATUS			current
		DESCRIPTION
				"TYPE: - Button
				 PAGE: - Output-Ch2
					Save Encoder  cmdID= 20514  value= 1  "
		::= { iqudc32CmdEntry 20514 }


	iqudc32MenuOutputCh2NewDisplay OBJECT-TYPE
		SYNTAX		RollCallString
		MAX-ACCESS		read-only
		STATUS			current
		DESCRIPTION
				"TYPE: - Display
				 PAGE: - Output-Ch2
					New Display  cmdID= 44446  format=   "
		::= { iqudc32CmdEntry 44446 }


	iqudc32VideoCh1ProcAmpEnable OBJECT-TYPE
		SYNTAX		INTEGER { disable(0), enable(1) }
		MAX-ACCESS		read-write
		STATUS			current
		DESCRIPTION
				"TYPE: - Checkbox
				 PAGE: - Video-Ch1
					Enable  cmdID= 20109 "
		::= { iqudc32CmdEntry 20109 }


	iqudc32VideoCh1ProcAmpContrast OBJECT-TYPE
		SYNTAX		INTEGER
		MAX-ACCESS		read-write
		STATUS			current
		DESCRIPTION
				"TYPE: - Number
				 PAGE: - Video-Ch1
					Contrast  cmdID= 20100  min= -60  max= 60  step= 2  format= %0.1fdB  div_scale= 10 
					Min = -6.0dB  Max = 6.0dB  Step = 0.2dB "
		::= { iqudc32CmdEntry 20100 }


	iqudc32VideoCh1ProcAmpSaturation OBJECT-TYPE
		SYNTAX		INTEGER
		MAX-ACCESS		read-write
		STATUS			current
		DESCRIPTION
				"TYPE: - Number
				 PAGE: - Video-Ch1
					Saturation  cmdID= 20106  min= -60  max= 60  step= 2  format= %0.1fdB  div_scale= 10 
					Min = -6.0dB  Max = 6.0dB  Step = 0.2dB "
		::= { iqudc32CmdEntry 20106 }


	iqudc32VideoCh1ProcAmpBlackLevel OBJECT-TYPE
		SYNTAX		INTEGER
		MAX-ACCESS		read-write
		STATUS			current
		DESCRIPTION
				"TYPE: - Number
				 PAGE: - Video-Ch1
					Black Level  cmdID= 20102  min= -1000  max= 1000  step= 8  format= %0.1fmV  div_scale= 10 
					Min = -100.0mV  Max = 100.0mV  Step = 0.8mV "
		::= { iqudc32CmdEntry 20102 }


	iqudc32VideoCh1ProcAmpGamma OBJECT-TYPE
		SYNTAX		INTEGER
		MAX-ACCESS		read-write
		STATUS			current
		DESCRIPTION
				"TYPE: - Number
				 PAGE: - Video-Ch1
					Gamma  cmdID= 20103  min= 4  max= 17  step= 1  format= %0.1f  div_scale= 10 
					Min = 0.4  Max = 1.7  Step = 0.1 "
		::= { iqudc32CmdEntry 20103 }


	iqudc32VideoCh1ProcAmpYCOffset OBJECT-TYPE
		SYNTAX		INTEGER
		MAX-ACCESS		read-write
		STATUS			current
		DESCRIPTION
				"TYPE: - Number
				 PAGE: - Video-Ch1
					YC Offset  cmdID= 20114  min= -20  max= 20  step= 2  format= %0.0f  div_scale= 1 
					Min = -20  Max = 20  Step = 2 "
		::= { iqudc32CmdEntry 20114 }


	iqudc32VideoCh1ProcAmpMasterGain OBJECT-TYPE
		SYNTAX		INTEGER
		MAX-ACCESS		read-write
		STATUS			current
		DESCRIPTION
				"TYPE: - Number
				 PAGE: - Video-Ch1
					Master Gain  cmdID= 20115  min= -60  max= 60  step= 2  format= %0.1fdB  div_scale= 10 
					Min = -6.0dB  Max = 6.0dB  Step = 0.2dB "
		::= { iqudc32CmdEntry 20115 }


	iqudc32VideoCh1NonlinearEnhancerEnable OBJECT-TYPE
		SYNTAX		INTEGER { disable(0), enable(1) }
		MAX-ACCESS		read-write
		STATUS			current
		DESCRIPTION
				"TYPE: - Checkbox
				 PAGE: - Video-Ch1
					Enable  cmdID= 20050 "
		::= { iqudc32CmdEntry 20050 }


	iqudc32VideoCh1NonlinearEnhancerLevel OBJECT-TYPE
		SYNTAX		INTEGER
		MAX-ACCESS		read-write
		STATUS			current
		DESCRIPTION
				"TYPE: - Number
				 PAGE: - Video-Ch1
					Level  cmdID= 20053  min= 0  max= 192  step= 1  format= %0.0f  div_scale= 1 
					Min = 0  Max = 192  Step = 1 "
		::= { iqudc32CmdEntry 20053 }


	iqudc32VideoCh1NonlinearEnhancerMode OBJECT-TYPE
		SYNTAX		INTEGER {
							val-Low(0),
							val-Medium(1),
							val-High(2),
							val-Super(3),
							val-Manual(4)
							}
		MAX-ACCESS		read-write
		STATUS			current
		DESCRIPTION
				"TYPE: - RadiobuttonList
				 PAGE: - Video-Ch1
					Mode  cmdID= 20051 
					Low  value= 0  
					Medium  value= 1  
					High  value= 2  
					Super  value= 3  
					Manual  value= 4  "
		::= { iqudc32CmdEntry 20051 }


	iqudc32MenuVideoCh1FrequencyBand20052 OBJECT-TYPE
		SYNTAX		INTEGER {
							val-Low(0),
							val-Medium(1),
							val-High(2)
							}
		MAX-ACCESS		read-write
		STATUS			current
		DESCRIPTION
				"TYPE: - RadiobuttonList
				 PAGE: - Video-Ch1
					Frequency Band  cmdID= 20052 
					Low  value= 0  
					Medium  value= 1  
					High  value= 2  "
		::= { iqudc32CmdEntry 20052 }


	iqudc32MenuVideoCh1NoiseRejection OBJECT-TYPE
		SYNTAX		INTEGER
		MAX-ACCESS		read-write
		STATUS			current
		DESCRIPTION
				"TYPE: - Number
				 PAGE: - Video-Ch1
					Noise Rejection  cmdID= 20054  min= 0  max= 100  step= 1  format= %0.0f  div_scale= 1 
					Min = 0  Max = 100  Step = 1 "
		::= { iqudc32CmdEntry 20054 }


	iqudc32VideoCh1ConversionAperturePreset OBJECT-TYPE
		SYNTAX		INTEGER { noAction(0),val-Preset(1) }
		MAX-ACCESS		read-write
		STATUS			current
		DESCRIPTION
				"TYPE: - Button
				 PAGE: - Video-Ch1
					Preset  cmdID= 20162  value= 1  "
		::= { iqudc32CmdEntry 20162 }


	iqudc32ConversionApertureHorizontalSharpness30100 OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch1
					Sharpness  cmdID= 30100 
					Soft 2  value= 0  
					Soft 1  value= 1  
					Normal  value= 2  
					Sharp 1  value= 3  
					Sharp 2  value= 4  "
		::= { iqudc32CmdEntry 30100 }


	iqudc32MenuVideoCh1Detail OBJECT-TYPE
		SYNTAX		INTEGER {
							val-Low-2(0),
							val-Low-1(1),
							val-Normal(2),
							val-High-1(3),
							val-High-2(4)
							}
		MAX-ACCESS		read-write
		STATUS			current
		DESCRIPTION
				"TYPE: - RadiobuttonList
				 PAGE: - Video-Ch1
					Detail  cmdID= 30101 
					Low 2  value= 0  
					Low 1  value= 1  
					Normal  value= 2  
					High 1  value= 3  
					High 2  value= 4  "
		::= { iqudc32CmdEntry 30101 }


	iqudc32VideoCh1VerticalLevel OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch1
					Level  cmdID= 20061 
					Soft 2  value= 0  
					Soft 1  value= 1  
					Normal  value= 2  
					Sharp 1  value= 3  
					Sharp 2  value= 4  "
		::= { iqudc32CmdEntry 20061 }


	iqudc32MenuVideoCh1FrequencyBand20060 OBJECT-TYPE
		SYNTAX		INTEGER {
							val-Low(0),
							val-Medium(1),
							val-High(2)
							}
		MAX-ACCESS		read-write
		STATUS			current
		DESCRIPTION
				"TYPE: - RadiobuttonList
				 PAGE: - Video-Ch1
					Frequency Band  cmdID= 20060 
					Low  value= 0  
					Medium  value= 1  
					High  value= 2  "
		::= { iqudc32CmdEntry 20060 }


	iqudc32VideoCh1NoiseReductionEnable OBJECT-TYPE
		SYNTAX		INTEGER { disable(0), enable(1) }
		MAX-ACCESS		read-write
		STATUS			current
		DESCRIPTION
				"TYPE: - Checkbox
				 PAGE: - Video-Ch1
					Enable  cmdID= 20004 "
		::= { iqudc32CmdEntry 20004 }


	iqudc32NoiseReductionRecursiveLuma20005 OBJECT-TYPE
		SYNTAX		INTEGER
		MAX-ACCESS		read-write
		STATUS			current
		DESCRIPTION
				"TYPE: - Number
				 PAGE: - Video-Ch1
					Luma  cmdID= 20005  min= 0  max= 7  step= 1  format= %0.0f  div_scale= 1 
					Min = 0  Max = 7  Step = 1 "
		::= { iqudc32CmdEntry 20005 }


	iqudc32NoiseReductionRecursiveChroma20001 OBJECT-TYPE
		SYNTAX		INTEGER
		MAX-ACCESS		read-write
		STATUS			current
		DESCRIPTION
				"TYPE: - Number
				 PAGE: - Video-Ch1
					Chroma  cmdID= 20001  min= 0  max= 7  step= 1  format= %0.0f  div_scale= 1 
					Min = 0  Max = 7  Step = 1 "
		::= { iqudc32CmdEntry 20001 }


	iqudc32NoiseReductionRecursiveMode20002 OBJECT-TYPE
		SYNTAX		INTEGER {
							val-Auto(0),
							val-Manual(1)
							}
		MAX-ACCESS		read-write
		STATUS			current
		DESCRIPTION
				"TYPE: - RadiobuttonList
				 PAGE: - Video-Ch1
					Mode  cmdID= 20002 
					Auto  value= 0  
					Manual  value= 1  "
		::= { iqudc32CmdEntry 20002 }


	iqudc32VideoCh1NoiseReductionThreshold OBJECT-TYPE
		SYNTAX		INTEGER
		MAX-ACCESS		read-write
		STATUS			current
		DESCRIPTION
				"TYPE: - Number
				 PAGE: - Video-Ch1
					Threshold  cmdID= 20008  min= 0  max= 7  step= 1  format= %0.0f  div_scale= 1 
					Min = 0  Max = 7  Step = 1 "
		::= { iqudc32CmdEntry 20008 }


	iqudc32NoiseReductionSpatialLevel20011 OBJECT-TYPE
		SYNTAX		INTEGER
		MAX-ACCESS		read-write
		STATUS			current
		DESCRIPTION
				"TYPE: - Number
				 PAGE: - Video-Ch1
					Level  cmdID= 20011  min= 0  max= 7  step= 1  format= %0.0f  div_scale= 1 
					Min = 0  Max = 7  Step = 1 "
		::= { iqudc32CmdEntry 20011 }


	iqudc32NoiseReductionSpatialMode20010 OBJECT-TYPE
		SYNTAX		INTEGER {
							val-Auto(0),
							val-Manual(1)
							}
		MAX-ACCESS		read-write
		STATUS			current
		DESCRIPTION
				"TYPE: - RadiobuttonList
				 PAGE: - Video-Ch1
					Mode  cmdID= 20010 
					Auto  value= 0  
					Manual  value= 1  "
		::= { iqudc32CmdEntry 20010 }


	iqudc32MenuVideoCh1Threshold OBJECT-TYPE
		SYNTAX		INTEGER
		MAX-ACCESS		read-write
		STATUS			current
		DESCRIPTION
				"TYPE: - Number
				 PAGE: - Video-Ch1
					Threshold  cmdID= 20012  min= 1  max= 4  step= 1  format= %0.0f  div_scale= 1 
					Min = 1  Max = 4  Step = 1 "
		::= { iqudc32CmdEntry 20012 }


	iqudc32MenuVideoCh1SplitScreen OBJECT-TYPE
		SYNTAX		INTEGER { disable(0), enable(1) }
		MAX-ACCESS		read-write
		STATUS			current
		DESCRIPTION
				"TYPE: - Checkbox
				 PAGE: - Video-Ch1
					Split Screen  cmdID= 20013 "
		::= { iqudc32CmdEntry 20013 }


	iqudc32VideoCh2ProcAmpEnable OBJECT-TYPE
		SYNTAX		INTEGER { disable(0), enable(1) }
		MAX-ACCESS		read-write
		STATUS			current
		DESCRIPTION
				"TYPE: - Checkbox
				 PAGE: - Video-Ch2
					Enable  cmdID= 20204 "
		::= { iqudc32CmdEntry 20204 }


	iqudc32VideoCh2ProcAmpContrast OBJECT-TYPE
		SYNTAX		INTEGER
		MAX-ACCESS		read-write
		STATUS			current
		DESCRIPTION
				"TYPE: - Number
				 PAGE: - Video-Ch2
					Contrast  cmdID= 20200  min= -60  max= 60  step= 2  format= %0.1fdB  div_scale= 10 
					Min = -6.0dB  Max = 6.0dB  Step = 0.2dB "
		::= { iqudc32CmdEntry 20200 }


	iqudc32VideoCh2ProcAmpSaturation OBJECT-TYPE
		SYNTAX		INTEGER
		MAX-ACCESS		read-write
		STATUS			current
		DESCRIPTION
				"TYPE: - Number
				 PAGE: - Video-Ch2
					Saturation  cmdID= 20201  min= -60  max= 60  step= 2  format= %0.1fdB  div_scale= 10 
					Min = -6.0dB  Max = 6.0dB  Step = 0.2dB "
		::= { iqudc32CmdEntry 20201 }


	iqudc32VideoCh2ProcAmpBlackLevel OBJECT-TYPE
		SYNTAX		INTEGER
		MAX-ACCESS		read-write
		STATUS			current
		DESCRIPTION
				"TYPE: - Number
				 PAGE: - Video-Ch2
					Black Level  cmdID= 20202  min= -1000  max= 1000  step= 8  format= %0.1fmV  div_scale= 10 
					Min = -100.0mV  Max = 100.0mV  Step = 0.8mV "
		::= { iqudc32CmdEntry 20202 }


	iqudc32VideoCh2ProcAmpGamma OBJECT-TYPE
		SYNTAX		INTEGER
		MAX-ACCESS		read-write
		STATUS			current
		DESCRIPTION
				"TYPE: - Number
				 PAGE: - Video-Ch2
					Gamma  cmdID= 20203  min= 4  max= 17  step= 1  format= %0.1f  div_scale= 10 
					Min = 0.4  Max = 1.7  Step = 0.1 "
		::= { iqudc32CmdEntry 20203 }


	iqudc32VideoCh2ProcAmpYCOffset OBJECT-TYPE
		SYNTAX		INTEGER
		MAX-ACCESS		read-write
		STATUS			current
		DESCRIPTION
				"TYPE: - Number
				 PAGE: - Video-Ch2
					YC Offset  cmdID= 20214  min= -20  max= 20  step= 2  format= %0.0f  div_scale= 1 
					Min = -20  Max = 20  Step = 2 "
		::= { iqudc32CmdEntry 20214 }


	iqudc32VideoCh2ProcAmpMasterGain OBJECT-TYPE
		SYNTAX		INTEGER
		MAX-ACCESS		read-write
		STATUS			current
		DESCRIPTION
				"TYPE: - Number
				 PAGE: - Video-Ch2
					Master Gain  cmdID= 20215  min= -60  max= 60  step= 2  format= %0.1fdB  div_scale= 10 
					Min = -6.0dB  Max = 6.0dB  Step = 0.2dB "
		::= { iqudc32CmdEntry 20215 }


	iqudc32VideoCh2NonlinearEnhancerEnable OBJECT-TYPE
		SYNTAX		INTEGER { disable(0), enable(1) }
		MAX-ACCESS		read-write
		STATUS			current
		DESCRIPTION
				"TYPE: - Checkbox
				 PAGE: - Video-Ch2
					Enable  cmdID= 20150 "
		::= { iqudc32CmdEntry 20150 }


	iqudc32VideoCh2NonlinearEnhancerLevel OBJECT-TYPE
		SYNTAX		INTEGER
		MAX-ACCESS		read-write
		STATUS			current
		DESCRIPTION
				"TYPE: - Number
				 PAGE: - Video-Ch2
					Level  cmdID= 20153  min= 0  max= 192  step= 1  format= %0.0f  div_scale= 1 
					Min = 0  Max = 192  Step = 1 "
		::= { iqudc32CmdEntry 20153 }


	iqudc32VideoCh2NonlinearEnhancerMode OBJECT-TYPE
		SYNTAX		INTEGER {
							val-Low(0),
							val-Medium(1),
							val-High(2),
							val-Super(3),
							val-Manual(4)
							}
		MAX-ACCESS		read-write
		STATUS			current
		DESCRIPTION
				"TYPE: - RadiobuttonList
				 PAGE: - Video-Ch2
					Mode  cmdID= 20151 
					Low  value= 0  
					Medium  value= 1  
					High  value= 2  
					Super  value= 3  
					Manual  value= 4  "
		::= { iqudc32CmdEntry 20151 }


	iqudc32MenuVideoCh2FrequencyBand20152 OBJECT-TYPE
		SYNTAX		INTEGER {
							val-Low(0),
							val-Medium(1),
							val-High(2)
							}
		MAX-ACCESS		read-write
		STATUS			current
		DESCRIPTION
				"TYPE: - RadiobuttonList
				 PAGE: - Video-Ch2
					Frequency Band  cmdID= 20152 
					Low  value= 0  
					Medium  value= 1  
					High  value= 2  "
		::= { iqudc32CmdEntry 20152 }


	iqudc32MenuVideoCh2NoiseRejection OBJECT-TYPE
		SYNTAX		INTEGER
		MAX-ACCESS		read-write
		STATUS			current
		DESCRIPTION
				"TYPE: - Number
				 PAGE: - Video-Ch2
					Noise Rejection  cmdID= 20154  min= 0  max= 100  step= 1  format= %0.0f  div_scale= 1 
					Min = 0  Max = 100  Step = 1 "
		::= { iqudc32CmdEntry 20154 }


	iqudc32VideoCh2ConversionAperturePreset OBJECT-TYPE
		SYNTAX		INTEGER { noAction(0),val-Preset(1) }
		MAX-ACCESS		read-write
		STATUS			current
		DESCRIPTION
				"TYPE: - Button
				 PAGE: - Video-Ch2
					Preset  cmdID= 20262  value= 1  "
		::= { iqudc32CmdEntry 20262 }


	iqudc32ConversionApertureHorizontalSharpness30200 OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch2
					Sharpness  cmdID= 30200 
					Soft 2  value= 0  
					Soft 1  value= 1  
					Normal  value= 2  
					Sharp 1  value= 3  
					Sharp 2  value= 4  "
		::= { iqudc32CmdEntry 30200 }


	iqudc32MenuVideoCh2Detail OBJECT-TYPE
		SYNTAX		INTEGER {
							val-Low-2(0),
							val-Low-1(1),
							val-Normal(2),
							val-High-1(3),
							val-High-2(4)
							}
		MAX-ACCESS		read-write
		STATUS			current
		DESCRIPTION
				"TYPE: - RadiobuttonList
				 PAGE: - Video-Ch2
					Detail  cmdID= 30201 
					Low 2  value= 0  
					Low 1  value= 1  
					Normal  value= 2  
					High 1  value= 3  
					High 2  value= 4  "
		::= { iqudc32CmdEntry 30201 }


	iqudc32VideoCh2VerticalLevel OBJECT-TYPE
		SYNTAX		INTEGER {
							val-Soft-2(0),
							val-Soft-1(1),
							val-Normal(2),
							val-Sharp-1(3),
							val-Sharp-2(4)
							}
		MAX-ACCESS		read-write
		STATUS			current
		DESCRIPTION
				"TYPE: - RadiobuttonList
				 PAGE: - Video-Ch2
					Level  cmdID= 20161 
					Soft 2  value= 0  
					Soft 1  value= 1  
					Normal  value= 2  
					Sharp 1  value= 3  
					Sharp 2  value= 4  "
		::= { iqudc32CmdEntry 20161 }


	iqudc32MenuVideoCh2FrequencyBand20160 OBJECT-TYPE
		SYNTAX		INTEGER {
							val-Low(0),
							val-Medium(1),
							val-High(2)
							}
		MAX-ACCESS		read-write
		STATUS			current
		DESCRIPTION
				"TYPE: - RadiobuttonList
				 PAGE: - Video-Ch2
					Frequency Band  cmdID= 20160 
					Low  value= 0  
					Medium  value= 1  
					High  value= 2  "
		::= { iqudc32CmdEntry 20160 }


	iqudc32VideoCh2NoiseReductionEnable OBJECT-TYPE
		SYNTAX		INTEGER { disable(0), enable(1) }
		MAX-ACCESS		read-write
		STATUS			current
		DESCRIPTION
				"TYPE: - Checkbox
				 PAGE: - Video-Ch2
					Enable  cmdID= 20104 "
		::= { iqudc32CmdEntry 20104 }


	iqudc32NoiseReductionRecursiveLuma20105 OBJECT-TYPE
		SYNTAX		INTEGER
		MAX-ACCESS		read-write
		STATUS			current
		DESCRIPTION
				"TYPE: - Number
				 PAGE: - Video-Ch2
					Luma  cmdID= 20105  min= 0  max= 7  step= 1  format= %0.0f  div_scale= 1 
					Min = 0  Max = 7  Step = 1 "
		::= { iqudc32CmdEntry 20105 }


	iqudc32NoiseReductionRecursiveChroma20101 OBJECT-TYPE
		SYNTAX		INTEGER
		MAX-ACCESS		read-write
		STATUS			current
		DESCRIPTION
				"TYPE: - Number
				 PAGE: - Video-Ch2
					Chroma  cmdID= 20101  min= 0  max= 7  step= 1  format= %0.0f  div_scale= 1 
					Min = 0  Max = 7  Step = 1 "
		::= { iqudc32CmdEntry 20101 }


	iqudc32NoiseReductionRecursiveMode20107 OBJECT-TYPE
		SYNTAX		INTEGER {
							val-Auto(0),
							val-Manual(1)
							}
		MAX-ACCESS		read-write
		STATUS			current
		DESCRIPTION
				"TYPE: - RadiobuttonList
				 PAGE: - Video-Ch2
					Mode  cmdID= 20107 
					Auto  value= 0  
					Manual  value= 1  "
		::= { iqudc32CmdEntry 20107 }


	iqudc32VideoCh2NoiseReductionThreshold OBJECT-TYPE
		SYNTAX		INTEGER
		MAX-ACCESS		read-write
		STATUS			current
		DESCRIPTION
				"TYPE: - Number
				 PAGE: - Video-Ch2
					Threshold  cmdID= 20108  min= 0  max= 7  step= 1  format= %0.0f  div_scale= 1 
					Min = 0  Max = 7  Step = 1 "
		::= { iqudc32CmdEntry 20108 }


	iqudc32NoiseReductionSpatialLevel20111 OBJECT-TYPE
		SYNTAX		INTEGER
		MAX-ACCESS		read-write
		STATUS			current
		DESCRIPTION
				"TYPE: - Number
				 PAGE: - Video-Ch2
					Level  cmdID= 20111  min= 0  max= 7  step= 1  format= %0.0f  div_scale= 1 
					Min = 0  Max = 7  Step = 1 "
		::= { iqudc32CmdEntry 20111 }


	iqudc32NoiseReductionSpatialMode20110 OBJECT-TYPE
		SYNTAX		INTEGER {
							val-Auto(0),
							val-Manual(1)
							}
		MAX-ACCESS		read-write
		STATUS			current
		DESCRIPTION
				"TYPE: - RadiobuttonList
				 PAGE: - Video-Ch2
					Mode  cmdID= 20110 
					Auto  value= 0  
					Manual  value= 1  "
		::= { iqudc32CmdEntry 20110 }


	iqudc32MenuVideoCh2Threshold OBJECT-TYPE
		SYNTAX		INTEGER
		MAX-ACCESS		read-write
		STATUS			current
		DESCRIPTION
				"TYPE: - Number
				 PAGE: - Video-Ch2
					Threshold  cmdID= 20112  min= 1  max= 4  step= 1  format= %0.0f  div_scale= 1 
					Min = 1  Max = 4  Step = 1 "
		::= { iqudc32CmdEntry 20112 }


	iqudc32MenuVideoCh2SplitScreen OBJECT-TYPE
		SYNTAX		INTEGER { disable(0), enable(1) }
		MAX-ACCESS		read-write
		STATUS			current
		DESCRIPTION
				"TYPE: - Checkbox
				 PAGE: - Video-Ch2
					Split Screen  cmdID= 20113 "
		::= { iqudc32CmdEntry 20113 }


	iqudc32MenuVideoCh2NewDisplay OBJECT-TYPE
		SYNTAX		RollCallString
		MAX-ACCESS		read-only
		STATUS			current
		DESCRIPTION
				"TYPE: - Display
				 PAGE: - Video-Ch2
					New Display  cmdID= 44447  format=   "
		::= { iqudc32CmdEntry 44447 }


	iqudc32ConvertCh1UpConversionCleanEdgeUpconver OBJECT-TYPE
		SYNTAX		INTEGER { disable(0), enable(1) }
		MAX-ACCESS		read-write
		STATUS			current
		DESCRIPTION
				"TYPE: - Checkbox
				 PAGE: - Convert-Ch1
					Clean Edge Upconver  cmdID= 30072 "
		::= { iqudc32CmdEntry 30072 }


	iqudc32ConvertCh1MotionProcessing OBJECT-TYPE
		SYNTAX		INTEGER { disable(0), enable(1) }
		MAX-ACCESS		read-write
		STATUS			current
		DESCRIPTION
				"TYPE: - Checkbox
				 PAGE: - Convert-Ch1
					Motion Process  cmdID= 30005 "
		::= { iqudc32CmdEntry 30005 }


	iqudc32ConvertCh1MotionProcessingEnhancedMotion OBJECT-TYPE
		SYNTAX		INTEGER { disable(0), enable(1) }
		MAX-ACCESS		read-write
		STATUS			current
		DESCRIPTION
				"TYPE: - Checkbox
				 PAGE: - Convert-Ch1
					Enhanced Motion  cmdID= 30002 "
		::= { iqudc32CmdEntry 30002 }


	iqudc32ConvertCh1MotionProcessingStillProcess OBJECT-TYPE
		SYNTAX		INTEGER { disable(0), enable(1) }
		MAX-ACCESS		read-write
		STATUS			current
		DESCRIPTION
				"TYPE: - Checkbox
				 PAGE: - Convert-Ch1
					Still Process  cmdID= 30003 "
		::= { iqudc32CmdEntry 30003 }


	iqudc32ConvertCh1MotionProcessingEnhancedStill OBJECT-TYPE
		SYNTAX		INTEGER { disable(0), enable(1) }
		MAX-ACCESS		read-write
		STATUS			current
		DESCRIPTION
				"TYPE: - Checkbox
				 PAGE: - Convert-Ch1
					Enhanced Still  cmdID= 30004 "
		::= { iqudc32CmdEntry 30004 }


	iqudc32ConvertCh1MotionProcessingEnhancedFilm OBJECT-TYPE
		SYNTAX		INTEGER { disable(0), enable(1) }
		MAX-ACCESS		read-write
		STATUS			current
		DESCRIPTION
				"TYPE: - Checkbox
				 PAGE: - Convert-Ch1
					Enhanced Film  cmdID= 30070 "
		::= { iqudc32CmdEntry 30070 }


	iqudc32ConvertCh1MotionProcessingEnhancedDeinterla OBJECT-TYPE
		SYNTAX		INTEGER { disable(0), enable(1) }
		MAX-ACCESS		read-write
		STATUS			current
		DESCRIPTION
				"TYPE: - Checkbox
				 PAGE: - Convert-Ch1
					Enhanced De-interla  cmdID= 30074 "
		::= { iqudc32CmdEntry 30074 }


	iqudc32ConvertCh1MotionProcessingCleanCut OBJECT-TYPE
		SYNTAX		INTEGER { disable(0), enable(1) }
		MAX-ACCESS		read-write
		STATUS			current
		DESCRIPTION
				"TYPE: - Checkbox
				 PAGE: - Convert-Ch1
					Clean Cut  cmdID= 30073 "
		::= { iqudc32CmdEntry 30073 }


	iqudc32ConvertCh1InputCadenceFilmCadence OBJECT-TYPE
		SYNTAX		INTEGER { disable(0), enable(1) }
		MAX-ACCESS		read-write
		STATUS			current
		DESCRIPTION
				"TYPE: - Checkbox
				 PAGE: - Convert-Ch1
					Film Cadence  cmdID= 30050 "
		::= { iqudc32CmdEntry 30050 }


	iqudc32MenuConvertCh1 OBJECT-TYPE
		SYNTAX		INTEGER {
							val-2-3(0),
							val-2-2-psf(1)
							}
		MAX-ACCESS		read-write
		STATUS			current
		DESCRIPTION
				"TYPE: - RadiobuttonList
				 PAGE: - Convert-Ch1
					59 Cadence  cmdID= 30051 
					2:3  value= 0  
					2:2 (psf)  value= 1  
					59 Cadence  cmdID= 30051 "
		::= { iqudc32CmdEntry 30051 }


	iqudc32MenuConvertCh123Source30052 OBJECT-TYPE
		SYNTAX		INTEGER {
							val-Automatic(0),
							val-Input-Timecode(1)
							}
		MAX-ACCESS		read-write
		STATUS			current
		DESCRIPTION
				"TYPE: - RadiobuttonList
				 PAGE: - Convert-Ch1
					2:3 Source  cmdID= 30052 
					Automatic  value= 0  
					Input Timecode  value= 1  "
		::= { iqudc32CmdEntry 30052 }


	iqudc32MenuConvertCh123StartHour30053 OBJECT-TYPE
		SYNTAX		INTEGER
		MAX-ACCESS		read-write
		STATUS			current
		DESCRIPTION
				"TYPE: - Number
				 PAGE: - Convert-Ch1
					2:3 Start Hour  cmdID= 30053  min= 0  max= 23  step= 1  format= %0.0f  div_scale= 1 
					Min = 0  Max = 23  Step = 1 "
		::= { iqudc32CmdEntry 30053 }


	iqudc32ConvertCh1OutputCadenceFilmCadence OBJECT-TYPE
		SYNTAX		INTEGER { disable(0), enable(1) }
		MAX-ACCESS		read-write
		STATUS			current
		DESCRIPTION
				"TYPE: - Checkbox
				 PAGE: - Convert-Ch1
					Film Cadence  cmdID= 30060 "
		::= { iqudc32CmdEntry 30060 }


	iqudc32ConvertCh1OutputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch1
					59 Cadence  cmdID= 30061 
					2:3  value= 0  
					2:2 (psf)  value= 1  "
		::= { iqudc32CmdEntry 30061 }


	iqudc32MenuConvertCh123Source30062 OBJECT-TYPE
		SYNTAX		INTEGER {
							val-Free-Run(0),
							val-Output-Timecode(1)
							}
		MAX-ACCESS		read-write
		STATUS			current
		DESCRIPTION
				"TYPE: - RadiobuttonList
				 PAGE: - Convert-Ch1
					2:3 Source  cmdID= 30062 
					Free Run  value= 0  
					Output Timecode  value= 1  "
		::= { iqudc32CmdEntry 30062 }


	iqudc32MenuConvertCh123StartHour30063 OBJECT-TYPE
		SYNTAX		INTEGER
		MAX-ACCESS		read-write
		STATUS			current
		DESCRIPTION
				"TYPE: - Number
				 PAGE: - Convert-Ch1
					2:3 Start Hour  cmdID= 30063  min= 0  max= 23  step= 1  format= %0.0f  div_scale= 1 
					Min = 0  Max = 23  Step = 1 "
		::= { iqudc32CmdEntry 30063 }


	iqudc32ConvertCh2UpConversionCleanEdgeUpconver OBJECT-TYPE
		SYNTAX		INTEGER { disable(0), enable(1) }
		MAX-ACCESS		read-write
		STATUS			current
		DESCRIPTION
				"TYPE: - Checkbox
				 PAGE: - Convert-Ch2
					Clean Edge Upconver  cmdID= 30172 "
		::= { iqudc32CmdEntry 30172 }


	iqudc32ConvertCh2MotionProcessing OBJECT-TYPE
		SYNTAX		INTEGER { disable(0), enable(1) }
		MAX-ACCESS		read-write
		STATUS			current
		DESCRIPTION
				"TYPE: - Checkbox
				 PAGE: - Convert-Ch2
					Motion Process  cmdID= 30105 "
		::= { iqudc32CmdEntry 30105 }


	iqudc32ConvertCh2MotionProcessingEnhancedMotion OBJECT-TYPE
		SYNTAX		INTEGER { disable(0), enable(1) }
		MAX-ACCESS		read-write
		STATUS			current
		DESCRIPTION
				"TYPE: - Checkbox
				 PAGE: - Convert-Ch2
					Enhanced Motion  cmdID= 30102 "
		::= { iqudc32CmdEntry 30102 }


	iqudc32ConvertCh2MotionProcessingStillProcess OBJECT-TYPE
		SYNTAX		INTEGER { disable(0), enable(1) }
		MAX-ACCESS		read-write
		STATUS			current
		DESCRIPTION
				"TYPE: - Checkbox
				 PAGE: - Convert-Ch2
					Still Process  cmdID= 30103 "
		::= { iqudc32CmdEntry 30103 }


	iqudc32ConvertCh2MotionProcessingEnhancedStill OBJECT-TYPE
		SYNTAX		INTEGER { disable(0), enable(1) }
		MAX-ACCESS		read-write
		STATUS			current
		DESCRIPTION
				"TYPE: - Checkbox
				 PAGE: - Convert-Ch2
					Enhanced Still  cmdID= 30104 "
		::= { iqudc32CmdEntry 30104 }


	iqudc32ConvertCh2MotionProcessingEnhancedFilm OBJECT-TYPE
		SYNTAX		INTEGER { disable(0), enable(1) }
		MAX-ACCESS		read-write
		STATUS			current
		DESCRIPTION
				"TYPE: - Checkbox
				 PAGE: - Convert-Ch2
					Enhanced Film  cmdID= 30170 "
		::= { iqudc32CmdEntry 30170 }


	iqudc32ConvertCh2MotionProcessingEnhancedDeinterla OBJECT-TYPE
		SYNTAX		INTEGER { disable(0), enable(1) }
		MAX-ACCESS		read-write
		STATUS			current
		DESCRIPTION
				"TYPE: - Checkbox
				 PAGE: - Convert-Ch2
					Enhanced De-interla  cmdID= 30174 "
		::= { iqudc32CmdEntry 30174 }


	iqudc32ConvertCh2MotionProcessingCleanCut OBJECT-TYPE
		SYNTAX		INTEGER { disable(0), enable(1) }
		MAX-ACCESS		read-write
		STATUS			current
		DESCRIPTION
				"TYPE: - Checkbox
				 PAGE: - Convert-Ch2
					Clean Cut  cmdID= 30173 "
		::= { iqudc32CmdEntry 30173 }


	iqudc32ConvertCh2InputCadenceFilmCadence OBJECT-TYPE
		SYNTAX		INTEGER { disable(0), enable(1) }
		MAX-ACCESS		read-write
		STATUS			current
		DESCRIPTION
				"TYPE: - Checkbox
				 PAGE: - Convert-Ch2
					Film Cadence  cmdID= 30150 "
		::= { iqudc32CmdEntry 30150 }


	iqudc32ConvertCh2InputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch2
					59 Cadence  cmdID= 30151 
					2:3  value= 0  
					2:2 (psf)  value= 1  "
		::= { iqudc32CmdEntry 30151 }


	iqudc32MenuConvertCh223Source30152 OBJECT-TYPE
		SYNTAX		INTEGER {
							val-Automatic(0),
							val-Input-Timecode(1)
							}
		MAX-ACCESS		read-write
		STATUS			current
		DESCRIPTION
				"TYPE: - RadiobuttonList
				 PAGE: - Convert-Ch2
					2:3 Source  cmdID= 30152 
					Automatic  value= 0  
					Input Timecode  value= 1  "
		::= { iqudc32CmdEntry 30152 }


	iqudc32MenuConvertCh223StartHour30153 OBJECT-TYPE
		SYNTAX		INTEGER
		MAX-ACCESS		read-write
		STATUS			current
		DESCRIPTION
				"TYPE: - Number
				 PAGE: - Convert-Ch2
					2:3 Start Hour  cmdID= 30153  min= 0  max= 23  step= 1  format= %0.0f  div_scale= 1 
					Min = 0  Max = 23  Step = 1 "
		::= { iqudc32CmdEntry 30153 }


	iqudc32ConvertCh2OutputCadenceFilmCadence OBJECT-TYPE
		SYNTAX		INTEGER { disable(0), enable(1) }
		MAX-ACCESS		read-write
		STATUS			current
		DESCRIPTION
				"TYPE: - Checkbox
				 PAGE: - Convert-Ch2
					Film Cadence  cmdID= 30160 "
		::= { iqudc32CmdEntry 30160 }


	iqudc32ConvertCh2OutputCadence59Cadence OBJECT-TYPE
		SYNTAX		INTEGER {
							val-2-3(0),
							val-2-2-psf(1)
							}
		MAX-ACCESS		read-write
		STATUS			current
		DESCRIPTION
				"TYPE: - RadiobuttonList
				 PAGE: - Convert-Ch2
					59 Cadence  cmdID= 30161 
					2:3  value= 0  
					2:2 (psf)  value= 1  "
		::= { iqudc32CmdEntry 30161 }


	iqudc32MenuConvertCh223Source30162 OBJECT-TYPE
		SYNTAX		INTEGER {
							val-Free-Run(0),
							val-Output-Timecode(1)
							}
		MAX-ACCESS		read-write
		STATUS			current
		DESCRIPTION
				"TYPE: - RadiobuttonList
				 PAGE: - Convert-Ch2
					2:3 Source  cmdID= 30162 
					Free Run  value= 0  
					Output Timecode  value= 1  "
		::= { iqudc32CmdEntry 30162 }


	iqudc32MenuConvertCh223StartHour30163 OBJECT-TYPE
		SYNTAX		INTEGER
		MAX-ACCESS		read-write
		STATUS			current
		DESCRIPTION
				"TYPE: - Number
				 PAGE: - Convert-Ch2
					2:3 Start Hour  cmdID= 30163  min= 0  max= 23  step= 1  format= %0.0f  div_scale= 1 
					Min = 0  Max = 23  Step = 1 "
		::= { iqudc32CmdEntry 30163 }


	iqudc32MenuConvertCh2NewDisplay OBJECT-TYPE
		SYNTAX		RollCallString
		MAX-ACCESS		read-only
		STATUS			current
		DESCRIPTION
				"TYPE: - Display
				 PAGE: - Convert-Ch2
					New Display  cmdID= 44448  format=   "
		::= { iqudc32CmdEntry 44448 }


	iqudc32MenuARCSidebarKeyerSyncMode40007 OBJECT-TYPE
		SYNTAX		INTEGER { disable(0), enable(1) }
		MAX-ACCESS		read-write
		STATUS			current
		DESCRIPTION
				"TYPE: - Checkbox
					Sync Mode  cmdID= 40007 "
		::= { iqudc32CmdEntry 40007 }


	iqudc32MenuARCSidebarKeyerSignallingDetected64020 OBJECT-TYPE
		SYNTAX		RollCallString
		MAX-ACCESS		read-only
		STATUS			current
		DESCRIPTION
				"TYPE: - Display
					Signalling Detected  cmdID= 64020  format=   "
		::= { iqudc32CmdEntry 64020 }


	iqudc32ARCSidebarKeyerSidebarKeyingOuMode40017 OBJECT-TYPE
		SYNTAX		INTEGER {
							val-Off(0),
							val-Output-Crop(1),
							val-Sidebar-Key(2)
							}
		MAX-ACCESS		read-write
		STATUS			current
		DESCRIPTION
				"TYPE: - RadiobuttonList
					Mode  cmdID= 40017 
					Off  value= 0  
					Output Crop  value= 1  
					Sidebar Key  value= 2  "
		::= { iqudc32CmdEntry 40017 }


	iqudc32MenuARCSidebarKeyerSidebarKeySource40018 OBJECT-TYPE
		SYNTAX		INTEGER {
							val-SDI-1(0),
							val-SDI-2(1),
							val-CVBS(2),
							val-SFP-1(3),
							val-SFP-2(4),
							val-Ch-2-Output(20)
							}
		MAX-ACCESS		read-write
		STATUS			current
		DESCRIPTION
				"TYPE: - RadiobuttonList
					Sidebar Key Source  cmdID= 40018 
					SDI 1  value= 0  
					SDI 2  value= 1  
					CVBS  value= 2  
					SFP 1  value= 3  
					SFP 2  value= 4  
					Ch 2 Output  value= 20  "
		::= { iqudc32CmdEntry 40018 }


	iqudc32MenuOutputCropPositioTop OBJECT-TYPE
		SYNTAX		INTEGER
		MAX-ACCESS		read-write
		STATUS			current
		DESCRIPTION
				"TYPE: - Number
					Top  cmdID= 40013  min= 0  max= 99  step= 1  format= %0.0f%%  div_scale= 1 
					Min = 0%  Max = 99%  Step = 1% "
		::= { iqudc32CmdEntry 40013 }


	iqudc32MenuOutputCropPositioBottom OBJECT-TYPE
		SYNTAX		INTEGER
		MAX-ACCESS		read-write
		STATUS			current
		DESCRIPTION
				"TYPE: - Number
					Bottom  cmdID= 40014  min= 0  max= 99  step= 1  format= %0.0f%%  div_scale= 1 
					Min = 0%  Max = 99%  Step = 1% "
		::= { iqudc32CmdEntry 40014 }


	iqudc32MenuOutputCropPositioLeft OBJECT-TYPE
		SYNTAX		INTEGER
		MAX-ACCESS		read-write
		STATUS			current
		DESCRIPTION
				"TYPE: - Number
					Left  cmdID= 40015  min= 0  max= 99  step= 1  format= %0.0f%%  div_scale= 1 
					Min = 0%  Max = 99%  Step = 1% "
		::= { iqudc32CmdEntry 40015 }


	iqudc32MenuOutputCropPositioRight OBJECT-TYPE
		SYNTAX		INTEGER
		MAX-ACCESS		read-write
		STATUS			current
		DESCRIPTION
				"TYPE: - Number
					Right  cmdID= 40016  min= 0  max= 99  step= 1  format= %0.0f%%  div_scale= 1 
					Min = 0%  Max = 99%  Step = 1% "
		::= { iqudc32CmdEntry 40016 }


	iqudc32MenuPostScalingControPostScalingEnable OBJECT-TYPE
		SYNTAX		INTEGER { disable(0), enable(1) }
		MAX-ACCESS		read-write
		STATUS			current
		DESCRIPTION
				"TYPE: - Checkbox
					Post Scaling Enable  cmdID= 40003 "
		::= { iqudc32CmdEntry 40003 }


	iqudc32MenuPostScalingControSize OBJECT-TYPE
		SYNTAX		INTEGER
		MAX-ACCESS		read-write
		STATUS			current
		DESCRIPTION
				"TYPE: - Number
					Size  cmdID= 40008  min= 80  max= 120  step= 1  format= %0.0f%%  div_scale= 1 
					Min = 80%  Max = 120%  Step = 1% "
		::= { iqudc32CmdEntry 40008 }


	iqudc32MenuPostScalingControAspect OBJECT-TYPE
		SYNTAX		INTEGER
		MAX-ACCESS		read-write
		STATUS			current
		DESCRIPTION
				"TYPE: - Number
					Aspect  cmdID= 40009  min= 70  max= 150  step= 1  format= %0.0f%%  div_scale= 1 
					Min = 70%  Max = 150%  Step = 1% "
		::= { iqudc32CmdEntry 40009 }


	iqudc32MenuPostScalingControPan OBJECT-TYPE
		SYNTAX		INTEGER
		MAX-ACCESS		read-write
		STATUS			current
		DESCRIPTION
				"TYPE: - Number
					Pan  cmdID= 40006  min= -50  max= 50  step= 1  format= %0.0f%  div_scale= 1 
					Min = -50 Max = 50 Step = 1"
		::= { iqudc32CmdEntry 40006 }


	iqudc32MenuPostScalingControTilt OBJECT-TYPE
		SYNTAX		INTEGER
		MAX-ACCESS		read-write
		STATUS			current
		DESCRIPTION
				"TYPE: - Number
					Tilt  cmdID= 40002  min= -50  max= 50  step= 1  format= %0.0f%  div_scale= 1 
					Min = -50 Max = 50 Step = 1"
		::= { iqudc32CmdEntry 40002 }


	iqudc32MenuScalerConfigUsePresets OBJECT-TYPE
		SYNTAX		INTEGER { disable(0), enable(1) }
		MAX-ACCESS		read-write
		STATUS			current
		DESCRIPTION
				"TYPE: - Checkbox
				 PAGE: - Scaler Config
					Use Presets  cmdID= 40136 "
		::= { iqudc32CmdEntry 40136 }


	iqudc32ScalerConfigPresetsSDInputis70240030 OBJECT-TYPE
		SYNTAX		INTEGER { disable(0), enable(1) }
		MAX-ACCESS		read-write
		STATUS			current
		DESCRIPTION
				"TYPE: - Checkbox
				 PAGE: - Scaler Config
					SD Input is 702  cmdID= 40030 "
		::= { iqudc32CmdEntry 40030 }


	iqudc32ScalerConfigPresetsSDOutputis70240037 OBJECT-TYPE
		SYNTAX		INTEGER { disable(0), enable(1) }
		MAX-ACCESS		read-write
		STATUS			current
		DESCRIPTION
				"TYPE: - Checkbox
				 PAGE: - Scaler Config
					SD Output is 702  cmdID= 40037 "
		::= { iqudc32CmdEntry 40037 }


	iqudc32PresetsSDCrossConversionSelectStdPreset40031 OBJECT-TYPE
		SYNTAX		INTEGER {
							val-None(0),
							val-16-9-LB-4-3-HC(1),
							val-16-9-LB-16-9-Ana(2),
							val-16-9-LB-14-9-LB(3),
							val-16-9-Ana-4-3-HC(4),
							val-16-9-Ana-16-9-LB(5),
							val-16-9-Ana-14-9-LB(6)
							}
		MAX-ACCESS		read-write
		STATUS			current
		DESCRIPTION
				"TYPE: - RadiobuttonList
				 PAGE: - Scaler Config
					Select Std Preset  cmdID= 40031 
					None  value= 0  
					16:9 LB > 4:3 HC  value= 1  
					16:9 LB > 16:9 Ana  value= 2  
					16:9 LB > 14:9 LB  value= 3  
					16:9 Ana > 4:3 HC  value= 4  
					16:9 Ana > 16:9 LB  value= 5  
					16:9 Ana > 14:9 LB  value= 6  "
		::= { iqudc32CmdEntry 40031 }


	iqudc32ScalerConfigHDCrossConversionSelectStdPreset40032 OBJECT-TYPE
		SYNTAX		INTEGER {
							val-None(0),
							val-14-9-PB-16-9-VC(1),
							val-4-3-PB-16-9-VC(2),
							val-4-3-PB-14-9-PB-VC(3)
							}
		MAX-ACCESS		read-write
		STATUS			current
		DESCRIPTION
				"TYPE: - RadiobuttonList
				 PAGE: - Scaler Config
					Select Std Preset  cmdID= 40032 
					None  value= 0  
					14:9 PB > 16:9 VC  value= 1  
					4:3 PB > 16:9 VC  value= 2  
					4:3 PB > 14:9 PB VC  value= 3  "
		::= { iqudc32CmdEntry 40032 }


	iqudc32ScalerConfigUpConversionSelectStdPreset40033 OBJECT-TYPE
		SYNTAX		INTEGER {
							val-4-3-16-9-VC(0),
							val-4-3-4-3-PB(1),
							val-16-9-LB-16-9(2),
							val-16-9-Ana-16-9(3),
							val-14-9-LB-14-9-PB(4)
							}
		MAX-ACCESS		read-write
		STATUS			current
		DESCRIPTION
				"TYPE: - RadiobuttonList
				 PAGE: - Scaler Config
					Select Std Preset  cmdID= 40033 
					4:3 > 16:9 VC  value= 0  
					4:3 > 4:3 PB  value= 1  
					16:9 LB > 16:9  value= 2  
					16:9 Ana > 16:9  value= 3  
					14:9 LB > 14:9 PB  value= 4  "
		::= { iqudc32CmdEntry 40033 }


	iqudc32ScalerConfigDownConversionSelectStdPreset40035 OBJECT-TYPE
		SYNTAX		INTEGER {
							val-16-9-4-3-HC(0),
							val-16-9-16-9-LB(1),
							val-16-9-16-9-Ana(2),
							val-4-3-PB-4-3(3),
							val-14-9-PB-14-9-LB(4)
							}
		MAX-ACCESS		read-write
		STATUS			current
		DESCRIPTION
				"TYPE: - RadiobuttonList
				 PAGE: - Scaler Config
					Select Std Preset  cmdID= 40035 
					16:9 > 4:3 HC  value= 0  
					16:9 > 16:9 LB  value= 1  
					16:9 > 16:9 Ana  value= 2  
					4:3 PB > 4:3  value= 3  
					14:9 PB > 14:9 LB  value= 4  "
		::= { iqudc32CmdEntry 40035 }


	iqudc32ScalerConfigInputConfigInputSignallingSo40100 OBJECT-TYPE
		SYNTAX		INTEGER {
							val-SMPTE-2016(0),
							val-L23-ETSI(1),
							val-L23-AFD(2),
							val-VI-SMPTE(3),
							val-VI-AFD(4)
							}
		MAX-ACCESS		read-write
		STATUS			current
		DESCRIPTION
				"TYPE: - RadiobuttonList
				 PAGE: - Scaler Config
					Input Signalling So  cmdID= 40100 
					SMPTE 2016  value= 0  
					L23 ETSI  value= 1  
					L23 AFD  value= 2  
					VI SMPTE  value= 3  
					VI AFD  value= 4  "
		::= { iqudc32CmdEntry 40100 }


	iqudc32ScalerConfigIfInputSignallingForceInputFormat40135 OBJECT-TYPE
		SYNTAX		INTEGER { disable(0), enable(1) }
		MAX-ACCESS		read-write
		STATUS			current
		DESCRIPTION
				"TYPE: - Checkbox
				 PAGE: - Scaler Config
					Force Input Format  cmdID= 40135 "
		::= { iqudc32CmdEntry 40135 }


	iqudc32ScalerConfigIfInputSignallingSDInputFormat40010 OBJECT-TYPE
		SYNTAX		INTEGER {
							val-Normal(0),
							val-Anamorphic(1),
							val-16-9-Letterbox(2),
							val-14-9-Letterbox(3)
							}
		MAX-ACCESS		read-write
		STATUS			current
		DESCRIPTION
				"TYPE: - RadiobuttonList
				 PAGE: - Scaler Config
					SD Input Format  cmdID= 40010 
					Normal  value= 0  
					Anamorphic  value= 1  
					16:9 Letterbox  value= 2  
					14:9 Letterbox  value= 3  "
		::= { iqudc32CmdEntry 40010 }


	iqudc32MenuScalerConfigHDInputFormat OBJECT-TYPE
		SYNTAX		INTEGER {
							val-Normal(0),
							val-14-9-Pillarbox(1),
							val-4-3-Pillarbox(2)
							}
		MAX-ACCESS		read-write
		STATUS			current
		DESCRIPTION
				"TYPE: - RadiobuttonList
				 PAGE: - Scaler Config
					HD Input Format  cmdID= 40050 
					Normal  value= 0  
					14:9 Pillarbox  value= 1  
					4:3 Pillarbox  value= 2  "
		::= { iqudc32CmdEntry 40050 }


	iqudc32ScalerConfigOutputConfigConversionScaling40012 OBJECT-TYPE
		SYNTAX		INTEGER {
							val-Fit-to-Height(0),
							val-Fit-to-Width(1),
							val-14-9(2)
							}
		MAX-ACCESS		read-write
		STATUS			current
		DESCRIPTION
				"TYPE: - RadiobuttonList
				 PAGE: - Scaler Config
					Conversion Scaling  cmdID= 40012 
					Fit to Height  value= 0  
					Fit to Width  value= 1  
					14:9  value= 2  "
		::= { iqudc32CmdEntry 40012 }


	iqudc32MenuScalerConfigSDOutputFormat OBJECT-TYPE
		SYNTAX		INTEGER {
							val-Normal(0),
							val-Anamorphic(1)
							}
		MAX-ACCESS		read-write
		STATUS			current
		DESCRIPTION
				"TYPE: - RadiobuttonList
				 PAGE: - Scaler Config
					SD Output Format  cmdID= 40011 
					Normal  value= 0  
					Anamorphic  value= 1  "
		::= { iqudc32CmdEntry 40011 }


	iqudc32MenuMemoriesRecallMemory OBJECT-TYPE
		SYNTAX		INTEGER {
							val-None-Selected(0),
							val-Arc-Memory-1(1),
							val-Arc-Memory-2(2),
							val-Arc-Memory-3(3),
							val-Arc-Memory-4(4),
							val-Arc-Memory-5(5),
							val-Arc-Memory-6(6),
							val-Arc-Memory-7(7),
							val-Arc-Memory-8(8),
							val-Arc-Memory-9(9),
							val-Arc-Memory-10(10),
							val-Arc-Memory-11(11),
							val-Arc-Memory-12(12),
							val-Arc-Memory-13(13),
							val-Arc-Memory-14(14),
							val-Arc-Memory-15(15),
							val-Arc-Memory-16(16),
							val-Arc-Memory-17(17),
							val-Arc-Memory-18(18),
							val-Arc-Memory-19(19),
							val-Arc-Memory-20(20),
							val-Arc-Memory-21(21),
							val-Arc-Memory-22(22),
							val-Arc-Memory-23(23),
							val-Arc-Memory-24(24),
							val-Arc-Memory-25(25),
							val-Arc-Memory-26(26),
							val-Arc-Memory-27(27),
							val-Arc-Memory-28(28),
							val-Arc-Memory-29(29),
							val-Arc-Memory-30(30),
							val-Arc-Memory-31(31),
							val-Arc-Memory-32(32)
							}
		MAX-ACCESS		read-write
		STATUS			current
		DESCRIPTION
				"TYPE: - RadiobuttonList
				 PAGE: - Memories
					Recall Memory  cmdID= 64002 
					None Selected  value= 0  
					Arc Memory 1  value= 1  
					Arc Memory 2  value= 2  
					Arc Memory 3  value= 3  
					Arc Memory 4  value= 4  
					Arc Memory 5  value= 5  
					Arc Memory 6  value= 6  
					Arc Memory 7  value= 7  
					Arc Memory 8  value= 8  
					Arc Memory 9  value= 9  
					Arc Memory 10  value= 10  
					Arc Memory 11  value= 11  
					Arc Memory 12  value= 12  
					Arc Memory 13  value= 13  
					Arc Memory 14  value= 14  
					Arc Memory 15  value= 15  
					Arc Memory 16  value= 16  
					Arc Memory 17  value= 17  
					Arc Memory 18  value= 18  
					Arc Memory 19  value= 19  
					Arc Memory 20  value= 20  
					Arc Memory 21  value= 21  
					Arc Memory 22  value= 22  
					Arc Memory 23  value= 23  
					Arc Memory 24  value= 24  
					Arc Memory 25  value= 25  
					Arc Memory 26  value= 26  
					Arc Memory 27  value= 27  
					Arc Memory 28  value= 28  
					Arc Memory 29  value= 29  
					Arc Memory 30  value= 30  
					Arc Memory 31  value= 31  
					Arc Memory 32  value= 32  "
		::= { iqudc32CmdEntry 64002 }


	iqudc32MenuMemoriesSelMemory OBJECT-TYPE
		SYNTAX		INTEGER {
							val-Arc-Memory-1(1),
							val-Arc-Memory-2(2),
							val-Arc-Memory-3(3),
							val-Arc-Memory-4(4),
							val-Arc-Memory-5(5),
							val-Arc-Memory-6(6),
							val-Arc-Memory-7(7),
							val-Arc-Memory-8(8),
							val-Arc-Memory-9(9),
							val-Arc-Memory-10(10),
							val-Arc-Memory-11(11),
							val-Arc-Memory-12(12),
							val-Arc-Memory-13(13),
							val-Arc-Memory-14(14),
							val-Arc-Memory-15(15),
							val-Arc-Memory-16(16),
							val-Arc-Memory-17(17),
							val-Arc-Memory-18(18),
							val-Arc-Memory-19(19),
							val-Arc-Memory-20(20),
							val-Arc-Memory-21(21),
							val-Arc-Memory-22(22),
							val-Arc-Memory-23(23),
							val-Arc-Memory-24(24),
							val-Arc-Memory-25(25),
							val-Arc-Memory-26(26),
							val-Arc-Memory-27(27),
							val-Arc-Memory-28(28),
							val-Arc-Memory-29(29),
							val-Arc-Memory-30(30),
							val-Arc-Memory-31(31),
							val-Arc-Memory-32(32)
							}
		MAX-ACCESS		read-write
		STATUS			current
		DESCRIPTION
				"TYPE: - RadiobuttonList
				 PAGE: - Memories
					Sel Memory  cmdID= 64000 
					Arc Memory 1  value= 1  
					Arc Memory 2  value= 2  
					Arc Memory 3  value= 3  
					Arc Memory 4  value= 4  
					Arc Memory 5  value= 5  
					Arc Memory 6  value= 6  
					Arc Memory 7  value= 7  
					Arc Memory 8  value= 8  
					Arc Memory 9  value= 9  
					Arc Memory 10  value= 10  
					Arc Memory 11  value= 11  
					Arc Memory 12  value= 12  
					Arc Memory 13  value= 13  
					Arc Memory 14  value= 14  
					Arc Memory 15  value= 15  
					Arc Memory 16  value= 16  
					Arc Memory 17  value= 17  
					Arc Memory 18  value= 18  
					Arc Memory 19  value= 19  
					Arc Memory 20  value= 20  
					Arc Memory 21  value= 21  
					Arc Memory 22  value= 22  
					Arc Memory 23  value= 23  
					Arc Memory 24  value= 24  
					Arc Memory 25  value= 25  
					Arc Memory 26  value= 26  
					Arc Memory 27  value= 27  
					Arc Memory 28  value= 28  
					Arc Memory 29  value= 29  
					Arc Memory 30  value= 30  
					Arc Memory 31  value= 31  
					Arc Memory 32  value= 32  "
		::= { iqudc32CmdEntry 64000 }


	iqudc32MenuMemoriesSaveMemory OBJECT-TYPE
		SYNTAX		INTEGER { noAction(0),val-Save-Memory(1) }
		MAX-ACCESS		read-write
		STATUS			current
		DESCRIPTION
				"TYPE: - Button
				 PAGE: - Memories
					Save Memory  cmdID= 64001  value= 1  "
		::= { iqudc32CmdEntry 64001 }


	iqudc32MenuMemoriesClearMemory OBJECT-TYPE
		SYNTAX		INTEGER { noAction(0),val-Clear-Memory(1) }
		MAX-ACCESS		read-write
		STATUS			current
		DESCRIPTION
				"TYPE: - Button
				 PAGE: - Memories
					Clear Memory  cmdID= 64005  value= 1  "
		::= { iqudc32CmdEntry 64005 }


	iqudc32MemoriesMemoryNameChangeName64003 OBJECT-TYPE
		SYNTAX		RollCallString
		MAX-ACCESS		read-write
		STATUS			current
		DESCRIPTION
				"TYPE: - Editstring
				 PAGE: - Memories
					Change Name  cmdID= 64003  "
		::= { iqudc32CmdEntry 64003 }


	iqudc32MenuMemoriesLastDisplayMemory OBJECT-TYPE
		SYNTAX		RollCallString
		MAX-ACCESS		read-only
		STATUS			current
		DESCRIPTION
				"TYPE: - Display
				 PAGE: - Memories
					Last Display Memory  cmdID= 64004  format=   "
		::= { iqudc32CmdEntry 64004 }


	iqudc32OutputSignallingCSMPTE2016Mode40130 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - Output Signalling C
					Mode  cmdID= 40130 
					Auto  value= 0  
					Pass  value= 1  
					Force  value= 2  
					Delete  value= 3  "
		::= { iqudc32CmdEntry 40130 }


	iqudc32MenuOutputSignallingCOutputLine625 OBJECT-TYPE
		SYNTAX		INTEGER
		MAX-ACCESS		read-write
		STATUS			current
		DESCRIPTION
				"TYPE: - Number
				 PAGE: - Output Signalling C
					Output Line 625  cmdID= 40139  min= 7  max= 22  step= 1  format= %0.0f  div_scale= 1 
					Min = 7  Max = 22  Step = 1 "
		::= { iqudc32CmdEntry 40139 }


	iqudc32MenuOutputSignallingCOutputLine525 OBJECT-TYPE
		SYNTAX		INTEGER
		MAX-ACCESS		read-write
		STATUS			current
		DESCRIPTION
				"TYPE: - Number
				 PAGE: - Output Signalling C
					Output Line 525  cmdID= 40140  min= 11  max= 19  step= 1  format= %0.0f  div_scale= 1 
					Min = 11  Max = 19  Step = 1 "
		::= { iqudc32CmdEntry 40140 }


	iqudc32MenuOutputSignallingCOutputLineHD OBJECT-TYPE
		SYNTAX		INTEGER
		MAX-ACCESS		read-write
		STATUS			current
		DESCRIPTION
				"TYPE: - Number
				 PAGE: - Output Signalling C
					Output Line HD  cmdID= 40138  min= 9  max= 20  step= 1  format= %0.0f  div_scale= 1 
					Min = 9  Max = 20  Step = 1 "
		::= { iqudc32CmdEntry 40138 }


	iqudc32MenuOutputSignallingCOutputLineStatus40141 OBJECT-TYPE
		SYNTAX		RollCallString
		MAX-ACCESS		read-only
		STATUS			current
		DESCRIPTION
				"TYPE: - Display
				 PAGE: - Output Signalling C
					Output Line Status  cmdID= 40141  format=   "
		::= { iqudc32CmdEntry 40141 }


	iqudc32OutputSignallingCVIMode40120 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - Output Signalling C
					Mode  cmdID= 40120 
					Auto  value= 0  
					Pass  value= 1  
					Force  value= 2  
					Delete  value= 3  "
		::= { iqudc32CmdEntry 40120 }


	iqudc32MenuOutputSignallingCOutputFormat OBJECT-TYPE
		SYNTAX		INTEGER {
							val-SMPTE(0),
							val-AFD(1)
							}
		MAX-ACCESS		read-write
		STATUS			current
		DESCRIPTION
				"TYPE: - RadiobuttonList
				 PAGE: - Output Signalling C
					Output Format  cmdID= 40121 
					SMPTE  value= 0  
					AFD  value= 1  "
		::= { iqudc32CmdEntry 40121 }


	iqudc32MenuOutputSignallingCVIPassData OBJECT-TYPE
		SYNTAX		INTEGER { disable(0), enable(1) }
		MAX-ACCESS		read-write
		STATUS			current
		DESCRIPTION
				"TYPE: - Checkbox
				 PAGE: - Output Signalling C
					VI Pass Data  cmdID= 40122 "
		::= { iqudc32CmdEntry 40122 }


	iqudc32OutputSignallingCL23Mode40112 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - Output Signalling C
					Mode  cmdID= 40112 
					Auto  value= 0  
					Pass  value= 1  
					Force  value= 2  
					Delete  value= 3  "
		::= { iqudc32CmdEntry 40112 }


	iqudc32MenuOutputSignallingC OBJECT-TYPE
		SYNTAX		INTEGER {
							val-ETSI(0),
							val-AFD(1)
							}
		MAX-ACCESS		read-write
		STATUS			current
		DESCRIPTION
				"TYPE: - RadiobuttonList
				 PAGE: - Output Signalling C
					Output Format  cmdID= 40113 
					ETSI  value= 0  
					AFD  value= 1  
					Output Format  cmdID= 40113 "
		::= { iqudc32CmdEntry 40113 }


	iqudc32MenuOutputSignallingCInputLine OBJECT-TYPE
		SYNTAX		INTEGER
		MAX-ACCESS		read-write
		STATUS			current
		DESCRIPTION
				"TYPE: - Number
				 PAGE: - Output Signalling C
					Input Line  cmdID= 40110  min= 10  max= 23  step= 1  format= %0.0f  div_scale= 1 
					Min = 10  Max = 23  Step = 1 "
		::= { iqudc32CmdEntry 40110 }


	iqudc32MenuOutputSignallingCOutputLine OBJECT-TYPE
		SYNTAX		INTEGER
		MAX-ACCESS		read-write
		STATUS			current
		DESCRIPTION
				"TYPE: - Number
				 PAGE: - Output Signalling C
					Output Line  cmdID= 40111  min= 10  max= 23  step= 1  format= %0.0f  div_scale= 1 
					Min = 10  Max = 23  Step = 1 "
		::= { iqudc32CmdEntry 40111 }


	iqudc32MenuOutputSignallingCOutputLineStatus20166 OBJECT-TYPE
		SYNTAX		RollCallString
		MAX-ACCESS		read-only
		STATUS			current
		DESCRIPTION
				"TYPE: - Display
				 PAGE: - Output Signalling C
					Output Line Status  cmdID= 20166  format=   "
		::= { iqudc32CmdEntry 20166 }


	iqudc32OutputSignallingCAFDUserBitsForceUserBitsVal20163 OBJECT-TYPE
		SYNTAX		INTEGER { disable(0), enable(1) }
		MAX-ACCESS		read-write
		STATUS			current
		DESCRIPTION
				"TYPE: - Checkbox
				 PAGE: - Output Signalling C
					Force User Bits Val  cmdID= 20163 "
		::= { iqudc32CmdEntry 20163 }


	iqudc32OutputSignallingCAFDUserBitsUserBitsValue40137 OBJECT-TYPE
		SYNTAX		INTEGER
		MAX-ACCESS		read-write
		STATUS			current
		DESCRIPTION
				"TYPE: - Number
				 PAGE: - Output Signalling C
					User Bits Value  cmdID= 40137  min= 0  max= 15  step= 1  format= %0.0f  div_scale= 1 
					Min = 0  Max = 15  Step = 1 "
		::= { iqudc32CmdEntry 40137 }


	iqudc32OutputSignallingCForceModeConfigSMPTE201640133 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-4-3-AFD-8(8),
							val-4-3-AFD-9(9),
							val-4-3-AFD-10(10),
							val-4-3-AFD-11(11),
							val-4-3-AFD-12(12),
							val-4-3-AFD-13(13),
							val-4-3-AFD-14(14),
							val-4-3-AFD-15(15),
							val-16-9-AFD-0(16),
							val-16-9-AFD-1(17),
							val-16-9-AFD-2(18),
							val-16-9-AFD-3(19),
							val-16-9-AFD-4(20),
							val-16-9-AFD-5(21),
							val-16-9-AFD-6(22),
							val-16-9-AFD-7(23),
							val-16-9-AFD-8(24),
							val-16-9-AFD-9(25),
							val-16-9-AFD-10(26),
							val-16-9-AFD-11(27),
							val-16-9-AFD-12(28),
							val-16-9-AFD-13(29),
							val-16-9-AFD-14(30),
							val-16-9-AFD-15(31)
							}
		MAX-ACCESS		read-write
		STATUS			current
		DESCRIPTION
				"TYPE: - RadiobuttonList
				 PAGE: - Output Signalling C
					SMPTE 2016  cmdID= 40133 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					4:3 AFD 8  value= 8  
					4:3 AFD 9  value= 9  
					4:3 AFD 10  value= 10  
					4:3 AFD 11  value= 11  
					4:3 AFD 12  value= 12  
					4:3 AFD 13  value= 13  
					4:3 AFD 14  value= 14  
					4:3 AFD 15  value= 15  
					16:9 AFD 0  value= 16  
					16:9 AFD 1  value= 17  
					16:9 AFD 2  value= 18  
					16:9 AFD 3  value= 19  
					16:9 AFD 4  value= 20  
					16:9 AFD 5  value= 21  
					16:9 AFD 6  value= 22  
					16:9 AFD 7  value= 23  
					16:9 AFD 8  value= 24  
					16:9 AFD 9  value= 25  
					16:9 AFD 10  value= 26  
					16:9 AFD 11  value= 27  
					16:9 AFD 12  value= 28  
					16:9 AFD 13  value= 29  
					16:9 AFD 14  value= 30  
					16:9 AFD 15  value= 31  "
		::= { iqudc32CmdEntry 40133 }


	iqudc32MenuOutputSignallingCSMPTERP186 OBJECT-TYPE
		SYNTAX		INTEGER {
							val-4-3(0),
							val-16-9(1)
							}
		MAX-ACCESS		read-write
		STATUS			current
		DESCRIPTION
				"TYPE: - RadiobuttonList
				 PAGE: - Output Signalling C
					SMPTE RP186  cmdID= 40134 
					4:3  value= 0  
					16:9  value= 1  "
		::= { iqudc32CmdEntry 40134 }


	iqudc32MenuOutputSignallingCAFD OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-16-9-AFD-0(8),
							val-16-9-AFD-1(9),
							val-16-9-AFD-2(10),
							val-16-9-AFD-3(11),
							val-16-9-AFD-4(12),
							val-16-9-AFD-5(13),
							val-16-9-AFD-6(14),
							val-16-9-AFD-7(15)
							}
		MAX-ACCESS		read-write
		STATUS			current
		DESCRIPTION
				"TYPE: - RadiobuttonList
				 PAGE: - Output Signalling C
					AFD  cmdID= 40131 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					16:9 AFD 0  value= 8  
					16:9 AFD 1  value= 9  
					16:9 AFD 2  value= 10  
					16:9 AFD 3  value= 11  
					16:9 AFD 4  value= 12  
					16:9 AFD 5  value= 13  
					16:9 AFD 6  value= 14  
					16:9 AFD 7  value= 15  "
		::= { iqudc32CmdEntry 40131 }


	iqudc32MenuOutputSignallingCETSI OBJECT-TYPE
		SYNTAX		INTEGER {
							val-4-3-FF(0),
							val-14-9-Centre(1),
							val-14-9-Top(2),
							val-16-9-Centre(3),
							val-16-9-Top(4),
							val-16-9-Centre-1(5),
							val-4-3-SP-14-9(6),
							val-16-9-FF(7)
							}
		MAX-ACCESS		read-write
		STATUS			current
		DESCRIPTION
				"TYPE: - RadiobuttonList
				 PAGE: - Output Signalling C
					ETSI  cmdID= 40132 
					4:3 FF  value= 0  
					14:9 Centre  value= 1  
					14:9 Top  value= 2  
					16:9 Centre  value= 3  
					16:9 Top  value= 4  
					>16:9 Centre  value= 5  
					4:3 SP 14:9  value= 6  
					16:9 FF  value= 7  "
		::= { iqudc32CmdEntry 40132 }


	iqudc32MenuARCSidebarKeyerSyncMode40107 OBJECT-TYPE
		SYNTAX		INTEGER { disable(0), enable(1) }
		MAX-ACCESS		read-write
		STATUS			current
		DESCRIPTION
				"TYPE: - Checkbox
				 PAGE: - ARC & Sidebar Keyer
					Sync Mode  cmdID= 40107 "
		::= { iqudc32CmdEntry 40107 }


	iqudc32MenuARCSidebarKeyerSignallingDetected64220 OBJECT-TYPE
		SYNTAX		RollCallString
		MAX-ACCESS		read-only
		STATUS			current
		DESCRIPTION
				"TYPE: - Display
				 PAGE: - ARC & Sidebar Keyer
					Signalling Detected  cmdID= 64220  format=   "
		::= { iqudc32CmdEntry 64220 }


	iqudc32ARCSidebarKeyerSidebarKeyingOuMode40023 OBJECT-TYPE
		SYNTAX		INTEGER {
							val-Off(0),
							val-Output-Crop(1),
							val-Sidebar-Key(2)
							}
		MAX-ACCESS		read-write
		STATUS			current
		DESCRIPTION
				"TYPE: - RadiobuttonList
				 PAGE: - ARC & Sidebar Keyer
					Mode  cmdID= 40023 
					Off  value= 0  
					Output Crop  value= 1  
					Sidebar Key  value= 2  "
		::= { iqudc32CmdEntry 40023 }


	iqudc32MenuARCSidebarKeyerSidebarKeySource40024 OBJECT-TYPE
		SYNTAX		INTEGER {
							val-SDI-1(0),
							val-SDI-2(1),
							val-CVBS(2),
							val-SFP-1(3),
							val-SFP-2(4),
							val-Ch-1-Output(20)
							}
		MAX-ACCESS		read-write
		STATUS			current
		DESCRIPTION
				"TYPE: - RadiobuttonList
				 PAGE: - ARC & Sidebar Keyer
					Sidebar Key Source  cmdID= 40024 
					SDI 1  value= 0  
					SDI 2  value= 1  
					CVBS  value= 2  
					SFP 1  value= 3  
					SFP 2  value= 4  
					Ch 1 Output  value= 20  "
		::= { iqudc32CmdEntry 40024 }


	iqudc32ARCSidebarKeyerOutputCropPositioTop OBJECT-TYPE
		SYNTAX		INTEGER
		MAX-ACCESS		read-write
		STATUS			current
		DESCRIPTION
				"TYPE: - Number
				 PAGE: - ARC & Sidebar Keyer
					Top  cmdID= 40019  min= 0  max= 99  step= 1  format= %0.0f%%  div_scale= 1 
					Min = 0%  Max = 99%  Step = 1% "
		::= { iqudc32CmdEntry 40019 }


	iqudc32ARCSidebarKeyerOutputCropPositioBottom OBJECT-TYPE
		SYNTAX		INTEGER
		MAX-ACCESS		read-write
		STATUS			current
		DESCRIPTION
				"TYPE: - Number
				 PAGE: - ARC & Sidebar Keyer
					Bottom  cmdID= 40020  min= 0  max= 99  step= 1  format= %0.0f%%  div_scale= 1 
					Min = 0%  Max = 99%  Step = 1% "
		::= { iqudc32CmdEntry 40020 }


	iqudc32ARCSidebarKeyerOutputCropPositioLeft OBJECT-TYPE
		SYNTAX		INTEGER
		MAX-ACCESS		read-write
		STATUS			current
		DESCRIPTION
				"TYPE: - Number
				 PAGE: - ARC & Sidebar Keyer
					Left  cmdID= 40021  min= 0  max= 99  step= 1  format= %0.0f%%  div_scale= 1 
					Min = 0%  Max = 99%  Step = 1% "
		::= { iqudc32CmdEntry 40021 }


	iqudc32ARCSidebarKeyerOutputCropPositioRight OBJECT-TYPE
		SYNTAX		INTEGER
		MAX-ACCESS		read-write
		STATUS			current
		DESCRIPTION
				"TYPE: - Number
				 PAGE: - ARC & Sidebar Keyer
					Right  cmdID= 40022  min= 0  max= 99  step= 1  format= %0.0f%%  div_scale= 1 
					Min = 0%  Max = 99%  Step = 1% "
		::= { iqudc32CmdEntry 40022 }


	iqudc32ARCSidebarKeyerPostScalingControPostScalingEnable OBJECT-TYPE
		SYNTAX		INTEGER { disable(0), enable(1) }
		MAX-ACCESS		read-write
		STATUS			current
		DESCRIPTION
				"TYPE: - Checkbox
				 PAGE: - ARC & Sidebar Keyer
					Post Scaling Enable  cmdID= 40103 "
		::= { iqudc32CmdEntry 40103 }


	iqudc32ARCSidebarKeyerPostScalingControSize OBJECT-TYPE
		SYNTAX		INTEGER
		MAX-ACCESS		read-write
		STATUS			current
		DESCRIPTION
				"TYPE: - Number
				 PAGE: - ARC & Sidebar Keyer
					Size  cmdID= 40108  min= 80  max= 120  step= 1  format= %0.0f%%  div_scale= 1 
					Min = 80%  Max = 120%  Step = 1% "
		::= { iqudc32CmdEntry 40108 }


	iqudc32ARCSidebarKeyerPostScalingControAspect OBJECT-TYPE
		SYNTAX		INTEGER
		MAX-ACCESS		read-write
		STATUS			current
		DESCRIPTION
				"TYPE: - Number
				 PAGE: - ARC & Sidebar Keyer
					Aspect  cmdID= 40109  min= 70  max= 150  step= 1  format= %0.0f%%  div_scale= 1 
					Min = 70%  Max = 150%  Step = 1% "
		::= { iqudc32CmdEntry 40109 }


	iqudc32ARCSidebarKeyerPostScalingControPan OBJECT-TYPE
		SYNTAX		INTEGER
		MAX-ACCESS		read-write
		STATUS			current
		DESCRIPTION
				"TYPE: - Number
				 PAGE: - ARC & Sidebar Keyer
					Pan  cmdID= 40106  min= -50  max= 50  step= 1  format= %0.0f%  div_scale= 1 
					Min = -50 Max = 50 Step = 1"
		::= { iqudc32CmdEntry 40106 }


	iqudc32ARCSidebarKeyerPostScalingControTilt OBJECT-TYPE
		SYNTAX		INTEGER
		MAX-ACCESS		read-write
		STATUS			current
		DESCRIPTION
				"TYPE: - Number
				 PAGE: - ARC & Sidebar Keyer
					Tilt  cmdID= 40102  min= -50  max= 50  step= 1  format= %0.0f%  div_scale= 1 
					Min = -50 Max = 50 Step = 1"
		::= { iqudc32CmdEntry 40102 }


	iqudc32ARCSidebarKeyerScalerConfigUsePresets OBJECT-TYPE
		SYNTAX		INTEGER { disable(0), enable(1) }
		MAX-ACCESS		read-write
		STATUS			current
		DESCRIPTION
				"TYPE: - Checkbox
				 PAGE: - ARC & Sidebar Keyer- Scaler Config
					Use Presets  cmdID= 40236 "
		::= { iqudc32CmdEntry 40236 }


	iqudc32ScalerConfigPresetsSDInputis70240040 OBJECT-TYPE
		SYNTAX		INTEGER { disable(0), enable(1) }
		MAX-ACCESS		read-write
		STATUS			current
		DESCRIPTION
				"TYPE: - Checkbox
				 PAGE: - ARC & Sidebar Keyer- Scaler Config
					SD Input is 702  cmdID= 40040 "
		::= { iqudc32CmdEntry 40040 }


	iqudc32ScalerConfigPresetsSDOutputis70240047 OBJECT-TYPE
		SYNTAX		INTEGER { disable(0), enable(1) }
		MAX-ACCESS		read-write
		STATUS			current
		DESCRIPTION
				"TYPE: - Checkbox
				 PAGE: - ARC & Sidebar Keyer- Scaler Config
					SD Output is 702  cmdID= 40047 "
		::= { iqudc32CmdEntry 40047 }


	iqudc32PresetsSDCrossConversionSelectStdPreset40041 OBJECT-TYPE
		SYNTAX		INTEGER {
							val-None(0),
							val-16-9-LB-4-3-HC(1),
							val-16-9-LB-16-9-Ana(2),
							val-16-9-LB-14-9-LB(3),
							val-16-9-Ana-4-3-HC(4),
							val-16-9-Ana-16-9-LB(5),
							val-16-9-Ana-14-9-LB(6)
							}
		MAX-ACCESS		read-write
		STATUS			current
		DESCRIPTION
				"TYPE: - RadiobuttonList
				 PAGE: - ARC & Sidebar Keyer- Scaler Config
					Select Std Preset  cmdID= 40041 
					None  value= 0  
					16:9 LB > 4:3 HC  value= 1  
					16:9 LB > 16:9 Ana  value= 2  
					16:9 LB > 14:9 LB  value= 3  
					16:9 Ana > 4:3 HC  value= 4  
					16:9 Ana > 16:9 LB  value= 5  
					16:9 Ana > 14:9 LB  value= 6  "
		::= { iqudc32CmdEntry 40041 }


	iqudc32ScalerConfigHDCrossConversionSelectStdPreset40046 OBJECT-TYPE
		SYNTAX		INTEGER {
							val-None(0),
							val-14-9-PB-16-9-VC(1),
							val-4-3-PB-16-9-VC(2),
							val-4-3-PB-14-9-PB-VC(3)
							}
		MAX-ACCESS		read-write
		STATUS			current
		DESCRIPTION
				"TYPE: - RadiobuttonList
				 PAGE: - ARC & Sidebar Keyer- Scaler Config
					Select Std Preset  cmdID= 40046 
					None  value= 0  
					14:9 PB > 16:9 VC  value= 1  
					4:3 PB > 16:9 VC  value= 2  
					4:3 PB > 14:9 PB VC  value= 3  "
		::= { iqudc32CmdEntry 40046 }


	iqudc32ScalerConfigUpConversionSelectStdPreset40043 OBJECT-TYPE
		SYNTAX		INTEGER {
							val-4-3-16-9-VC(0),
							val-4-3-4-3-PB(1),
							val-16-9-LB-16-9(2),
							val-16-9-Ana-16-9(3),
							val-14-9-LB-14-9-PB(4)
							}
		MAX-ACCESS		read-write
		STATUS			current
		DESCRIPTION
				"TYPE: - RadiobuttonList
				 PAGE: - ARC & Sidebar Keyer- Scaler Config
					Select Std Preset  cmdID= 40043 
					4:3 > 16:9 VC  value= 0  
					4:3 > 4:3 PB  value= 1  
					16:9 LB > 16:9  value= 2  
					16:9 Ana > 16:9  value= 3  
					14:9 LB > 14:9 PB  value= 4  "
		::= { iqudc32CmdEntry 40043 }


	iqudc32ScalerConfigDownConversionSelectStdPreset40045 OBJECT-TYPE
		SYNTAX		INTEGER {
							val-16-9-4-3-HC(0),
							val-16-9-16-9-LB(1),
							val-16-9-16-9-Ana(2),
							val-4-3-PB-4-3(3),
							val-14-9-PB-14-9-LB(4)
							}
		MAX-ACCESS		read-write
		STATUS			current
		DESCRIPTION
				"TYPE: - RadiobuttonList
				 PAGE: - ARC & Sidebar Keyer- Scaler Config
					Select Std Preset  cmdID= 40045 
					16:9 > 4:3 HC  value= 0  
					16:9 > 16:9 LB  value= 1  
					16:9 > 16:9 Ana  value= 2  
					4:3 PB > 4:3  value= 3  
					14:9 PB > 14:9 LB  value= 4  "
		::= { iqudc32CmdEntry 40045 }


	iqudc32ScalerConfigInputConfigInputSignallingSo40202 OBJECT-TYPE
		SYNTAX		INTEGER {
							val-SMPTE-2016(0),
							val-L23-ETSI(1),
							val-L23-AFD(2),
							val-VI-SMPTE(3),
							val-VI-AFD(4)
							}
		MAX-ACCESS		read-write
		STATUS			current
		DESCRIPTION
				"TYPE: - RadiobuttonList
				 PAGE: - ARC & Sidebar Keyer- Scaler Config
					Input Signalling So  cmdID= 40202 
					SMPTE 2016  value= 0  
					L23 ETSI  value= 1  
					L23 AFD  value= 2  
					VI SMPTE  value= 3  
					VI AFD  value= 4  "
		::= { iqudc32CmdEntry 40202 }


	iqudc32ScalerConfigIfInputSignallingForceInputFormat40235 OBJECT-TYPE
		SYNTAX		INTEGER { disable(0), enable(1) }
		MAX-ACCESS		read-write
		STATUS			current
		DESCRIPTION
				"TYPE: - Checkbox
				 PAGE: - ARC & Sidebar Keyer- Scaler Config
					Force Input Format  cmdID= 40235 "
		::= { iqudc32CmdEntry 40235 }


	iqudc32ScalerConfigIfInputSignallingSDInputFormat40114 OBJECT-TYPE
		SYNTAX		INTEGER {
							val-Normal(0),
							val-Anamorphic(1),
							val-16-9-Letterbox(2),
							val-14-9-Letterbox(3)
							}
		MAX-ACCESS		read-write
		STATUS			current
		DESCRIPTION
				"TYPE: - RadiobuttonList
				 PAGE: - ARC & Sidebar Keyer- Scaler Config
					SD Input Format  cmdID= 40114 
					Normal  value= 0  
					Anamorphic  value= 1  
					16:9 Letterbox  value= 2  
					14:9 Letterbox  value= 3  "
		::= { iqudc32CmdEntry 40114 }


	iqudc32ARCSidebarKeyerScalerConfigHDInputFormat OBJECT-TYPE
		SYNTAX		INTEGER {
							val-Normal(0),
							val-14-9-Pillarbox(1),
							val-4-3-Pillarbox(2)
							}
		MAX-ACCESS		read-write
		STATUS			current
		DESCRIPTION
				"TYPE: - RadiobuttonList
				 PAGE: - ARC & Sidebar Keyer- Scaler Config
					HD Input Format  cmdID= 40117 
					Normal  value= 0  
					14:9 Pillarbox  value= 1  
					4:3 Pillarbox  value= 2  "
		::= { iqudc32CmdEntry 40117 }


	iqudc32ScalerConfigOutputConfigConversionScaling40116 OBJECT-TYPE
		SYNTAX		INTEGER {
							val-Fit-to-Height(0),
							val-Fit-to-Width(1),
							val-14-9(2)
							}
		MAX-ACCESS		read-write
		STATUS			current
		DESCRIPTION
				"TYPE: - RadiobuttonList
				 PAGE: - ARC & Sidebar Keyer- Scaler Config
					Conversion Scaling  cmdID= 40116 
					Fit to Height  value= 0  
					Fit to Width  value= 1  
					14:9  value= 2  "
		::= { iqudc32CmdEntry 40116 }


	iqudc32ARCSidebarKeyerScalerConfigSDOutputFormat OBJECT-TYPE
		SYNTAX		INTEGER {
							val-Normal(0),
							val-Anamorphic(1)
							}
		MAX-ACCESS		read-write
		STATUS			current
		DESCRIPTION
				"TYPE: - RadiobuttonList
				 PAGE: - ARC & Sidebar Keyer- Scaler Config
					SD Output Format  cmdID= 40115 
					Normal  value= 0  
					Anamorphic  value= 1  "
		::= { iqudc32CmdEntry 40115 }


	iqudc32ARCSidebarKeyerMemoriesRecallMemory OBJECT-TYPE
		SYNTAX		INTEGER {
							val-None-Selected(0),
							val-Arc-Memory-1(1),
							val-Arc-Memory-2(2),
							val-Arc-Memory-3(3),
							val-Arc-Memory-4(4),
							val-Arc-Memory-5(5),
							val-Arc-Memory-6(6),
							val-Arc-Memory-7(7),
							val-Arc-Memory-8(8),
							val-Arc-Memory-9(9),
							val-Arc-Memory-10(10),
							val-Arc-Memory-11(11),
							val-Arc-Memory-12(12),
							val-Arc-Memory-13(13),
							val-Arc-Memory-14(14),
							val-Arc-Memory-15(15),
							val-Arc-Memory-16(16),
							val-Arc-Memory-17(17),
							val-Arc-Memory-18(18),
							val-Arc-Memory-19(19),
							val-Arc-Memory-20(20),
							val-Arc-Memory-21(21),
							val-Arc-Memory-22(22),
							val-Arc-Memory-23(23),
							val-Arc-Memory-24(24),
							val-Arc-Memory-25(25),
							val-Arc-Memory-26(26),
							val-Arc-Memory-27(27),
							val-Arc-Memory-28(28),
							val-Arc-Memory-29(29),
							val-Arc-Memory-30(30),
							val-Arc-Memory-31(31),
							val-Arc-Memory-32(32)
							}
		MAX-ACCESS		read-write
		STATUS			current
		DESCRIPTION
				"TYPE: - RadiobuttonList
				 PAGE: - ARC & Sidebar Keyer- Memories
					Recall Memory  cmdID= 64008 
					None Selected  value= 0  
					Arc Memory 1  value= 1  
					Arc Memory 2  value= 2  
					Arc Memory 3  value= 3  
					Arc Memory 4  value= 4  
					Arc Memory 5  value= 5  
					Arc Memory 6  value= 6  
					Arc Memory 7  value= 7  
					Arc Memory 8  value= 8  
					Arc Memory 9  value= 9  
					Arc Memory 10  value= 10  
					Arc Memory 11  value= 11  
					Arc Memory 12  value= 12  
					Arc Memory 13  value= 13  
					Arc Memory 14  value= 14  
					Arc Memory 15  value= 15  
					Arc Memory 16  value= 16  
					Arc Memory 17  value= 17  
					Arc Memory 18  value= 18  
					Arc Memory 19  value= 19  
					Arc Memory 20  value= 20  
					Arc Memory 21  value= 21  
					Arc Memory 22  value= 22  
					Arc Memory 23  value= 23  
					Arc Memory 24  value= 24  
					Arc Memory 25  value= 25  
					Arc Memory 26  value= 26  
					Arc Memory 27  value= 27  
					Arc Memory 28  value= 28  
					Arc Memory 29  value= 29  
					Arc Memory 30  value= 30  
					Arc Memory 31  value= 31  
					Arc Memory 32  value= 32  "
		::= { iqudc32CmdEntry 64008 }


	iqudc32ARCSidebarKeyerMemoriesSelMemory OBJECT-TYPE
		SYNTAX		INTEGER {
							val-Arc-Memory-1(1),
							val-Arc-Memory-2(2),
							val-Arc-Memory-3(3),
							val-Arc-Memory-4(4),
							val-Arc-Memory-5(5),
							val-Arc-Memory-6(6),
							val-Arc-Memory-7(7),
							val-Arc-Memory-8(8),
							val-Arc-Memory-9(9),
							val-Arc-Memory-10(10),
							val-Arc-Memory-11(11),
							val-Arc-Memory-12(12),
							val-Arc-Memory-13(13),
							val-Arc-Memory-14(14),
							val-Arc-Memory-15(15),
							val-Arc-Memory-16(16),
							val-Arc-Memory-17(17),
							val-Arc-Memory-18(18),
							val-Arc-Memory-19(19),
							val-Arc-Memory-20(20),
							val-Arc-Memory-21(21),
							val-Arc-Memory-22(22),
							val-Arc-Memory-23(23),
							val-Arc-Memory-24(24),
							val-Arc-Memory-25(25),
							val-Arc-Memory-26(26),
							val-Arc-Memory-27(27),
							val-Arc-Memory-28(28),
							val-Arc-Memory-29(29),
							val-Arc-Memory-30(30),
							val-Arc-Memory-31(31),
							val-Arc-Memory-32(32)
							}
		MAX-ACCESS		read-write
		STATUS			current
		DESCRIPTION
				"TYPE: - RadiobuttonList
				 PAGE: - ARC & Sidebar Keyer- Memories
					Sel Memory  cmdID= 64006 
					Arc Memory 1  value= 1  
					Arc Memory 2  value= 2  
					Arc Memory 3  value= 3  
					Arc Memory 4  value= 4  
					Arc Memory 5  value= 5  
					Arc Memory 6  value= 6  
					Arc Memory 7  value= 7  
					Arc Memory 8  value= 8  
					Arc Memory 9  value= 9  
					Arc Memory 10  value= 10  
					Arc Memory 11  value= 11  
					Arc Memory 12  value= 12  
					Arc Memory 13  value= 13  
					Arc Memory 14  value= 14  
					Arc Memory 15  value= 15  
					Arc Memory 16  value= 16  
					Arc Memory 17  value= 17  
					Arc Memory 18  value= 18  
					Arc Memory 19  value= 19  
					Arc Memory 20  value= 20  
					Arc Memory 21  value= 21  
					Arc Memory 22  value= 22  
					Arc Memory 23  value= 23  
					Arc Memory 24  value= 24  
					Arc Memory 25  value= 25  
					Arc Memory 26  value= 26  
					Arc Memory 27  value= 27  
					Arc Memory 28  value= 28  
					Arc Memory 29  value= 29  
					Arc Memory 30  value= 30  
					Arc Memory 31  value= 31  
					Arc Memory 32  value= 32  "
		::= { iqudc32CmdEntry 64006 }


	iqudc32ARCSidebarKeyerMemoriesSaveMemory OBJECT-TYPE
		SYNTAX		INTEGER { noAction(0),val-Save-Memory(1) }
		MAX-ACCESS		read-write
		STATUS			current
		DESCRIPTION
				"TYPE: - Button
				 PAGE: - ARC & Sidebar Keyer- Memories
					Save Memory  cmdID= 64007  value= 1  "
		::= { iqudc32CmdEntry 64007 }


	iqudc32ARCSidebarKeyerMemoriesClearMemory OBJECT-TYPE
		SYNTAX		INTEGER { noAction(0),val-Clear-Memory(1) }
		MAX-ACCESS		read-write
		STATUS			current
		DESCRIPTION
				"TYPE: - Button
				 PAGE: - ARC & Sidebar Keyer- Memories
					Clear Memory  cmdID= 64013  value= 1  "
		::= { iqudc32CmdEntry 64013 }


	iqudc32MemoriesMemoryNameChangeName64009 OBJECT-TYPE
		SYNTAX		RollCallString
		MAX-ACCESS		read-write
		STATUS			current
		DESCRIPTION
				"TYPE: - Editstring
				 PAGE: - ARC & Sidebar Keyer- Memories
					Change Name  cmdID= 64009  "
		::= { iqudc32CmdEntry 64009 }


	iqudc32ARCSidebarKeyerMemoriesLastDisplayMemory OBJECT-TYPE
		SYNTAX		RollCallString
		MAX-ACCESS		read-only
		STATUS			current
		DESCRIPTION
				"TYPE: - Display
				 PAGE: - ARC & Sidebar Keyer- Memories
					Last Display Memory  cmdID= 64012  format=   "
		::= { iqudc32CmdEntry 64012 }


	iqudc32OutputSignallingCSMPTE2016Mode40230 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer- Output Signalling C
					Mode  cmdID= 40230 
					Auto  value= 0  
					Pass  value= 1  
					Force  value= 2  
					Delete  value= 3  "
		::= { iqudc32CmdEntry 40230 }


	iqudc32ARCSidebarKeyerOutputSignallingCOutputLine625 OBJECT-TYPE
		SYNTAX		INTEGER
		MAX-ACCESS		read-write
		STATUS			current
		DESCRIPTION
				"TYPE: - Number
				 PAGE: - ARC & Sidebar Keyer- Output Signalling C
					Output Line 625  cmdID= 40239  min= 7  max= 22  step= 1  format= %0.0f  div_scale= 1 
					Min = 7  Max = 22  Step = 1 "
		::= { iqudc32CmdEntry 40239 }


	iqudc32ARCSidebarKeyerOutputSignallingCOutputLine525 OBJECT-TYPE
		SYNTAX		INTEGER
		MAX-ACCESS		read-write
		STATUS			current
		DESCRIPTION
				"TYPE: - Number
				 PAGE: - ARC & Sidebar Keyer- Output Signalling C
					Output Line 525  cmdID= 40240  min= 11  max= 19  step= 1  format= %0.0f  div_scale= 1 
					Min = 11  Max = 19  Step = 1 "
		::= { iqudc32CmdEntry 40240 }


	iqudc32ARCSidebarKeyerOutputSignallingCOutputLineHD OBJECT-TYPE
		SYNTAX		INTEGER
		MAX-ACCESS		read-write
		STATUS			current
		DESCRIPTION
				"TYPE: - Number
				 PAGE: - ARC & Sidebar Keyer- Output Signalling C
					Output Line HD  cmdID= 40238  min= 9  max= 20  step= 1  format= %0.0f  div_scale= 1 
					Min = 9  Max = 20  Step = 1 "
		::= { iqudc32CmdEntry 40238 }


	iqudc32ARCSidebarKeyerOutputSignallingCOutputLineStatus40241 OBJECT-TYPE
		SYNTAX		RollCallString
		MAX-ACCESS		read-only
		STATUS			current
		DESCRIPTION
				"TYPE: - Display
				 PAGE: - ARC & Sidebar Keyer- Output Signalling C
					Output Line Status  cmdID= 40241  format=   "
		::= { iqudc32CmdEntry 40241 }


	iqudc32OutputSignallingCVIMode40220 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer- Output Signalling C
					Mode  cmdID= 40220 
					Auto  value= 0  
					Pass  value= 1  
					Force  value= 2  
					Delete  value= 3  "
		::= { iqudc32CmdEntry 40220 }


	iqudc32ARCSidebarKeyerOutputSignallingCOutputFormat OBJECT-TYPE
		SYNTAX		INTEGER {
							val-SMPTE(0),
							val-AFD(1)
							}
		MAX-ACCESS		read-write
		STATUS			current
		DESCRIPTION
				"TYPE: - RadiobuttonList
				 PAGE: - ARC & Sidebar Keyer- Output Signalling C
					Output Format  cmdID= 40221 
					SMPTE  value= 0  
					AFD  value= 1  "
		::= { iqudc32CmdEntry 40221 }


	iqudc32ARCSidebarKeyerOutputSignallingCVIPassData OBJECT-TYPE
		SYNTAX		INTEGER { disable(0), enable(1) }
		MAX-ACCESS		read-write
		STATUS			current
		DESCRIPTION
				"TYPE: - Checkbox
				 PAGE: - ARC & Sidebar Keyer- Output Signalling C
					VI Pass Data  cmdID= 40222 "
		::= { iqudc32CmdEntry 40222 }


	iqudc32OutputSignallingCL23Mode40212 OBJECT-TYPE
		SYNTAX		INTEGER {
							val-Auto(0),
							val-Pass(1),
							val-Force(2),
							val-Delete(3)
							}
		MAX-ACCESS		read-write
		STATUS			current
		DESCRIPTION
				"TYPE: - RadiobuttonList
				 PAGE: - ARC & Sidebar Keyer- Output Signalling C
					Mode  cmdID= 40212 
					Auto  value= 0  
					Pass  value= 1  
					Force  value= 2  
					Delete  value= 3  "
		::= { iqudc32CmdEntry 40212 }


	iqudc32ARCSidebarKeyerOutputSignallingC OBJECT-TYPE
		SYNTAX		INTEGER {
							val-ETSI(0),
							val-AFD(1)
							}
		MAX-ACCESS		read-write
		STATUS			current
		DESCRIPTION
				"TYPE: - RadiobuttonList
				 PAGE: - ARC & Sidebar Keyer- Output Signalling C
					Output Format  cmdID= 40213 
					ETSI  value= 0  
					AFD  value= 1  
					Output Format  cmdID= 40213 "
		::= { iqudc32CmdEntry 40213 }


	iqudc32ARCSidebarKeyerOutputSignallingCInputLine OBJECT-TYPE
		SYNTAX		INTEGER
		MAX-ACCESS		read-write
		STATUS			current
		DESCRIPTION
				"TYPE: - Number
				 PAGE: - ARC & Sidebar Keyer- Output Signalling C
					Input Line  cmdID= 40210  min= 10  max= 23  step= 1  format= %0.0f  div_scale= 1 
					Min = 10  Max = 23  Step = 1 "
		::= { iqudc32CmdEntry 40210 }


	iqudc32ARCSidebarKeyerOutputSignallingCOutputLine OBJECT-TYPE
		SYNTAX		INTEGER
		MAX-ACCESS		read-write
		STATUS			current
		DESCRIPTION
				"TYPE: - Number
				 PAGE: - ARC & Sidebar Keyer- Output Signalling C
					Output Line  cmdID= 40211  min= 10  max= 23  step= 1  format= %0.0f  div_scale= 1 
					Min = 10  Max = 23  Step = 1 "
		::= { iqudc32CmdEntry 40211 }


	iqudc32ARCSidebarKeyerOutputSignallingCOutputLineStatus20176 OBJECT-TYPE
		SYNTAX		RollCallString
		MAX-ACCESS		read-only
		STATUS			current
		DESCRIPTION
				"TYPE: - Display
				 PAGE: - ARC & Sidebar Keyer- Output Signalling C
					Output Line Status  cmdID= 20176  format=   "
		::= { iqudc32CmdEntry 20176 }


	iqudc32OutputSignallingCAFDUserBitsForceUserBitsVal20173 OBJECT-TYPE
		SYNTAX		INTEGER { disable(0), enable(1) }
		MAX-ACCESS		read-write
		STATUS			current
		DESCRIPTION
				"TYPE: - Checkbox
				 PAGE: - ARC & Sidebar Keyer- Output Signalling C
					Force User Bits Val  cmdID= 20173 "
		::= { iqudc32CmdEntry 20173 }


	iqudc32OutputSignallingCAFDUserBitsUserBitsValue40237 OBJECT-TYPE
		SYNTAX		INTEGER
		MAX-ACCESS		read-write
		STATUS			current
		DESCRIPTION
				"TYPE: - Number
				 PAGE: - ARC & Sidebar Keyer- Output Signalling C
					User Bits Value  cmdID= 40237  min= 0  max= 15  step= 1  format= %0.0f  div_scale= 1 
					Min = 0  Max = 15  Step = 1 "
		::= { iqudc32CmdEntry 40237 }


	iqudc32OutputSignallingCForceModeConfigSMPTE201640233 OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-4-3-AFD-8(8),
							val-4-3-AFD-9(9),
							val-4-3-AFD-10(10),
							val-4-3-AFD-11(11),
							val-4-3-AFD-12(12),
							val-4-3-AFD-13(13),
							val-4-3-AFD-14(14),
							val-4-3-AFD-15(15),
							val-16-9-AFD-0(16),
							val-16-9-AFD-1(17),
							val-16-9-AFD-2(18),
							val-16-9-AFD-3(19),
							val-16-9-AFD-4(20),
							val-16-9-AFD-5(21),
							val-16-9-AFD-6(22),
							val-16-9-AFD-7(23),
							val-16-9-AFD-8(24),
							val-16-9-AFD-9(25),
							val-16-9-AFD-10(26),
							val-16-9-AFD-11(27),
							val-16-9-AFD-12(28),
							val-16-9-AFD-13(29),
							val-16-9-AFD-14(30),
							val-16-9-AFD-15(31)
							}
		MAX-ACCESS		read-write
		STATUS			current
		DESCRIPTION
				"TYPE: - RadiobuttonList
				 PAGE: - ARC & Sidebar Keyer- Output Signalling C
					SMPTE 2016  cmdID= 40233 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					4:3 AFD 8  value= 8  
					4:3 AFD 9  value= 9  
					4:3 AFD 10  value= 10  
					4:3 AFD 11  value= 11  
					4:3 AFD 12  value= 12  
					4:3 AFD 13  value= 13  
					4:3 AFD 14  value= 14  
					4:3 AFD 15  value= 15  
					16:9 AFD 0  value= 16  
					16:9 AFD 1  value= 17  
					16:9 AFD 2  value= 18  
					16:9 AFD 3  value= 19  
					16:9 AFD 4  value= 20  
					16:9 AFD 5  value= 21  
					16:9 AFD 6  value= 22  
					16:9 AFD 7  value= 23  
					16:9 AFD 8  value= 24  
					16:9 AFD 9  value= 25  
					16:9 AFD 10  value= 26  
					16:9 AFD 11  value= 27  
					16:9 AFD 12  value= 28  
					16:9 AFD 13  value= 29  
					16:9 AFD 14  value= 30  
					16:9 AFD 15  value= 31  "
		::= { iqudc32CmdEntry 40233 }


	iqudc32ARCSidebarKeyerOutputSignallingCSMPTERP186 OBJECT-TYPE
		SYNTAX		INTEGER {
							val-4-3(0),
							val-16-9(1)
							}
		MAX-ACCESS		read-write
		STATUS			current
		DESCRIPTION
				"TYPE: - RadiobuttonList
				 PAGE: - ARC & Sidebar Keyer- Output Signalling C
					SMPTE RP186  cmdID= 40234 
					4:3  value= 0  
					16:9  value= 1  "
		::= { iqudc32CmdEntry 40234 }


	iqudc32ARCSidebarKeyerOutputSignallingCAFD OBJECT-TYPE
		SYNTAX		INTEGER {
							val-4-3-AFD-0(0),
							val-4-3-AFD-1(1),
							val-4-3-AFD-2(2),
							val-4-3-AFD-3(3),
							val-4-3-AFD-4(4),
							val-4-3-AFD-5(5),
							val-4-3-AFD-6(6),
							val-4-3-AFD-7(7),
							val-16-9-AFD-0(8),
							val-16-9-AFD-1(9),
							val-16-9-AFD-2(10),
							val-16-9-AFD-3(11),
							val-16-9-AFD-4(12),
							val-16-9-AFD-5(13),
							val-16-9-AFD-6(14),
							val-16-9-AFD-7(15)
							}
		MAX-ACCESS		read-write
		STATUS			current
		DESCRIPTION
				"TYPE: - RadiobuttonList
				 PAGE: - ARC & Sidebar Keyer- Output Signalling C
					AFD  cmdID= 40231 
					4:3 AFD 0  value= 0  
					4:3 AFD 1  value= 1  
					4:3 AFD 2  value= 2  
					4:3 AFD 3  value= 3  
					4:3 AFD 4  value= 4  
					4:3 AFD 5  value= 5  
					4:3 AFD 6  value= 6  
					4:3 AFD 7  value= 7  
					16:9 AFD 0  value= 8  
					16:9 AFD 1  value= 9  
					16:9 AFD 2  value= 10  
					16:9 AFD 3  value= 11  
					16:9 AFD 4  value= 12  
					16:9 AFD 5  value= 13  
					16:9 AFD 6  value= 14  
					16:9 AFD 7  value= 15  "
		::= { iqudc32CmdEntry 40231 }


	iqudc32ARCSidebarKeyerOutputSignallingCETSI OBJECT-TYPE
		SYNTAX		INTEGER {
							val-4-3-FF(0),
							val-14-9-Centre(1),
							val-14-9-Top(2),
							val-16-9-Centre(3),
							val-16-9-Top(4),
							val-16-9-Centre-1(5),
							val-4-3-SP-14-9(6),
							val-16-9-FF(7)
							}
		MAX-ACCESS		read-write
		STATUS			current
		DESCRIPTION
				"TYPE: - RadiobuttonList
				 PAGE: - ARC & Sidebar Keyer- Output Signalling C
					ETSI  cmdID= 40232 
					4:3 FF  value= 0  
					14:9 Centre  value= 1  
					14:9 Top  value= 2  
					16:9 Centre  value= 3  
					16:9 Top  value= 4  
					>16:9 Centre  value= 5  
					4:3 SP 14:9  value= 6  
					16:9 FF  value= 7  "
		::= { iqudc32CmdEntry 40232 }


	iqudc32MenuARCSidebarKeyerNewDisplay OBJECT-TYPE
		SYNTAX		RollCallString
		MAX-ACCESS		read-only
		STATUS			current
		DESCRIPTION
				"TYPE: - Display
				 PAGE: - ARC & Sidebar Keyer
					New Display  cmdID= 44449  format=   "
		::= { iqudc32CmdEntry 44449 }


	iqudc32AudioRoutingCh1InputPairsStatusEmbedded1 OBJECT-TYPE
		SYNTAX		RollCallString
		MAX-ACCESS		read-only
		STATUS			current
		DESCRIPTION
				"TYPE: - Display
				 PAGE: - Audio Routing-Ch1
					Embedded 1  cmdID= 63112  format=   "
		::= { iqudc32CmdEntry 63112 }


	iqudc32AudioRoutingCh1InputPairsStatusEmbedded2 OBJECT-TYPE
		SYNTAX		RollCallString
		MAX-ACCESS		read-only
		STATUS			current
		DESCRIPTION
				"TYPE: - Display
				 PAGE: - Audio Routing-Ch1
					Embedded 2  cmdID= 63113  format=   "
		::= { iqudc32CmdEntry 63113 }


	iqudc32AudioRoutingCh1InputPairsStatusEmbedded3 OBJECT-TYPE
		SYNTAX		RollCallString
		MAX-ACCESS		read-only
		STATUS			current
		DESCRIPTION
				"TYPE: - Display
				 PAGE: - Audio Routing-Ch1
					Embedded 3  cmdID= 63102  format=   "
		::= { iqudc32CmdEntry 63102 }


	iqudc32AudioRoutingCh1InputPairsStatusEmbedded4 OBJECT-TYPE
		SYNTAX		RollCallString
		MAX-ACCESS		read-only
		STATUS			current
		DESCRIPTION
				"TYPE: - Display
				 PAGE: - Audio Routing-Ch1
					Embedded 4  cmdID= 63103  format=   "
		::= { iqudc32CmdEntry 63103 }


	iqudc32AudioRoutingCh1InputPairsStatusEmbedded5 OBJECT-TYPE
		SYNTAX		RollCallString
		MAX-ACCESS		read-only
		STATUS			current
		DESCRIPTION
				"TYPE: - Display
				 PAGE: - Audio Routing-Ch1
					Embedded 5  cmdID= 63114  format=   "
		::= { iqudc32CmdEntry 63114 }


	iqudc32AudioRoutingCh1InputPairsStatusEmbedded6 OBJECT-TYPE
		SYNTAX		RollCallString
		MAX-ACCESS		read-only
		STATUS			current
		DESCRIPTION
				"TYPE: - Display
				 PAGE: - Audio Routing-Ch1
					Embedded 6  cmdID= 63105  format=   "
		::= { iqudc32CmdEntry 63105 }


	iqudc32AudioRoutingCh1InputPairsStatusEmbedded7 OBJECT-TYPE
		SYNTAX		RollCallString
		MAX-ACCESS		read-only
		STATUS			current
		DESCRIPTION
				"TYPE: - Display
				 PAGE: - Audio Routing-Ch1
					Embedded 7  cmdID= 63106  format=   "
		::= { iqudc32CmdEntry 63106 }


	iqudc32AudioRoutingCh1InputPairsStatusEmbedded8 OBJECT-TYPE
		SYNTAX		RollCallString
		MAX-ACCESS		read-only
		STATUS			current
		DESCRIPTION
				"TYPE: - Display
				 PAGE: - Audio Routing-Ch1
					Embedded 8  cmdID= 63107  format=   "
		::= { iqudc32CmdEntry 63107 }


	iqudc32AudioRoutingCh1InputPairsStatusAES1 OBJECT-TYPE
		SYNTAX		RollCallString
		MAX-ACCESS		read-only
		STATUS			current
		DESCRIPTION
				"TYPE: - Display
				 PAGE: - Audio Routing-Ch1
					AES 1  cmdID= 63120  format=   "
		::= { iqudc32CmdEntry 63120 }


	iqudc32AudioRoutingCh1InputPairsStatusAES2 OBJECT-TYPE
		SYNTAX		RollCallString
		MAX-ACCESS		read-only
		STATUS			current
		DESCRIPTION
				"TYPE: - Display
				 PAGE: - Audio Routing-Ch1
					AES 2  cmdID= 63121  format=   "
		::= { iqudc32CmdEntry 63121 }


	iqudc32AudioRoutingCh1InputPairsStatusAES3 OBJECT-TYPE
		SYNTAX		RollCallString
		MAX-ACCESS		read-only
		STATUS			current
		DESCRIPTION
				"TYPE: - Display
				 PAGE: - Audio Routing-Ch1
					AES 3  cmdID= 63123  format=   "
		::= { iqudc32CmdEntry 63123 }


	iqudc32AudioRoutingCh1InputPairsStatusAES4 OBJECT-TYPE
		SYNTAX		RollCallString
		MAX-ACCESS		read-only
		STATUS			current
		DESCRIPTION
				"TYPE: - Display
				 PAGE: - Audio Routing-Ch1
					AES 4  cmdID= 63124  format=   "
		::= { iqudc32CmdEntry 63124 }


	iqudc32AudioRoutingCh1InputPairsStatusAES5 OBJECT-TYPE
		SYNTAX		RollCallString
		MAX-ACCESS		read-only
		STATUS			current
		DESCRIPTION
				"TYPE: - Display
				 PAGE: - Audio Routing-Ch1
					AES 5  cmdID= 63125  format=   "
		::= { iqudc32CmdEntry 63125 }


	iqudc32AudioRoutingCh1InputPairsStatusAES6 OBJECT-TYPE
		SYNTAX		RollCallString
		MAX-ACCESS		read-only
		STATUS			current
		DESCRIPTION
				"TYPE: - Display
				 PAGE: - Audio Routing-Ch1
					AES 6  cmdID= 63126  format=   "
		::= { iqudc32CmdEntry 63126 }


	iqudc32AudioRoutingCh1InputPairsStatusAES7 OBJECT-TYPE
		SYNTAX		RollCallString
		MAX-ACCESS		read-only
		STATUS			current
		DESCRIPTION
				"TYPE: - Display
				 PAGE: - Audio Routing-Ch1
					AES 7  cmdID= 63127  format=   "
		::= { iqudc32CmdEntry 63127 }


	iqudc32AudioRoutingCh1InputPairsStatusAES8 OBJECT-TYPE
		SYNTAX		RollCallString
		MAX-ACCESS		read-only
		STATUS			current
		DESCRIPTION
				"TYPE: - Display
				 PAGE: - Audio Routing-Ch1
					AES 8  cmdID= 63128  format=   "
		::= { iqudc32CmdEntry 63128 }


	iqudc32AudioRoutingCh1InputPairsStatusAnalog1 OBJECT-TYPE
		SYNTAX		RollCallString
		MAX-ACCESS		read-only
		STATUS			current
		DESCRIPTION
				"TYPE: - Display
				 PAGE: - Audio Routing-Ch1
					Analog 1  cmdID= 63129  format=   "
		::= { iqudc32CmdEntry 63129 }


	iqudc32AudioRoutingCh1InputPairsStatusAnalog2 OBJECT-TYPE
		SYNTAX		RollCallString
		MAX-ACCESS		read-only
		STATUS			current
		DESCRIPTION
				"TYPE: - Display
				 PAGE: - Audio Routing-Ch1
					Analog 2  cmdID= 63130  format=   "
		::= { iqudc32CmdEntry 63130 }


	iqudc32AudioRoutingCh1InputPairsStatusDolbyDecoder1 OBJECT-TYPE
		SYNTAX		RollCallString
		MAX-ACCESS		read-only
		STATUS			current
		DESCRIPTION
				"TYPE: - Display
				 PAGE: - Audio Routing-Ch1
					Dolby Decoder 1  cmdID= 63131  format=   "
		::= { iqudc32CmdEntry 63131 }


	iqudc32AudioRoutingCh1InputPairsStatusDolbyDecoder2 OBJECT-TYPE
		SYNTAX		RollCallString
		MAX-ACCESS		read-only
		STATUS			current
		DESCRIPTION
				"TYPE: - Display
				 PAGE: - Audio Routing-Ch1
					Dolby Decoder 2  cmdID= 63132  format=   "
		::= { iqudc32CmdEntry 63132 }


	iqudc32AudioRoutingCh1InputPairsStatusDolbyDecoder3 OBJECT-TYPE
		SYNTAX		RollCallString
		MAX-ACCESS		read-only
		STATUS			current
		DESCRIPTION
				"TYPE: - Display
				 PAGE: - Audio Routing-Ch1
					Dolby Decoder 3  cmdID= 63133  format=   "
		::= { iqudc32CmdEntry 63133 }


	iqudc32AudioRoutingCh1InputPairsStatusDolbyDecoder4 OBJECT-TYPE
		SYNTAX		RollCallString
		MAX-ACCESS		read-only
		STATUS			current
		DESCRIPTION
				"TYPE: - Display
				 PAGE: - Audio Routing-Ch1
					Dolby Decoder 4  cmdID= 63134  format=   "
		::= { iqudc32CmdEntry 63134 }


	iqudc32AudioRoutingCh1InputPairsStatusDolbyDownmix OBJECT-TYPE
		SYNTAX		RollCallString
		MAX-ACCESS		read-only
		STATUS			current
		DESCRIPTION
				"TYPE: - Display
				 PAGE: - Audio Routing-Ch1
					Dolby Downmix  cmdID= 63135  format=   "
		::= { iqudc32CmdEntry 63135 }


	iqudc32AudioRoutingCh1InputPairsStatusDolbyEncoder OBJECT-TYPE
		SYNTAX		RollCallString
		MAX-ACCESS		read-only
		STATUS			current
		DESCRIPTION
				"TYPE: - Display
				 PAGE: - Audio Routing-Ch1
					Dolby Encoder  cmdID= 63136  format=   "
		::= { iqudc32CmdEntry 63136 }


	iqudc32ProcessPairs18Pair1InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 1
					Input Pairs Source  cmdID= 50005 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50005 }


	iqudc32ProcessPairs18Pair2InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 2
					Input Pairs Source  cmdID= 50007 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50007 }


	iqudc32ProcessPairs18Pair3InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 3
					Input Pairs Source  cmdID= 50004 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50004 }


	iqudc32ProcessPairs18Pair4InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 4
					Input Pairs Source  cmdID= 50006 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50006 }


	iqudc32ProcessPairs18Pair5InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 5
					Input Pairs Source  cmdID= 50008 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50008 }


	iqudc32ProcessPairs18Pair6InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 6
					Input Pairs Source  cmdID= 50010 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50010 }


	iqudc32ProcessPairs18Pair7InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 7
					Input Pairs Source  cmdID= 50012 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50012 }


	iqudc32ProcessPairs18Pair8InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch1- Process Pairs 1-8- Pair 8
					Input Pairs Source  cmdID= 50017 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50017 }


	iqudc32AudioRoutingCh1ProcessPairs18SPair1 OBJECT-TYPE
		SYNTAX		RollCallString
		MAX-ACCESS		read-only
		STATUS			current
		DESCRIPTION
				"TYPE: - Display
				 PAGE: - Audio Routing-Ch1- Process Pairs 1-8 S
					Pair 1  cmdID= 63137  format=   "
		::= { iqudc32CmdEntry 63137 }


	iqudc32AudioRoutingCh1ProcessPairs18SPair2 OBJECT-TYPE
		SYNTAX		RollCallString
		MAX-ACCESS		read-only
		STATUS			current
		DESCRIPTION
				"TYPE: - Display
				 PAGE: - Audio Routing-Ch1- Process Pairs 1-8 S
					Pair 2  cmdID= 63138  format=   "
		::= { iqudc32CmdEntry 63138 }


	iqudc32AudioRoutingCh1ProcessPairs18SPair3 OBJECT-TYPE
		SYNTAX		RollCallString
		MAX-ACCESS		read-only
		STATUS			current
		DESCRIPTION
				"TYPE: - Display
				 PAGE: - Audio Routing-Ch1- Process Pairs 1-8 S
					Pair 3  cmdID= 63139  format=   "
		::= { iqudc32CmdEntry 63139 }


	iqudc32AudioRoutingCh1ProcessPairs18SPair4 OBJECT-TYPE
		SYNTAX		RollCallString
		MAX-ACCESS		read-only
		STATUS			current
		DESCRIPTION
				"TYPE: - Display
				 PAGE: - Audio Routing-Ch1- Process Pairs 1-8 S
					Pair 4  cmdID= 63140  format=   "
		::= { iqudc32CmdEntry 63140 }


	iqudc32AudioRoutingCh1ProcessPairs18SPair5 OBJECT-TYPE
		SYNTAX		RollCallString
		MAX-ACCESS		read-only
		STATUS			current
		DESCRIPTION
				"TYPE: - Display
				 PAGE: - Audio Routing-Ch1- Process Pairs 1-8 S
					Pair 5  cmdID= 63141  format=   "
		::= { iqudc32CmdEntry 63141 }


	iqudc32AudioRoutingCh1ProcessPairs18SPair6 OBJECT-TYPE
		SYNTAX		RollCallString
		MAX-ACCESS		read-only
		STATUS			current
		DESCRIPTION
				"TYPE: - Display
				 PAGE: - Audio Routing-Ch1- Process Pairs 1-8 S
					Pair 6  cmdID= 63142  format=   "
		::= { iqudc32CmdEntry 63142 }


	iqudc32AudioRoutingCh1ProcessPairs18SPair7 OBJECT-TYPE
		SYNTAX		RollCallString
		MAX-ACCESS		read-only
		STATUS			current
		DESCRIPTION
				"TYPE: - Display
				 PAGE: - Audio Routing-Ch1- Process Pairs 1-8 S
					Pair 7  cmdID= 63143  format=   "
		::= { iqudc32CmdEntry 63143 }


	iqudc32AudioRoutingCh1ProcessPairs18SPair8 OBJECT-TYPE
		SYNTAX		RollCallString
		MAX-ACCESS		read-only
		STATUS			current
		DESCRIPTION
				"TYPE: - Display
				 PAGE: - Audio Routing-Ch1- Process Pairs 1-8 S
					Pair 8  cmdID= 63144  format=   "
		::= { iqudc32CmdEntry 63144 }


	iqudc32AudioRoutingCh2InputPairsStatusEmbedded1 OBJECT-TYPE
		SYNTAX		RollCallString
		MAX-ACCESS		read-only
		STATUS			current
		DESCRIPTION
				"TYPE: - Display
				 PAGE: - Audio Routing-Ch2
					Embedded 1  cmdID= 63200  format=   "
		::= { iqudc32CmdEntry 63200 }


	iqudc32AudioRoutingCh2InputPairsStatusEmbedded2 OBJECT-TYPE
		SYNTAX		RollCallString
		MAX-ACCESS		read-only
		STATUS			current
		DESCRIPTION
				"TYPE: - Display
				 PAGE: - Audio Routing-Ch2
					Embedded 2  cmdID= 63201  format=   "
		::= { iqudc32CmdEntry 63201 }


	iqudc32AudioRoutingCh2InputPairsStatusEmbedded3 OBJECT-TYPE
		SYNTAX		RollCallString
		MAX-ACCESS		read-only
		STATUS			current
		DESCRIPTION
				"TYPE: - Display
				 PAGE: - Audio Routing-Ch2
					Embedded 3  cmdID= 63202  format=   "
		::= { iqudc32CmdEntry 63202 }


	iqudc32AudioRoutingCh2InputPairsStatusEmbedded4 OBJECT-TYPE
		SYNTAX		RollCallString
		MAX-ACCESS		read-only
		STATUS			current
		DESCRIPTION
				"TYPE: - Display
				 PAGE: - Audio Routing-Ch2
					Embedded 4  cmdID= 63203  format=   "
		::= { iqudc32CmdEntry 63203 }


	iqudc32AudioRoutingCh2InputPairsStatusEmbedded5 OBJECT-TYPE
		SYNTAX		RollCallString
		MAX-ACCESS		read-only
		STATUS			current
		DESCRIPTION
				"TYPE: - Display
				 PAGE: - Audio Routing-Ch2
					Embedded 5  cmdID= 63204  format=   "
		::= { iqudc32CmdEntry 63204 }


	iqudc32AudioRoutingCh2InputPairsStatusEmbedded6 OBJECT-TYPE
		SYNTAX		RollCallString
		MAX-ACCESS		read-only
		STATUS			current
		DESCRIPTION
				"TYPE: - Display
				 PAGE: - Audio Routing-Ch2
					Embedded 6  cmdID= 63205  format=   "
		::= { iqudc32CmdEntry 63205 }


	iqudc32AudioRoutingCh2InputPairsStatusEmbedded7 OBJECT-TYPE
		SYNTAX		RollCallString
		MAX-ACCESS		read-only
		STATUS			current
		DESCRIPTION
				"TYPE: - Display
				 PAGE: - Audio Routing-Ch2
					Embedded 7  cmdID= 63206  format=   "
		::= { iqudc32CmdEntry 63206 }


	iqudc32AudioRoutingCh2InputPairsStatusEmbedded8 OBJECT-TYPE
		SYNTAX		RollCallString
		MAX-ACCESS		read-only
		STATUS			current
		DESCRIPTION
				"TYPE: - Display
				 PAGE: - Audio Routing-Ch2
					Embedded 8  cmdID= 63207  format=   "
		::= { iqudc32CmdEntry 63207 }


	iqudc32AudioRoutingCh2InputPairsStatusAES1 OBJECT-TYPE
		SYNTAX		RollCallString
		MAX-ACCESS		read-only
		STATUS			current
		DESCRIPTION
				"TYPE: - Display
				 PAGE: - Audio Routing-Ch2
					AES 1  cmdID= 63220  format=   "
		::= { iqudc32CmdEntry 63220 }


	iqudc32AudioRoutingCh2InputPairsStatusAES2 OBJECT-TYPE
		SYNTAX		RollCallString
		MAX-ACCESS		read-only
		STATUS			current
		DESCRIPTION
				"TYPE: - Display
				 PAGE: - Audio Routing-Ch2
					AES 2  cmdID= 63221  format=   "
		::= { iqudc32CmdEntry 63221 }


	iqudc32AudioRoutingCh2InputPairsStatusAES3 OBJECT-TYPE
		SYNTAX		RollCallString
		MAX-ACCESS		read-only
		STATUS			current
		DESCRIPTION
				"TYPE: - Display
				 PAGE: - Audio Routing-Ch2
					AES 3  cmdID= 63223  format=   "
		::= { iqudc32CmdEntry 63223 }


	iqudc32AudioRoutingCh2InputPairsStatusAES4 OBJECT-TYPE
		SYNTAX		RollCallString
		MAX-ACCESS		read-only
		STATUS			current
		DESCRIPTION
				"TYPE: - Display
				 PAGE: - Audio Routing-Ch2
					AES 4  cmdID= 63224  format=   "
		::= { iqudc32CmdEntry 63224 }


	iqudc32AudioRoutingCh2InputPairsStatusAES5 OBJECT-TYPE
		SYNTAX		RollCallString
		MAX-ACCESS		read-only
		STATUS			current
		DESCRIPTION
				"TYPE: - Display
				 PAGE: - Audio Routing-Ch2
					AES 5  cmdID= 63225  format=   "
		::= { iqudc32CmdEntry 63225 }


	iqudc32AudioRoutingCh2InputPairsStatusAES6 OBJECT-TYPE
		SYNTAX		RollCallString
		MAX-ACCESS		read-only
		STATUS			current
		DESCRIPTION
				"TYPE: - Display
				 PAGE: - Audio Routing-Ch2
					AES 6  cmdID= 63226  format=   "
		::= { iqudc32CmdEntry 63226 }


	iqudc32AudioRoutingCh2InputPairsStatusAES7 OBJECT-TYPE
		SYNTAX		RollCallString
		MAX-ACCESS		read-only
		STATUS			current
		DESCRIPTION
				"TYPE: - Display
				 PAGE: - Audio Routing-Ch2
					AES 7  cmdID= 63227  format=   "
		::= { iqudc32CmdEntry 63227 }


	iqudc32AudioRoutingCh2InputPairsStatusAES8 OBJECT-TYPE
		SYNTAX		RollCallString
		MAX-ACCESS		read-only
		STATUS			current
		DESCRIPTION
				"TYPE: - Display
				 PAGE: - Audio Routing-Ch2
					AES 8  cmdID= 63228  format=   "
		::= { iqudc32CmdEntry 63228 }


	iqudc32AudioRoutingCh2InputPairsStatusAnalog1 OBJECT-TYPE
		SYNTAX		RollCallString
		MAX-ACCESS		read-only
		STATUS			current
		DESCRIPTION
				"TYPE: - Display
				 PAGE: - Audio Routing-Ch2
					Analog 1  cmdID= 63229  format=   "
		::= { iqudc32CmdEntry 63229 }


	iqudc32AudioRoutingCh2InputPairsStatusAnalog2 OBJECT-TYPE
		SYNTAX		RollCallString
		MAX-ACCESS		read-only
		STATUS			current
		DESCRIPTION
				"TYPE: - Display
				 PAGE: - Audio Routing-Ch2
					Analog 2  cmdID= 63236  format=   "
		::= { iqudc32CmdEntry 63236 }


	iqudc32AudioRoutingCh2InputPairsStatusDolbyDecoder1 OBJECT-TYPE
		SYNTAX		RollCallString
		MAX-ACCESS		read-only
		STATUS			current
		DESCRIPTION
				"TYPE: - Display
				 PAGE: - Audio Routing-Ch2
					Dolby Decoder 1  cmdID= 63230  format=   "
		::= { iqudc32CmdEntry 63230 }


	iqudc32AudioRoutingCh2InputPairsStatusDolbyDecoder2 OBJECT-TYPE
		SYNTAX		RollCallString
		MAX-ACCESS		read-only
		STATUS			current
		DESCRIPTION
				"TYPE: - Display
				 PAGE: - Audio Routing-Ch2
					Dolby Decoder 2  cmdID= 63231  format=   "
		::= { iqudc32CmdEntry 63231 }


	iqudc32AudioRoutingCh2InputPairsStatusDolbyDecoder3 OBJECT-TYPE
		SYNTAX		RollCallString
		MAX-ACCESS		read-only
		STATUS			current
		DESCRIPTION
				"TYPE: - Display
				 PAGE: - Audio Routing-Ch2
					Dolby Decoder 3  cmdID= 63232  format=   "
		::= { iqudc32CmdEntry 63232 }


	iqudc32AudioRoutingCh2InputPairsStatusDolbyDecoder4 OBJECT-TYPE
		SYNTAX		RollCallString
		MAX-ACCESS		read-only
		STATUS			current
		DESCRIPTION
				"TYPE: - Display
				 PAGE: - Audio Routing-Ch2
					Dolby Decoder 4  cmdID= 63233  format=   "
		::= { iqudc32CmdEntry 63233 }


	iqudc32AudioRoutingCh2InputPairsStatusDolbyDownmix OBJECT-TYPE
		SYNTAX		RollCallString
		MAX-ACCESS		read-only
		STATUS			current
		DESCRIPTION
				"TYPE: - Display
				 PAGE: - Audio Routing-Ch2
					Dolby Downmix  cmdID= 63234  format=   "
		::= { iqudc32CmdEntry 63234 }


	iqudc32AudioRoutingCh2InputPairsStatusDolbyEncoder OBJECT-TYPE
		SYNTAX		RollCallString
		MAX-ACCESS		read-only
		STATUS			current
		DESCRIPTION
				"TYPE: - Display
				 PAGE: - Audio Routing-Ch2
					Dolby Encoder  cmdID= 63235  format=   "
		::= { iqudc32CmdEntry 63235 }


	iqudc32ProcessPairs18ProcessPair1InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 1
					Input Pairs Source  cmdID= 50242 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50242 }


	iqudc32ProcessPairs18ProcessPair2InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 2
					Input Pairs Source  cmdID= 50243 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50243 }


	iqudc32ProcessPairs18ProcessPair3InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 3
					Input Pairs Source  cmdID= 50244 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50244 }


	iqudc32ProcessPairs18ProcessPair4InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 4
					Input Pairs Source  cmdID= 50245 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50245 }


	iqudc32ProcessPairs18ProcessPair5InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 5
					Input Pairs Source  cmdID= 50246 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50246 }


	iqudc32ProcessPairs18ProcessPair6InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 6
					Input Pairs Source  cmdID= 50247 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50247 }


	iqudc32ProcessPairs18ProcessPair7InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 7
					Input Pairs Source  cmdID= 50248 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50248 }


	iqudc32ProcessPairs18ProcessPair8InputPairsSource OBJECT-TYPE
		SYNTAX		INTEGER {
							val-Embedded-1(1),
							val-Embedded-2(2),
							val-Embedded-3(3),
							val-Embedded-4(4),
							val-Embedded-5(5),
							val-Embedded-6(6),
							val-Embedded-7(7),
							val-Embedded-8(8),
							val-AES-1(9),
							val-AES-2(10),
							val-AES-3(11),
							val-AES-4(12),
							val-AES-5(13),
							val-AES-6(14),
							val-AES-7(15),
							val-AES-8(16),
							val-Analog-1(17),
							val-Analog-2(18),
							val-Dolby-Decoder-1(19),
							val-Dolby-Decoder-2(20),
							val-Dolby-Decoder-3(21),
							val-Dolby-Decoder-4(22),
							val-Dolby-Downmix(23),
							val-Dolby-Encoder(24)
							}
		MAX-ACCESS		read-write
		STATUS			current
		DESCRIPTION
				"TYPE: - RadiobuttonList
				 PAGE: - Audio Routing-Ch2- Process Pairs 1-8- Process Pair 8
					Input Pairs Source  cmdID= 50249 
					Embedded 1  value= 1  
					Embedded 2  value= 2  
					Embedded 3  value= 3  
					Embedded 4  value= 4  
					Embedded 5  value= 5  
					Embedded 6  value= 6  
					Embedded 7  value= 7  
					Embedded 8  value= 8  
					AES 1  value= 9  
					AES 2  value= 10  
					AES 3  value= 11  
					AES 4  value= 12  
					AES 5  value= 13  
					AES 6  value= 14  
					AES 7  value= 15  
					AES 8  value= 16  
					Analog 1  value= 17  
					Analog 2  value= 18  
					Dolby Decoder 1  value= 19  
					Dolby Decoder 2  value= 20  
					Dolby Decoder 3  value= 21  
					Dolby Decoder 4  value= 22  
					Dolby Downmix  value= 23  
					Dolby Encoder  value= 24  "
		::= { iqudc32CmdEntry 50249 }


	iqudc32AudioRoutingCh2ProcessPairs18SPair1 OBJECT-TYPE
		SYNTAX		RollCallString
		MAX-ACCESS		read-only
		STATUS			current
		DESCRIPTION
				"TYPE: - Display
				 PAGE: - Audio Routing-Ch2- Process Pairs 1-8 S
					Pair 1  cmdID= 63145  format=   "
		::= { iqudc32CmdEntry 63145 }


	iqudc32AudioRoutingCh2ProcessPairs18SPair2 OBJECT-TYPE
		SYNTAX		RollCallString
		MAX-ACCESS		read-only
		STATUS			current
		DESCRIPTION
				"TYPE: - Display
				 PAGE: - Audio Routing-Ch2- Process Pairs 1-8 S
					Pair 2  cmdID= 63146  format=   "
		::= { iqudc32CmdEntry 63146 }


	iqudc32AudioRoutingCh2ProcessPairs18SPair3 OBJECT-TYPE
		SYNTAX		RollCallString
		MAX-ACCESS		read-only
		STATUS			current
		DESCRIPTION
				"TYPE: - Display
				 PAGE: - Audio Routing-Ch2- Process Pairs 1-8 S
					Pair 3  cmdID= 63147  format=   "
		::= { iqudc32CmdEntry 63147 }


	iqudc32AudioRoutingCh2ProcessPairs18SPair4 OBJECT-TYPE
		SYNTAX		RollCallString
		MAX-ACCESS		read-only
		STATUS			current
		DESCRIPTION
				"TYPE: - Display
				 PAGE: - Audio Routing-Ch2- Process Pairs 1-8 S
					Pair 4  cmdID= 63148  format=   "
		::= { iqudc32CmdEntry 63148 }


	iqudc32AudioRoutingCh2ProcessPairs18SPair5 OBJECT-TYPE
		SYNTAX		RollCallString
		MAX-ACCESS		read-only
		STATUS			current
		DESCRIPTION
				"TYPE: - Display
				 PAGE: - Audio Routing-Ch2- Process Pairs 1-8 S
					Pair 5  cmdID= 63149  format=   "
		::= { iqudc32CmdEntry 63149 }


	iqudc32AudioRoutingCh2ProcessPairs18SPair6 OBJECT-TYPE
		SYNTAX		RollCallString
		MAX-ACCESS		read-only
		STATUS			current
		DESCRIPTION
				"TYPE: - Display
				 PAGE: - Audio Routing-Ch2- Process Pairs 1-8 S
					Pair 6  cmdID= 63150  format=   "
		::= { iqudc32CmdEntry 63150 }


	iqudc32AudioRoutingCh2ProcessPairs18SPair7 OBJECT-TYPE
		SYNTAX		RollCallString
		MAX-ACCESS		read-only
		STATUS			current
		DESCRIPTION
				"TYPE: - Display
				 PAGE: - Audio Routing-Ch2- Process Pairs 1-8 S
					Pair 7  cmdID= 63151  format=   "
		::= { iqudc32CmdEntry 63151 }


	iqudc32AudioRoutingCh2ProcessPairs18SPair8 OBJECT-TYPE
		SYNTAX		RollCallString
		MAX-ACCESS		read-only
		STATUS			current
		DESCRIPTION
				"TYPE: - Display
				 PAGE: - Audio Routing-Ch2- Process Pairs 1-8 S
					Pair 8  cmdID= 63152  format=   "
		::= { iqudc32CmdEntry 63152 }


	iqudc32MenuAudioRoutingCh2NewDisplay OBJECT-TYPE
		SYNTAX		RollCallString
		MAX-ACCESS		read-only
		STATUS			current
		DESCRIPTION
				"TYPE: - Display
				 PAGE: - Audio Routing-Ch2
					New Display  cmdID= 44450  format=   "
		::= { iqudc32CmdEntry 44450 }


	iqudc32OutputPairs18OutputPair1LProcessPairsSourc52000 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 1 L
					Process Pairs Sourc  cmdID= 52000 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52000 }


	iqudc32OutputPairs18OutputPair1LInvertPhase50700 OBJECT-TYPE
		SYNTAX		INTEGER { disable(0), enable(1) }
		MAX-ACCESS		read-write
		STATUS			current
		DESCRIPTION
				"TYPE: - Checkbox
				 PAGE: - Audio Shuffle-Ch1- Output Pairs 1-8- Output Pair 1 L
					Invert Phase  cmdID= 50700 "
		::= { iqudc32CmdEntry 50700 }


	iqudc32OutputPairs18OutputPair1LControl50100 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 1 L
					Control  cmdID= 50100 
					Use Routing  value= 0  
					Tone  value= 1  
					Silence  value= 2  "
		::= { iqudc32CmdEntry 50100 }


	iqudc32OutputPairs18OutputPair1RProcessPairsSourc52008 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 1 R
					Process Pairs Sourc  cmdID= 52008 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52008 }


	iqudc32OutputPairs18OutputPair1RInvertPhase50708 OBJECT-TYPE
		SYNTAX		INTEGER { disable(0), enable(1) }
		MAX-ACCESS		read-write
		STATUS			current
		DESCRIPTION
				"TYPE: - Checkbox
				 PAGE: - Audio Shuffle-Ch1- Output Pairs 1-8- Output Pair 1 R
					Invert Phase  cmdID= 50708 "
		::= { iqudc32CmdEntry 50708 }


	iqudc32OutputPairs18OutputPair1RControl50108 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 1 R
					Control  cmdID= 50108 
					Use Routing  value= 0  
					Tone  value= 1  
					Silence  value= 2  "
		::= { iqudc32CmdEntry 50108 }


	iqudc32OutputPairs18OutputPair2LProcessPairsSourc52001 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 2 L
					Process Pairs Sourc  cmdID= 52001 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52001 }


	iqudc32OutputPairs18OutputPair2LInvertPhase50701 OBJECT-TYPE
		SYNTAX		INTEGER { disable(0), enable(1) }
		MAX-ACCESS		read-write
		STATUS			current
		DESCRIPTION
				"TYPE: - Checkbox
				 PAGE: - Audio Shuffle-Ch1- Output Pairs 1-8- Output Pair 2 L
					Invert Phase  cmdID= 50701 "
		::= { iqudc32CmdEntry 50701 }


	iqudc32OutputPairs18OutputPair2LControl50101 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 2 L
					Control  cmdID= 50101 
					Use Routing  value= 0  
					Tone  value= 1  
					Silence  value= 2  "
		::= { iqudc32CmdEntry 50101 }


	iqudc32OutputPairs18OutputPair2RProcessPairsSourc52009 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 2 R
					Process Pairs Sourc  cmdID= 52009 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52009 }


	iqudc32OutputPairs18OutputPair2RInvertPhase50709 OBJECT-TYPE
		SYNTAX		INTEGER { disable(0), enable(1) }
		MAX-ACCESS		read-write
		STATUS			current
		DESCRIPTION
				"TYPE: - Checkbox
				 PAGE: - Audio Shuffle-Ch1- Output Pairs 1-8- Output Pair 2 R
					Invert Phase  cmdID= 50709 "
		::= { iqudc32CmdEntry 50709 }


	iqudc32OutputPairs18OutputPair2RControl50109 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 2 R
					Control  cmdID= 50109 
					Use Routing  value= 0  
					Tone  value= 1  
					Silence  value= 2  "
		::= { iqudc32CmdEntry 50109 }


	iqudc32OutputPairs18OutputPair3LProcessPairsSourc52002 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 3 L
					Process Pairs Sourc  cmdID= 52002 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52002 }


	iqudc32OutputPairs18OutputPair3LInvertPhase50702 OBJECT-TYPE
		SYNTAX		INTEGER { disable(0), enable(1) }
		MAX-ACCESS		read-write
		STATUS			current
		DESCRIPTION
				"TYPE: - Checkbox
				 PAGE: - Audio Shuffle-Ch1- Output Pairs 1-8- Output Pair 3 L
					Invert Phase  cmdID= 50702 "
		::= { iqudc32CmdEntry 50702 }


	iqudc32OutputPairs18OutputPair3LControl50102 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 3 L
					Control  cmdID= 50102 
					Use Routing  value= 0  
					Tone  value= 1  
					Silence  value= 2  "
		::= { iqudc32CmdEntry 50102 }


	iqudc32OutputPairs18OutputPair3RProcessPairsSourc52010 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 3 R
					Process Pairs Sourc  cmdID= 52010 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52010 }


	iqudc32OutputPairs18OutputPair3RInvertPhase50710 OBJECT-TYPE
		SYNTAX		INTEGER { disable(0), enable(1) }
		MAX-ACCESS		read-write
		STATUS			current
		DESCRIPTION
				"TYPE: - Checkbox
				 PAGE: - Audio Shuffle-Ch1- Output Pairs 1-8- Output Pair 3 R
					Invert Phase  cmdID= 50710 "
		::= { iqudc32CmdEntry 50710 }


	iqudc32OutputPairs18OutputPair3RControl50110 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 3 R
					Control  cmdID= 50110 
					Use Routing  value= 0  
					Tone  value= 1  
					Silence  value= 2  "
		::= { iqudc32CmdEntry 50110 }


	iqudc32OutputPairs18OutputPair4LProcessPairsSourc52003 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 4 L
					Process Pairs Sourc  cmdID= 52003 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52003 }


	iqudc32OutputPairs18OutputPair4LInvertPhase50703 OBJECT-TYPE
		SYNTAX		INTEGER { disable(0), enable(1) }
		MAX-ACCESS		read-write
		STATUS			current
		DESCRIPTION
				"TYPE: - Checkbox
				 PAGE: - Audio Shuffle-Ch1- Output Pairs 1-8- Output Pair 4 L
					Invert Phase  cmdID= 50703 "
		::= { iqudc32CmdEntry 50703 }


	iqudc32OutputPairs18OutputPair4LControl50103 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 4 L
					Control  cmdID= 50103 
					Use Routing  value= 0  
					Tone  value= 1  
					Silence  value= 2  "
		::= { iqudc32CmdEntry 50103 }


	iqudc32OutputPairs18OutputPair4RProcessPairsSourc52011 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 4 R
					Process Pairs Sourc  cmdID= 52011 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52011 }


	iqudc32OutputPairs18OutputPair4RInvertPhase50711 OBJECT-TYPE
		SYNTAX		INTEGER { disable(0), enable(1) }
		MAX-ACCESS		read-write
		STATUS			current
		DESCRIPTION
				"TYPE: - Checkbox
				 PAGE: - Audio Shuffle-Ch1- Output Pairs 1-8- Output Pair 4 R
					Invert Phase  cmdID= 50711 "
		::= { iqudc32CmdEntry 50711 }


	iqudc32OutputPairs18OutputPair4RControl50111 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 4 R
					Control  cmdID= 50111 
					Use Routing  value= 0  
					Tone  value= 1  
					Silence  value= 2  "
		::= { iqudc32CmdEntry 50111 }


	iqudc32OutputPairs18OutputPair5LProcessPairsSourc52004 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 5 L
					Process Pairs Sourc  cmdID= 52004 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52004 }


	iqudc32OutputPairs18OutputPair5LInvertPhase50704 OBJECT-TYPE
		SYNTAX		INTEGER { disable(0), enable(1) }
		MAX-ACCESS		read-write
		STATUS			current
		DESCRIPTION
				"TYPE: - Checkbox
				 PAGE: - Audio Shuffle-Ch1- Output Pairs 1-8- Output Pair 5 L
					Invert Phase  cmdID= 50704 "
		::= { iqudc32CmdEntry 50704 }


	iqudc32OutputPairs18OutputPair5LControl50104 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 5 L
					Control  cmdID= 50104 
					Use Routing  value= 0  
					Tone  value= 1  
					Silence  value= 2  "
		::= { iqudc32CmdEntry 50104 }


	iqudc32OutputPairs18OutputPair5RProcessPairsSourc52012 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 5 R
					Process Pairs Sourc  cmdID= 52012 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52012 }


	iqudc32OutputPairs18OutputPair5RInvertPhase50712 OBJECT-TYPE
		SYNTAX		INTEGER { disable(0), enable(1) }
		MAX-ACCESS		read-write
		STATUS			current
		DESCRIPTION
				"TYPE: - Checkbox
				 PAGE: - Audio Shuffle-Ch1- Output Pairs 1-8- Output Pair 5 R
					Invert Phase  cmdID= 50712 "
		::= { iqudc32CmdEntry 50712 }


	iqudc32OutputPairs18OutputPair5RControl50112 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 5 R
					Control  cmdID= 50112 
					Use Routing  value= 0  
					Tone  value= 1  
					Silence  value= 2  "
		::= { iqudc32CmdEntry 50112 }


	iqudc32OutputPairs18OutputPair6LProcessPairsSourc52005 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 6 L
					Process Pairs Sourc  cmdID= 52005 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52005 }


	iqudc32OutputPairs18OutputPair6LInvertPhase50705 OBJECT-TYPE
		SYNTAX		INTEGER { disable(0), enable(1) }
		MAX-ACCESS		read-write
		STATUS			current
		DESCRIPTION
				"TYPE: - Checkbox
				 PAGE: - Audio Shuffle-Ch1- Output Pairs 1-8- Output Pair 6 L
					Invert Phase  cmdID= 50705 "
		::= { iqudc32CmdEntry 50705 }


	iqudc32OutputPairs18OutputPair6LControl50105 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 6 L
					Control  cmdID= 50105 
					Use Routing  value= 0  
					Tone  value= 1  
					Silence  value= 2  "
		::= { iqudc32CmdEntry 50105 }


	iqudc32OutputPairs18OutputPair6RProcessPairsSourc52013 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 6 R
					Process Pairs Sourc  cmdID= 52013 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52013 }


	iqudc32OutputPairs18OutputPair6RInvertPhase50713 OBJECT-TYPE
		SYNTAX		INTEGER { disable(0), enable(1) }
		MAX-ACCESS		read-write
		STATUS			current
		DESCRIPTION
				"TYPE: - Checkbox
				 PAGE: - Audio Shuffle-Ch1- Output Pairs 1-8- Output Pair 6 R
					Invert Phase  cmdID= 50713 "
		::= { iqudc32CmdEntry 50713 }


	iqudc32OutputPairs18OutputPair6RControl50113 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 6 R
					Control  cmdID= 50113 
					Use Routing  value= 0  
					Tone  value= 1  
					Silence  value= 2  "
		::= { iqudc32CmdEntry 50113 }


	iqudc32OutputPairs18OutputPair7LProcessPairsSourc52006 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 7 L
					Process Pairs Sourc  cmdID= 52006 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52006 }


	iqudc32OutputPairs18OutputPair7LInvertPhase50706 OBJECT-TYPE
		SYNTAX		INTEGER { disable(0), enable(1) }
		MAX-ACCESS		read-write
		STATUS			current
		DESCRIPTION
				"TYPE: - Checkbox
				 PAGE: - Audio Shuffle-Ch1- Output Pairs 1-8- Output Pair 7 L
					Invert Phase  cmdID= 50706 "
		::= { iqudc32CmdEntry 50706 }


	iqudc32OutputPairs18OutputPair7LControl50106 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 7 L
					Control  cmdID= 50106 
					Use Routing  value= 0  
					Tone  value= 1  
					Silence  value= 2  "
		::= { iqudc32CmdEntry 50106 }


	iqudc32OutputPairs18OutputPair7RProcessPairsSourc52014 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 7 R
					Process Pairs Sourc  cmdID= 52014 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52014 }


	iqudc32OutputPairs18OutputPair7RInvertPhase50714 OBJECT-TYPE
		SYNTAX		INTEGER { disable(0), enable(1) }
		MAX-ACCESS		read-write
		STATUS			current
		DESCRIPTION
				"TYPE: - Checkbox
				 PAGE: - Audio Shuffle-Ch1- Output Pairs 1-8- Output Pair 7 R
					Invert Phase  cmdID= 50714 "
		::= { iqudc32CmdEntry 50714 }


	iqudc32OutputPairs18OutputPair7RControl50114 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 7 R
					Control  cmdID= 50114 
					Use Routing  value= 0  
					Tone  value= 1  
					Silence  value= 2  "
		::= { iqudc32CmdEntry 50114 }


	iqudc32OutputPairs18OutputPair8LProcessPairsSourc52007 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 8 L
					Process Pairs Sourc  cmdID= 52007 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52007 }


	iqudc32OutputPairs18OutputPair8LInvertPhase50707 OBJECT-TYPE
		SYNTAX		INTEGER { disable(0), enable(1) }
		MAX-ACCESS		read-write
		STATUS			current
		DESCRIPTION
				"TYPE: - Checkbox
				 PAGE: - Audio Shuffle-Ch1- Output Pairs 1-8- Output Pair 8 L
					Invert Phase  cmdID= 50707 "
		::= { iqudc32CmdEntry 50707 }


	iqudc32OutputPairs18OutputPair8LControl50107 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 8 L
					Control  cmdID= 50107 
					Use Routing  value= 0  
					Tone  value= 1  
					Silence  value= 2  "
		::= { iqudc32CmdEntry 50107 }


	iqudc32OutputPairs18OutputPair8RProcessPairsSourc52015 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch1- Output Pairs 1-8- Output Pair 8 R
					Process Pairs Sourc  cmdID= 52015 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 52015 }


	iqudc32OutputPairs18OutputPair8RInvertPhase50715 OBJECT-TYPE
		SYNTAX		INTEGER { disable(0), enable(1) }
		MAX-ACCESS		read-write
		STATUS			current
		DESCRIPTION
				"TYPE: - Checkbox
				 PAGE: - Audio Shuffle-Ch1- Output Pairs 1-8- Output Pair 8 R
					Invert Phase  cmdID= 50715 "
		::= { iqudc32CmdEntry 50715 }


	iqudc32OutputPairs18OutputPair8RControl50115 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch1- Output Pairs 1-8- Output Pair 8 R
					Control  cmdID= 50115 
					Use Routing  value= 0  
					Tone  value= 1  
					Silence  value= 2  "
		::= { iqudc32CmdEntry 50115 }


	iqudc32AudioShuffleCh1OutputPairs18StPair1 OBJECT-TYPE
		SYNTAX		RollCallString
		MAX-ACCESS		read-only
		STATUS			current
		DESCRIPTION
				"TYPE: - Display
				 PAGE: - Audio Shuffle-Ch1- Output Pairs 1-8 St
					Pair 1  cmdID= 50335  format=   "
		::= { iqudc32CmdEntry 50335 }


	iqudc32AudioShuffleCh1OutputPairs18StPair2 OBJECT-TYPE
		SYNTAX		RollCallString
		MAX-ACCESS		read-only
		STATUS			current
		DESCRIPTION
				"TYPE: - Display
				 PAGE: - Audio Shuffle-Ch1- Output Pairs 1-8 St
					Pair 2  cmdID= 50336  format=   "
		::= { iqudc32CmdEntry 50336 }


	iqudc32AudioShuffleCh1OutputPairs18StPair3 OBJECT-TYPE
		SYNTAX		RollCallString
		MAX-ACCESS		read-only
		STATUS			current
		DESCRIPTION
				"TYPE: - Display
				 PAGE: - Audio Shuffle-Ch1- Output Pairs 1-8 St
					Pair 3  cmdID= 50337  format=   "
		::= { iqudc32CmdEntry 50337 }


	iqudc32AudioShuffleCh1OutputPairs18StPair4 OBJECT-TYPE
		SYNTAX		RollCallString
		MAX-ACCESS		read-only
		STATUS			current
		DESCRIPTION
				"TYPE: - Display
				 PAGE: - Audio Shuffle-Ch1- Output Pairs 1-8 St
					Pair 4  cmdID= 50338  format=   "
		::= { iqudc32CmdEntry 50338 }


	iqudc32AudioShuffleCh1OutputPairs18StPair5 OBJECT-TYPE
		SYNTAX		RollCallString
		MAX-ACCESS		read-only
		STATUS			current
		DESCRIPTION
				"TYPE: - Display
				 PAGE: - Audio Shuffle-Ch1- Output Pairs 1-8 St
					Pair 5  cmdID= 50339  format=   "
		::= { iqudc32CmdEntry 50339 }


	iqudc32AudioShuffleCh1OutputPairs18StPair6 OBJECT-TYPE
		SYNTAX		RollCallString
		MAX-ACCESS		read-only
		STATUS			current
		DESCRIPTION
				"TYPE: - Display
				 PAGE: - Audio Shuffle-Ch1- Output Pairs 1-8 St
					Pair 6  cmdID= 50340  format=   "
		::= { iqudc32CmdEntry 50340 }


	iqudc32AudioShuffleCh1OutputPairs18StPair7 OBJECT-TYPE
		SYNTAX		RollCallString
		MAX-ACCESS		read-only
		STATUS			current
		DESCRIPTION
				"TYPE: - Display
				 PAGE: - Audio Shuffle-Ch1- Output Pairs 1-8 St
					Pair 7  cmdID= 50341  format=   "
		::= { iqudc32CmdEntry 50341 }


	iqudc32AudioShuffleCh1OutputPairs18StPair8 OBJECT-TYPE
		SYNTAX		RollCallString
		MAX-ACCESS		read-only
		STATUS			current
		DESCRIPTION
				"TYPE: - Display
				 PAGE: - Audio Shuffle-Ch1- Output Pairs 1-8 St
					Pair 8  cmdID= 50342  format=   "
		::= { iqudc32CmdEntry 50342 }


	iqudc32MenuAudioShuffleCh1NewDisplay OBJECT-TYPE
		SYNTAX		RollCallString
		MAX-ACCESS		read-only
		STATUS			current
		DESCRIPTION
				"TYPE: - Display
				 PAGE: - Audio Shuffle-Ch1
					New Display  cmdID= 44461  format=   "
		::= { iqudc32CmdEntry 44461 }


	iqudc32OutputPairs18OutputPair1LProcessPairsSourc50800 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 1 L
					Process Pairs Sourc  cmdID= 50800 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50800 }


	iqudc32OutputPairs18OutputPair1LInvertPhase50816 OBJECT-TYPE
		SYNTAX		INTEGER { disable(0), enable(1) }
		MAX-ACCESS		read-write
		STATUS			current
		DESCRIPTION
				"TYPE: - Checkbox
				 PAGE: - Audio Shuffle-Ch2- Output Pairs 1-8- Output Pair 1 L
					Invert Phase  cmdID= 50816 "
		::= { iqudc32CmdEntry 50816 }


	iqudc32OutputPairs18OutputPair1LControl50832 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 1 L
					Control  cmdID= 50832 
					Use Routing  value= 0  
					Tone  value= 1  
					Silence  value= 2  "
		::= { iqudc32CmdEntry 50832 }


	iqudc32OutputPairs18OutputPair1RProcessPairsSourc50808 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 1 R
					Process Pairs Sourc  cmdID= 50808 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50808 }


	iqudc32OutputPairs18OutputPair1RInvertPhase50824 OBJECT-TYPE
		SYNTAX		INTEGER { disable(0), enable(1) }
		MAX-ACCESS		read-write
		STATUS			current
		DESCRIPTION
				"TYPE: - Checkbox
				 PAGE: - Audio Shuffle-Ch2- Output Pairs 1-8- Output Pair 1 R
					Invert Phase  cmdID= 50824 "
		::= { iqudc32CmdEntry 50824 }


	iqudc32OutputPairs18OutputPair1RControl50840 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 1 R
					Control  cmdID= 50840 
					Use Routing  value= 0  
					Tone  value= 1  
					Silence  value= 2  "
		::= { iqudc32CmdEntry 50840 }


	iqudc32OutputPairs18OutputPair2LProcessPairsSourc50801 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 2 L
					Process Pairs Sourc  cmdID= 50801 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50801 }


	iqudc32OutputPairs18OutputPair2LInvertPhase50817 OBJECT-TYPE
		SYNTAX		INTEGER { disable(0), enable(1) }
		MAX-ACCESS		read-write
		STATUS			current
		DESCRIPTION
				"TYPE: - Checkbox
				 PAGE: - Audio Shuffle-Ch2- Output Pairs 1-8- Output Pair 2 L
					Invert Phase  cmdID= 50817 "
		::= { iqudc32CmdEntry 50817 }


	iqudc32OutputPairs18OutputPair2LControl50833 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 2 L
					Control  cmdID= 50833 
					Use Routing  value= 0  
					Tone  value= 1  
					Silence  value= 2  "
		::= { iqudc32CmdEntry 50833 }


	iqudc32OutputPairs18OutputPair2RProcessPairsSourc50809 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 2 R
					Process Pairs Sourc  cmdID= 50809 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50809 }


	iqudc32OutputPairs18OutputPair2RInvertPhase50825 OBJECT-TYPE
		SYNTAX		INTEGER { disable(0), enable(1) }
		MAX-ACCESS		read-write
		STATUS			current
		DESCRIPTION
				"TYPE: - Checkbox
				 PAGE: - Audio Shuffle-Ch2- Output Pairs 1-8- Output Pair 2 R
					Invert Phase  cmdID= 50825 "
		::= { iqudc32CmdEntry 50825 }


	iqudc32OutputPairs18OutputPair2RControl50841 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 2 R
					Control  cmdID= 50841 
					Use Routing  value= 0  
					Tone  value= 1  
					Silence  value= 2  "
		::= { iqudc32CmdEntry 50841 }


	iqudc32OutputPairs18OutputPair3LProcessPairsSourc50802 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 3 L
					Process Pairs Sourc  cmdID= 50802 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50802 }


	iqudc32OutputPairs18OutputPair3LInvertPhase50818 OBJECT-TYPE
		SYNTAX		INTEGER { disable(0), enable(1) }
		MAX-ACCESS		read-write
		STATUS			current
		DESCRIPTION
				"TYPE: - Checkbox
				 PAGE: - Audio Shuffle-Ch2- Output Pairs 1-8- Output Pair 3 L
					Invert Phase  cmdID= 50818 "
		::= { iqudc32CmdEntry 50818 }


	iqudc32OutputPairs18OutputPair3LControl50834 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 3 L
					Control  cmdID= 50834 
					Use Routing  value= 0  
					Tone  value= 1  
					Silence  value= 2  "
		::= { iqudc32CmdEntry 50834 }


	iqudc32OutputPairs18OutputPair3RProcessPairsSourc50810 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 3 R
					Process Pairs Sourc  cmdID= 50810 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50810 }


	iqudc32OutputPairs18OutputPair3RInvertPhase50826 OBJECT-TYPE
		SYNTAX		INTEGER { disable(0), enable(1) }
		MAX-ACCESS		read-write
		STATUS			current
		DESCRIPTION
				"TYPE: - Checkbox
				 PAGE: - Audio Shuffle-Ch2- Output Pairs 1-8- Output Pair 3 R
					Invert Phase  cmdID= 50826 "
		::= { iqudc32CmdEntry 50826 }


	iqudc32OutputPairs18OutputPair3RControl50842 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 3 R
					Control  cmdID= 50842 
					Use Routing  value= 0  
					Tone  value= 1  
					Silence  value= 2  "
		::= { iqudc32CmdEntry 50842 }


	iqudc32OutputPairs18OutputPair4LProcessPairsSourc50803 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 4 L
					Process Pairs Sourc  cmdID= 50803 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50803 }


	iqudc32OutputPairs18OutputPair4LInvertPhase50819 OBJECT-TYPE
		SYNTAX		INTEGER { disable(0), enable(1) }
		MAX-ACCESS		read-write
		STATUS			current
		DESCRIPTION
				"TYPE: - Checkbox
				 PAGE: - Audio Shuffle-Ch2- Output Pairs 1-8- Output Pair 4 L
					Invert Phase  cmdID= 50819 "
		::= { iqudc32CmdEntry 50819 }


	iqudc32OutputPairs18OutputPair4LControl50835 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 4 L
					Control  cmdID= 50835 
					Use Routing  value= 0  
					Tone  value= 1  
					Silence  value= 2  "
		::= { iqudc32CmdEntry 50835 }


	iqudc32OutputPairs18OutputPair4RProcessPairsSourc50811 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 4 R
					Process Pairs Sourc  cmdID= 50811 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50811 }


	iqudc32OutputPairs18OutputPair4RInvertPhase50827 OBJECT-TYPE
		SYNTAX		INTEGER { disable(0), enable(1) }
		MAX-ACCESS		read-write
		STATUS			current
		DESCRIPTION
				"TYPE: - Checkbox
				 PAGE: - Audio Shuffle-Ch2- Output Pairs 1-8- Output Pair 4 R
					Invert Phase  cmdID= 50827 "
		::= { iqudc32CmdEntry 50827 }


	iqudc32OutputPairs18OutputPair4RControl50843 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 4 R
					Control  cmdID= 50843 
					Use Routing  value= 0  
					Tone  value= 1  
					Silence  value= 2  "
		::= { iqudc32CmdEntry 50843 }


	iqudc32OutputPairs18OutputPair5LProcessPairsSourc50804 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 5 L
					Process Pairs Sourc  cmdID= 50804 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50804 }


	iqudc32OutputPairs18OutputPair5LInvertPhase50820 OBJECT-TYPE
		SYNTAX		INTEGER { disable(0), enable(1) }
		MAX-ACCESS		read-write
		STATUS			current
		DESCRIPTION
				"TYPE: - Checkbox
				 PAGE: - Audio Shuffle-Ch2- Output Pairs 1-8- Output Pair 5 L
					Invert Phase  cmdID= 50820 "
		::= { iqudc32CmdEntry 50820 }


	iqudc32OutputPairs18OutputPair5LControl50836 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 5 L
					Control  cmdID= 50836 
					Use Routing  value= 0  
					Tone  value= 1  
					Silence  value= 2  "
		::= { iqudc32CmdEntry 50836 }


	iqudc32OutputPairs18OutputPair5RProcessPairsSourc50812 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 5 R
					Process Pairs Sourc  cmdID= 50812 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50812 }


	iqudc32OutputPairs18OutputPair5RInvertPhase50828 OBJECT-TYPE
		SYNTAX		INTEGER { disable(0), enable(1) }
		MAX-ACCESS		read-write
		STATUS			current
		DESCRIPTION
				"TYPE: - Checkbox
				 PAGE: - Audio Shuffle-Ch2- Output Pairs 1-8- Output Pair 5 R
					Invert Phase  cmdID= 50828 "
		::= { iqudc32CmdEntry 50828 }


	iqudc32OutputPairs18OutputPair5RControl50844 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 5 R
					Control  cmdID= 50844 
					Use Routing  value= 0  
					Tone  value= 1  
					Silence  value= 2  "
		::= { iqudc32CmdEntry 50844 }


	iqudc32OutputPairs18OutputPair6LProcessPairsSourc50805 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 6 L
					Process Pairs Sourc  cmdID= 50805 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50805 }


	iqudc32OutputPairs18OutputPair6LInvertPhase50821 OBJECT-TYPE
		SYNTAX		INTEGER { disable(0), enable(1) }
		MAX-ACCESS		read-write
		STATUS			current
		DESCRIPTION
				"TYPE: - Checkbox
				 PAGE: - Audio Shuffle-Ch2- Output Pairs 1-8- Output Pair 6 L
					Invert Phase  cmdID= 50821 "
		::= { iqudc32CmdEntry 50821 }


	iqudc32OutputPairs18OutputPair6LControl50837 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 6 L
					Control  cmdID= 50837 
					Use Routing  value= 0  
					Tone  value= 1  
					Silence  value= 2  "
		::= { iqudc32CmdEntry 50837 }


	iqudc32OutputPairs18OutputPair6RProcessPairsSourc50813 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 6 R
					Process Pairs Sourc  cmdID= 50813 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50813 }


	iqudc32OutputPairs18OutputPair6RInvertPhase50829 OBJECT-TYPE
		SYNTAX		INTEGER { disable(0), enable(1) }
		MAX-ACCESS		read-write
		STATUS			current
		DESCRIPTION
				"TYPE: - Checkbox
				 PAGE: - Audio Shuffle-Ch2- Output Pairs 1-8- Output Pair 6 R
					Invert Phase  cmdID= 50829 "
		::= { iqudc32CmdEntry 50829 }


	iqudc32OutputPairs18OutputPair6RControl50845 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 6 R
					Control  cmdID= 50845 
					Use Routing  value= 0  
					Tone  value= 1  
					Silence  value= 2  "
		::= { iqudc32CmdEntry 50845 }


	iqudc32OutputPairs18OutputPair7LProcessPairsSourc50806 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 7 L
					Process Pairs Sourc  cmdID= 50806 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50806 }


	iqudc32OutputPairs18OutputPair7LInvertPhase50822 OBJECT-TYPE
		SYNTAX		INTEGER { disable(0), enable(1) }
		MAX-ACCESS		read-write
		STATUS			current
		DESCRIPTION
				"TYPE: - Checkbox
				 PAGE: - Audio Shuffle-Ch2- Output Pairs 1-8- Output Pair 7 L
					Invert Phase  cmdID= 50822 "
		::= { iqudc32CmdEntry 50822 }


	iqudc32OutputPairs18OutputPair7LControl50838 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 7 L
					Control  cmdID= 50838 
					Use Routing  value= 0  
					Tone  value= 1  
					Silence  value= 2  "
		::= { iqudc32CmdEntry 50838 }


	iqudc32OutputPairs18OutputPair7RProcessPairsSourc50814 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 7 R
					Process Pairs Sourc  cmdID= 50814 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50814 }


	iqudc32OutputPairs18OutputPair7RInvertPhase50830 OBJECT-TYPE
		SYNTAX		INTEGER { disable(0), enable(1) }
		MAX-ACCESS		read-write
		STATUS			current
		DESCRIPTION
				"TYPE: - Checkbox
				 PAGE: - Audio Shuffle-Ch2- Output Pairs 1-8- Output Pair 7 R
					Invert Phase  cmdID= 50830 "
		::= { iqudc32CmdEntry 50830 }


	iqudc32OutputPairs18OutputPair7RControl50846 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 7 R
					Control  cmdID= 50846 
					Use Routing  value= 0  
					Tone  value= 1  
					Silence  value= 2  "
		::= { iqudc32CmdEntry 50846 }


	iqudc32OutputPairs18OutputPair8LProcessPairsSourc50807 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 8 L
					Process Pairs Sourc  cmdID= 50807 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50807 }


	iqudc32OutputPairs18OutputPair8LInvertPhase50823 OBJECT-TYPE
		SYNTAX		INTEGER { disable(0), enable(1) }
		MAX-ACCESS		read-write
		STATUS			current
		DESCRIPTION
				"TYPE: - Checkbox
				 PAGE: - Audio Shuffle-Ch2- Output Pairs 1-8- Output Pair 8 L
					Invert Phase  cmdID= 50823 "
		::= { iqudc32CmdEntry 50823 }


	iqudc32OutputPairs18OutputPair8LControl50839 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 8 L
					Control  cmdID= 50839 
					Use Routing  value= 0  
					Tone  value= 1  
					Silence  value= 2  "
		::= { iqudc32CmdEntry 50839 }


	iqudc32OutputPairs18OutputPair8RProcessPairsSourc50815 OBJECT-TYPE
		SYNTAX		INTEGER {
							val-Pair-1-L(1),
							val-Pair-1-R(2),
							val-Pair-2-L(3),
							val-Pair-2-R(4),
							val-Pair-3-L(5),
							val-Pair-3-R(6),
							val-Pair-4-L(7),
							val-Pair-4-R(8),
							val-Pair-5-L(9),
							val-Pair-5-R(10),
							val-Pair-6-L(11),
							val-Pair-6-R(12),
							val-Pair-7-L(13),
							val-Pair-7-R(14),
							val-Pair-8-L(15),
							val-Pair-8-R(16)
							}
		MAX-ACCESS		read-write
		STATUS			current
		DESCRIPTION
				"TYPE: - RadiobuttonList
				 PAGE: - Audio Shuffle-Ch2- Output Pairs 1-8- Output Pair 8 R
					Process Pairs Sourc  cmdID= 50815 
					Pair 1 L  value= 1  
					Pair 1 R  value= 2  
					Pair 2 L  value= 3  
					Pair 2 R  value= 4  
					Pair 3 L  value= 5  
					Pair 3 R  value= 6  
					Pair 4 L  value= 7  
					Pair 4 R  value= 8  
					Pair 5 L  value= 9  
					Pair 5 R  value= 10  
					Pair 6 L  value= 11  
					Pair 6 R  value= 12  
					Pair 7 L  value= 13  
					Pair 7 R  value= 14  
					Pair 8 L  value= 15  
					Pair 8 R  value= 16  "
		::= { iqudc32CmdEntry 50815 }


	iqudc32OutputPairs18OutputPair8RInvertPhase50831 OBJECT-TYPE
		SYNTAX		INTEGER { disable(0), enable(1) }
		MAX-ACCESS		read-write
		STATUS			current
		DESCRIPTION
				"TYPE: - Checkbox
				 PAGE: - Audio Shuffle-Ch2- Output Pairs 1-8- Output Pair 8 R
					Invert Phase  cmdID= 50831 "
		::= { iqudc32CmdEntry 50831 }


	iqudc32OutputPairs18OutputPair8RControl50847 OBJECT-TYPE
		SYNTAX		INTEGER {
							val-Use-Routing(0),
							val-Tone(1),
							val-Silence(2)
							}
		MAX-ACCESS		read-write
		STATUS			current
		DESCRIPTION
				"TYPE: - RadiobuttonList
				 PAGE: - Audio Shuffle-Ch2- Output Pairs 1-8- Output Pair 8 R
					Control  cmdID= 50847 
					Use Routing  value= 0  
					Tone  value= 1  
					Silence  value= 2  "
		::= { iqudc32CmdEntry 50847 }


	iqudc32AudioShuffleCh2OutputPairs18StPair1 OBJECT-TYPE
		SYNTAX		RollCallString
		MAX-ACCESS		read-only
		STATUS			current
		DESCRIPTION
				"TYPE: - Display
				 PAGE: - Audio Shuffle-Ch2- Output Pairs 1-8 St
					Pair 1  cmdID= 50348  format=   "
		::= { iqudc32CmdEntry 50348 }


	iqudc32AudioShuffleCh2OutputPairs18StPair2 OBJECT-TYPE
		SYNTAX		RollCallString
		MAX-ACCESS		read-only
		STATUS			current
		DESCRIPTION
				"TYPE: - Display
				 PAGE: - Audio Shuffle-Ch2- Output Pairs 1-8 St
					Pair 2  cmdID= 50349  format=   "
		::= { iqudc32CmdEntry 50349 }


	iqudc32AudioShuffleCh2OutputPairs18StPair3 OBJECT-TYPE
		SYNTAX		RollCallString
		MAX-ACCESS		read-only
		STATUS			current
		DESCRIPTION
				"TYPE: - Display
				 PAGE: - Audio Shuffle-Ch2- Output Pairs 1-8 St
					Pair 3  cmdID= 50350  format=   "
		::= { iqudc32CmdEntry 50350 }


	iqudc32AudioShuffleCh2OutputPairs18StPair4 OBJECT-TYPE
		SYNTAX		RollCallString
		MAX-ACCESS		read-only
		STATUS			current
		DESCRIPTION
				"TYPE: - Display
				 PAGE: - Audio Shuffle-Ch2- Output Pairs 1-8 St
					Pair 4  cmdID= 50351  format=   "
		::= { iqudc32CmdEntry 50351 }


	iqudc32AudioShuffleCh2OutputPairs18StPair5 OBJECT-TYPE
		SYNTAX		RollCallString
		MAX-ACCESS		read-only
		STATUS			current
		DESCRIPTION
				"TYPE: - Display
				 PAGE: - Audio Shuffle-Ch2- Output Pairs 1-8 St
					Pair 5  cmdID= 50352  format=   "
		::= { iqudc32CmdEntry 50352 }


	iqudc32AudioShuffleCh2OutputPairs18StPair6 OBJECT-TYPE
		SYNTAX		RollCallString
		MAX-ACCESS		read-only
		STATUS			current
		DESCRIPTION
				"TYPE: - Display
				 PAGE: - Audio Shuffle-Ch2- Output Pairs 1-8 St
					Pair 6  cmdID= 50353  format=   "
		::= { iqudc32CmdEntry 50353 }


	iqudc32AudioShuffleCh2OutputPairs18StPair7 OBJECT-TYPE
		SYNTAX		RollCallString
		MAX-ACCESS		read-only
		STATUS			current
		DESCRIPTION
				"TYPE: - Display
				 PAGE: - Audio Shuffle-Ch2- Output Pairs 1-8 St
					Pair 7  cmdID= 50354  format=   "
		::= { iqudc32CmdEntry 50354 }


	iqudc32AudioShuffleCh2OutputPairs18StPair8 OBJECT-TYPE
		SYNTAX		RollCallString
		MAX-ACCESS		read-only
		STATUS			current
		DESCRIPTION
				"TYPE: - Display
				 PAGE: - Audio Shuffle-Ch2- Output Pairs 1-8 St
					Pair 8  cmdID= 50355  format=   "
		::= { iqudc32CmdEntry 50355 }


	iqudc32MenuAudioShuffleCh2NewDisplay OBJECT-TYPE
		SYNTAX		RollCallString
		MAX-ACCESS		read-only
		STATUS			current
		DESCRIPTION
				"TYPE: - Display
				 PAGE: - Audio Shuffle-Ch2
					New Display  cmdID= 44457  format=   "
		::= { iqudc32CmdEntry 44457 }


	iqudc32AudioControlCh1GainPair1L OBJECT-TYPE
		SYNTAX		INTEGER
		MAX-ACCESS		read-write
		STATUS			current
		DESCRIPTION
				"TYPE: - Number
				 PAGE: - Audio Control-Ch1
					Pair 1 L  cmdID= 50228  min= -180  max= 180  step= 1  format= %0.1fdB  div_scale= 10 
					Min = -18.0dB  Max = 18.0dB  Step = 0.1dB "
		::= { iqudc32CmdEntry 50228 }


	iqudc32AudioControlCh1GainPair1R OBJECT-TYPE
		SYNTAX		INTEGER
		MAX-ACCESS		read-write
		STATUS			current
		DESCRIPTION
				"TYPE: - Number
				 PAGE: - Audio Control-Ch1
					Pair 1 R  cmdID= 50229  min= -180  max= 180  step= 1  format= %0.1fdB  div_scale= 10 
					Min = -18.0dB  Max = 18.0dB  Step = 0.1dB "
		::= { iqudc32CmdEntry 50229 }


	iqudc32AudioControlCh1GainPair2L OBJECT-TYPE
		SYNTAX		INTEGER
		MAX-ACCESS		read-write
		STATUS			current
		DESCRIPTION
				"TYPE: - Number
				 PAGE: - Audio Control-Ch1
					Pair 2 L  cmdID= 50202  min= -180  max= 180  step= 1  format= %0.1fdB  div_scale= 10 
					Min = -18.0dB  Max = 18.0dB  Step = 0.1dB "
		::= { iqudc32CmdEntry 50202 }


	iqudc32AudioControlCh1GainPair2R OBJECT-TYPE
		SYNTAX		INTEGER
		MAX-ACCESS		read-write
		STATUS			current
		DESCRIPTION
				"TYPE: - Number
				 PAGE: - Audio Control-Ch1
					Pair 2 R  cmdID= 50231  min= -180  max= 180  step= 1  format= %0.1fdB  div_scale= 10 
					Min = -18.0dB  Max = 18.0dB  Step = 0.1dB "
		::= { iqudc32CmdEntry 50231 }


	iqudc32AudioControlCh1GainPair3L OBJECT-TYPE
		SYNTAX		INTEGER
		MAX-ACCESS		read-write
		STATUS			current
		DESCRIPTION
				"TYPE: - Number
				 PAGE: - Audio Control-Ch1
					Pair 3 L  cmdID= 50204  min= -180  max= 180  step= 1  format= %0.1fdB  div_scale= 10 
					Min = -18.0dB  Max = 18.0dB  Step = 0.1dB "
		::= { iqudc32CmdEntry 50204 }


	iqudc32AudioControlCh1GainPair3R OBJECT-TYPE
		SYNTAX		INTEGER
		MAX-ACCESS		read-write
		STATUS			current
		DESCRIPTION
				"TYPE: - Number
				 PAGE: - Audio Control-Ch1
					Pair 3 R  cmdID= 50205  min= -180  max= 180  step= 1  format= %0.1fdB  div_scale= 10 
					Min = -18.0dB  Max = 18.0dB  Step = 0.1dB "
		::= { iqudc32CmdEntry 50205 }


	iqudc32AudioControlCh1GainPair4L OBJECT-TYPE
		SYNTAX		INTEGER
		MAX-ACCESS		read-write
		STATUS			current
		DESCRIPTION
				"TYPE: - Number
				 PAGE: - Audio Control-Ch1
					Pair 4 L  cmdID= 50206  min= -180  max= 180  step= 1  format= %0.1fdB  div_scale= 10 
					Min = -18.0dB  Max = 18.0dB  Step = 0.1dB "
		::= { iqudc32CmdEntry 50206 }


	iqudc32AudioControlCh1GainPair4R OBJECT-TYPE
		SYNTAX		INTEGER
		MAX-ACCESS		read-write
		STATUS			current
		DESCRIPTION
				"TYPE: - Number
				 PAGE: - Audio Control-Ch1
					Pair 4 R  cmdID= 50235  min= -180  max= 180  step= 1  format= %0.1fdB  div_scale= 10 
					Min = -18.0dB  Max = 18.0dB  Step = 0.1dB "
		::= { iqudc32CmdEntry 50235 }


	iqudc32AudioControlCh1GainPair5L OBJECT-TYPE
		SYNTAX		INTEGER
		MAX-ACCESS		read-write
		STATUS			current
		DESCRIPTION
				"TYPE: - Number
				 PAGE: - Audio Control-Ch1
					Pair 5 L  cmdID= 50208  min= -180  max= 180  step= 1  format= %0.1fdB  div_scale= 10 
					Min = -18.0dB  Max = 18.0dB  Step = 0.1dB "
		::= { iqudc32CmdEntry 50208 }


	iqudc32AudioControlCh1GainPair5R OBJECT-TYPE
		SYNTAX		INTEGER
		MAX-ACCESS		read-write
		STATUS			current
		DESCRIPTION
				"TYPE: - Number
				 PAGE: - Audio Control-Ch1
					Pair 5 R  cmdID= 50209  min= -180  max= 180  step= 1  format= %0.1fdB  div_scale= 10 
					Min = -18.0dB  Max = 18.0dB  Step = 0.1dB "
		::= { iqudc32CmdEntry 50209 }


	iqudc32AudioControlCh1GainPair6L OBJECT-TYPE
		SYNTAX		INTEGER
		MAX-ACCESS		read-write
		STATUS			current
		DESCRIPTION
				"TYPE: - Number
				 PAGE: - Audio Control-Ch1
					Pair 6 L  cmdID= 50210  min= -180  max= 180  step= 1  format= %0.1fdB  div_scale= 10 
					Min = -18.0dB  Max = 18.0dB  Step = 0.1dB "
		::= { iqudc32CmdEntry 50210 }


	iqudc32AudioControlCh1GainPair6R OBJECT-TYPE
		SYNTAX		INTEGER
		MAX-ACCESS		read-write
		STATUS			current
		DESCRIPTION
				"TYPE: - Number
				 PAGE: - Audio Control-Ch1
					Pair 6 R  cmdID= 50211  min= -180  max= 180  step= 1  format= %0.1fdB  div_scale= 10 
					Min = -18.0dB  Max = 18.0dB  Step = 0.1dB "
		::= { iqudc32CmdEntry 50211 }


	iqudc32AudioControlCh1GainPair7L OBJECT-TYPE
		SYNTAX		INTEGER
		MAX-ACCESS		read-write
		STATUS			current
		DESCRIPTION
				"TYPE: - Number
				 PAGE: - Audio Control-Ch1
					Pair 7 L  cmdID= 50238  min= -180  max= 180  step= 1  format= %0.1fdB  div_scale= 10 
					Min = -18.0dB  Max = 18.0dB  Step = 0.1dB "
		::= { iqudc32CmdEntry 50238 }


	iqudc32AudioControlCh1GainPair7R OBJECT-TYPE
		SYNTAX		INTEGER
		MAX-ACCESS		read-write
		STATUS			current
		DESCRIPTION
				"TYPE: - Number
				 PAGE: - Audio Control-Ch1
					Pair 7 R  cmdID= 50239  min= -180  max= 180  step= 1  format= %0.1fdB  div_scale= 10 
					Min = -18.0dB  Max = 18.0dB  Step = 0.1dB "
		::= { iqudc32CmdEntry 50239 }


	iqudc32AudioControlCh1GainPair8L OBJECT-TYPE
		SYNTAX		INTEGER
		MAX-ACCESS		read-write
		STATUS			current
		DESCRIPTION
				"TYPE: - Number
				 PAGE: - Audio Control-Ch1
					Pair 8 L  cmdID= 50240  min= -180  max= 180  step= 1  format= %0.1fdB  div_scale= 10 
					Min = -18.0dB  Max = 18.0dB  Step = 0.1dB "
		::= { iqudc32CmdEntry 50240 }


	iqudc32AudioControlCh1GainPair8R OBJECT-TYPE
		SYNTAX		INTEGER
		MAX-ACCESS		read-write
		STATUS			current
		DESCRIPTION
				"TYPE: - Number
				 PAGE: - Audio Control-Ch1
					Pair 8 R  cmdID= 50241  min= -180  max= 180  step= 1  format= %0.1fdB  div_scale= 10 
					Min = -18.0dB  Max = 18.0dB  Step = 0.1dB "
		::= { iqudc32CmdEntry 50241 }


	iqudc32MenuAudioControlCh1ToneFrequency OBJECT-TYPE
		SYNTAX		INTEGER
		MAX-ACCESS		read-write
		STATUS			current
		DESCRIPTION
				"TYPE: - Number
				 PAGE: - Audio Control-Ch1
					Tone Frequency  cmdID= 50500  min= 100  max= 10000  step= 100  format= %0.1f KHz  div_scale= 1000 
					Min = 0.1 KHz  Max = 10.0 KHz  Step = 0.1 KHz "
		::= { iqudc32CmdEntry 50500 }


	iqudc32MenuAudioControlCh1DolbyEAlignmentO OBJECT-TYPE
		SYNTAX		INTEGER
		MAX-ACCESS		read-write
		STATUS			current
		DESCRIPTION
				"TYPE: - Number
				 PAGE: - Audio Control-Ch1
					Dolby E Alignment O  cmdID= 50502  min= -10  max= 10  step= 1  format= %0.0f Lines  div_scale= 1 
					Min = -10 Lines  Max = 10 Lines  Step = 1 Lines "
		::= { iqudc32CmdEntry 50502 }


	iqudc32DelayGlobalDelayPairOPair150319 OBJECT-TYPE
		SYNTAX		INTEGER
		MAX-ACCESS		read-write
		STATUS			current
		DESCRIPTION
				"TYPE: - Number
				 PAGE: - Audio Control-Ch1
					Pair 1  cmdID= 50319  min= -40  max= 200  step= 1  format= %0.0f ms  div_scale= 1 
					Min = -40 ms  Max = 200 ms  Step = 1 ms "
		::= { iqudc32CmdEntry 50319 }


	iqudc32DelayGlobalDelayPairOPair1Total50327 OBJECT-TYPE
		SYNTAX		RollCallString
		MAX-ACCESS		read-only
		STATUS			current
		DESCRIPTION
				"TYPE: - Display
				 PAGE: - Audio Control-Ch1
					Pair 1 Total  cmdID= 50327  format=   "
		::= { iqudc32CmdEntry 50327 }


	iqudc32DelayGlobalDelayPairOPair250320 OBJECT-TYPE
		SYNTAX		INTEGER
		MAX-ACCESS		read-write
		STATUS			current
		DESCRIPTION
				"TYPE: - Number
				 PAGE: - Audio Control-Ch1
					Pair 2  cmdID= 50320  min= -40  max= 200  step= 1  format= %0.0f ms  div_scale= 1 
					Min = -40 ms  Max = 200 ms  Step = 1 ms "
		::= { iqudc32CmdEntry 50320 }


	iqudc32DelayGlobalDelayPairOPair2Total50328 OBJECT-TYPE
		SYNTAX		RollCallString
		MAX-ACCESS		read-only
		STATUS			current
		DESCRIPTION
				"TYPE: - Display
				 PAGE: - Audio Control-Ch1
					Pair 2 Total  cmdID= 50328  format=   "
		::= { iqudc32CmdEntry 50328 }


	iqudc32DelayGlobalDelayPairOPair350321 OBJECT-TYPE
		SYNTAX		INTEGER
		MAX-ACCESS		read-write
		STATUS			current
		DESCRIPTION
				"TYPE: - Number
				 PAGE: - Audio Control-Ch1
					Pair 3  cmdID= 50321  min= -40  max= 200  step= 1  format= %0.0f ms  div_scale= 1 
					Min = -40 ms  Max = 200 ms  Step = 1 ms "
		::= { iqudc32CmdEntry 50321 }


	iqudc32DelayGlobalDelayPairOPair3Total50329 OBJECT-TYPE
		SYNTAX		RollCallString
		MAX-ACCESS		read-only
		STATUS			current
		DESCRIPTION
				"TYPE: - Display
				 PAGE: - Audio Control-Ch1
					Pair 3 Total  cmdID= 50329  format=   "
		::= { iqudc32CmdEntry 50329 }


	iqudc32DelayGlobalDelayPairOPair450322 OBJECT-TYPE
		SYNTAX		INTEGER
		MAX-ACCESS		read-write
		STATUS			current
		DESCRIPTION
				"TYPE: - Number
				 PAGE: - Audio Control-Ch1
					Pair 4  cmdID= 50322  min= -40  max= 200  step= 1  format= %0.0f ms  div_scale= 1 
					Min = -40 ms  Max = 200 ms  Step = 1 ms "
		::= { iqudc32CmdEntry 50322 }


	iqudc32DelayGlobalDelayPairOPair4Total50330 OBJECT-TYPE
		SYNTAX		RollCallString
		MAX-ACCESS		read-only
		STATUS			current
		DESCRIPTION
				"TYPE: - Display
				 PAGE: - Audio Control-Ch1
					Pair 4 Total  cmdID= 50330  format=   "
		::= { iqudc32CmdEntry 50330 }


	iqudc32DelayGlobalDelayPairOPair550323 OBJECT-TYPE
		SYNTAX		INTEGER
		MAX-ACCESS		read-write
		STATUS			current
		DESCRIPTION
				"TYPE: - Number
				 PAGE: - Audio Control-Ch1
					Pair 5  cmdID= 50323  min= -40  max= 200  step= 1  format= %0.0f ms  div_scale= 1 
					Min = -40 ms  Max = 200 ms  Step = 1 ms "
		::= { iqudc32CmdEntry 50323 }


	iqudc32DelayGlobalDelayPairOPair5Total50331 OBJECT-TYPE
		SYNTAX		RollCallString
		MAX-ACCESS		read-only
		STATUS			current
		DESCRIPTION
				"TYPE: - Display
				 PAGE: - Audio Control-Ch1
					Pair 5 Total  cmdID= 50331  format=   "
		::= { iqudc32CmdEntry 50331 }


	iqudc32DelayGlobalDelayPairOPair650324 OBJECT-TYPE
		SYNTAX		INTEGER
		MAX-ACCESS		read-write
		STATUS			current
		DESCRIPTION
				"TYPE: - Number
				 PAGE: - Audio Control-Ch1
					Pair 6  cmdID= 50324  min= -40  max= 200  step= 1  format= %0.0f ms  div_scale= 1 
					Min = -40 ms  Max = 200 ms  Step = 1 ms "
		::= { iqudc32CmdEntry 50324 }


	iqudc32DelayGlobalDelayPairOPair6Total50332 OBJECT-TYPE
		SYNTAX		RollCallString
		MAX-ACCESS		read-only
		STATUS			current
		DESCRIPTION
				"TYPE: - Display
				 PAGE: - Audio Control-Ch1
					Pair 6 Total  cmdID= 50332  format=   "
		::= { iqudc32CmdEntry 50332 }


	iqudc32DelayGlobalDelayPairOPair750325 OBJECT-TYPE
		SYNTAX		INTEGER
		MAX-ACCESS		read-write
		STATUS			current
		DESCRIPTION
				"TYPE: - Number
				 PAGE: - Audio Control-Ch1
					Pair 7  cmdID= 50325  min= -40  max= 200  step= 1  format= %0.0f ms  div_scale= 1 
					Min = -40 ms  Max = 200 ms  Step = 1 ms "
		::= { iqudc32CmdEntry 50325 }


	iqudc32DelayGlobalDelayPairOPair7Total50333 OBJECT-TYPE
		SYNTAX		RollCallString
		MAX-ACCESS		read-only
		STATUS			current
		DESCRIPTION
				"TYPE: - Display
				 PAGE: - Audio Control-Ch1
					Pair 7 Total  cmdID= 50333  format=   "
		::= { iqudc32CmdEntry 50333 }


	iqudc32DelayGlobalDelayPairOPair850326 OBJECT-TYPE
		SYNTAX		INTEGER
		MAX-ACCESS		read-write
		STATUS			current
		DESCRIPTION
				"TYPE: - Number
				 PAGE: - Audio Control-Ch1
					Pair 8  cmdID= 50326  min= -40  max= 200  step= 1  format= %0.0f ms  div_scale= 1 
					Min = -40 ms  Max = 200 ms  Step = 1 ms "
		::= { iqudc32CmdEntry 50326 }


	iqudc32DelayGlobalDelayPairOPair8Total50334 OBJECT-TYPE
		SYNTAX		RollCallString
		MAX-ACCESS		read-only
		STATUS			current
		DESCRIPTION
				"TYPE: - Display
				 PAGE: - Audio Control-Ch1
					Pair 8 Total  cmdID= 50334  format=   "
		::= { iqudc32CmdEntry 50334 }


	iqudc32AudioControlCh1GlobalDelayAudio OBJECT-TYPE
		SYNTAX		INTEGER
		MAX-ACCESS		read-write
		STATUS			current
		DESCRIPTION
				"TYPE: - Number
				 PAGE: - Audio Control-Ch1
					Audio  cmdID= 50316  min= -40  max= 200  step= 1  format= %0.0f ms  div_scale= 1 
					Min = -40 ms  Max = 200 ms  Step = 1 ms "
		::= { iqudc32CmdEntry 50316 }


	iqudc32AudioControlCh1GlobalDelayAudioTotal OBJECT-TYPE
		SYNTAX		RollCallString
		MAX-ACCESS		read-only
		STATUS			current
		DESCRIPTION
				"TYPE: - Display
				 PAGE: - Audio Control-Ch1
					Audio Total  cmdID= 50301  format=   "
		::= { iqudc32CmdEntry 50301 }


	iqudc32AudioControlCh1GlobalDelayVideoTotal OBJECT-TYPE
		SYNTAX		RollCallString
		MAX-ACCESS		read-only
		STATUS			current
		DESCRIPTION
				"TYPE: - Display
				 PAGE: - Audio Control-Ch1
					Video Total  cmdID= 50302  format=   "
		::= { iqudc32CmdEntry 50302 }


	iqudc32MenuAudioControlCh1NewDisplay OBJECT-TYPE
		SYNTAX		RollCallString
		MAX-ACCESS		read-only
		STATUS			current
		DESCRIPTION
				"TYPE: - Display
				 PAGE: - Audio Control-Ch1
					New Display  cmdID= 44462  format=   "
		::= { iqudc32CmdEntry 44462 }


	iqudc32AudioControlCh2GainPair1L OBJECT-TYPE
		SYNTAX		INTEGER
		MAX-ACCESS		read-write
		STATUS			current
		DESCRIPTION
				"TYPE: - Number
				 PAGE: - Audio Control-Ch2
					Pair 1 L  cmdID= 50300  min= -180  max= 180  step= 1  format= %0.1fdB  div_scale= 10 
					Min = -18.0dB  Max = 18.0dB  Step = 0.1dB "
		::= { iqudc32CmdEntry 50300 }


	iqudc32AudioControlCh2GainPair1R OBJECT-TYPE
		SYNTAX		INTEGER
		MAX-ACCESS		read-write
		STATUS			current
		DESCRIPTION
				"TYPE: - Number
				 PAGE: - Audio Control-Ch2
					Pair 1 R  cmdID= 50317  min= -180  max= 180  step= 1  format= %0.1fdB  div_scale= 10 
					Min = -18.0dB  Max = 18.0dB  Step = 0.1dB "
		::= { iqudc32CmdEntry 50317 }


	iqudc32AudioControlCh2GainPair2L OBJECT-TYPE
		SYNTAX		INTEGER
		MAX-ACCESS		read-write
		STATUS			current
		DESCRIPTION
				"TYPE: - Number
				 PAGE: - Audio Control-Ch2
					Pair 2 L  cmdID= 50318  min= -180  max= 180  step= 1  format= %0.1fdB  div_scale= 10 
					Min = -18.0dB  Max = 18.0dB  Step = 0.1dB "
		::= { iqudc32CmdEntry 50318 }


	iqudc32AudioControlCh2GainPair2R OBJECT-TYPE
		SYNTAX		INTEGER
		MAX-ACCESS		read-write
		STATUS			current
		DESCRIPTION
				"TYPE: - Number
				 PAGE: - Audio Control-Ch2
					Pair 2 R  cmdID= 50303  min= -180  max= 180  step= 1  format= %0.1fdB  div_scale= 10 
					Min = -18.0dB  Max = 18.0dB  Step = 0.1dB "
		::= { iqudc32CmdEntry 50303 }


	iqudc32AudioControlCh2GainPair3L OBJECT-TYPE
		SYNTAX		INTEGER
		MAX-ACCESS		read-write
		STATUS			current
		DESCRIPTION
				"TYPE: - Number
				 PAGE: - Audio Control-Ch2
					Pair 3 L  cmdID= 50304  min= -180  max= 180  step= 1  format= %0.1fdB  div_scale= 10 
					Min = -18.0dB  Max = 18.0dB  Step = 0.1dB "
		::= { iqudc32CmdEntry 50304 }


	iqudc32AudioControlCh2GainPair3R OBJECT-TYPE
		SYNTAX		INTEGER
		MAX-ACCESS		read-write
		STATUS			current
		DESCRIPTION
				"TYPE: - Number
				 PAGE: - Audio Control-Ch2
					Pair 3 R  cmdID= 50305  min= -180  max= 180  step= 1  format= %0.1fdB  div_scale= 10 
					Min = -18.0dB  Max = 18.0dB  Step = 0.1dB "
		::= { iqudc32CmdEntry 50305 }


	iqudc32AudioControlCh2GainPair4L OBJECT-TYPE
		SYNTAX		INTEGER
		MAX-ACCESS		read-write
		STATUS			current
		DESCRIPTION
				"TYPE: - Number
				 PAGE: - Audio Control-Ch2
					Pair 4 L  cmdID= 50306  min= -180  max= 180  step= 1  format= %0.1fdB  div_scale= 10 
					Min = -18.0dB  Max = 18.0dB  Step = 0.1dB "
		::= { iqudc32CmdEntry 50306 }


	iqudc32AudioControlCh2GainPair4R OBJECT-TYPE
		SYNTAX		INTEGER
		MAX-ACCESS		read-write
		STATUS			current
		DESCRIPTION
				"TYPE: - Number
				 PAGE: - Audio Control-Ch2
					Pair 4 R  cmdID= 50307  min= -180  max= 180  step= 1  format= %0.1fdB  div_scale= 10 
					Min = -18.0dB  Max = 18.0dB  Step = 0.1dB "
		::= { iqudc32CmdEntry 50307 }


	iqudc32AudioControlCh2GainPair5L OBJECT-TYPE
		SYNTAX		INTEGER
		MAX-ACCESS		read-write
		STATUS			current
		DESCRIPTION
				"TYPE: - Number
				 PAGE: - Audio Control-Ch2
					Pair 5 L  cmdID= 50308  min= -180  max= 180  step= 1  format= %0.1fdB  div_scale= 10 
					Min = -18.0dB  Max = 18.0dB  Step = 0.1dB "
		::= { iqudc32CmdEntry 50308 }


	iqudc32AudioControlCh2GainPair5R OBJECT-TYPE
		SYNTAX		INTEGER
		MAX-ACCESS		read-write
		STATUS			current
		DESCRIPTION
				"TYPE: - Number
				 PAGE: - Audio Control-Ch2
					Pair 5 R  cmdID= 50309  min= -180  max= 180  step= 1  format= %0.1fdB  div_scale= 10 
					Min = -18.0dB  Max = 18.0dB  Step = 0.1dB "
		::= { iqudc32CmdEntry 50309 }


	iqudc32AudioControlCh2GainPair6L OBJECT-TYPE
		SYNTAX		INTEGER
		MAX-ACCESS		read-write
		STATUS			current
		DESCRIPTION
				"TYPE: - Number
				 PAGE: - Audio Control-Ch2
					Pair 6 L  cmdID= 50310  min= -180  max= 180  step= 1  format= %0.1fdB  div_scale= 10 
					Min = -18.0dB  Max = 18.0dB  Step = 0.1dB "
		::= { iqudc32CmdEntry 50310 }


	iqudc32AudioControlCh2GainPair6R OBJECT-TYPE
		SYNTAX		INTEGER
		MAX-ACCESS		read-write
		STATUS			current
		DESCRIPTION
				"TYPE: - Number
				 PAGE: - Audio Control-Ch2
					Pair 6 R  cmdID= 50311  min= -180  max= 180  step= 1  format= %0.1fdB  div_scale= 10 
					Min = -18.0dB  Max = 18.0dB  Step = 0.1dB "
		::= { iqudc32CmdEntry 50311 }


	iqudc32AudioControlCh2GainPair7L OBJECT-TYPE
		SYNTAX		INTEGER
		MAX-ACCESS		read-write
		STATUS			current
		DESCRIPTION
				"TYPE: - Number
				 PAGE: - Audio Control-Ch2
					Pair 7 L  cmdID= 50312  min= -180  max= 180  step= 1  format= %0.1fdB  div_scale= 10 
					Min = -18.0dB  Max = 18.0dB  Step = 0.1dB "
		::= { iqudc32CmdEntry 50312 }


	iqudc32AudioControlCh2GainPair7R OBJECT-TYPE
		SYNTAX		INTEGER
		MAX-ACCESS		read-write
		STATUS			current
		DESCRIPTION
				"TYPE: - Number
				 PAGE: - Audio Control-Ch2
					Pair 7 R  cmdID= 50313  min= -180  max= 180  step= 1  format= %0.1fdB  div_scale= 10 
					Min = -18.0dB  Max = 18.0dB  Step = 0.1dB "
		::= { iqudc32CmdEntry 50313 }


	iqudc32AudioControlCh2GainPair8L OBJECT-TYPE
		SYNTAX		INTEGER
		MAX-ACCESS		read-write
		STATUS			current
		DESCRIPTION
				"TYPE: - Number
				 PAGE: - Audio Control-Ch2
					Pair 8 L  cmdID= 50314  min= -180  max= 180  step= 1  format= %0.1fdB  div_scale= 10 
					Min = -18.0dB  Max = 18.0dB  Step = 0.1dB "
		::= { iqudc32CmdEntry 50314 }


	iqudc32AudioControlCh2GainPair8R OBJECT-TYPE
		SYNTAX		INTEGER
		MAX-ACCESS		read-write
		STATUS			current
		DESCRIPTION
				"TYPE: - Number
				 PAGE: - Audio Control-Ch2
					Pair 8 R  cmdID= 50315  min= -180  max= 180  step= 1  format= %0.1fdB  div_scale= 10 
					Min = -18.0dB  Max = 18.0dB  Step = 0.1dB "
		::= { iqudc32CmdEntry 50315 }


	iqudc32MenuAudioControlCh2ToneFrequency OBJECT-TYPE
		SYNTAX		INTEGER
		MAX-ACCESS		read-write
		STATUS			current
		DESCRIPTION
				"TYPE: - Number
				 PAGE: - Audio Control-Ch2
					Tone Frequency  cmdID= 50600  min= 100  max= 10000  step= 100  format= %0.1f KHz  div_scale= 1000 
					Min = 0.1 KHz  Max = 10.0 KHz  Step = 0.1 KHz "
		::= { iqudc32CmdEntry 50600 }


	iqudc32MenuAudioControlCh2DolbyEAlignmentO OBJECT-TYPE
		SYNTAX		INTEGER
		MAX-ACCESS		read-write
		STATUS			current
		DESCRIPTION
				"TYPE: - Number
				 PAGE: - Audio Control-Ch2
					Dolby E Alignment O  cmdID= 50504  min= -10  max= 10  step= 1  format= %0.0f Lines  div_scale= 1 
					Min = -10 Lines  Max = 10 Lines  Step = 1 Lines "
		::= { iqudc32CmdEntry 50504 }


	iqudc32DelayGlobalDelayPairOPair150505 OBJECT-TYPE
		SYNTAX		INTEGER
		MAX-ACCESS		read-write
		STATUS			current
		DESCRIPTION
				"TYPE: - Number
				 PAGE: - Audio Control-Ch2
					Pair 1  cmdID= 50505  min= -40  max= 200  step= 1  format= %0.0f ms  div_scale= 1 
					Min = -40 ms  Max = 200 ms  Step = 1 ms "
		::= { iqudc32CmdEntry 50505 }


	iqudc32DelayGlobalDelayPairOPair1Total50513 OBJECT-TYPE
		SYNTAX		RollCallString
		MAX-ACCESS		read-only
		STATUS			current
		DESCRIPTION
				"TYPE: - Display
				 PAGE: - Audio Control-Ch2
					Pair 1 Total  cmdID= 50513  format=   "
		::= { iqudc32CmdEntry 50513 }


	iqudc32DelayGlobalDelayPairOPair250506 OBJECT-TYPE
		SYNTAX		INTEGER
		MAX-ACCESS		read-write
		STATUS			current
		DESCRIPTION
				"TYPE: - Number
				 PAGE: - Audio Control-Ch2
					Pair 2  cmdID= 50506  min= -40  max= 200  step= 1  format= %0.0f ms  div_scale= 1 
					Min = -40 ms  Max = 200 ms  Step = 1 ms "
		::= { iqudc32CmdEntry 50506 }


	iqudc32DelayGlobalDelayPairOPair2Total50514 OBJECT-TYPE
		SYNTAX		RollCallString
		MAX-ACCESS		read-only
		STATUS			current
		DESCRIPTION
				"TYPE: - Display
				 PAGE: - Audio Control-Ch2
					Pair 2 Total  cmdID= 50514  format=   "
		::= { iqudc32CmdEntry 50514 }


	iqudc32DelayGlobalDelayPairOPair350507 OBJECT-TYPE
		SYNTAX		INTEGER
		MAX-ACCESS		read-write
		STATUS			current
		DESCRIPTION
				"TYPE: - Number
				 PAGE: - Audio Control-Ch2
					Pair 3  cmdID= 50507  min= -40  max= 200  step= 1  format= %0.0f ms  div_scale= 1 
					Min = -40 ms  Max = 200 ms  Step = 1 ms "
		::= { iqudc32CmdEntry 50507 }


	iqudc32DelayGlobalDelayPairOPair3Total50515 OBJECT-TYPE
		SYNTAX		RollCallString
		MAX-ACCESS		read-only
		STATUS			current
		DESCRIPTION
				"TYPE: - Display
				 PAGE: - Audio Control-Ch2
					Pair 3 Total  cmdID= 50515  format=   "
		::= { iqudc32CmdEntry 50515 }


	iqudc32DelayGlobalDelayPairOPair450508 OBJECT-TYPE
		SYNTAX		INTEGER
		MAX-ACCESS		read-write
		STATUS			current
		DESCRIPTION
				"TYPE: - Number
				 PAGE: - Audio Control-Ch2
					Pair 4  cmdID= 50508  min= -40  max= 200  step= 1  format= %0.0f ms  div_scale= 1 
					Min = -40 ms  Max = 200 ms  Step = 1 ms "
		::= { iqudc32CmdEntry 50508 }


	iqudc32DelayGlobalDelayPairOPair4Total50516 OBJECT-TYPE
		SYNTAX		RollCallString
		MAX-ACCESS		read-only
		STATUS			current
		DESCRIPTION
				"TYPE: - Display
				 PAGE: - Audio Control-Ch2
					Pair 4 Total  cmdID= 50516  format=   "
		::= { iqudc32CmdEntry 50516 }


	iqudc32DelayGlobalDelayPairOPair550509 OBJECT-TYPE
		SYNTAX		INTEGER
		MAX-ACCESS		read-write
		STATUS			current
		DESCRIPTION
				"TYPE: - Number
				 PAGE: - Audio Control-Ch2
					Pair 5  cmdID= 50509  min= -40  max= 200  step= 1  format= %0.0f ms  div_scale= 1 
					Min = -40 ms  Max = 200 ms  Step = 1 ms "
		::= { iqudc32CmdEntry 50509 }


	iqudc32DelayGlobalDelayPairOPair5Total50517 OBJECT-TYPE
		SYNTAX		RollCallString
		MAX-ACCESS		read-only
		STATUS			current
		DESCRIPTION
				"TYPE: - Display
				 PAGE: - Audio Control-Ch2
					Pair 5 Total  cmdID= 50517  format=   "
		::= { iqudc32CmdEntry 50517 }


	iqudc32DelayGlobalDelayPairOPair650510 OBJECT-TYPE
		SYNTAX		INTEGER
		MAX-ACCESS		read-write
		STATUS			current
		DESCRIPTION
				"TYPE: - Number
				 PAGE: - Audio Control-Ch2
					Pair 6  cmdID= 50510  min= -40  max= 200  step= 1  format= %0.0f ms  div_scale= 1 
					Min = -40 ms  Max = 200 ms  Step = 1 ms "
		::= { iqudc32CmdEntry 50510 }


	iqudc32DelayGlobalDelayPairOPair6Total50518 OBJECT-TYPE
		SYNTAX		RollCallString
		MAX-ACCESS		read-only
		STATUS			current
		DESCRIPTION
				"TYPE: - Display
				 PAGE: - Audio Control-Ch2
					Pair 6 Total  cmdID= 50518  format=   "
		::= { iqudc32CmdEntry 50518 }


	iqudc32DelayGlobalDelayPairOPair750511 OBJECT-TYPE
		SYNTAX		INTEGER
		MAX-ACCESS		read-write
		STATUS			current
		DESCRIPTION
				"TYPE: - Number
				 PAGE: - Audio Control-Ch2
					Pair 7  cmdID= 50511  min= -40  max= 200  step= 1  format= %0.0f ms  div_scale= 1 
					Min = -40 ms  Max = 200 ms  Step = 1 ms "
		::= { iqudc32CmdEntry 50511 }


	iqudc32DelayGlobalDelayPairOPair7Total50519 OBJECT-TYPE
		SYNTAX		RollCallString
		MAX-ACCESS		read-only
		STATUS			current
		DESCRIPTION
				"TYPE: - Display
				 PAGE: - Audio Control-Ch2
					Pair 7 Total  cmdID= 50519  format=   "
		::= { iqudc32CmdEntry 50519 }


	iqudc32DelayGlobalDelayPairOPair850512 OBJECT-TYPE
		SYNTAX		INTEGER
		MAX-ACCESS		read-write
		STATUS			current
		DESCRIPTION
				"TYPE: - Number
				 PAGE: - Audio Control-Ch2
					Pair 8  cmdID= 50512  min= -40  max= 200  step= 1  format= %0.0f ms  div_scale= 1 
					Min = -40 ms  Max = 200 ms  Step = 1 ms "
		::= { iqudc32CmdEntry 50512 }


	iqudc32DelayGlobalDelayPairOPair8Total50520 OBJECT-TYPE
		SYNTAX		RollCallString
		MAX-ACCESS		read-only
		STATUS			current
		DESCRIPTION
				"TYPE: - Display
				 PAGE: - Audio Control-Ch2
					Pair 8 Total  cmdID= 50520  format=   "
		::= { iqudc32CmdEntry 50520 }


	iqudc32AudioControlCh2GlobalDelay OBJECT-TYPE
		SYNTAX		INTEGER
		MAX-ACCESS		read-write
		STATUS			current
		DESCRIPTION
				"TYPE: - Number
				 PAGE: - Audio Control-Ch2
					Global  cmdID= 50400  min= -40  max= 200  step= 1  format= %0.0f ms  div_scale= 1 
					Min = -40 ms  Max = 200 ms  Step = 1 ms "
		::= { iqudc32CmdEntry 50400 }


	iqudc32AudioControlCh2GlobalDelayGlobalTotal OBJECT-TYPE
		SYNTAX		RollCallString
		MAX-ACCESS		read-only
		STATUS			current
		DESCRIPTION
				"TYPE: - Display
				 PAGE: - Audio Control-Ch2
					Global Total  cmdID= 50401  format=   "
		::= { iqudc32CmdEntry 50401 }


	iqudc32AudioControlCh2GlobalDelayVideoTotal OBJECT-TYPE
		SYNTAX		RollCallString
		MAX-ACCESS		read-only
		STATUS			current
		DESCRIPTION
				"TYPE: - Display
				 PAGE: - Audio Control-Ch2
					Video Total  cmdID= 50402  format=   "
		::= { iqudc32CmdEntry 50402 }


	iqudc32MenuAudioControlCh2NewDisplay OBJECT-TYPE
		SYNTAX		RollCallString
		MAX-ACCESS		read-only
		STATUS			current
		DESCRIPTION
				"TYPE: - Display
				 PAGE: - Audio Control-Ch2
					New Display  cmdID= 44458  format=   "
		::= { iqudc32CmdEntry 44458 }


	iqudc32AudioIOAESAESOutput14AES1 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 1  cmdID= 40400 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40400 }


	iqudc32MenuAudioIOAESAES2 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 2  cmdID= 40401 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40401 }


	iqudc32MenuAudioIOAESAES3 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 3  cmdID= 40402 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40402 }


	iqudc32MenuAudioIOAESAES4 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 4  cmdID= 40403 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40403 }


	iqudc32AudioIOAESAESOutput58AES5 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 5  cmdID= 40404 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40404 }


	iqudc32MenuAudioIOAESAES6 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 6  cmdID= 40405 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40405 }


	iqudc32MenuAudioIOAESAES7 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 7  cmdID= 40406 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40406 }


	iqudc32MenuAudioIOAESAES8 OBJECT-TYPE
		SYNTAX		INTEGER {
							val-Use-as-Input(0),
							val-Ch-1-Pair-1(1),
							val-Ch-1-Pair-2(2),
							val-Ch-1-Pair-3(3),
							val-Ch-1-Pair-4(4),
							val-Ch-1-Pair-5(5),
							val-Ch-1-Pair-6(6),
							val-Ch-1-Pair-7(7),
							val-Ch-1-Pair-8(8),
							val-Ch-2-Pair-1(9),
							val-Ch-2-Pair-2(10),
							val-Ch-2-Pair-3(11),
							val-Ch-2-Pair-4(12),
							val-Ch-2-Pair-5(13),
							val-Ch-2-Pair-6(14),
							val-Ch-2-Pair-7(15),
							val-Ch-2-Pair-8(16)
							}
		MAX-ACCESS		read-write
		STATUS			current
		DESCRIPTION
				"TYPE: - RadiobuttonList
				 PAGE: - Audio I/O AES
					AES 8  cmdID= 40407 
					Use as Input  value= 0  
					Ch 1 Pair 1  value= 1  
					Ch 1 Pair 2  value= 2  
					Ch 1 Pair 3  value= 3  
					Ch 1 Pair 4  value= 4  
					Ch 1 Pair 5  value= 5  
					Ch 1 Pair 6  value= 6  
					Ch 1 Pair 7  value= 7  
					Ch 1 Pair 8  value= 8  
					Ch 2 Pair 1  value= 9  
					Ch 2 Pair 2  value= 10  
					Ch 2 Pair 3  value= 11  
					Ch 2 Pair 4  value= 12  
					Ch 2 Pair 5  value= 13  
					Ch 2 Pair 6  value= 14  
					Ch 2 Pair 7  value= 15  
					Ch 2 Pair 8  value= 16  "
		::= { iqudc32CmdEntry 40407 }


	iqudc32MenuAudioIOAESNewDisplay OBJECT-TYPE
		SYNTAX		RollCallString
		MAX-ACCESS		read-only
		STATUS			current
		DESCRIPTION
				"TYPE: - Display
				 PAGE: - Audio I/O AES
					New Display  cmdID= 40005  format=   "
		::= { iqudc32CmdEntry 40005 }


	iqudc32AudioIOAnalogAnalogOutput12Analog1 OBJECT-TYPE
		SYNTAX		INTEGER {
							val-Ch-1-Pair-1(0),
							val-Ch-1-Pair-2(1),
							val-Ch-1-Pair-3(2),
							val-Ch-1-Pair-4(3),
							val-Ch-1-Pair-5(4),
							val-Ch-1-Pair-6(5),
							val-Ch-1-Pair-7(6),
							val-Ch-1-Pair-8(7),
							val-Ch-2-Pair-1(8),
							val-Ch-2-Pair-2(9),
							val-Ch-2-Pair-3(10),
							val-Ch-2-Pair-4(11),
							val-Ch-2-Pair-5(12),
							val-Ch-2-Pair-6(13),
							val-Ch-2-Pair-7(14),
							val-Ch-2-Pair-8(15)
							}
		MAX-ACCESS		read-write
		STATUS			current
		DESCRIPTION
				"TYPE: - RadiobuttonList
				 PAGE: - Audio I/O Analog
					Analog 1  cmdID= 40410 
					Ch 1 Pair 1  value= 0  
					Ch 1 Pair 2  value= 1  
					Ch 1 Pair 3  value= 2  
					Ch 1 Pair 4  value= 3  
					Ch 1 Pair 5  value= 4  
					Ch 1 Pair 6  value= 5  
					Ch 1 Pair 7  value= 6  
					Ch 1 Pair 8  value= 7  
					Ch 2 Pair 1  value= 8  
					Ch 2 Pair 2  value= 9  
					Ch 2 Pair 3  value= 10  
					Ch 2 Pair 4  value= 11  
					Ch 2 Pair 5  value= 12  
					Ch 2 Pair 6  value= 13  
					Ch 2 Pair 7  value= 14  
					Ch 2 Pair 8  value= 15  "
		::= { iqudc32CmdEntry 40410 }


	iqudc32MenuAudioIOAnalogAnalog2 OBJECT-TYPE
		SYNTAX		INTEGER {
							val-Ch-1-Pair-1(0),
							val-Ch-1-Pair-2(1),
							val-Ch-1-Pair-3(2),
							val-Ch-1-Pair-4(3),
							val-Ch-1-Pair-5(4),
							val-Ch-1-Pair-6(5),
							val-Ch-1-Pair-7(6),
							val-Ch-1-Pair-8(7),
							val-Ch-2-Pair-1(8),
							val-Ch-2-Pair-2(9),
							val-Ch-2-Pair-3(10),
							val-Ch-2-Pair-4(11),
							val-Ch-2-Pair-5(12),
							val-Ch-2-Pair-6(13),
							val-Ch-2-Pair-7(14),
							val-Ch-2-Pair-8(15)
							}
		MAX-ACCESS		read-write
		STATUS			current
		DESCRIPTION
				"TYPE: - RadiobuttonList
				 PAGE: - Audio I/O Analog
					Analog 2  cmdID= 40411 
					Ch 1 Pair 1  value= 0  
					Ch 1 Pair 2  value= 1  
					Ch 1 Pair 3  value= 2  
					Ch 1 Pair 4  value= 3  
					Ch 1 Pair 5  value= 4  
					Ch 1 Pair 6  value= 5  
					Ch 1 Pair 7  value= 6  
					Ch 1 Pair 8  value= 7  
					Ch 2 Pair 1  value= 8  
					Ch 2 Pair 2  value= 9  
					Ch 2 Pair 3  value= 10  
					Ch 2 Pair 4  value= 11  
					Ch 2 Pair 5  value= 12  
					Ch 2 Pair 6  value= 13  
					Ch 2 Pair 7  value= 14  
					Ch 2 Pair 8  value= 15  "
		::= { iqudc32CmdEntry 40411 }


	iqudc32InputAnalogInADCHeadrPair1 OBJECT-TYPE
		SYNTAX		INTEGER
		MAX-ACCESS		read-write
		STATUS			current
		DESCRIPTION
				"TYPE: - Number
				 PAGE: - Audio I/O Analog
					Pair 1  cmdID= 40000  min= 24  max= 48  step= 1  format= %d  div_scale= 2 
					Min = 12  Max = 24  Step = 0 "
		::= { iqudc32CmdEntry 40000 }


	iqudc32InputAnalogInADCHeadrPair2 OBJECT-TYPE
		SYNTAX		INTEGER
		MAX-ACCESS		read-write
		STATUS			current
		DESCRIPTION
				"TYPE: - Number
				 PAGE: - Audio I/O Analog
					Pair 2  cmdID= 40001  min= 24  max= 48  step= 1  format= %d  div_scale= 2 
					Min = 12  Max = 24  Step = 0 "
		::= { iqudc32CmdEntry 40001 }


	iqudc32OutputAnalogOutDACLevePair1 OBJECT-TYPE
		SYNTAX		INTEGER
		MAX-ACCESS		read-write
		STATUS			current
		DESCRIPTION
				"TYPE: - Number
				 PAGE: - Audio I/O Analog
					Pair 1  cmdID= 40200  min= 24  max= 48  step= 1  format= %d  div_scale= 2 
					Min = 12  Max = 24  Step = 0 "
		::= { iqudc32CmdEntry 40200 }


	iqudc32OutputAnalogOutDACLevePair2 OBJECT-TYPE
		SYNTAX		INTEGER
		MAX-ACCESS		read-write
		STATUS			current
		DESCRIPTION
				"TYPE: - Number
				 PAGE: - Audio I/O Analog
					Pair 2  cmdID= 40201  min= 24  max= 48  step= 1  format= %d  div_scale= 2 
					Min = 12  Max = 24  Step = 0 "
		::= { iqudc32CmdEntry 40201 }


	iqudc32MenuAudioIOAnalogNewDisplay OBJECT-TYPE
		SYNTAX		RollCallString
		MAX-ACCESS		read-only
		STATUS			current
		DESCRIPTION
				"TYPE: - Display
				 PAGE: - Audio I/O Analog
					New Display  cmdID= 40004  format=   "
		::= { iqudc32CmdEntry 40004 }


	iqudc32DolbySetupDolbyCh1Mode OBJECT-TYPE
		SYNTAX		INTEGER {
							val-Decode(0),
							val-Encode(1),
							val-Transcode(2)
							}
		MAX-ACCESS		read-write
		STATUS			current
		DESCRIPTION
				"TYPE: - RadiobuttonList
				 PAGE: - Dolby Setup
					Mode  cmdID= 40529 
					Decode  value= 0  
					Encode  value= 1  
					Transcode  value= 2  "
		::= { iqudc32CmdEntry 40529 }


	iqudc32DolbySetupDolbyCh1DolbyEDelayCompen OBJECT-TYPE
		SYNTAX		INTEGER {
							val-Early-Early(0),
							val-Early-Normal(1),
							val-Early-Late(2),
							val-Normal-Normal(3),
							val-Normal-Late(4),
							val-Late-Late(5)
							}
		MAX-ACCESS		read-write
		STATUS			current
		DESCRIPTION
				"TYPE: - RadiobuttonList
				 PAGE: - Dolby Setup
					DolbyE Delay Compen  cmdID= 40507 
					Early > Early  value= 0  
					Early > Normal  value= 1  
					Early > Late  value= 2  
					Normal > Normal  value= 3  
					Normal > Late  value= 4  
					Late > Late  value= 5  "
		::= { iqudc32CmdEntry 40507 }


	iqudc32DolbySetupDolbyCh1MetadataSource OBJECT-TYPE
		SYNTAX		INTEGER {
							val-Dolby-Decoder(0),
							val-SMPTE-2020(1)
							}
		MAX-ACCESS		read-write
		STATUS			current
		DESCRIPTION
				"TYPE: - RadiobuttonList
				 PAGE: - Dolby Setup
					Metadata Source  cmdID= 40506 
					Dolby Decoder  value= 0  
					SMPTE 2020  value= 1  "
		::= { iqudc32CmdEntry 40506 }


	iqudc32DolbyCh1SMPTE2020OutputOutputLine OBJECT-TYPE
		SYNTAX		INTEGER
		MAX-ACCESS		read-write
		STATUS			current
		DESCRIPTION
				"TYPE: - Number
				 PAGE: - Dolby Setup
					Output Line  cmdID= 40510  min= 8  max= 20  step= 1  format= %0.0f  div_scale= 1 
					Min = 8  Max = 20  Step = 1 "
		::= { iqudc32CmdEntry 40510 }


	iqudc32DolbyCh1SMPTE2020OutputOutputEnable OBJECT-TYPE
		SYNTAX		INTEGER { disable(0), enable(1) }
		MAX-ACCESS		read-write
		STATUS			current
		DESCRIPTION
				"TYPE: - Checkbox
				 PAGE: - Dolby Setup
					Output Enable  cmdID= 40509 "
		::= { iqudc32CmdEntry 40509 }


	iqudc32DolbySetupDolbyCh1DecoderSource OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Decoder Source  cmdID= 40500 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc32CmdEntry 40500 }


	iqudc32MenuDolbySetupEncoderSource1 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 1  cmdID= 40520 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc32CmdEntry 40520 }


	iqudc32MenuDolbySetupEncoderSource2 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 2  cmdID= 40521 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc32CmdEntry 40521 }


	iqudc32MenuDolbySetupEncoderSource3 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 3  cmdID= 40522 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc32CmdEntry 40522 }


	iqudc32MenuDolbySetupEncoderSource4 OBJECT-TYPE
		SYNTAX		INTEGER {
							val-Embedded-1(0),
							val-Embedded-2(1),
							val-Embedded-3(2),
							val-Embedded-4(3),
							val-Embedded-5(4),
							val-Embedded-6(5),
							val-Embedded-7(6),
							val-Embedded-8(7),
							val-AES-1(8),
							val-AES-2(9),
							val-AES-3(10),
							val-AES-4(11),
							val-AES-5(12),
							val-AES-6(13),
							val-AES-7(14),
							val-AES-8(15)
							}
		MAX-ACCESS		read-write
		STATUS			current
		DESCRIPTION
				"TYPE: - RadiobuttonList
				 PAGE: - Dolby Setup
					Encoder Source 4  cmdID= 40523 
					Embedded 1  value= 0  
					Embedded 2  value= 1  
					Embedded 3  value= 2  
					Embedded 4  value= 3  
					Embedded 5  value= 4  
					Embedded 6  value= 5  
					Embedded 7  value= 6  
					Embedded 8  value= 7  
					AES 1  value= 8  
					AES 2  value= 9  
					AES 3  value= 10  
					AES 4  value= 11  
					AES 5  value= 12  
					AES 6  value= 13  
					AES 7  value= 14  
					AES 8  value= 15  "
		::= { iqudc32CmdEntry 40523 }


	iqudc32MenuDolbySetupEncoderFormat OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Format  cmdID= 40524 
					1  value= 0  
					2  value= 1  
					3  value= 2  
					4  value= 3  
					5  value= 4  
					6  value= 5  
					7  value= 6  
					8  value= 7  "
		::= { iqudc32CmdEntry 40524 }


	iqudc32MenuDolbySetupEncoderFormatED OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Format E D  cmdID= 40525 
					1  value= 0  
					2  value= 1  
					3  value= 2  
					4  value= 3  
					5  value= 4  
					6  value= 5  
					7  value= 6  
					8  value= 7  "
		::= { iqudc32CmdEntry 40525 }


	iqudc32MenuDolbySetupEncoderRate OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Rate  cmdID= 40526 
					1  value= 0  
					2  value= 1  
					3  value= 2  
					4  value= 3  
					5  value= 4  
					6  value= 5  
					7  value= 6  
					8  value= 7  "
		::= { iqudc32CmdEntry 40526 }


	iqudc32MenuDolbySetupEncoderBitDepth OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Bit Depth  cmdID= 40527 
					1  value= 0  
					2  value= 1  
					3  value= 2  
					4  value= 3  
					5  value= 4  
					6  value= 5  
					7  value= 6  
					8  value= 7  "
		::= { iqudc32CmdEntry 40527 }


	iqudc32MenuDolbySetupEncoderConfig OBJECT-TYPE
		SYNTAX		INTEGER {
							val-1(0),
							val-2(1),
							val-3(2),
							val-4(3),
							val-5(4),
							val-6(5),
							val-7(6),
							val-8(7)
							}
		MAX-ACCESS		read-write
		STATUS			current
		DESCRIPTION
				"TYPE: - RadiobuttonList
				 PAGE: - Dolby Setup
					Encoder Config  cmdID= 40528 
					1  value= 0  
					2  value= 1  
					3  value= 2  
					4  value= 3  
					5  value= 4  
					6  value= 5  
					7  value= 6  
					8  value= 7  "
		::= { iqudc32CmdEntry 40528 }


	iqudc32MenuDolbySetupInputStatus OBJECT-TYPE
		SYNTAX		RollCallString
		MAX-ACCESS		read-only
		STATUS			current
		DESCRIPTION
				"TYPE: - Display
				 PAGE: - Dolby Setup
					Input Status  cmdID= 40501  format=   "
		::= { iqudc32CmdEntry 40501 }


	iqudc32MenuDolbySetupDecoderRate OBJECT-TYPE
		SYNTAX		RollCallString
		MAX-ACCESS		read-only
		STATUS			current
		DESCRIPTION
				"TYPE: - Display
				 PAGE: - Dolby Setup
					Decoder Rate  cmdID= 40503  format=   "
		::= { iqudc32CmdEntry 40503 }


	iqudc32MenuDolbySetupDecoderFormat OBJECT-TYPE
		SYNTAX		RollCallString
		MAX-ACCESS		read-only
		STATUS			current
		DESCRIPTION
				"TYPE: - Display
				 PAGE: - Dolby Setup
					Decoder Format  cmdID= 40502  format=   "
		::= { iqudc32CmdEntry 40502 }


	iqudc32MenuDolbySetupDecoderVersion OBJECT-TYPE
		SYNTAX		RollCallString
		MAX-ACCESS		read-only
		STATUS			current
		DESCRIPTION
				"TYPE: - Display
				 PAGE: - Dolby Setup
					Decoder Version  cmdID= 40504  format=   "
		::= { iqudc32CmdEntry 40504 }


	iqudc32MenuDolbySetupEncoderVersion OBJECT-TYPE
		SYNTAX		RollCallString
		MAX-ACCESS		read-only
		STATUS			current
		DESCRIPTION
				"TYPE: - Display
				 PAGE: - Dolby Setup
					Encoder Version  cmdID= 40508  format=   "
		::= { iqudc32CmdEntry 40508 }


	iqudc32MenuDolbySetupNewDisplay OBJECT-TYPE
		SYNTAX		RollCallString
		MAX-ACCESS		read-only
		STATUS			current
		DESCRIPTION
				"TYPE: - Display
				 PAGE: - Dolby Setup
					New Display  cmdID= 44467  format=   "
		::= { iqudc32CmdEntry 44467 }


	iqudc32MenuGenlockSourceCh12 OBJECT-TYPE
		SYNTAX		INTEGER {
							val-Module-Reference(0),
							val-Chassis-Reference-A(1),
							val-Chassis-Reference-B(2),
							val-Ch-1-Input(3),
							val-Ch-2-Input(4),
							val-Free-Run(5)
							}
		MAX-ACCESS		read-write
		STATUS			current
		DESCRIPTION
				"TYPE: - RadiobuttonList
				 PAGE: - Genlock
					Source Ch 1 & 2  cmdID= 30000 
					Module Reference  value= 0  
					Chassis Reference A  value= 1  
					Chassis Reference B  value= 2  
					Ch 1 Input  value= 3  
					Ch 2 Input  value= 4  
					Free Run  value= 5  "
		::= { iqudc32CmdEntry 30000 }


	iqudc32GenlockTimingCh1VerticalTiming OBJECT-TYPE
		SYNTAX		INTEGER
		MAX-ACCESS		read-write
		STATUS			current
		DESCRIPTION
				"TYPE: - Number
				 PAGE: - Genlock
					Vertical Timing  cmdID= 30010  min= -1125  max= 1125  step= 1  format= %0.0f lines  div_scale= 1 
					Min = -1125 lines  Max = 1125 lines  Step = 1 lines "
		::= { iqudc32CmdEntry 30010 }


	iqudc32GenlockTimingCh1HorizontalTiming OBJECT-TYPE
		SYNTAX		INTEGER
		MAX-ACCESS		read-write
		STATUS			current
		DESCRIPTION
				"TYPE: - Number
				 PAGE: - Genlock
					Horizontal Timing  cmdID= 30011  min= -2640  max= 2640  step= 1  format= %0.0f pixels  div_scale= 1 
					Min = -2640 pixels  Max = 2640 pixels  Step = 1 pixels "
		::= { iqudc32CmdEntry 30011 }


	iqudc32GenlockTimingCh1Status OBJECT-TYPE
		SYNTAX		RollCallString
		MAX-ACCESS		read-only
		STATUS			current
		DESCRIPTION
				"TYPE: - Display
				 PAGE: - Genlock
					Status  cmdID= 61006  format=   "
		::= { iqudc32CmdEntry 61006 }


	iqudc32GenlockTimingCh2VerticalTiming OBJECT-TYPE
		SYNTAX		INTEGER
		MAX-ACCESS		read-write
		STATUS			current
		DESCRIPTION
				"TYPE: - Number
				 PAGE: - Genlock
					Vertical Timing  cmdID= 30012  min= -1125  max= 1125  step= 1  format= %0.0f lines  div_scale= 1 
					Min = -1125 lines  Max = 1125 lines  Step = 1 lines "
		::= { iqudc32CmdEntry 30012 }


	iqudc32GenlockTimingCh2HorizontalTiming OBJECT-TYPE
		SYNTAX		INTEGER
		MAX-ACCESS		read-write
		STATUS			current
		DESCRIPTION
				"TYPE: - Number
				 PAGE: - Genlock
					Horizontal Timing  cmdID= 30013  min= -2640  max= 2640  step= 1  format= %0.0f pixels  div_scale= 1 
					Min = -2640 pixels  Max = 2640 pixels  Step = 1 pixels "
		::= { iqudc32CmdEntry 30013 }


	iqudc32GenlockTimingCh2Status OBJECT-TYPE
		SYNTAX		RollCallString
		MAX-ACCESS		read-only
		STATUS			current
		DESCRIPTION
				"TYPE: - Display
				 PAGE: - Genlock
					Status  cmdID= 61007  format=   "
		::= { iqudc32CmdEntry 61007 }


	iqudc32MenuTimecodeCh1SourceHD OBJECT-TYPE
		SYNTAX		INTEGER {
							val-LTC(0),
							val-VITC(1)
							}
		MAX-ACCESS		read-write
		STATUS			current
		DESCRIPTION
				"TYPE: - RadiobuttonList
				 PAGE: - Timecode-Ch1
					Source (HD)  cmdID= 60100 
					LTC  value= 0  
					VITC  value= 1  "
		::= { iqudc32CmdEntry 60100 }


	iqudc32MenuTimecodeCh1SourceSD OBJECT-TYPE
		SYNTAX		INTEGER {
							val-VITC(0),
							val-ATC-LTC(1),
							val-ATC-VITC(2)
							}
		MAX-ACCESS		read-write
		STATUS			current
		DESCRIPTION
				"TYPE: - RadiobuttonList
				 PAGE: - Timecode-Ch1
					Source (SD)  cmdID= 60101 
					VITC  value= 0  
					ATC LTC  value= 1  
					ATC VITC  value= 2  "
		::= { iqudc32CmdEntry 60101 }


	iqudc32MenuTimecodeCh1Status OBJECT-TYPE
		SYNTAX		RollCallString
		MAX-ACCESS		read-only
		STATUS			current
		DESCRIPTION
				"TYPE: - Display
				 PAGE: - Timecode-Ch1
					Status  cmdID= 60112  format=   "
		::= { iqudc32CmdEntry 60112 }


	iqudc32MenuTimecodeCh1Mode OBJECT-TYPE
		SYNTAX		INTEGER {
							val-Follow-Input(0),
							val-Generate(1)
							}
		MAX-ACCESS		read-write
		STATUS			current
		DESCRIPTION
				"TYPE: - RadiobuttonList
				 PAGE: - Timecode-Ch1
					Mode  cmdID= 60102 
					Follow Input  value= 0  
					Generate  value= 1  "
		::= { iqudc32CmdEntry 60102 }


	iqudc32MenuTimecodeCh1OnTimecodeLoss OBJECT-TYPE
		SYNTAX		INTEGER {
							val-Freeze(0),
							val-Free-Run(1)
							}
		MAX-ACCESS		read-write
		STATUS			current
		DESCRIPTION
				"TYPE: - RadiobuttonList
				 PAGE: - Timecode-Ch1
					On Timecode Loss  cmdID= 60107 
					Freeze  value= 0  
					Free Run  value= 1  "
		::= { iqudc32CmdEntry 60107 }


	iqudc32MenuTimecodeCh1TimecodeEntry OBJECT-TYPE
		SYNTAX		RollCallString
		MAX-ACCESS		read-write
		STATUS			current
		DESCRIPTION
				"TYPE: - Editstring
				 PAGE: - Timecode-Ch1
					Timecode Entry  cmdID= 60110  "
		::= { iqudc32CmdEntry 60110 }


	iqudc32MenuTimecodeCh1TimecodeLoad OBJECT-TYPE
		SYNTAX		INTEGER { noAction(0),val-Timecode-Load(1) }
		MAX-ACCESS		read-write
		STATUS			current
		DESCRIPTION
				"TYPE: - Button
				 PAGE: - Timecode-Ch1
					Timecode Load  cmdID= 60113  value= 1  "
		::= { iqudc32CmdEntry 60113 }


	iqudc32MenuTimecodeCh1NondropFrame OBJECT-TYPE
		SYNTAX		INTEGER { disable(0), enable(1) }
		MAX-ACCESS		read-write
		STATUS			current
		DESCRIPTION
				"TYPE: - Checkbox
				 PAGE: - Timecode-Ch1
					Non-drop Frame  cmdID= 60109 "
		::= { iqudc32CmdEntry 60109 }


	iqudc32MenuTimecodeCh1VITCEnable OBJECT-TYPE
		SYNTAX		INTEGER { disable(0), enable(1) }
		MAX-ACCESS		read-write
		STATUS			current
		DESCRIPTION
				"TYPE: - Checkbox
				 PAGE: - Timecode-Ch1
					VITC Enable  cmdID= 60111 "
		::= { iqudc32CmdEntry 60111 }


	iqudc32MenuTimecodeCh1OutputLine525 OBJECT-TYPE
		SYNTAX		INTEGER
		MAX-ACCESS		read-write
		STATUS			current
		DESCRIPTION
				"TYPE: - Number
				 PAGE: - Timecode-Ch1
					Output Line (525)  cmdID= 60103  min= 11  max= 17  step= 1  format= %0.0f  div_scale= 1 
					Min = 11  Max = 17  Step = 1 "
		::= { iqudc32CmdEntry 60103 }


	iqudc32MenuTimecodeCh1OutputLine625 OBJECT-TYPE
		SYNTAX		INTEGER
		MAX-ACCESS		read-write
		STATUS			current
		DESCRIPTION
				"TYPE: - Number
				 PAGE: - Timecode-Ch1
					Output Line (625)  cmdID= 60104  min= 7  max= 20  step= 1  format= %0.0f  div_scale= 1 
					Min = 7  Max = 20  Step = 1 "
		::= { iqudc32CmdEntry 60104 }


	iqudc32MenuTimecodeCh1OutputLineStatus OBJECT-TYPE
		SYNTAX		RollCallString
		MAX-ACCESS		read-only
		STATUS			current
		DESCRIPTION
				"TYPE: - Display
				 PAGE: - Timecode-Ch1
					Output Line Status  cmdID= 20165  format=   "
		::= { iqudc32CmdEntry 20165 }


	iqudc32MenuTimecodeCh1NewDisplay OBJECT-TYPE
		SYNTAX		RollCallString
		MAX-ACCESS		read-only
		STATUS			current
		DESCRIPTION
				"TYPE: - Display
				 PAGE: - Timecode-Ch1
					New Display  cmdID= 44465  format=   "
		::= { iqudc32CmdEntry 44465 }


	iqudc32MenuTimecodeCh2SourceHD OBJECT-TYPE
		SYNTAX		INTEGER {
							val-LTC(0),
							val-VITC(1)
							}
		MAX-ACCESS		read-write
		STATUS			current
		DESCRIPTION
				"TYPE: - RadiobuttonList
				 PAGE: - Timecode-Ch2
					Source (HD)  cmdID= 60214 
					LTC  value= 0  
					VITC  value= 1  "
		::= { iqudc32CmdEntry 60214 }


	iqudc32MenuTimecodeCh2SourceSD OBJECT-TYPE
		SYNTAX		INTEGER {
							val-VITC(0),
							val-ATC-LTC(1),
							val-ATC-VITC(2)
							}
		MAX-ACCESS		read-write
		STATUS			current
		DESCRIPTION
				"TYPE: - RadiobuttonList
				 PAGE: - Timecode-Ch2
					Source (SD)  cmdID= 60215 
					VITC  value= 0  
					ATC LTC  value= 1  
					ATC VITC  value= 2  "
		::= { iqudc32CmdEntry 60215 }


	iqudc32MenuTimecodeCh2Status OBJECT-TYPE
		SYNTAX		RollCallString
		MAX-ACCESS		read-only
		STATUS			current
		DESCRIPTION
				"TYPE: - Display
				 PAGE: - Timecode-Ch2
					Status  cmdID= 60212  format=   "
		::= { iqudc32CmdEntry 60212 }


	iqudc32MenuTimecodeCh2Mode OBJECT-TYPE
		SYNTAX		INTEGER {
							val-Follow-Input(0),
							val-Generate(1)
							}
		MAX-ACCESS		read-write
		STATUS			current
		DESCRIPTION
				"TYPE: - RadiobuttonList
				 PAGE: - Timecode-Ch2
					Mode  cmdID= 60202 
					Follow Input  value= 0  
					Generate  value= 1  "
		::= { iqudc32CmdEntry 60202 }


	iqudc32MenuTimecodeCh2OnTimecodeLoss OBJECT-TYPE
		SYNTAX		INTEGER {
							val-Freeze(0),
							val-Free-Run(1)
							}
		MAX-ACCESS		read-write
		STATUS			current
		DESCRIPTION
				"TYPE: - RadiobuttonList
				 PAGE: - Timecode-Ch2
					On Timecode Loss  cmdID= 60207 
					Freeze  value= 0  
					Free Run  value= 1  "
		::= { iqudc32CmdEntry 60207 }


	iqudc32MenuTimecodeCh2TimecodeEntry OBJECT-TYPE
		SYNTAX		RollCallString
		MAX-ACCESS		read-write
		STATUS			current
		DESCRIPTION
				"TYPE: - Editstring
				 PAGE: - Timecode-Ch2
					Timecode Entry  cmdID= 60210  "
		::= { iqudc32CmdEntry 60210 }


	iqudc32MenuTimecodeCh2TimecodeLoad OBJECT-TYPE
		SYNTAX		INTEGER { noAction(0),val-Timecode-Load(1) }
		MAX-ACCESS		read-write
		STATUS			current
		DESCRIPTION
				"TYPE: - Button
				 PAGE: - Timecode-Ch2
					Timecode Load  cmdID= 60213  value= 1  "
		::= { iqudc32CmdEntry 60213 }


	iqudc32MenuTimecodeCh2NondropFrame OBJECT-TYPE
		SYNTAX		INTEGER { disable(0), enable(1) }
		MAX-ACCESS		read-write
		STATUS			current
		DESCRIPTION
				"TYPE: - Checkbox
				 PAGE: - Timecode-Ch2
					Non-drop Frame  cmdID= 60220 "
		::= { iqudc32CmdEntry 60220 }


	iqudc32MenuTimecodeCh2VITCEnable OBJECT-TYPE
		SYNTAX		INTEGER { disable(0), enable(1) }
		MAX-ACCESS		read-write
		STATUS			current
		DESCRIPTION
				"TYPE: - Checkbox
				 PAGE: - Timecode-Ch2
					VITC Enable  cmdID= 60211 "
		::= { iqudc32CmdEntry 60211 }


	iqudc32MenuTimecodeCh2OutputLine525 OBJECT-TYPE
		SYNTAX		INTEGER
		MAX-ACCESS		read-write
		STATUS			current
		DESCRIPTION
				"TYPE: - Number
				 PAGE: - Timecode-Ch2
					Output Line (525)  cmdID= 60203  min= 11  max= 17  step= 1  format= %0.0f  div_scale= 1 
					Min = 11  Max = 17  Step = 1 "
		::= { iqudc32CmdEntry 60203 }


	iqudc32MenuTimecodeCh2OutputLine625 OBJECT-TYPE
		SYNTAX		INTEGER
		MAX-ACCESS		read-write
		STATUS			current
		DESCRIPTION
				"TYPE: - Number
				 PAGE: - Timecode-Ch2
					Output Line (625)  cmdID= 60204  min= 7  max= 20  step= 1  format= %0.0f  div_scale= 1 
					Min = 7  Max = 20  Step = 1 "
		::= { iqudc32CmdEntry 60204 }


	iqudc32MenuTimecodeCh2OutputLineStatus OBJECT-TYPE
		SYNTAX		RollCallString
		MAX-ACCESS		read-only
		STATUS			current
		DESCRIPTION
				"TYPE: - Display
				 PAGE: - Timecode-Ch2
					Output Line Status  cmdID= 20175  format=   "
		::= { iqudc32CmdEntry 20175 }


	iqudc32MenuTimecodeCh2NewDisplay OBJECT-TYPE
		SYNTAX		RollCallString
		MAX-ACCESS		read-only
		STATUS			current
		DESCRIPTION
				"TYPE: - Display
				 PAGE: - Timecode-Ch2
					New Display  cmdID= 44451  format=   "
		::= { iqudc32CmdEntry 44451 }


	iqudc32MetadataCh1ClosedCaptionsInputStatus OBJECT-TYPE
		SYNTAX		RollCallString
		MAX-ACCESS		read-only
		STATUS			current
		DESCRIPTION
				"TYPE: - Display
				 PAGE: - Metadata-Ch1
					Input Status  cmdID= 60208  format=   "
		::= { iqudc32CmdEntry 60208 }


	iqudc32MetadataCh1ClosedCaptionsCEA608OutputEnab OBJECT-TYPE
		SYNTAX		INTEGER { disable(0), enable(1) }
		MAX-ACCESS		read-write
		STATUS			current
		DESCRIPTION
				"TYPE: - Checkbox
				 PAGE: - Metadata-Ch1
					CEA-608 Output Enab  cmdID= 60200 "
		::= { iqudc32CmdEntry 60200 }


	iqudc32MetadataCh1ClosedCaptionsCEA708OutputEnab OBJECT-TYPE
		SYNTAX		INTEGER { disable(0), enable(1) }
		MAX-ACCESS		read-write
		STATUS			current
		DESCRIPTION
				"TYPE: - Checkbox
				 PAGE: - Metadata-Ch1
					CEA-708 Output Enab  cmdID= 60201 "
		::= { iqudc32CmdEntry 60201 }


	iqudc32MetadataCh1ClosedCaptionsCEA708OutputLine60216 OBJECT-TYPE
		SYNTAX		INTEGER
		MAX-ACCESS		read-write
		STATUS			current
		DESCRIPTION
				"TYPE: - Number
				 PAGE: - Metadata-Ch1
					CEA-708 Output Line  cmdID= 60216  min= 8  max= 20  step= 1  format= %0.0f  div_scale= 1 
					Min = 8  Max = 20  Step = 1 "
		::= { iqudc32CmdEntry 60216 }


	iqudc32MetadataCh1ClosedCaptionsCEA708OutputLine60221 OBJECT-TYPE
		SYNTAX		RollCallString
		MAX-ACCESS		read-only
		STATUS			current
		DESCRIPTION
				"TYPE: - Display
				 PAGE: - Metadata-Ch1
					CEA-708 Output Line  cmdID= 60221  format=   "
		::= { iqudc32CmdEntry 60221 }


	iqudc32MetadataCh1Teletext625CaptionsSource OBJECT-TYPE
		SYNTAX		INTEGER {
							val-WST(0),
							val-CEA-608(1)
							}
		MAX-ACCESS		read-write
		STATUS			current
		DESCRIPTION
				"TYPE: - RadiobuttonList
				 PAGE: - Metadata-Ch1
					625 Captions Source  cmdID= 60471 
					WST  value= 0  
					CEA-608  value= 1  "
		::= { iqudc32CmdEntry 60471 }


	iqudc32TeletextSDVBISetupWSTOriginLine760400 OBJECT-TYPE
		SYNTAX		INTEGER { disable(0), enable(1) }
		MAX-ACCESS		read-write
		STATUS			current
		DESCRIPTION
				"TYPE: - Checkbox
				 PAGE: - Metadata-Ch1
					WST Origin Line 7  cmdID= 60400 "
		::= { iqudc32CmdEntry 60400 }


	iqudc32TeletextSDVBISetupWSTOriginLine860401 OBJECT-TYPE
		SYNTAX		INTEGER { disable(0), enable(1) }
		MAX-ACCESS		read-write
		STATUS			current
		DESCRIPTION
				"TYPE: - Checkbox
				 PAGE: - Metadata-Ch1
					WST Origin Line 8  cmdID= 60401 "
		::= { iqudc32CmdEntry 60401 }


	iqudc32TeletextSDVBISetupWSTOriginLine960402 OBJECT-TYPE
		SYNTAX		INTEGER { disable(0), enable(1) }
		MAX-ACCESS		read-write
		STATUS			current
		DESCRIPTION
				"TYPE: - Checkbox
				 PAGE: - Metadata-Ch1
					WST Origin Line 9  cmdID= 60402 "
		::= { iqudc32CmdEntry 60402 }


	iqudc32TeletextSDVBISetupWSTOriginLine1060403 OBJECT-TYPE
		SYNTAX		INTEGER { disable(0), enable(1) }
		MAX-ACCESS		read-write
		STATUS			current
		DESCRIPTION
				"TYPE: - Checkbox
				 PAGE: - Metadata-Ch1
					WST Origin Line 10  cmdID= 60403 "
		::= { iqudc32CmdEntry 60403 }


	iqudc32TeletextSDVBISetupWSTOriginLine1160404 OBJECT-TYPE
		SYNTAX		INTEGER { disable(0), enable(1) }
		MAX-ACCESS		read-write
		STATUS			current
		DESCRIPTION
				"TYPE: - Checkbox
				 PAGE: - Metadata-Ch1
					WST Origin Line 11  cmdID= 60404 "
		::= { iqudc32CmdEntry 60404 }


	iqudc32TeletextSDVBISetupWSTOriginLine1260405 OBJECT-TYPE
		SYNTAX		INTEGER { disable(0), enable(1) }
		MAX-ACCESS		read-write
		STATUS			current
		DESCRIPTION
				"TYPE: - Checkbox
				 PAGE: - Metadata-Ch1
					WST Origin Line 12  cmdID= 60405 "
		::= { iqudc32CmdEntry 60405 }


	iqudc32TeletextSDVBISetupWSTOriginLine1360406 OBJECT-TYPE
		SYNTAX		INTEGER { disable(0), enable(1) }
		MAX-ACCESS		read-write
		STATUS			current
		DESCRIPTION
				"TYPE: - Checkbox
				 PAGE: - Metadata-Ch1
					WST Origin Line 13  cmdID= 60406 "
		::= { iqudc32CmdEntry 60406 }


	iqudc32TeletextSDVBISetupWSTOriginLine1460407 OBJECT-TYPE
		SYNTAX		INTEGER { disable(0), enable(1) }
		MAX-ACCESS		read-write
		STATUS			current
		DESCRIPTION
				"TYPE: - Checkbox
				 PAGE: - Metadata-Ch1
					WST Origin Line 14  cmdID= 60407 "
		::= { iqudc32CmdEntry 60407 }


	iqudc32TeletextSDVBISetupWSTOriginLine1560408 OBJECT-TYPE
		SYNTAX		INTEGER { disable(0), enable(1) }
		MAX-ACCESS		read-write
		STATUS			current
		DESCRIPTION
				"TYPE: - Checkbox
				 PAGE: - Metadata-Ch1
					WST Origin Line 15  cmdID= 60408 "
		::= { iqudc32CmdEntry 60408 }


	iqudc32TeletextSDVBISetupWSTOriginLine1660409 OBJECT-TYPE
		SYNTAX		INTEGER { disable(0), enable(1) }
		MAX-ACCESS		read-write
		STATUS			current
		DESCRIPTION
				"TYPE: - Checkbox
				 PAGE: - Metadata-Ch1
					WST Origin Line 16  cmdID= 60409 "
		::= { iqudc32CmdEntry 60409 }


	iqudc32TeletextSDVBISetupWSTOriginLine1760410 OBJECT-TYPE
		SYNTAX		INTEGER { disable(0), enable(1) }
		MAX-ACCESS		read-write
		STATUS			current
		DESCRIPTION
				"TYPE: - Checkbox
				 PAGE: - Metadata-Ch1
					WST Origin Line 17  cmdID= 60410 "
		::= { iqudc32CmdEntry 60410 }


	iqudc32TeletextSDVBISetupWSTOriginLine1860411 OBJECT-TYPE
		SYNTAX		INTEGER { disable(0), enable(1) }
		MAX-ACCESS		read-write
		STATUS			current
		DESCRIPTION
				"TYPE: - Checkbox
				 PAGE: - Metadata-Ch1
					WST Origin Line 18  cmdID= 60411 "
		::= { iqudc32CmdEntry 60411 }


	iqudc32TeletextSDVBISetupWSTOriginLine1960412 OBJECT-TYPE
		SYNTAX		INTEGER { disable(0), enable(1) }
		MAX-ACCESS		read-write
		STATUS			current
		DESCRIPTION
				"TYPE: - Checkbox
				 PAGE: - Metadata-Ch1
					WST Origin Line 19  cmdID= 60412 "
		::= { iqudc32CmdEntry 60412 }


	iqudc32TeletextSDVBISetupWSTOriginLine2060413 OBJECT-TYPE
		SYNTAX		INTEGER { disable(0), enable(1) }
		MAX-ACCESS		read-write
		STATUS			current
		DESCRIPTION
				"TYPE: - Checkbox
				 PAGE: - Metadata-Ch1
					WST Origin Line 20  cmdID= 60413 "
		::= { iqudc32CmdEntry 60413 }


	iqudc32TeletextSDVBISetupWSTOriginLine2160414 OBJECT-TYPE
		SYNTAX		INTEGER { disable(0), enable(1) }
		MAX-ACCESS		read-write
		STATUS			current
		DESCRIPTION
				"TYPE: - Checkbox
				 PAGE: - Metadata-Ch1
					WST Origin Line 21  cmdID= 60414 "
		::= { iqudc32CmdEntry 60414 }


	iqudc32TeletextSDVBISetupWSTOriginLine2260415 OBJECT-TYPE
		SYNTAX		INTEGER { disable(0), enable(1) }
		MAX-ACCESS		read-write
		STATUS			current
		DESCRIPTION
				"TYPE: - Checkbox
				 PAGE: - Metadata-Ch1
					WST Origin Line 22  cmdID= 60415 "
		::= { iqudc32CmdEntry 60415 }


	iqudc32TeletextSDVBISetupWSTOriginLine7S60416 OBJECT-TYPE
		SYNTAX		RollCallString
		MAX-ACCESS		read-only
		STATUS			current
		DESCRIPTION
				"TYPE: - Display
				 PAGE: - Metadata-Ch1
					WST Origin Line 7 S  cmdID= 60416  format=   "
		::= { iqudc32CmdEntry 60416 }


	iqudc32TeletextSDVBISetupWSTOriginLine8S60417 OBJECT-TYPE
		SYNTAX		RollCallString
		MAX-ACCESS		read-only
		STATUS			current
		DESCRIPTION
				"TYPE: - Display
				 PAGE: - Metadata-Ch1
					WST Origin Line 8 S  cmdID= 60417  format=   "
		::= { iqudc32CmdEntry 60417 }


	iqudc32TeletextSDVBISetupWSTOriginLine9S60418 OBJECT-TYPE
		SYNTAX		RollCallString
		MAX-ACCESS		read-only
		STATUS			current
		DESCRIPTION
				"TYPE: - Display
				 PAGE: - Metadata-Ch1
					WST Origin Line 9 S  cmdID= 60418  format=   "
		::= { iqudc32CmdEntry 60418 }


	iqudc32TeletextSDVBISetupWSTOriginLine1060419 OBJECT-TYPE
		SYNTAX		RollCallString
		MAX-ACCESS		read-only
		STATUS			current
		DESCRIPTION
				"TYPE: - Display
				 PAGE: - Metadata-Ch1
					WST Origin Line 10   cmdID= 60419  format=   "
		::= { iqudc32CmdEntry 60419 }


	iqudc32TeletextSDVBISetupWSTOriginLine1160420 OBJECT-TYPE
		SYNTAX		RollCallString
		MAX-ACCESS		read-only
		STATUS			current
		DESCRIPTION
				"TYPE: - Display
				 PAGE: - Metadata-Ch1
					WST Origin Line 11   cmdID= 60420  format=   "
		::= { iqudc32CmdEntry 60420 }


	iqudc32TeletextSDVBISetupWSTOriginLine1260421 OBJECT-TYPE
		SYNTAX		RollCallString
		MAX-ACCESS		read-only
		STATUS			current
		DESCRIPTION
				"TYPE: - Display
				 PAGE: - Metadata-Ch1
					WST Origin Line 12   cmdID= 60421  format=   "
		::= { iqudc32CmdEntry 60421 }


	iqudc32TeletextSDVBISetupWSTOriginLine1360422 OBJECT-TYPE
		SYNTAX		RollCallString
		MAX-ACCESS		read-only
		STATUS			current
		DESCRIPTION
				"TYPE: - Display
				 PAGE: - Metadata-Ch1
					WST Origin Line 13   cmdID= 60422  format=   "
		::= { iqudc32CmdEntry 60422 }


	iqudc32TeletextSDVBISetupWSTOriginLine1460423 OBJECT-TYPE
		SYNTAX		RollCallString
		MAX-ACCESS		read-only
		STATUS			current
		DESCRIPTION
				"TYPE: - Display
				 PAGE: - Metadata-Ch1
					WST Origin Line 14   cmdID= 60423  format=   "
		::= { iqudc32CmdEntry 60423 }


	iqudc32TeletextSDVBISetupWSTOriginLine1560424 OBJECT-TYPE
		SYNTAX		RollCallString
		MAX-ACCESS		read-only
		STATUS			current
		DESCRIPTION
				"TYPE: - Display
				 PAGE: - Metadata-Ch1
					WST Origin Line 15   cmdID= 60424  format=   "
		::= { iqudc32CmdEntry 60424 }


	iqudc32TeletextSDVBISetupWSTOriginLine1660425 OBJECT-TYPE
		SYNTAX		RollCallString
		MAX-ACCESS		read-only
		STATUS			current
		DESCRIPTION
				"TYPE: - Display
				 PAGE: - Metadata-Ch1
					WST Origin Line 16   cmdID= 60425  format=   "
		::= { iqudc32CmdEntry 60425 }


	iqudc32TeletextSDVBISetupWSTOriginLine1760426 OBJECT-TYPE
		SYNTAX		RollCallString
		MAX-ACCESS		read-only
		STATUS			current
		DESCRIPTION
				"TYPE: - Display
				 PAGE: - Metadata-Ch1
					WST Origin Line 17   cmdID= 60426  format=   "
		::= { iqudc32CmdEntry 60426 }


	iqudc32TeletextSDVBISetupWSTOriginLine1860427 OBJECT-TYPE
		SYNTAX		RollCallString
		MAX-ACCESS		read-only
		STATUS			current
		DESCRIPTION
				"TYPE: - Display
				 PAGE: - Metadata-Ch1
					WST Origin Line 18   cmdID= 60427  format=   "
		::= { iqudc32CmdEntry 60427 }


	iqudc32TeletextSDVBISetupWSTOriginLine1960428 OBJECT-TYPE
		SYNTAX		RollCallString
		MAX-ACCESS		read-only
		STATUS			current
		DESCRIPTION
				"TYPE: - Display
				 PAGE: - Metadata-Ch1
					WST Origin Line 19   cmdID= 60428  format=   "
		::= { iqudc32CmdEntry 60428 }


	iqudc32TeletextSDVBISetupWSTOriginLine2060429 OBJECT-TYPE
		SYNTAX		RollCallString
		MAX-ACCESS		read-only
		STATUS			current
		DESCRIPTION
				"TYPE: - Display
				 PAGE: - Metadata-Ch1
					WST Origin Line 20   cmdID= 60429  format=   "
		::= { iqudc32CmdEntry 60429 }


	iqudc32TeletextSDVBISetupWSTOriginLine2160430 OBJECT-TYPE
		SYNTAX		RollCallString
		MAX-ACCESS		read-only
		STATUS			current
		DESCRIPTION
				"TYPE: - Display
				 PAGE: - Metadata-Ch1
					WST Origin Line 21   cmdID= 60430  format=   "
		::= { iqudc32CmdEntry 60430 }


	iqudc32TeletextSDVBISetupWSTOriginLine2260431 OBJECT-TYPE
		SYNTAX		RollCallString
		MAX-ACCESS		read-only
		STATUS			current
		DESCRIPTION
				"TYPE: - Display
				 PAGE: - Metadata-Ch1
					WST Origin Line 22   cmdID= 60431  format=   "
		::= { iqudc32CmdEntry 60431 }


	iqudc32TeletextSDVBISetupWSTOPLine7Statu60432 OBJECT-TYPE
		SYNTAX		RollCallString
		MAX-ACCESS		read-only
		STATUS			current
		DESCRIPTION
				"TYPE: - Display
				 PAGE: - Metadata-Ch1
					WST OP Line 7 Statu  cmdID= 60432  format=   "
		::= { iqudc32CmdEntry 60432 }


	iqudc32TeletextSDVBISetupWSTOPLine8Statu60433 OBJECT-TYPE
		SYNTAX		RollCallString
		MAX-ACCESS		read-only
		STATUS			current
		DESCRIPTION
				"TYPE: - Display
				 PAGE: - Metadata-Ch1
					WST OP Line 8 Statu  cmdID= 60433  format=   "
		::= { iqudc32CmdEntry 60433 }


	iqudc32TeletextSDVBISetupWSTOPLine9Statu60434 OBJECT-TYPE
		SYNTAX		RollCallString
		MAX-ACCESS		read-only
		STATUS			current
		DESCRIPTION
				"TYPE: - Display
				 PAGE: - Metadata-Ch1
					WST OP Line 9 Statu  cmdID= 60434  format=   "
		::= { iqudc32CmdEntry 60434 }


	iqudc32TeletextSDVBISetupWSTOPLine10Stat60435 OBJECT-TYPE
		SYNTAX		RollCallString
		MAX-ACCESS		read-only
		STATUS			current
		DESCRIPTION
				"TYPE: - Display
				 PAGE: - Metadata-Ch1
					WST OP Line 10 Stat  cmdID= 60435  format=   "
		::= { iqudc32CmdEntry 60435 }


	iqudc32TeletextSDVBISetupWSTOPLine11Stat60436 OBJECT-TYPE
		SYNTAX		RollCallString
		MAX-ACCESS		read-only
		STATUS			current
		DESCRIPTION
				"TYPE: - Display
				 PAGE: - Metadata-Ch1
					WST OP Line 11 Stat  cmdID= 60436  format=   "
		::= { iqudc32CmdEntry 60436 }


	iqudc32TeletextSDVBISetupWSTOPLine12Stat60437 OBJECT-TYPE
		SYNTAX		RollCallString
		MAX-ACCESS		read-only
		STATUS			current
		DESCRIPTION
				"TYPE: - Display
				 PAGE: - Metadata-Ch1
					WST OP Line 12 Stat  cmdID= 60437  format=   "
		::= { iqudc32CmdEntry 60437 }


	iqudc32TeletextSDVBISetupWSTOPLine13Stat60438 OBJECT-TYPE
		SYNTAX		RollCallString
		MAX-ACCESS		read-only
		STATUS			current
		DESCRIPTION
				"TYPE: - Display
				 PAGE: - Metadata-Ch1
					WST OP Line 13 Stat  cmdID= 60438  format=   "
		::= { iqudc32CmdEntry 60438 }


	iqudc32TeletextSDVBISetupWSTOPLine14Stat60439 OBJECT-TYPE
		SYNTAX		RollCallString
		MAX-ACCESS		read-only
		STATUS			current
		DESCRIPTION
				"TYPE: - Display
				 PAGE: - Metadata-Ch1
					WST OP Line 14 Stat  cmdID= 60439  format=   "
		::= { iqudc32CmdEntry 60439 }


	iqudc32TeletextSDVBISetupWSTOPLine15Stat60440 OBJECT-TYPE
		SYNTAX		RollCallString
		MAX-ACCESS		read-only
		STATUS			current
		DESCRIPTION
				"TYPE: - Display
				 PAGE: - Metadata-Ch1
					WST OP Line 15 Stat  cmdID= 60440  format=   "
		::= { iqudc32CmdEntry 60440 }


	iqudc32TeletextSDVBISetupWSTOPLine16Stat60441 OBJECT-TYPE
		SYNTAX		RollCallString
		MAX-ACCESS		read-only
		STATUS			current
		DESCRIPTION
				"TYPE: - Display
				 PAGE: - Metadata-Ch1
					WST OP Line 16 Stat  cmdID= 60441  format=   "
		::= { iqudc32CmdEntry 60441 }


	iqudc32TeletextSDVBISetupWSTOPLine17Stat60442 OBJECT-TYPE
		SYNTAX		RollCallString
		MAX-ACCESS		read-only
		STATUS			current
		DESCRIPTION
				"TYPE: - Display
				 PAGE: - Metadata-Ch1
					WST OP Line 17 Stat  cmdID= 60442  format=   "
		::= { iqudc32CmdEntry 60442 }


	iqudc32TeletextSDVBISetupWSTOPLine18Stat60443 OBJECT-TYPE
		SYNTAX		RollCallString
		MAX-ACCESS		read-only
		STATUS			current
		DESCRIPTION
				"TYPE: - Display
				 PAGE: - Metadata-Ch1
					WST OP Line 18 Stat  cmdID= 60443  format=   "
		::= { iqudc32CmdEntry 60443 }


	iqudc32TeletextSDVBISetupWSTOPLine19Stat60444 OBJECT-TYPE
		SYNTAX		RollCallString
		MAX-ACCESS		read-only
		STATUS			current
		DESCRIPTION
				"TYPE: - Display
				 PAGE: - Metadata-Ch1
					WST OP Line 19 Stat  cmdID= 60444  format=   "
		::= { iqudc32CmdEntry 60444 }


	iqudc32TeletextSDVBISetupWSTOPLine20Stat60445 OBJECT-TYPE
		SYNTAX		RollCallString
		MAX-ACCESS		read-only
		STATUS			current
		DESCRIPTION
				"TYPE: - Display
				 PAGE: - Metadata-Ch1
					WST OP Line 20 Stat  cmdID= 60445  format=   "
		::= { iqudc32CmdEntry 60445 }


	iqudc32TeletextSDVBISetupWSTOPLine21Stat60446 OBJECT-TYPE
		SYNTAX		RollCallString
		MAX-ACCESS		read-only
		STATUS			current
		DESCRIPTION
				"TYPE: - Display
				 PAGE: - Metadata-Ch1
					WST OP Line 21 Stat  cmdID= 60446  format=   "
		::= { iqudc32CmdEntry 60446 }


	iqudc32TeletextSDVBISetupWSTOPLine22Stat60447 OBJECT-TYPE
		SYNTAX		RollCallString
		MAX-ACCESS		read-only
		STATUS			current
		DESCRIPTION
				"TYPE: - Display
				 PAGE: - Metadata-Ch1
					WST OP Line 22 Stat  cmdID= 60447  format=   "
		::= { iqudc32CmdEntry 60447 }


	iqudc32TeletextSDVBISetupAllowWSTRemap60466 OBJECT-TYPE
		SYNTAX		INTEGER { disable(0), enable(1) }
		MAX-ACCESS		read-write
		STATUS			current
		DESCRIPTION
				"TYPE: - Checkbox
				 PAGE: - Metadata-Ch1
					Allow WST Remap  cmdID= 60466 "
		::= { iqudc32CmdEntry 60466 }


	iqudc32TeletextSDVBISetupWSTOriginLine60467 OBJECT-TYPE
		SYNTAX		INTEGER
		MAX-ACCESS		read-write
		STATUS			current
		DESCRIPTION
				"TYPE: - Number
				 PAGE: - Metadata-Ch1
					WST Origin Line  cmdID= 60467  min= 7  max= 22  step= 1  format= %0.0f  div_scale= 1 
					Min = 7  Max = 22  Step = 1 "
		::= { iqudc32CmdEntry 60467 }


	iqudc32TeletextSDVBISetupWSTOriginLineSta60468 OBJECT-TYPE
		SYNTAX		RollCallString
		MAX-ACCESS		read-only
		STATUS			current
		DESCRIPTION
				"TYPE: - Display
				 PAGE: - Metadata-Ch1
					WST Origin Line Sta  cmdID= 60468  format=   "
		::= { iqudc32CmdEntry 60468 }


	iqudc32TeletextSDVBISetupWSTOutputLine60469 OBJECT-TYPE
		SYNTAX		INTEGER
		MAX-ACCESS		read-write
		STATUS			current
		DESCRIPTION
				"TYPE: - Number
				 PAGE: - Metadata-Ch1
					WST Output Line  cmdID= 60469  min= 7  max= 22  step= 1  format= %0.0f  div_scale= 1 
					Min = 7  Max = 22  Step = 1 "
		::= { iqudc32CmdEntry 60469 }


	iqudc32TeletextSDVBISetupWSTOutputLineSta60470 OBJECT-TYPE
		SYNTAX		RollCallString
		MAX-ACCESS		read-only
		STATUS			current
		DESCRIPTION
				"TYPE: - Display
				 PAGE: - Metadata-Ch1
					WST Output Line Sta  cmdID= 60470  format=   "
		::= { iqudc32CmdEntry 60470 }


	iqudc32TeletextSMPTERDD8SMPTERDD82031InputP60448 OBJECT-TYPE
		SYNTAX		INTEGER {
							val-SMPTE-RDD8(0),
							val-SMPTE-2031(1)
							}
		MAX-ACCESS		read-write
		STATUS			current
		DESCRIPTION
				"TYPE: - RadiobuttonList
				 PAGE: - Metadata-Ch1
					RDD8 / 2031 Input P  cmdID= 60448 
					SMPTE RDD8  value= 0  
					SMPTE 2031  value= 1  "
		::= { iqudc32CmdEntry 60448 }


	iqudc32TeletextSMPTERDD8SMPTERDD82031Output60449 OBJECT-TYPE
		SYNTAX		INTEGER { disable(0), enable(1) }
		MAX-ACCESS		read-write
		STATUS			current
		DESCRIPTION
				"TYPE: - Checkbox
				 PAGE: - Metadata-Ch1
					RDD8 / 2031 Output   cmdID= 60449 "
		::= { iqudc32CmdEntry 60449 }


	iqudc32TeletextSMPTERDD8SMPTERDD82031Output60450 OBJECT-TYPE
		SYNTAX		INTEGER {
							val-SMPTE-RDD8(0),
							val-SMPTE-2031(1)
							}
		MAX-ACCESS		read-write
		STATUS			current
		DESCRIPTION
				"TYPE: - RadiobuttonList
				 PAGE: - Metadata-Ch1
					RDD8 / 2031 Output   cmdID= 60450 
					SMPTE RDD8  value= 0  
					SMPTE 2031  value= 1  "
		::= { iqudc32CmdEntry 60450 }


	iqudc32TeletextSMPTERDD8RDD8OutputLinePK60451 OBJECT-TYPE
		SYNTAX		INTEGER
		MAX-ACCESS		read-write
		STATUS			current
		DESCRIPTION
				"TYPE: - Number
				 PAGE: - Metadata-Ch1- SMPTE RDD8
					RDD8 Output Line PK  cmdID= 60451  min= 8  max= 20  step= 1  format= %0.0f  div_scale= 1 
					Min = 8  Max = 20  Step = 1 "
		::= { iqudc32CmdEntry 60451 }


	iqudc32TeletextSMPTERDD8RDD8OutputLinePK60452 OBJECT-TYPE
		SYNTAX		INTEGER
		MAX-ACCESS		read-write
		STATUS			current
		DESCRIPTION
				"TYPE: - Number
				 PAGE: - Metadata-Ch1- SMPTE RDD8
					RDD8 Output Line PK  cmdID= 60452  min= 8  max= 20  step= 1  format= %0.0f  div_scale= 1 
					Min = 8  Max = 20  Step = 1 "
		::= { iqudc32CmdEntry 60452 }


	iqudc32TeletextSMPTERDD8RDD8OutputLinePK60453 OBJECT-TYPE
		SYNTAX		INTEGER
		MAX-ACCESS		read-write
		STATUS			current
		DESCRIPTION
				"TYPE: - Number
				 PAGE: - Metadata-Ch1- SMPTE RDD8
					RDD8 Output Line PK  cmdID= 60453  min= 8  max= 20  step= 1  format= %0.0f  div_scale= 1 
					Min = 8  Max = 20  Step = 1 "
		::= { iqudc32CmdEntry 60453 }


	iqudc32TeletextSMPTERDD8RDD8OutputLinePK60454 OBJECT-TYPE
		SYNTAX		RollCallString
		MAX-ACCESS		read-only
		STATUS			current
		DESCRIPTION
				"TYPE: - Display
				 PAGE: - Metadata-Ch1- SMPTE RDD8
					RDD8 Output Line PK  cmdID= 60454  format=   "
		::= { iqudc32CmdEntry 60454 }


	iqudc32TeletextSMPTERDD8RDD8OutputLinePK60455 OBJECT-TYPE
		SYNTAX		RollCallString
		MAX-ACCESS		read-only
		STATUS			current
		DESCRIPTION
				"TYPE: - Display
				 PAGE: - Metadata-Ch1- SMPTE RDD8
					RDD8 Output Line PK  cmdID= 60455  format=   "
		::= { iqudc32CmdEntry 60455 }


	iqudc32TeletextSMPTERDD8RDD8OutputLinePK60456 OBJECT-TYPE
		SYNTAX		RollCallString
		MAX-ACCESS		read-only
		STATUS			current
		DESCRIPTION
				"TYPE: - Display
				 PAGE: - Metadata-Ch1- SMPTE RDD8
					RDD8 Output Line PK  cmdID= 60456  format=   "
		::= { iqudc32CmdEntry 60456 }


	iqudc32TeletextSMPTE20312031DataUnitIDP60457 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch1- SMPTE 2031
					2031 Data Unit ID P  cmdID= 60457 
					0x03 EBU Teletext S  value= 0  
					0x02 EBU Teletext N  value= 1  
					0xC0 Inverted Telet  value= 2  "
		::= { iqudc32CmdEntry 60457 }


	iqudc32TeletextSMPTE20312031DataUnitIDP60458 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch1- SMPTE 2031
					2031 Data Unit ID P  cmdID= 60458 
					0x03 EBU Teletext S  value= 0  
					0x02 EBU Teletext N  value= 1  
					0xC0 Inverted Telet  value= 2  "
		::= { iqudc32CmdEntry 60458 }


	iqudc32TeletextSMPTE20312031DataUnitIDP60459 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch1- SMPTE 2031
					2031 Data Unit ID P  cmdID= 60459 
					0x03 EBU Teletext S  value= 0  
					0x02 EBU Teletext N  value= 1  
					0xC0 Inverted Telet  value= 2  "
		::= { iqudc32CmdEntry 60459 }


	iqudc32TeletextSMPTE20312031DataUnitIDP60460 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch1- SMPTE 2031
					2031 Data Unit ID P  cmdID= 60460 
					0x03 EBU Teletext S  value= 0  
					0x02 EBU Teletext N  value= 1  
					0xC0 Inverted Telet  value= 2  "
		::= { iqudc32CmdEntry 60460 }


	iqudc32TeletextSMPTE20312031DataUnitIDP60461 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch1- SMPTE 2031
					2031 Data Unit ID P  cmdID= 60461 
					0x03 EBU Teletext S  value= 0  
					0x02 EBU Teletext N  value= 1  
					0xC0 Inverted Telet  value= 2  "
		::= { iqudc32CmdEntry 60461 }


	iqudc32TeletextSMPTE20312031OutputLineAl60462 OBJECT-TYPE
		SYNTAX		INTEGER
		MAX-ACCESS		read-write
		STATUS			current
		DESCRIPTION
				"TYPE: - Number
				 PAGE: - Metadata-Ch1- SMPTE 2031
					2031 Output Line Al  cmdID= 60462  min= 8  max= 20  step= 1  format= %0.0f  div_scale= 1 
					Min = 8  Max = 20  Step = 1 "
		::= { iqudc32CmdEntry 60462 }


	iqudc32TeletextSMPTE20312031OutputLineAl60463 OBJECT-TYPE
		SYNTAX		RollCallString
		MAX-ACCESS		read-only
		STATUS			current
		DESCRIPTION
				"TYPE: - Display
				 PAGE: - Metadata-Ch1- SMPTE 2031
					2031 Output Line Al  cmdID= 60463  format=   "
		::= { iqudc32CmdEntry 60463 }


	iqudc32MetadataCh1TeletextNewDisplay OBJECT-TYPE
		SYNTAX		RollCallString
		MAX-ACCESS		read-only
		STATUS			current
		DESCRIPTION
				"TYPE: - Display
				 PAGE: - Metadata-Ch1
					New Display  cmdID= 44466  format=   "
		::= { iqudc32CmdEntry 44466 }


	iqudc32MetadataCh2ClosedCaptionsInputStatus OBJECT-TYPE
		SYNTAX		RollCallString
		MAX-ACCESS		read-only
		STATUS			current
		DESCRIPTION
				"TYPE: - Display
				 PAGE: - Metadata-Ch2
					Input Status  cmdID= 60308  format=   "
		::= { iqudc32CmdEntry 60308 }


	iqudc32MetadataCh2ClosedCaptionsCEA608OutputEnab OBJECT-TYPE
		SYNTAX		INTEGER { disable(0), enable(1) }
		MAX-ACCESS		read-write
		STATUS			current
		DESCRIPTION
				"TYPE: - Checkbox
				 PAGE: - Metadata-Ch2
					CEA-608 Output Enab  cmdID= 60300 "
		::= { iqudc32CmdEntry 60300 }


	iqudc32MetadataCh2ClosedCaptionsCEA708OutputEnab OBJECT-TYPE
		SYNTAX		INTEGER { disable(0), enable(1) }
		MAX-ACCESS		read-write
		STATUS			current
		DESCRIPTION
				"TYPE: - Checkbox
				 PAGE: - Metadata-Ch2
					CEA-708 Output Enab  cmdID= 60301 "
		::= { iqudc32CmdEntry 60301 }


	iqudc32MetadataCh2ClosedCaptionsCEA708OutputLine60302 OBJECT-TYPE
		SYNTAX		INTEGER
		MAX-ACCESS		read-write
		STATUS			current
		DESCRIPTION
				"TYPE: - Number
				 PAGE: - Metadata-Ch2
					CEA-708 Output Line  cmdID= 60302  min= 8  max= 20  step= 1  format= %0.0f  div_scale= 1 
					Min = 8  Max = 20  Step = 1 "
		::= { iqudc32CmdEntry 60302 }


	iqudc32MetadataCh2ClosedCaptionsCEA708OutputLine60222 OBJECT-TYPE
		SYNTAX		RollCallString
		MAX-ACCESS		read-only
		STATUS			current
		DESCRIPTION
				"TYPE: - Display
				 PAGE: - Metadata-Ch2
					CEA-708 Output Line  cmdID= 60222  format=   "
		::= { iqudc32CmdEntry 60222 }


	iqudc32MetadataCh2Teletext625CaptionsSource OBJECT-TYPE
		SYNTAX		INTEGER {
							val-WST(0),
							val-CEA-608(1)
							}
		MAX-ACCESS		read-write
		STATUS			current
		DESCRIPTION
				"TYPE: - RadiobuttonList
				 PAGE: - Metadata-Ch2
					625 Captions Source  cmdID= 60671 
					WST  value= 0  
					CEA-608  value= 1  "
		::= { iqudc32CmdEntry 60671 }


	iqudc32TeletextSDVBISetupWSTOriginLine760600 OBJECT-TYPE
		SYNTAX		INTEGER { disable(0), enable(1) }
		MAX-ACCESS		read-write
		STATUS			current
		DESCRIPTION
				"TYPE: - Checkbox
				 PAGE: - Metadata-Ch2
					WST Origin Line 7  cmdID= 60600 "
		::= { iqudc32CmdEntry 60600 }


	iqudc32TeletextSDVBISetupWSTOriginLine860601 OBJECT-TYPE
		SYNTAX		INTEGER { disable(0), enable(1) }
		MAX-ACCESS		read-write
		STATUS			current
		DESCRIPTION
				"TYPE: - Checkbox
				 PAGE: - Metadata-Ch2
					WST Origin Line 8  cmdID= 60601 "
		::= { iqudc32CmdEntry 60601 }


	iqudc32TeletextSDVBISetupWSTOriginLine960602 OBJECT-TYPE
		SYNTAX		INTEGER { disable(0), enable(1) }
		MAX-ACCESS		read-write
		STATUS			current
		DESCRIPTION
				"TYPE: - Checkbox
				 PAGE: - Metadata-Ch2
					WST Origin Line 9  cmdID= 60602 "
		::= { iqudc32CmdEntry 60602 }


	iqudc32TeletextSDVBISetupWSTOriginLine1060603 OBJECT-TYPE
		SYNTAX		INTEGER { disable(0), enable(1) }
		MAX-ACCESS		read-write
		STATUS			current
		DESCRIPTION
				"TYPE: - Checkbox
				 PAGE: - Metadata-Ch2
					WST Origin Line 10  cmdID= 60603 "
		::= { iqudc32CmdEntry 60603 }


	iqudc32TeletextSDVBISetupWSTOriginLine1160604 OBJECT-TYPE
		SYNTAX		INTEGER { disable(0), enable(1) }
		MAX-ACCESS		read-write
		STATUS			current
		DESCRIPTION
				"TYPE: - Checkbox
				 PAGE: - Metadata-Ch2
					WST Origin Line 11  cmdID= 60604 "
		::= { iqudc32CmdEntry 60604 }


	iqudc32TeletextSDVBISetupWSTOriginLine1260605 OBJECT-TYPE
		SYNTAX		INTEGER { disable(0), enable(1) }
		MAX-ACCESS		read-write
		STATUS			current
		DESCRIPTION
				"TYPE: - Checkbox
				 PAGE: - Metadata-Ch2
					WST Origin Line 12  cmdID= 60605 "
		::= { iqudc32CmdEntry 60605 }


	iqudc32TeletextSDVBISetupWSTOriginLine1360606 OBJECT-TYPE
		SYNTAX		INTEGER { disable(0), enable(1) }
		MAX-ACCESS		read-write
		STATUS			current
		DESCRIPTION
				"TYPE: - Checkbox
				 PAGE: - Metadata-Ch2
					WST Origin Line 13  cmdID= 60606 "
		::= { iqudc32CmdEntry 60606 }


	iqudc32TeletextSDVBISetupWSTOriginLine1460607 OBJECT-TYPE
		SYNTAX		INTEGER { disable(0), enable(1) }
		MAX-ACCESS		read-write
		STATUS			current
		DESCRIPTION
				"TYPE: - Checkbox
				 PAGE: - Metadata-Ch2
					WST Origin Line 14  cmdID= 60607 "
		::= { iqudc32CmdEntry 60607 }


	iqudc32TeletextSDVBISetupWSTOriginLine1560608 OBJECT-TYPE
		SYNTAX		INTEGER { disable(0), enable(1) }
		MAX-ACCESS		read-write
		STATUS			current
		DESCRIPTION
				"TYPE: - Checkbox
				 PAGE: - Metadata-Ch2
					WST Origin Line 15  cmdID= 60608 "
		::= { iqudc32CmdEntry 60608 }


	iqudc32TeletextSDVBISetupWSTOriginLine1660609 OBJECT-TYPE
		SYNTAX		INTEGER { disable(0), enable(1) }
		MAX-ACCESS		read-write
		STATUS			current
		DESCRIPTION
				"TYPE: - Checkbox
				 PAGE: - Metadata-Ch2
					WST Origin Line 16  cmdID= 60609 "
		::= { iqudc32CmdEntry 60609 }


	iqudc32TeletextSDVBISetupWSTOriginLine1760610 OBJECT-TYPE
		SYNTAX		INTEGER { disable(0), enable(1) }
		MAX-ACCESS		read-write
		STATUS			current
		DESCRIPTION
				"TYPE: - Checkbox
				 PAGE: - Metadata-Ch2
					WST Origin Line 17  cmdID= 60610 "
		::= { iqudc32CmdEntry 60610 }


	iqudc32TeletextSDVBISetupWSTOriginLine1860611 OBJECT-TYPE
		SYNTAX		INTEGER { disable(0), enable(1) }
		MAX-ACCESS		read-write
		STATUS			current
		DESCRIPTION
				"TYPE: - Checkbox
				 PAGE: - Metadata-Ch2
					WST Origin Line 18  cmdID= 60611 "
		::= { iqudc32CmdEntry 60611 }


	iqudc32TeletextSDVBISetupWSTOriginLine1960612 OBJECT-TYPE
		SYNTAX		INTEGER { disable(0), enable(1) }
		MAX-ACCESS		read-write
		STATUS			current
		DESCRIPTION
				"TYPE: - Checkbox
				 PAGE: - Metadata-Ch2
					WST Origin Line 19  cmdID= 60612 "
		::= { iqudc32CmdEntry 60612 }


	iqudc32TeletextSDVBISetupWSTOriginLine2060613 OBJECT-TYPE
		SYNTAX		INTEGER { disable(0), enable(1) }
		MAX-ACCESS		read-write
		STATUS			current
		DESCRIPTION
				"TYPE: - Checkbox
				 PAGE: - Metadata-Ch2
					WST Origin Line 20  cmdID= 60613 "
		::= { iqudc32CmdEntry 60613 }


	iqudc32TeletextSDVBISetupWSTOriginLine2160614 OBJECT-TYPE
		SYNTAX		INTEGER { disable(0), enable(1) }
		MAX-ACCESS		read-write
		STATUS			current
		DESCRIPTION
				"TYPE: - Checkbox
				 PAGE: - Metadata-Ch2
					WST Origin Line 21  cmdID= 60614 "
		::= { iqudc32CmdEntry 60614 }


	iqudc32TeletextSDVBISetupWSTOriginLine2260615 OBJECT-TYPE
		SYNTAX		INTEGER { disable(0), enable(1) }
		MAX-ACCESS		read-write
		STATUS			current
		DESCRIPTION
				"TYPE: - Checkbox
				 PAGE: - Metadata-Ch2
					WST Origin Line 22  cmdID= 60615 "
		::= { iqudc32CmdEntry 60615 }


	iqudc32TeletextSDVBISetupWSTOriginLine7S60616 OBJECT-TYPE
		SYNTAX		RollCallString
		MAX-ACCESS		read-only
		STATUS			current
		DESCRIPTION
				"TYPE: - Display
				 PAGE: - Metadata-Ch2
					WST Origin Line 7 S  cmdID= 60616  format=   "
		::= { iqudc32CmdEntry 60616 }


	iqudc32TeletextSDVBISetupWSTOriginLine8S60617 OBJECT-TYPE
		SYNTAX		RollCallString
		MAX-ACCESS		read-only
		STATUS			current
		DESCRIPTION
				"TYPE: - Display
				 PAGE: - Metadata-Ch2
					WST Origin Line 8 S  cmdID= 60617  format=   "
		::= { iqudc32CmdEntry 60617 }


	iqudc32TeletextSDVBISetupWSTOriginLine9S60618 OBJECT-TYPE
		SYNTAX		RollCallString
		MAX-ACCESS		read-only
		STATUS			current
		DESCRIPTION
				"TYPE: - Display
				 PAGE: - Metadata-Ch2
					WST Origin Line 9 S  cmdID= 60618  format=   "
		::= { iqudc32CmdEntry 60618 }


	iqudc32TeletextSDVBISetupWSTOriginLine1060619 OBJECT-TYPE
		SYNTAX		RollCallString
		MAX-ACCESS		read-only
		STATUS			current
		DESCRIPTION
				"TYPE: - Display
				 PAGE: - Metadata-Ch2
					WST Origin Line 10   cmdID= 60619  format=   "
		::= { iqudc32CmdEntry 60619 }


	iqudc32TeletextSDVBISetupWSTOriginLine1160620 OBJECT-TYPE
		SYNTAX		RollCallString
		MAX-ACCESS		read-only
		STATUS			current
		DESCRIPTION
				"TYPE: - Display
				 PAGE: - Metadata-Ch2
					WST Origin Line 11   cmdID= 60620  format=   "
		::= { iqudc32CmdEntry 60620 }


	iqudc32TeletextSDVBISetupWSTOriginLine1260621 OBJECT-TYPE
		SYNTAX		RollCallString
		MAX-ACCESS		read-only
		STATUS			current
		DESCRIPTION
				"TYPE: - Display
				 PAGE: - Metadata-Ch2
					WST Origin Line 12   cmdID= 60621  format=   "
		::= { iqudc32CmdEntry 60621 }


	iqudc32TeletextSDVBISetupWSTOriginLine1360622 OBJECT-TYPE
		SYNTAX		RollCallString
		MAX-ACCESS		read-only
		STATUS			current
		DESCRIPTION
				"TYPE: - Display
				 PAGE: - Metadata-Ch2
					WST Origin Line 13   cmdID= 60622  format=   "
		::= { iqudc32CmdEntry 60622 }


	iqudc32TeletextSDVBISetupWSTOriginLine1460623 OBJECT-TYPE
		SYNTAX		RollCallString
		MAX-ACCESS		read-only
		STATUS			current
		DESCRIPTION
				"TYPE: - Display
				 PAGE: - Metadata-Ch2
					WST Origin Line 14   cmdID= 60623  format=   "
		::= { iqudc32CmdEntry 60623 }


	iqudc32TeletextSDVBISetupWSTOriginLine1560624 OBJECT-TYPE
		SYNTAX		RollCallString
		MAX-ACCESS		read-only
		STATUS			current
		DESCRIPTION
				"TYPE: - Display
				 PAGE: - Metadata-Ch2
					WST Origin Line 15   cmdID= 60624  format=   "
		::= { iqudc32CmdEntry 60624 }


	iqudc32TeletextSDVBISetupWSTOriginLine1660625 OBJECT-TYPE
		SYNTAX		RollCallString
		MAX-ACCESS		read-only
		STATUS			current
		DESCRIPTION
				"TYPE: - Display
				 PAGE: - Metadata-Ch2
					WST Origin Line 16   cmdID= 60625  format=   "
		::= { iqudc32CmdEntry 60625 }


	iqudc32TeletextSDVBISetupWSTOriginLine1760626 OBJECT-TYPE
		SYNTAX		RollCallString
		MAX-ACCESS		read-only
		STATUS			current
		DESCRIPTION
				"TYPE: - Display
				 PAGE: - Metadata-Ch2
					WST Origin Line 17   cmdID= 60626  format=   "
		::= { iqudc32CmdEntry 60626 }


	iqudc32TeletextSDVBISetupWSTOriginLine1860627 OBJECT-TYPE
		SYNTAX		RollCallString
		MAX-ACCESS		read-only
		STATUS			current
		DESCRIPTION
				"TYPE: - Display
				 PAGE: - Metadata-Ch2
					WST Origin Line 18   cmdID= 60627  format=   "
		::= { iqudc32CmdEntry 60627 }


	iqudc32TeletextSDVBISetupWSTOriginLine1960628 OBJECT-TYPE
		SYNTAX		RollCallString
		MAX-ACCESS		read-only
		STATUS			current
		DESCRIPTION
				"TYPE: - Display
				 PAGE: - Metadata-Ch2
					WST Origin Line 19   cmdID= 60628  format=   "
		::= { iqudc32CmdEntry 60628 }


	iqudc32TeletextSDVBISetupWSTOriginLine2060629 OBJECT-TYPE
		SYNTAX		RollCallString
		MAX-ACCESS		read-only
		STATUS			current
		DESCRIPTION
				"TYPE: - Display
				 PAGE: - Metadata-Ch2
					WST Origin Line 20   cmdID= 60629  format=   "
		::= { iqudc32CmdEntry 60629 }


	iqudc32TeletextSDVBISetupWSTOriginLine2160630 OBJECT-TYPE
		SYNTAX		RollCallString
		MAX-ACCESS		read-only
		STATUS			current
		DESCRIPTION
				"TYPE: - Display
				 PAGE: - Metadata-Ch2
					WST Origin Line 21   cmdID= 60630  format=   "
		::= { iqudc32CmdEntry 60630 }


	iqudc32TeletextSDVBISetupWSTOriginLine2260631 OBJECT-TYPE
		SYNTAX		RollCallString
		MAX-ACCESS		read-only
		STATUS			current
		DESCRIPTION
				"TYPE: - Display
				 PAGE: - Metadata-Ch2
					WST Origin Line 22   cmdID= 60631  format=   "
		::= { iqudc32CmdEntry 60631 }


	iqudc32TeletextSDVBISetupWSTOPLine7Statu60632 OBJECT-TYPE
		SYNTAX		RollCallString
		MAX-ACCESS		read-only
		STATUS			current
		DESCRIPTION
				"TYPE: - Display
				 PAGE: - Metadata-Ch2
					WST OP Line 7 Statu  cmdID= 60632  format=   "
		::= { iqudc32CmdEntry 60632 }


	iqudc32TeletextSDVBISetupWSTOPLine8Statu60633 OBJECT-TYPE
		SYNTAX		RollCallString
		MAX-ACCESS		read-only
		STATUS			current
		DESCRIPTION
				"TYPE: - Display
				 PAGE: - Metadata-Ch2
					WST OP Line 8 Statu  cmdID= 60633  format=   "
		::= { iqudc32CmdEntry 60633 }


	iqudc32TeletextSDVBISetupWSTOPLine9Statu60634 OBJECT-TYPE
		SYNTAX		RollCallString
		MAX-ACCESS		read-only
		STATUS			current
		DESCRIPTION
				"TYPE: - Display
				 PAGE: - Metadata-Ch2
					WST OP Line 9 Statu  cmdID= 60634  format=   "
		::= { iqudc32CmdEntry 60634 }


	iqudc32TeletextSDVBISetupWSTOPLine10Stat60635 OBJECT-TYPE
		SYNTAX		RollCallString
		MAX-ACCESS		read-only
		STATUS			current
		DESCRIPTION
				"TYPE: - Display
				 PAGE: - Metadata-Ch2
					WST OP Line 10 Stat  cmdID= 60635  format=   "
		::= { iqudc32CmdEntry 60635 }


	iqudc32TeletextSDVBISetupWSTOPLine11Stat60636 OBJECT-TYPE
		SYNTAX		RollCallString
		MAX-ACCESS		read-only
		STATUS			current
		DESCRIPTION
				"TYPE: - Display
				 PAGE: - Metadata-Ch2
					WST OP Line 11 Stat  cmdID= 60636  format=   "
		::= { iqudc32CmdEntry 60636 }


	iqudc32TeletextSDVBISetupWSTOPLine12Stat60637 OBJECT-TYPE
		SYNTAX		RollCallString
		MAX-ACCESS		read-only
		STATUS			current
		DESCRIPTION
				"TYPE: - Display
				 PAGE: - Metadata-Ch2
					WST OP Line 12 Stat  cmdID= 60637  format=   "
		::= { iqudc32CmdEntry 60637 }


	iqudc32TeletextSDVBISetupWSTOPLine13Stat60638 OBJECT-TYPE
		SYNTAX		RollCallString
		MAX-ACCESS		read-only
		STATUS			current
		DESCRIPTION
				"TYPE: - Display
				 PAGE: - Metadata-Ch2
					WST OP Line 13 Stat  cmdID= 60638  format=   "
		::= { iqudc32CmdEntry 60638 }


	iqudc32TeletextSDVBISetupWSTOPLine14Stat60639 OBJECT-TYPE
		SYNTAX		RollCallString
		MAX-ACCESS		read-only
		STATUS			current
		DESCRIPTION
				"TYPE: - Display
				 PAGE: - Metadata-Ch2
					WST OP Line 14 Stat  cmdID= 60639  format=   "
		::= { iqudc32CmdEntry 60639 }


	iqudc32TeletextSDVBISetupWSTOPLine15Stat60640 OBJECT-TYPE
		SYNTAX		RollCallString
		MAX-ACCESS		read-only
		STATUS			current
		DESCRIPTION
				"TYPE: - Display
				 PAGE: - Metadata-Ch2
					WST OP Line 15 Stat  cmdID= 60640  format=   "
		::= { iqudc32CmdEntry 60640 }


	iqudc32TeletextSDVBISetupWSTOPLine16Stat60641 OBJECT-TYPE
		SYNTAX		RollCallString
		MAX-ACCESS		read-only
		STATUS			current
		DESCRIPTION
				"TYPE: - Display
				 PAGE: - Metadata-Ch2
					WST OP Line 16 Stat  cmdID= 60641  format=   "
		::= { iqudc32CmdEntry 60641 }


	iqudc32TeletextSDVBISetupWSTOPLine17Stat60642 OBJECT-TYPE
		SYNTAX		RollCallString
		MAX-ACCESS		read-only
		STATUS			current
		DESCRIPTION
				"TYPE: - Display
				 PAGE: - Metadata-Ch2
					WST OP Line 17 Stat  cmdID= 60642  format=   "
		::= { iqudc32CmdEntry 60642 }


	iqudc32TeletextSDVBISetupWSTOPLine18Stat60643 OBJECT-TYPE
		SYNTAX		RollCallString
		MAX-ACCESS		read-only
		STATUS			current
		DESCRIPTION
				"TYPE: - Display
				 PAGE: - Metadata-Ch2
					WST OP Line 18 Stat  cmdID= 60643  format=   "
		::= { iqudc32CmdEntry 60643 }


	iqudc32TeletextSDVBISetupWSTOPLine19Stat60644 OBJECT-TYPE
		SYNTAX		RollCallString
		MAX-ACCESS		read-only
		STATUS			current
		DESCRIPTION
				"TYPE: - Display
				 PAGE: - Metadata-Ch2
					WST OP Line 19 Stat  cmdID= 60644  format=   "
		::= { iqudc32CmdEntry 60644 }


	iqudc32TeletextSDVBISetupWSTOPLine20Stat60645 OBJECT-TYPE
		SYNTAX		RollCallString
		MAX-ACCESS		read-only
		STATUS			current
		DESCRIPTION
				"TYPE: - Display
				 PAGE: - Metadata-Ch2
					WST OP Line 20 Stat  cmdID= 60645  format=   "
		::= { iqudc32CmdEntry 60645 }


	iqudc32TeletextSDVBISetupWSTOPLine21Stat60646 OBJECT-TYPE
		SYNTAX		RollCallString
		MAX-ACCESS		read-only
		STATUS			current
		DESCRIPTION
				"TYPE: - Display
				 PAGE: - Metadata-Ch2
					WST OP Line 21 Stat  cmdID= 60646  format=   "
		::= { iqudc32CmdEntry 60646 }


	iqudc32TeletextSDVBISetupWSTOPLine22Stat60647 OBJECT-TYPE
		SYNTAX		RollCallString
		MAX-ACCESS		read-only
		STATUS			current
		DESCRIPTION
				"TYPE: - Display
				 PAGE: - Metadata-Ch2
					WST OP Line 22 Stat  cmdID= 60647  format=   "
		::= { iqudc32CmdEntry 60647 }


	iqudc32TeletextSDVBISetupAllowWSTRemap60666 OBJECT-TYPE
		SYNTAX		INTEGER { disable(0), enable(1) }
		MAX-ACCESS		read-write
		STATUS			current
		DESCRIPTION
				"TYPE: - Checkbox
				 PAGE: - Metadata-Ch2
					Allow WST Remap  cmdID= 60666 "
		::= { iqudc32CmdEntry 60666 }


	iqudc32TeletextSDVBISetupWSTOriginLine60667 OBJECT-TYPE
		SYNTAX		INTEGER
		MAX-ACCESS		read-write
		STATUS			current
		DESCRIPTION
				"TYPE: - Number
				 PAGE: - Metadata-Ch2
					WST Origin Line  cmdID= 60667  min= 7  max= 22  step= 1  format= %0.0f  div_scale= 1 
					Min = 7  Max = 22  Step = 1 "
		::= { iqudc32CmdEntry 60667 }


	iqudc32TeletextSDVBISetupWSTOriginLineSta60668 OBJECT-TYPE
		SYNTAX		RollCallString
		MAX-ACCESS		read-only
		STATUS			current
		DESCRIPTION
				"TYPE: - Display
				 PAGE: - Metadata-Ch2
					WST Origin Line Sta  cmdID= 60668  format=   "
		::= { iqudc32CmdEntry 60668 }


	iqudc32TeletextSDVBISetupWSTOutputLine60669 OBJECT-TYPE
		SYNTAX		INTEGER
		MAX-ACCESS		read-write
		STATUS			current
		DESCRIPTION
				"TYPE: - Number
				 PAGE: - Metadata-Ch2
					WST Output Line  cmdID= 60669  min= 7  max= 22  step= 1  format= %0.0f  div_scale= 1 
					Min = 7  Max = 22  Step = 1 "
		::= { iqudc32CmdEntry 60669 }


	iqudc32TeletextSDVBISetupWSTOutputLineSta60670 OBJECT-TYPE
		SYNTAX		RollCallString
		MAX-ACCESS		read-only
		STATUS			current
		DESCRIPTION
				"TYPE: - Display
				 PAGE: - Metadata-Ch2
					WST Output Line Sta  cmdID= 60670  format=   "
		::= { iqudc32CmdEntry 60670 }


	iqudc32TeletextSMPTERDD8SMPTERDD82031InputP60648 OBJECT-TYPE
		SYNTAX		INTEGER {
							val-SMPTE-RDD8(0),
							val-SMPTE-2031(1)
							}
		MAX-ACCESS		read-write
		STATUS			current
		DESCRIPTION
				"TYPE: - RadiobuttonList
				 PAGE: - Metadata-Ch2
					RDD8 / 2031 Input P  cmdID= 60648 
					SMPTE RDD8  value= 0  
					SMPTE 2031  value= 1  "
		::= { iqudc32CmdEntry 60648 }


	iqudc32TeletextSMPTERDD8SMPTERDD82031Output60649 OBJECT-TYPE
		SYNTAX		INTEGER { disable(0), enable(1) }
		MAX-ACCESS		read-write
		STATUS			current
		DESCRIPTION
				"TYPE: - Checkbox
				 PAGE: - Metadata-Ch2
					RDD8 / 2031 Output   cmdID= 60649 "
		::= { iqudc32CmdEntry 60649 }


	iqudc32TeletextSMPTERDD8SMPTERDD82031Output60650 OBJECT-TYPE
		SYNTAX		INTEGER {
							val-SMPTE-RDD8(0),
							val-SMPTE-2031(1)
							}
		MAX-ACCESS		read-write
		STATUS			current
		DESCRIPTION
				"TYPE: - RadiobuttonList
				 PAGE: - Metadata-Ch2
					RDD8 / 2031 Output   cmdID= 60650 
					SMPTE RDD8  value= 0  
					SMPTE 2031  value= 1  "
		::= { iqudc32CmdEntry 60650 }


	iqudc32TeletextSMPTERDD8RDD8OutputLinePK60651 OBJECT-TYPE
		SYNTAX		INTEGER
		MAX-ACCESS		read-write
		STATUS			current
		DESCRIPTION
				"TYPE: - Number
				 PAGE: - Metadata-Ch2- SMPTE RDD8
					RDD8 Output Line PK  cmdID= 60651  min= 8  max= 20  step= 1  format= %0.0f  div_scale= 1 
					Min = 8  Max = 20  Step = 1 "
		::= { iqudc32CmdEntry 60651 }


	iqudc32TeletextSMPTERDD8RDD8OutputLinePK60652 OBJECT-TYPE
		SYNTAX		INTEGER
		MAX-ACCESS		read-write
		STATUS			current
		DESCRIPTION
				"TYPE: - Number
				 PAGE: - Metadata-Ch2- SMPTE RDD8
					RDD8 Output Line PK  cmdID= 60652  min= 8  max= 20  step= 1  format= %0.0f  div_scale= 1 
					Min = 8  Max = 20  Step = 1 "
		::= { iqudc32CmdEntry 60652 }


	iqudc32TeletextSMPTERDD8RDD8OutputLinePK60653 OBJECT-TYPE
		SYNTAX		INTEGER
		MAX-ACCESS		read-write
		STATUS			current
		DESCRIPTION
				"TYPE: - Number
				 PAGE: - Metadata-Ch2- SMPTE RDD8
					RDD8 Output Line PK  cmdID= 60653  min= 8  max= 20  step= 1  format= %0.0f  div_scale= 1 
					Min = 8  Max = 20  Step = 1 "
		::= { iqudc32CmdEntry 60653 }


	iqudc32TeletextSMPTERDD8RDD8OutputLinePK60654 OBJECT-TYPE
		SYNTAX		RollCallString
		MAX-ACCESS		read-only
		STATUS			current
		DESCRIPTION
				"TYPE: - Display
				 PAGE: - Metadata-Ch2- SMPTE RDD8
					RDD8 Output Line PK  cmdID= 60654  format=   "
		::= { iqudc32CmdEntry 60654 }


	iqudc32TeletextSMPTERDD8RDD8OutputLinePK60655 OBJECT-TYPE
		SYNTAX		RollCallString
		MAX-ACCESS		read-only
		STATUS			current
		DESCRIPTION
				"TYPE: - Display
				 PAGE: - Metadata-Ch2- SMPTE RDD8
					RDD8 Output Line PK  cmdID= 60655  format=   "
		::= { iqudc32CmdEntry 60655 }


	iqudc32TeletextSMPTERDD8RDD8OutputLinePK60656 OBJECT-TYPE
		SYNTAX		RollCallString
		MAX-ACCESS		read-only
		STATUS			current
		DESCRIPTION
				"TYPE: - Display
				 PAGE: - Metadata-Ch2- SMPTE RDD8
					RDD8 Output Line PK  cmdID= 60656  format=   "
		::= { iqudc32CmdEntry 60656 }


	iqudc32TeletextSMPTE20312031DataUnitIDP60657 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch2- SMPTE 2031
					2031 Data Unit ID P  cmdID= 60657 
					0x03 EBU Teletext S  value= 0  
					0x02 EBU Teletext N  value= 1  
					0xC0 Inverted Telet  value= 2  "
		::= { iqudc32CmdEntry 60657 }


	iqudc32TeletextSMPTE20312031DataUnitIDP60658 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch2- SMPTE 2031
					2031 Data Unit ID P  cmdID= 60658 
					0x03 EBU Teletext S  value= 0  
					0x02 EBU Teletext N  value= 1  
					0xC0 Inverted Telet  value= 2  "
		::= { iqudc32CmdEntry 60658 }


	iqudc32TeletextSMPTE20312031DataUnitIDP60659 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch2- SMPTE 2031
					2031 Data Unit ID P  cmdID= 60659 
					0x03 EBU Teletext S  value= 0  
					0x02 EBU Teletext N  value= 1  
					0xC0 Inverted Telet  value= 2  "
		::= { iqudc32CmdEntry 60659 }


	iqudc32TeletextSMPTE20312031DataUnitIDP60660 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch2- SMPTE 2031
					2031 Data Unit ID P  cmdID= 60660 
					0x03 EBU Teletext S  value= 0  
					0x02 EBU Teletext N  value= 1  
					0xC0 Inverted Telet  value= 2  "
		::= { iqudc32CmdEntry 60660 }


	iqudc32TeletextSMPTE20312031DataUnitIDP60661 OBJECT-TYPE
		SYNTAX		INTEGER {
							val-0x03-EBU-Teletext-S(0),
							val-0x02-EBU-Teletext-N(1),
							val-0xC0-Inverted-Telet(2)
							}
		MAX-ACCESS		read-write
		STATUS			current
		DESCRIPTION
				"TYPE: - RadiobuttonList
				 PAGE: - Metadata-Ch2- SMPTE 2031
					2031 Data Unit ID P  cmdID= 60661 
					0x03 EBU Teletext S  value= 0  
					0x02 EBU Teletext N  value= 1  
					0xC0 Inverted Telet  value= 2  "
		::= { iqudc32CmdEntry 60661 }


	iqudc32TeletextSMPTE20312031OutputLineAl60662 OBJECT-TYPE
		SYNTAX		INTEGER
		MAX-ACCESS		read-write
		STATUS			current
		DESCRIPTION
				"TYPE: - Number
				 PAGE: - Metadata-Ch2- SMPTE 2031
					2031 Output Line Al  cmdID= 60662  min= 8  max= 20  step= 1  format= %0.0f  div_scale= 1 
					Min = 8  Max = 20  Step = 1 "
		::= { iqudc32CmdEntry 60662 }


	iqudc32TeletextSMPTE20312031OutputLineAl60663 OBJECT-TYPE
		SYNTAX		RollCallString
		MAX-ACCESS		read-only
		STATUS			current
		DESCRIPTION
				"TYPE: - Display
				 PAGE: - Metadata-Ch2- SMPTE 2031
					2031 Output Line Al  cmdID= 60663  format=   "
		::= { iqudc32CmdEntry 60663 }


	iqudc32MetadataCh2TeletextNewDisplay OBJECT-TYPE
		SYNTAX		RollCallString
		MAX-ACCESS		read-only
		STATUS			current
		DESCRIPTION
				"TYPE: - Display
				 PAGE: - Metadata-Ch2
					New Display  cmdID= 44452  format=   "
		::= { iqudc32CmdEntry 44452 }


	iqudc32AncillaryBridgeChAncDataStoresIPBlock1DID60472 OBJECT-TYPE
		SYNTAX		INTEGER
		MAX-ACCESS		read-write
		STATUS			current
		DESCRIPTION
				"TYPE: - Number
				 PAGE: - Ancillary Bridge-Ch- Anc Data Stores IP 
					Block 1 DID  cmdID= 60472  min= 0  max= 255  step= 1  format= %0.0f  div_scale= 1 
					Min = 0  Max = 255  Step = 1 "
		::= { iqudc32CmdEntry 60472 }


	iqudc32AncillaryBridgeChAncDataStoresIPBlock1SDID60473 OBJECT-TYPE
		SYNTAX		INTEGER
		MAX-ACCESS		read-write
		STATUS			current
		DESCRIPTION
				"TYPE: - Number
				 PAGE: - Ancillary Bridge-Ch- Anc Data Stores IP 
					Block 1 SDID  cmdID= 60473  min= 0  max= 255  step= 1  format= %0.0f  div_scale= 1 
					Min = 0  Max = 255  Step = 1 "
		::= { iqudc32CmdEntry 60473 }


	iqudc32AncillaryBridgeChAncDataStoresIPBlock2DID60474 OBJECT-TYPE
		SYNTAX		INTEGER
		MAX-ACCESS		read-write
		STATUS			current
		DESCRIPTION
				"TYPE: - Number
				 PAGE: - Ancillary Bridge-Ch- Anc Data Stores IP 
					Block 2 DID  cmdID= 60474  min= 0  max= 255  step= 1  format= %0.0f  div_scale= 1 
					Min = 0  Max = 255  Step = 1 "
		::= { iqudc32CmdEntry 60474 }


	iqudc32AncillaryBridgeChAncDataStoresIPBlock2SDID60475 OBJECT-TYPE
		SYNTAX		INTEGER
		MAX-ACCESS		read-write
		STATUS			current
		DESCRIPTION
				"TYPE: - Number
				 PAGE: - Ancillary Bridge-Ch- Anc Data Stores IP 
					Block 2 SDID  cmdID= 60475  min= 0  max= 255  step= 1  format= %0.0f  div_scale= 1 
					Min = 0  Max = 255  Step = 1 "
		::= { iqudc32CmdEntry 60475 }


	iqudc32AncillaryBridgeChAncDataStoresIPBlock3DID60476 OBJECT-TYPE
		SYNTAX		INTEGER
		MAX-ACCESS		read-write
		STATUS			current
		DESCRIPTION
				"TYPE: - Number
				 PAGE: - Ancillary Bridge-Ch- Anc Data Stores IP 
					Block 3 DID  cmdID= 60476  min= 0  max= 255  step= 1  format= %0.0f  div_scale= 1 
					Min = 0  Max = 255  Step = 1 "
		::= { iqudc32CmdEntry 60476 }


	iqudc32AncillaryBridgeChAncDataStoresIPBlock3SDID60477 OBJECT-TYPE
		SYNTAX		INTEGER
		MAX-ACCESS		read-write
		STATUS			current
		DESCRIPTION
				"TYPE: - Number
				 PAGE: - Ancillary Bridge-Ch- Anc Data Stores IP 
					Block 3 SDID  cmdID= 60477  min= 0  max= 255  step= 1  format= %0.0f  div_scale= 1 
					Min = 0  Max = 255  Step = 1 "
		::= { iqudc32CmdEntry 60477 }


	iqudc32AncillaryBridgeChAncDataStoresIPBlock4DID60478 OBJECT-TYPE
		SYNTAX		INTEGER
		MAX-ACCESS		read-write
		STATUS			current
		DESCRIPTION
				"TYPE: - Number
				 PAGE: - Ancillary Bridge-Ch- Anc Data Stores IP 
					Block 4 DID  cmdID= 60478  min= 0  max= 255  step= 1  format= %0.0f  div_scale= 1 
					Min = 0  Max = 255  Step = 1 "
		::= { iqudc32CmdEntry 60478 }


	iqudc32AncillaryBridgeChAncDataStoresIPBlock4SDID60479 OBJECT-TYPE
		SYNTAX		INTEGER
		MAX-ACCESS		read-write
		STATUS			current
		DESCRIPTION
				"TYPE: - Number
				 PAGE: - Ancillary Bridge-Ch- Anc Data Stores IP 
					Block 4 SDID  cmdID= 60479  min= 0  max= 255  step= 1  format= %0.0f  div_scale= 1 
					Min = 0  Max = 255  Step = 1 "
		::= { iqudc32CmdEntry 60479 }


	iqudc32AncillaryBridgeChAncDataStoresIPBlock5DID60480 OBJECT-TYPE
		SYNTAX		INTEGER
		MAX-ACCESS		read-write
		STATUS			current
		DESCRIPTION
				"TYPE: - Number
				 PAGE: - Ancillary Bridge-Ch- Anc Data Stores IP 
					Block 5 DID  cmdID= 60480  min= 0  max= 255  step= 1  format= %0.0f  div_scale= 1 
					Min = 0  Max = 255  Step = 1 "
		::= { iqudc32CmdEntry 60480 }


	iqudc32AncillaryBridgeChAncDataStoresIPBlock5SDID60481 OBJECT-TYPE
		SYNTAX		INTEGER
		MAX-ACCESS		read-write
		STATUS			current
		DESCRIPTION
				"TYPE: - Number
				 PAGE: - Ancillary Bridge-Ch- Anc Data Stores IP 
					Block 5 SDID  cmdID= 60481  min= 0  max= 255  step= 1  format= %0.0f  div_scale= 1 
					Min = 0  Max = 255  Step = 1 "
		::= { iqudc32CmdEntry 60481 }


	iqudc32AncillaryBridgeChAncDataStoresIPBlock6DID60482 OBJECT-TYPE
		SYNTAX		INTEGER
		MAX-ACCESS		read-write
		STATUS			current
		DESCRIPTION
				"TYPE: - Number
				 PAGE: - Ancillary Bridge-Ch- Anc Data Stores IP 
					Block 6 DID  cmdID= 60482  min= 0  max= 255  step= 1  format= %0.0f  div_scale= 1 
					Min = 0  Max = 255  Step = 1 "
		::= { iqudc32CmdEntry 60482 }


	iqudc32AncillaryBridgeChAncDataStoresIPBlock6SDID60483 OBJECT-TYPE
		SYNTAX		INTEGER
		MAX-ACCESS		read-write
		STATUS			current
		DESCRIPTION
				"TYPE: - Number
				 PAGE: - Ancillary Bridge-Ch- Anc Data Stores IP 
					Block 6 SDID  cmdID= 60483  min= 0  max= 255  step= 1  format= %0.0f  div_scale= 1 
					Min = 0  Max = 255  Step = 1 "
		::= { iqudc32CmdEntry 60483 }


	iqudc32AncillaryBridgeChAncDataStoresIPBlock7DID60484 OBJECT-TYPE
		SYNTAX		INTEGER
		MAX-ACCESS		read-write
		STATUS			current
		DESCRIPTION
				"TYPE: - Number
				 PAGE: - Ancillary Bridge-Ch- Anc Data Stores IP 
					Block 7 DID  cmdID= 60484  min= 0  max= 255  step= 1  format= %0.0f  div_scale= 1 
					Min = 0  Max = 255  Step = 1 "
		::= { iqudc32CmdEntry 60484 }


	iqudc32AncillaryBridgeChAncDataStoresIPBlock7SDID60485 OBJECT-TYPE
		SYNTAX		INTEGER
		MAX-ACCESS		read-write
		STATUS			current
		DESCRIPTION
				"TYPE: - Number
				 PAGE: - Ancillary Bridge-Ch- Anc Data Stores IP 
					Block 7 SDID  cmdID= 60485  min= 0  max= 255  step= 1  format= %0.0f  div_scale= 1 
					Min = 0  Max = 255  Step = 1 "
		::= { iqudc32CmdEntry 60485 }


	iqudc32AncillaryBridgeChAncDataStoresDetBlock1HANCVANC60486 OBJECT-TYPE
		SYNTAX		RollCallString
		MAX-ACCESS		read-only
		STATUS			current
		DESCRIPTION
				"TYPE: - Display
				 PAGE: - Ancillary Bridge-Ch- Anc Data Stores Det
					Block 1 HANC/VANC  cmdID= 60486  format=   "
		::= { iqudc32CmdEntry 60486 }


	iqudc32AncillaryBridgeChAncDataStoresDetBlock1Line60487 OBJECT-TYPE
		SYNTAX		RollCallString
		MAX-ACCESS		read-only
		STATUS			current
		DESCRIPTION
				"TYPE: - Display
				 PAGE: - Ancillary Bridge-Ch- Anc Data Stores Det
					Block 1 Line  cmdID= 60487  format=   "
		::= { iqudc32CmdEntry 60487 }


	iqudc32AncillaryBridgeChAncDataStoresDetBlock1Status60488 OBJECT-TYPE
		SYNTAX		RollCallString
		MAX-ACCESS		read-only
		STATUS			current
		DESCRIPTION
				"TYPE: - Display
				 PAGE: - Ancillary Bridge-Ch- Anc Data Stores Det
					Block 1 Status  cmdID= 60488  format=   "
		::= { iqudc32CmdEntry 60488 }


	iqudc32AncillaryBridgeChAncDataStoresDetBLOCK2HANCVANC60489 OBJECT-TYPE
		SYNTAX		RollCallString
		MAX-ACCESS		read-only
		STATUS			current
		DESCRIPTION
				"TYPE: - Display
				 PAGE: - Ancillary Bridge-Ch- Anc Data Stores Det
					BLOCK 2 HANC/VANC  cmdID= 60489  format=   "
		::= { iqudc32CmdEntry 60489 }


	iqudc32AncillaryBridgeChAncDataStoresDetBLOCK2Line60490 OBJECT-TYPE
		SYNTAX		RollCallString
		MAX-ACCESS		read-only
		STATUS			current
		DESCRIPTION
				"TYPE: - Display
				 PAGE: - Ancillary Bridge-Ch- Anc Data Stores Det
					BLOCK 2 Line  cmdID= 60490  format=   
					Block 4 Line  cmdID= 60490  format=   
					Block 5 Line  cmdID= 60490  format=   
					Block 6 Line  cmdID= 60490  format=   
					Block 7 Line  cmdID= 60490  format=   "
		::= { iqudc32CmdEntry 60490 }


	iqudc32AncillaryBridgeChAncDataStoresDetBLOCK2Status60491 OBJECT-TYPE
		SYNTAX		RollCallString
		MAX-ACCESS		read-only
		STATUS			current
		DESCRIPTION
				"TYPE: - Display
				 PAGE: - Ancillary Bridge-Ch- Anc Data Stores Det
					BLOCK 2 Status  cmdID= 60491  format=   "
		::= { iqudc32CmdEntry 60491 }


	iqudc32AncillaryBridgeChAncDataStoresDetBlock3HANCVANC60492 OBJECT-TYPE
		SYNTAX		RollCallString
		MAX-ACCESS		read-only
		STATUS			current
		DESCRIPTION
				"TYPE: - Display
				 PAGE: - Ancillary Bridge-Ch- Anc Data Stores Det
					Block 3 HANC/VANC  cmdID= 60492  format=   "
		::= { iqudc32CmdEntry 60492 }


	iqudc32AncillaryBridgeChAncDataStoresDetBlock3Line60493 OBJECT-TYPE
		SYNTAX		RollCallString
		MAX-ACCESS		read-only
		STATUS			current
		DESCRIPTION
				"TYPE: - Display
				 PAGE: - Ancillary Bridge-Ch- Anc Data Stores Det
					Block 3 Line  cmdID= 60493  format=   "
		::= { iqudc32CmdEntry 60493 }


	iqudc32AncillaryBridgeChAncDataStoresDetBlock3Status60494 OBJECT-TYPE
		SYNTAX		RollCallString
		MAX-ACCESS		read-only
		STATUS			current
		DESCRIPTION
				"TYPE: - Display
				 PAGE: - Ancillary Bridge-Ch- Anc Data Stores Det
					Block 3 Status  cmdID= 60494  format=   "
		::= { iqudc32CmdEntry 60494 }


	iqudc32AncillaryBridgeChAncDataStoresDetBlock4HANCVANC60495 OBJECT-TYPE
		SYNTAX		RollCallString
		MAX-ACCESS		read-only
		STATUS			current
		DESCRIPTION
				"TYPE: - Display
				 PAGE: - Ancillary Bridge-Ch- Anc Data Stores Det
					Block 4 HANC/VANC  cmdID= 60495  format=   "
		::= { iqudc32CmdEntry 60495 }


	iqudc32AncillaryBridgeChAncDataStoresDetBlock4Status60497 OBJECT-TYPE
		SYNTAX		RollCallString
		MAX-ACCESS		read-only
		STATUS			current
		DESCRIPTION
				"TYPE: - Display
				 PAGE: - Ancillary Bridge-Ch- Anc Data Stores Det
					Block 4 Status  cmdID= 60497  format=   "
		::= { iqudc32CmdEntry 60497 }


	iqudc32AncillaryBridgeChAncDataStoresDetBlock5HANCVANC60498 OBJECT-TYPE
		SYNTAX		RollCallString
		MAX-ACCESS		read-only
		STATUS			current
		DESCRIPTION
				"TYPE: - Display
				 PAGE: - Ancillary Bridge-Ch- Anc Data Stores Det
					Block 5 HANC/VANC  cmdID= 60498  format=   "
		::= { iqudc32CmdEntry 60498 }


	iqudc32AncillaryBridgeChAncDataStoresDetBlock5Status60500 OBJECT-TYPE
		SYNTAX		RollCallString
		MAX-ACCESS		read-only
		STATUS			current
		DESCRIPTION
				"TYPE: - Display
				 PAGE: - Ancillary Bridge-Ch- Anc Data Stores Det
					Block 5 Status  cmdID= 60500  format=   "
		::= { iqudc32CmdEntry 60500 }


	iqudc32AncillaryBridgeChAncDataStoresDetBlock6HANCVANC60501 OBJECT-TYPE
		SYNTAX		RollCallString
		MAX-ACCESS		read-only
		STATUS			current
		DESCRIPTION
				"TYPE: - Display
				 PAGE: - Ancillary Bridge-Ch- Anc Data Stores Det
					Block 6 HANC/VANC  cmdID= 60501  format=   "
		::= { iqudc32CmdEntry 60501 }


	iqudc32AncillaryBridgeChAncDataStoresDetBlock6Status60503 OBJECT-TYPE
		SYNTAX		RollCallString
		MAX-ACCESS		read-only
		STATUS			current
		DESCRIPTION
				"TYPE: - Display
				 PAGE: - Ancillary Bridge-Ch- Anc Data Stores Det
					Block 6 Status  cmdID= 60503  format=   "
		::= { iqudc32CmdEntry 60503 }


	iqudc32AncillaryBridgeChAncDataStoresDetBlock7HANCVANC60504 OBJECT-TYPE
		SYNTAX		RollCallString
		MAX-ACCESS		read-only
		STATUS			current
		DESCRIPTION
				"TYPE: - Display
				 PAGE: - Ancillary Bridge-Ch- Anc Data Stores Det
					Block 7 HANC/VANC  cmdID= 60504  format=   "
		::= { iqudc32CmdEntry 60504 }


	iqudc32AncillaryBridgeChAncDataStoresDetBlock7Status60506 OBJECT-TYPE
		SYNTAX		RollCallString
		MAX-ACCESS		read-only
		STATUS			current
		DESCRIPTION
				"TYPE: - Display
				 PAGE: - Ancillary Bridge-Ch- Anc Data Stores Det
					Block 7 Status  cmdID= 60506  format=   "
		::= { iqudc32CmdEntry 60506 }


	iqudc32AncillaryBridgeChAncDataStoresOPBlock1OPEnable60507 OBJECT-TYPE
		SYNTAX		INTEGER { disable(0), enable(1) }
		MAX-ACCESS		read-write
		STATUS			current
		DESCRIPTION
				"TYPE: - Checkbox
				 PAGE: - Ancillary Bridge-Ch- Anc Data Stores OP 
					Block 1 OP Enable  cmdID= 60507 "
		::= { iqudc32CmdEntry 60507 }


	iqudc32AncillaryBridgeChAncDataStoresOPBlock1OPLine60508 OBJECT-TYPE
		SYNTAX		INTEGER
		MAX-ACCESS		read-write
		STATUS			current
		DESCRIPTION
				"TYPE: - Number
				 PAGE: - Ancillary Bridge-Ch- Anc Data Stores OP 
					Block 1 OP Line  cmdID= 60508  min= 0  max= 1023  step= 1  format= %u  div_scale= 1 
					Min = 0  Max = 49152  Step = 0 "
		::= { iqudc32CmdEntry 60508 }


	iqudc32AncillaryBridgeChAncDataStoresOPBlock2OPEnable60509 OBJECT-TYPE
		SYNTAX		INTEGER { disable(0), enable(1) }
		MAX-ACCESS		read-write
		STATUS			current
		DESCRIPTION
				"TYPE: - Checkbox
				 PAGE: - Ancillary Bridge-Ch- Anc Data Stores OP 
					Block 2 OP Enable  cmdID= 60509 "
		::= { iqudc32CmdEntry 60509 }


	iqudc32AncillaryBridgeChAncDataStoresOPBlock2OPLine60510 OBJECT-TYPE
		SYNTAX		INTEGER
		MAX-ACCESS		read-write
		STATUS			current
		DESCRIPTION
				"TYPE: - Number
				 PAGE: - Ancillary Bridge-Ch- Anc Data Stores OP 
					Block 2 OP Line  cmdID= 60510  min= 0  max= 1023  step= 1  format= %u  div_scale= 1 
					Min = 0  Max = 49152  Step = 0 "
		::= { iqudc32CmdEntry 60510 }


	iqudc32AncillaryBridgeChAncDataStoresOPBlock3OPEnable60511 OBJECT-TYPE
		SYNTAX		INTEGER { disable(0), enable(1) }
		MAX-ACCESS		read-write
		STATUS			current
		DESCRIPTION
				"TYPE: - Checkbox
				 PAGE: - Ancillary Bridge-Ch- Anc Data Stores OP 
					Block 3 OP Enable  cmdID= 60511 "
		::= { iqudc32CmdEntry 60511 }


	iqudc32AncillaryBridgeChAncDataStoresOPBlock3OPLine60512 OBJECT-TYPE
		SYNTAX		INTEGER
		MAX-ACCESS		read-write
		STATUS			current
		DESCRIPTION
				"TYPE: - Number
				 PAGE: - Ancillary Bridge-Ch- Anc Data Stores OP 
					Block 3 OP Line  cmdID= 60512  min= 0  max= 1023  step= 1  format= %u  div_scale= 1 
					Min = 0  Max = 49152  Step = 0 "
		::= { iqudc32CmdEntry 60512 }


	iqudc32AncillaryBridgeChAncDataStoresOPBlock4OPEnable60513 OBJECT-TYPE
		SYNTAX		INTEGER { disable(0), enable(1) }
		MAX-ACCESS		read-write
		STATUS			current
		DESCRIPTION
				"TYPE: - Checkbox
				 PAGE: - Ancillary Bridge-Ch- Anc Data Stores OP 
					Block 4 OP Enable  cmdID= 60513 "
		::= { iqudc32CmdEntry 60513 }


	iqudc32AncillaryBridgeChAncDataStoresOPBlock4OPLine60514 OBJECT-TYPE
		SYNTAX		INTEGER
		MAX-ACCESS		read-write
		STATUS			current
		DESCRIPTION
				"TYPE: - Number
				 PAGE: - Ancillary Bridge-Ch- Anc Data Stores OP 
					Block 4 OP Line  cmdID= 60514  min= 0  max= 1023  step= 1  format= %u  div_scale= 1 
					Min = 0  Max = 49152  Step = 0 "
		::= { iqudc32CmdEntry 60514 }


	iqudc32AncillaryBridgeChAncDataStoresOPBlock5OPEnable60515 OBJECT-TYPE
		SYNTAX		INTEGER { disable(0), enable(1) }
		MAX-ACCESS		read-write
		STATUS			current
		DESCRIPTION
				"TYPE: - Checkbox
				 PAGE: - Ancillary Bridge-Ch- Anc Data Stores OP 
					Block 5 OP Enable  cmdID= 60515 "
		::= { iqudc32CmdEntry 60515 }


	iqudc32AncillaryBridgeChAncDataStoresOPBlock5OPLine60516 OBJECT-TYPE
		SYNTAX		INTEGER
		MAX-ACCESS		read-write
		STATUS			current
		DESCRIPTION
				"TYPE: - Number
				 PAGE: - Ancillary Bridge-Ch- Anc Data Stores OP 
					Block 5 OP Line  cmdID= 60516  min= 0  max= 1023  step= 1  format= %u  div_scale= 1 
					Min = 0  Max = 49152  Step = 0 "
		::= { iqudc32CmdEntry 60516 }


	iqudc32AncillaryBridgeChAncDataStoresOPBlock6OPEnable60517 OBJECT-TYPE
		SYNTAX		INTEGER { disable(0), enable(1) }
		MAX-ACCESS		read-write
		STATUS			current
		DESCRIPTION
				"TYPE: - Checkbox
				 PAGE: - Ancillary Bridge-Ch- Anc Data Stores OP 
					Block 6 OP Enable  cmdID= 60517 "
		::= { iqudc32CmdEntry 60517 }


	iqudc32AncillaryBridgeChAncDataStoresOPBlock6OPLine60518 OBJECT-TYPE
		SYNTAX		INTEGER
		MAX-ACCESS		read-write
		STATUS			current
		DESCRIPTION
				"TYPE: - Number
				 PAGE: - Ancillary Bridge-Ch- Anc Data Stores OP 
					Block 6 OP Line  cmdID= 60518  min= 0  max= 1023  step= 1  format= %u  div_scale= 1 
					Min = 0  Max = 49152  Step = 0 "
		::= { iqudc32CmdEntry 60518 }


	iqudc32AncillaryBridgeChAncDataStoresOPBlock7OPEnable60519 OBJECT-TYPE
		SYNTAX		INTEGER { disable(0), enable(1) }
		MAX-ACCESS		read-write
		STATUS			current
		DESCRIPTION
				"TYPE: - Checkbox
				 PAGE: - Ancillary Bridge-Ch- Anc Data Stores OP 
					Block 7 OP Enable  cmdID= 60519 "
		::= { iqudc32CmdEntry 60519 }


	iqudc32AncillaryBridgeChAncDataStoresOPBlock7OPLine60520 OBJECT-TYPE
		SYNTAX		INTEGER
		MAX-ACCESS		read-write
		STATUS			current
		DESCRIPTION
				"TYPE: - Number
				 PAGE: - Ancillary Bridge-Ch- Anc Data Stores OP 
					Block 7 OP Line  cmdID= 60520  min= 0  max= 1023  step= 1  format= %u  div_scale= 1 
					Min = 0  Max = 49152  Step = 0 "
		::= { iqudc32CmdEntry 60520 }


	iqudc32MetadataCh2AncillaryBridgeChNewDisplay44468 OBJECT-TYPE
		SYNTAX		RollCallString
		MAX-ACCESS		read-only
		STATUS			current
		DESCRIPTION
				"TYPE: - Display
				 PAGE: - Ancillary Bridge-Ch
					New Display  cmdID= 44468  format=   "
		::= { iqudc32CmdEntry 44468 }


	iqudc32AncillaryBridgeChAncDataStoresIPBlock1DID60672 OBJECT-TYPE
		SYNTAX		INTEGER
		MAX-ACCESS		read-write
		STATUS			current
		DESCRIPTION
				"TYPE: - Number
				 PAGE: - Ancillary Bridge-Ch- Anc Data Stores IP 
					Block 1 DID  cmdID= 60672  min= 0  max= 255  step= 1  format= %0.0f  div_scale= 1 
					Min = 0  Max = 255  Step = 1 "
		::= { iqudc32CmdEntry 60672 }


	iqudc32AncillaryBridgeChAncDataStoresIPBlock1SDID60673 OBJECT-TYPE
		SYNTAX		INTEGER
		MAX-ACCESS		read-write
		STATUS			current
		DESCRIPTION
				"TYPE: - Number
				 PAGE: - Ancillary Bridge-Ch- Anc Data Stores IP 
					Block 1 SDID  cmdID= 60673  min= 0  max= 255  step= 1  format= %0.0f  div_scale= 1 
					Min = 0  Max = 255  Step = 1 "
		::= { iqudc32CmdEntry 60673 }


	iqudc32AncillaryBridgeChAncDataStoresIPBlock2DID60674 OBJECT-TYPE
		SYNTAX		INTEGER
		MAX-ACCESS		read-write
		STATUS			current
		DESCRIPTION
				"TYPE: - Number
				 PAGE: - Ancillary Bridge-Ch- Anc Data Stores IP 
					Block 2 DID  cmdID= 60674  min= 0  max= 255  step= 1  format= %0.0f  div_scale= 1 
					Min = 0  Max = 255  Step = 1 "
		::= { iqudc32CmdEntry 60674 }


	iqudc32AncillaryBridgeChAncDataStoresIPBlock2SDID60675 OBJECT-TYPE
		SYNTAX		INTEGER
		MAX-ACCESS		read-write
		STATUS			current
		DESCRIPTION
				"TYPE: - Number
				 PAGE: - Ancillary Bridge-Ch- Anc Data Stores IP 
					Block 2 SDID  cmdID= 60675  min= 0  max= 255  step= 1  format= %0.0f  div_scale= 1 
					Min = 0  Max = 255  Step = 1 "
		::= { iqudc32CmdEntry 60675 }


	iqudc32AncillaryBridgeChAncDataStoresIPBlock3DID60676 OBJECT-TYPE
		SYNTAX		INTEGER
		MAX-ACCESS		read-write
		STATUS			current
		DESCRIPTION
				"TYPE: - Number
				 PAGE: - Ancillary Bridge-Ch- Anc Data Stores IP 
					Block 3 DID  cmdID= 60676  min= 0  max= 255  step= 1  format= %0.0f  div_scale= 1 
					Min = 0  Max = 255  Step = 1 "
		::= { iqudc32CmdEntry 60676 }


	iqudc32AncillaryBridgeChAncDataStoresIPBlock3SDID60677 OBJECT-TYPE
		SYNTAX		INTEGER
		MAX-ACCESS		read-write
		STATUS			current
		DESCRIPTION
				"TYPE: - Number
				 PAGE: - Ancillary Bridge-Ch- Anc Data Stores IP 
					Block 3 SDID  cmdID= 60677  min= 0  max= 255  step= 1  format= %0.0f  div_scale= 1 
					Min = 0  Max = 255  Step = 1 "
		::= { iqudc32CmdEntry 60677 }


	iqudc32AncillaryBridgeChAncDataStoresIPBlock4DID60678 OBJECT-TYPE
		SYNTAX		INTEGER
		MAX-ACCESS		read-write
		STATUS			current
		DESCRIPTION
				"TYPE: - Number
				 PAGE: - Ancillary Bridge-Ch- Anc Data Stores IP 
					Block 4 DID  cmdID= 60678  min= 0  max= 255  step= 1  format= %0.0f  div_scale= 1 
					Min = 0  Max = 255  Step = 1 "
		::= { iqudc32CmdEntry 60678 }


	iqudc32AncillaryBridgeChAncDataStoresIPBlock4SDID60679 OBJECT-TYPE
		SYNTAX		INTEGER
		MAX-ACCESS		read-write
		STATUS			current
		DESCRIPTION
				"TYPE: - Number
				 PAGE: - Ancillary Bridge-Ch- Anc Data Stores IP 
					Block 4 SDID  cmdID= 60679  min= 0  max= 255  step= 1  format= %0.0f  div_scale= 1 
					Min = 0  Max = 255  Step = 1 "
		::= { iqudc32CmdEntry 60679 }


	iqudc32AncillaryBridgeChAncDataStoresIPBlock5DID60680 OBJECT-TYPE
		SYNTAX		INTEGER
		MAX-ACCESS		read-write
		STATUS			current
		DESCRIPTION
				"TYPE: - Number
				 PAGE: - Ancillary Bridge-Ch- Anc Data Stores IP 
					Block 5 DID  cmdID= 60680  min= 0  max= 255  step= 1  format= %0.0f  div_scale= 1 
					Min = 0  Max = 255  Step = 1 "
		::= { iqudc32CmdEntry 60680 }


	iqudc32AncillaryBridgeChAncDataStoresIPBlock5SDID60681 OBJECT-TYPE
		SYNTAX		INTEGER
		MAX-ACCESS		read-write
		STATUS			current
		DESCRIPTION
				"TYPE: - Number
				 PAGE: - Ancillary Bridge-Ch- Anc Data Stores IP 
					Block 5 SDID  cmdID= 60681  min= 0  max= 255  step= 1  format= %0.0f  div_scale= 1 
					Min = 0  Max = 255  Step = 1 "
		::= { iqudc32CmdEntry 60681 }


	iqudc32AncillaryBridgeChAncDataStoresIPBlock6DID60682 OBJECT-TYPE
		SYNTAX		INTEGER
		MAX-ACCESS		read-write
		STATUS			current
		DESCRIPTION
				"TYPE: - Number
				 PAGE: - Ancillary Bridge-Ch- Anc Data Stores IP 
					Block 6 DID  cmdID= 60682  min= 0  max= 255  step= 1  format= %0.0f  div_scale= 1 
					Min = 0  Max = 255  Step = 1 "
		::= { iqudc32CmdEntry 60682 }


	iqudc32AncillaryBridgeChAncDataStoresIPBlock6SDID60683 OBJECT-TYPE
		SYNTAX		INTEGER
		MAX-ACCESS		read-write
		STATUS			current
		DESCRIPTION
				"TYPE: - Number
				 PAGE: - Ancillary Bridge-Ch- Anc Data Stores IP 
					Block 6 SDID  cmdID= 60683  min= 0  max= 255  step= 1  format= %0.0f  div_scale= 1 
					Min = 0  Max = 255  Step = 1 "
		::= { iqudc32CmdEntry 60683 }


	iqudc32AncillaryBridgeChAncDataStoresIPBlock7DID60684 OBJECT-TYPE
		SYNTAX		INTEGER
		MAX-ACCESS		read-write
		STATUS			current
		DESCRIPTION
				"TYPE: - Number
				 PAGE: - Ancillary Bridge-Ch- Anc Data Stores IP 
					Block 7 DID  cmdID= 60684  min= 0  max= 255  step= 1  format= %0.0f  div_scale= 1 
					Min = 0  Max = 255  Step = 1 "
		::= { iqudc32CmdEntry 60684 }


	iqudc32AncillaryBridgeChAncDataStoresIPBlock7SDID60685 OBJECT-TYPE
		SYNTAX		INTEGER
		MAX-ACCESS		read-write
		STATUS			current
		DESCRIPTION
				"TYPE: - Number
				 PAGE: - Ancillary Bridge-Ch- Anc Data Stores IP 
					Block 7 SDID  cmdID= 60685  min= 0  max= 255  step= 1  format= %0.0f  div_scale= 1 
					Min = 0  Max = 255  Step = 1 "
		::= { iqudc32CmdEntry 60685 }


	iqudc32AncillaryBridgeChAncDataStoresDetBlock1HANCVANC60686 OBJECT-TYPE
		SYNTAX		RollCallString
		MAX-ACCESS		read-only
		STATUS			current
		DESCRIPTION
				"TYPE: - Display
				 PAGE: - Ancillary Bridge-Ch- Anc Data Stores Det
					Block 1 HANC/VANC  cmdID= 60686  format=   "
		::= { iqudc32CmdEntry 60686 }


	iqudc32AncillaryBridgeChAncDataStoresDetBlock1Line60687 OBJECT-TYPE
		SYNTAX		RollCallString
		MAX-ACCESS		read-only
		STATUS			current
		DESCRIPTION
				"TYPE: - Display
				 PAGE: - Ancillary Bridge-Ch- Anc Data Stores Det
					Block 1 Line  cmdID= 60687  format=   "
		::= { iqudc32CmdEntry 60687 }


	iqudc32AncillaryBridgeChAncDataStoresDetBlock1Status60688 OBJECT-TYPE
		SYNTAX		RollCallString
		MAX-ACCESS		read-only
		STATUS			current
		DESCRIPTION
				"TYPE: - Display
				 PAGE: - Ancillary Bridge-Ch- Anc Data Stores Det
					Block 1 Status  cmdID= 60688  format=   "
		::= { iqudc32CmdEntry 60688 }


	iqudc32AncillaryBridgeChAncDataStoresDetBLOCK2HANCVANC60689 OBJECT-TYPE
		SYNTAX		RollCallString
		MAX-ACCESS		read-only
		STATUS			current
		DESCRIPTION
				"TYPE: - Display
				 PAGE: - Ancillary Bridge-Ch- Anc Data Stores Det
					BLOCK 2 HANC/VANC  cmdID= 60689  format=   "
		::= { iqudc32CmdEntry 60689 }


	iqudc32AncillaryBridgeChAncDataStoresDetBLOCK2Line60690 OBJECT-TYPE
		SYNTAX		RollCallString
		MAX-ACCESS		read-only
		STATUS			current
		DESCRIPTION
				"TYPE: - Display
				 PAGE: - Ancillary Bridge-Ch- Anc Data Stores Det
					BLOCK 2 Line  cmdID= 60690  format=   
					Block 4 Line  cmdID= 60690  format=   
					Block 5 Line  cmdID= 60690  format=   
					Block 6 Line  cmdID= 60690  format=   
					Block 7 Line  cmdID= 60690  format=   "
		::= { iqudc32CmdEntry 60690 }


	iqudc32AncillaryBridgeChAncDataStoresDetBLOCK2Status60691 OBJECT-TYPE
		SYNTAX		RollCallString
		MAX-ACCESS		read-only
		STATUS			current
		DESCRIPTION
				"TYPE: - Display
				 PAGE: - Ancillary Bridge-Ch- Anc Data Stores Det
					BLOCK 2 Status  cmdID= 60691  format=   "
		::= { iqudc32CmdEntry 60691 }


	iqudc32AncillaryBridgeChAncDataStoresDetBlock3HANCVANC60692 OBJECT-TYPE
		SYNTAX		RollCallString
		MAX-ACCESS		read-only
		STATUS			current
		DESCRIPTION
				"TYPE: - Display
				 PAGE: - Ancillary Bridge-Ch- Anc Data Stores Det
					Block 3 HANC/VANC  cmdID= 60692  format=   "
		::= { iqudc32CmdEntry 60692 }


	iqudc32AncillaryBridgeChAncDataStoresDetBlock3Line60693 OBJECT-TYPE
		SYNTAX		RollCallString
		MAX-ACCESS		read-only
		STATUS			current
		DESCRIPTION
				"TYPE: - Display
				 PAGE: - Ancillary Bridge-Ch- Anc Data Stores Det
					Block 3 Line  cmdID= 60693  format=   "
		::= { iqudc32CmdEntry 60693 }


	iqudc32AncillaryBridgeChAncDataStoresDetBlock3Status60694 OBJECT-TYPE
		SYNTAX		RollCallString
		MAX-ACCESS		read-only
		STATUS			current
		DESCRIPTION
				"TYPE: - Display
				 PAGE: - Ancillary Bridge-Ch- Anc Data Stores Det
					Block 3 Status  cmdID= 60694  format=   "
		::= { iqudc32CmdEntry 60694 }


	iqudc32AncillaryBridgeChAncDataStoresDetBlock4HANCVANC60695 OBJECT-TYPE
		SYNTAX		RollCallString
		MAX-ACCESS		read-only
		STATUS			current
		DESCRIPTION
				"TYPE: - Display
				 PAGE: - Ancillary Bridge-Ch- Anc Data Stores Det
					Block 4 HANC/VANC  cmdID= 60695  format=   "
		::= { iqudc32CmdEntry 60695 }


	iqudc32AncillaryBridgeChAncDataStoresDetBlock4Status60697 OBJECT-TYPE
		SYNTAX		RollCallString
		MAX-ACCESS		read-only
		STATUS			current
		DESCRIPTION
				"TYPE: - Display
				 PAGE: - Ancillary Bridge-Ch- Anc Data Stores Det
					Block 4 Status  cmdID= 60697  format=   "
		::= { iqudc32CmdEntry 60697 }


	iqudc32AncillaryBridgeChAncDataStoresDetBlock5HANCVANC60698 OBJECT-TYPE
		SYNTAX		RollCallString
		MAX-ACCESS		read-only
		STATUS			current
		DESCRIPTION
				"TYPE: - Display
				 PAGE: - Ancillary Bridge-Ch- Anc Data Stores Det
					Block 5 HANC/VANC  cmdID= 60698  format=   "
		::= { iqudc32CmdEntry 60698 }


	iqudc32AncillaryBridgeChAncDataStoresDetBlock5Status60700 OBJECT-TYPE
		SYNTAX		RollCallString
		MAX-ACCESS		read-only
		STATUS			current
		DESCRIPTION
				"TYPE: - Display
				 PAGE: - Ancillary Bridge-Ch- Anc Data Stores Det
					Block 5 Status  cmdID= 60700  format=   "
		::= { iqudc32CmdEntry 60700 }


	iqudc32AncillaryBridgeChAncDataStoresDetBlock6HANCVANC60701 OBJECT-TYPE
		SYNTAX		RollCallString
		MAX-ACCESS		read-only
		STATUS			current
		DESCRIPTION
				"TYPE: - Display
				 PAGE: - Ancillary Bridge-Ch- Anc Data Stores Det
					Block 6 HANC/VANC  cmdID= 60701  format=   "
		::= { iqudc32CmdEntry 60701 }


	iqudc32AncillaryBridgeChAncDataStoresDetBlock6Status60703 OBJECT-TYPE
		SYNTAX		RollCallString
		MAX-ACCESS		read-only
		STATUS			current
		DESCRIPTION
				"TYPE: - Display
				 PAGE: - Ancillary Bridge-Ch- Anc Data Stores Det
					Block 6 Status  cmdID= 60703  format=   "
		::= { iqudc32CmdEntry 60703 }


	iqudc32AncillaryBridgeChAncDataStoresDetBlock7HANCVANC60704 OBJECT-TYPE
		SYNTAX		RollCallString
		MAX-ACCESS		read-only
		STATUS			current
		DESCRIPTION
				"TYPE: - Display
				 PAGE: - Ancillary Bridge-Ch- Anc Data Stores Det
					Block 7 HANC/VANC  cmdID= 60704  format=   "
		::= { iqudc32CmdEntry 60704 }


	iqudc32AncillaryBridgeChAncDataStoresDetBlock7Status60706 OBJECT-TYPE
		SYNTAX		RollCallString
		MAX-ACCESS		read-only
		STATUS			current
		DESCRIPTION
				"TYPE: - Display
				 PAGE: - Ancillary Bridge-Ch- Anc Data Stores Det
					Block 7 Status  cmdID= 60706  format=   "
		::= { iqudc32CmdEntry 60706 }


	iqudc32AncillaryBridgeChAncDataStoresOPBlock1OPEnable60707 OBJECT-TYPE
		SYNTAX		INTEGER { disable(0), enable(1) }
		MAX-ACCESS		read-write
		STATUS			current
		DESCRIPTION
				"TYPE: - Checkbox
				 PAGE: - Ancillary Bridge-Ch- Anc Data Stores OP 
					Block 1 OP Enable  cmdID= 60707 "
		::= { iqudc32CmdEntry 60707 }


	iqudc32AncillaryBridgeChAncDataStoresOPBlock1OPLine60708 OBJECT-TYPE
		SYNTAX		INTEGER
		MAX-ACCESS		read-write
		STATUS			current
		DESCRIPTION
				"TYPE: - Number
				 PAGE: - Ancillary Bridge-Ch- Anc Data Stores OP 
					Block 1 OP Line  cmdID= 60708  min= 0  max= 1023  step= 1  format= %u  div_scale= 1 
					Min = 0  Max = 49152  Step = 0 "
		::= { iqudc32CmdEntry 60708 }


	iqudc32AncillaryBridgeChAncDataStoresOPBlock2OPEnable60709 OBJECT-TYPE
		SYNTAX		INTEGER { disable(0), enable(1) }
		MAX-ACCESS		read-write
		STATUS			current
		DESCRIPTION
				"TYPE: - Checkbox
				 PAGE: - Ancillary Bridge-Ch- Anc Data Stores OP 
					Block 2 OP Enable  cmdID= 60709 "
		::= { iqudc32CmdEntry 60709 }


	iqudc32AncillaryBridgeChAncDataStoresOPBlock2OPLine60710 OBJECT-TYPE
		SYNTAX		INTEGER
		MAX-ACCESS		read-write
		STATUS			current
		DESCRIPTION
				"TYPE: - Number
				 PAGE: - Ancillary Bridge-Ch- Anc Data Stores OP 
					Block 2 OP Line  cmdID= 60710  min= 0  max= 1023  step= 1  format= %u  div_scale= 1 
					Min = 0  Max = 49152  Step = 0 "
		::= { iqudc32CmdEntry 60710 }


	iqudc32AncillaryBridgeChAncDataStoresOPBlock3OPEnable60711 OBJECT-TYPE
		SYNTAX		INTEGER { disable(0), enable(1) }
		MAX-ACCESS		read-write
		STATUS			current
		DESCRIPTION
				"TYPE: - Checkbox
				 PAGE: - Ancillary Bridge-Ch- Anc Data Stores OP 
					Block 3 OP Enable  cmdID= 60711 "
		::= { iqudc32CmdEntry 60711 }


	iqudc32AncillaryBridgeChAncDataStoresOPBlock3OPLine60712 OBJECT-TYPE
		SYNTAX		INTEGER
		MAX-ACCESS		read-write
		STATUS			current
		DESCRIPTION
				"TYPE: - Number
				 PAGE: - Ancillary Bridge-Ch- Anc Data Stores OP 
					Block 3 OP Line  cmdID= 60712  min= 0  max= 1023  step= 1  format= %u  div_scale= 1 
					Min = 0  Max = 49152  Step = 0 "
		::= { iqudc32CmdEntry 60712 }


	iqudc32AncillaryBridgeChAncDataStoresOPBlock4OPEnable60713 OBJECT-TYPE
		SYNTAX		INTEGER { disable(0), enable(1) }
		MAX-ACCESS		read-write
		STATUS			current
		DESCRIPTION
				"TYPE: - Checkbox
				 PAGE: - Ancillary Bridge-Ch- Anc Data Stores OP 
					Block 4 OP Enable  cmdID= 60713 "
		::= { iqudc32CmdEntry 60713 }


	iqudc32AncillaryBridgeChAncDataStoresOPBlock4OPLine60714 OBJECT-TYPE
		SYNTAX		INTEGER
		MAX-ACCESS		read-write
		STATUS			current
		DESCRIPTION
				"TYPE: - Number
				 PAGE: - Ancillary Bridge-Ch- Anc Data Stores OP 
					Block 4 OP Line  cmdID= 60714  min= 0  max= 1023  step= 1  format= %u  div_scale= 1 
					Min = 0  Max = 49152  Step = 0 "
		::= { iqudc32CmdEntry 60714 }


	iqudc32AncillaryBridgeChAncDataStoresOPBlock5OPEnable60715 OBJECT-TYPE
		SYNTAX		INTEGER { disable(0), enable(1) }
		MAX-ACCESS		read-write
		STATUS			current
		DESCRIPTION
				"TYPE: - Checkbox
				 PAGE: - Ancillary Bridge-Ch- Anc Data Stores OP 
					Block 5 OP Enable  cmdID= 60715 "
		::= { iqudc32CmdEntry 60715 }


	iqudc32AncillaryBridgeChAncDataStoresOPBlock5OPLine60716 OBJECT-TYPE
		SYNTAX		INTEGER
		MAX-ACCESS		read-write
		STATUS			current
		DESCRIPTION
				"TYPE: - Number
				 PAGE: - Ancillary Bridge-Ch- Anc Data Stores OP 
					Block 5 OP Line  cmdID= 60716  min= 0  max= 1023  step= 1  format= %u  div_scale= 1 
					Min = 0  Max = 49152  Step = 0 "
		::= { iqudc32CmdEntry 60716 }


	iqudc32AncillaryBridgeChAncDataStoresOPBlock6OPEnable60717 OBJECT-TYPE
		SYNTAX		INTEGER { disable(0), enable(1) }
		MAX-ACCESS		read-write
		STATUS			current
		DESCRIPTION
				"TYPE: - Checkbox
				 PAGE: - Ancillary Bridge-Ch- Anc Data Stores OP 
					Block 6 OP Enable  cmdID= 60717 "
		::= { iqudc32CmdEntry 60717 }


	iqudc32AncillaryBridgeChAncDataStoresOPBlock6OPLine60718 OBJECT-TYPE
		SYNTAX		INTEGER
		MAX-ACCESS		read-write
		STATUS			current
		DESCRIPTION
				"TYPE: - Number
				 PAGE: - Ancillary Bridge-Ch- Anc Data Stores OP 
					Block 6 OP Line  cmdID= 60718  min= 0  max= 1023  step= 1  format= %u  div_scale= 1 
					Min = 0  Max = 49152  Step = 0 "
		::= { iqudc32CmdEntry 60718 }


	iqudc32AncillaryBridgeChAncDataStoresOPBlock7OPEnable60719 OBJECT-TYPE
		SYNTAX		INTEGER { disable(0), enable(1) }
		MAX-ACCESS		read-write
		STATUS			current
		DESCRIPTION
				"TYPE: - Checkbox
				 PAGE: - Ancillary Bridge-Ch- Anc Data Stores OP 
					Block 7 OP Enable  cmdID= 60719 "
		::= { iqudc32CmdEntry 60719 }


	iqudc32AncillaryBridgeChAncDataStoresOPBlock7OPLine60720 OBJECT-TYPE
		SYNTAX		INTEGER
		MAX-ACCESS		read-write
		STATUS			current
		DESCRIPTION
				"TYPE: - Number
				 PAGE: - Ancillary Bridge-Ch- Anc Data Stores OP 
					Block 7 OP Line  cmdID= 60720  min= 0  max= 1023  step= 1  format= %u  div_scale= 1 
					Min = 0  Max = 49152  Step = 0 "
		::= { iqudc32CmdEntry 60720 }


	iqudc32MetadataCh2AncillaryBridgeChNewDisplay44469 OBJECT-TYPE
		SYNTAX		RollCallString
		MAX-ACCESS		read-only
		STATUS			current
		DESCRIPTION
				"TYPE: - Display
				 PAGE: - Ancillary Bridge-Ch
					New Display  cmdID= 44469  format=   "
		::= { iqudc32CmdEntry 44469 }


	iqudc32GPIOGPI1GPIO1Mode OBJECT-TYPE
		SYNTAX		INTEGER {
							val-Unused(0),
							val-Input-GPI1(1),
							val-Output-GPO1(2)
							}
		MAX-ACCESS		read-write
		STATUS			current
		DESCRIPTION
				"TYPE: - RadiobuttonList
				 PAGE: - GPIO
					GPI/O 1 Mode  cmdID= 40600 
					Unused  value= 0  
					Input (GPI1)  value= 1  
					Output (GPO1)  value= 2  "
		::= { iqudc32CmdEntry 40600 }


	iqudc32MetadataCh2GPIOGPI1ipSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5),
							val-User-Memory-1(6),
							val-User-Memory-2(7),
							val-User-Memory-3(8),
							val-User-Memory-4(9),
							val-User-Memory-5(10),
							val-User-Memory-6(11),
							val-User-Memory-7(12),
							val-User-Memory-8(13),
							val-User-Memory-9(14),
							val-User-Memory-10(15),
							val-User-Memory-11(16),
							val-User-Memory-12(17),
							val-User-Memory-13(18),
							val-User-Memory-14(19),
							val-User-Memory-15(20),
							val-User-Memory-16(21)
							}
		MAX-ACCESS		read-write
		STATUS			current
		DESCRIPTION
				"TYPE: - RadiobuttonList
				 PAGE: - GPIO
					GPI 1-i/p Select  cmdID= 40602 
					Unused  value= 255  
					Freeze Ch1  value= 0  
					Black Ch1  value= 1  
					Pattern Ch1  value= 2  
					Freeze Ch2  value= 3  
					Black Ch2  value= 4  
					Pattern Ch2  value= 5  
					User Memory 1  value= 6  
					User Memory 2  value= 7  
					User Memory 3  value= 8  
					User Memory 4  value= 9  
					User Memory 5  value= 10  
					User Memory 6  value= 11  
					User Memory 7  value= 12  
					User Memory 8  value= 13  
					User Memory 9  value= 14  
					User Memory 10  value= 15  
					User Memory 11  value= 16  
					User Memory 12  value= 17  
					User Memory 13  value= 18  
					User Memory 14  value= 19  
					User Memory 15  value= 20  
					User Memory 16  value= 21  "
		::= { iqudc32CmdEntry 40602 }


	iqudc32MetadataCh2GPIOGPO1opSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5)
							}
		MAX-ACCESS		read-write
		STATUS			current
		DESCRIPTION
				"TYPE: - RadiobuttonList
				 PAGE: - GPIO
					GPO 1-o/p Select  cmdID= 40603 
					Unused  value= 255  
					Freeze Ch1  value= 0  
					Black Ch1  value= 1  
					Pattern Ch1  value= 2  
					Freeze Ch2  value= 3  
					Black Ch2  value= 4  
					Pattern Ch2  value= 5  "
		::= { iqudc32CmdEntry 40603 }


	iqudc32GPIOGPI2GPIO2Mode OBJECT-TYPE
		SYNTAX		INTEGER {
							val-Unused(0),
							val-Input-GPI2(1),
							val-Output-GPO2(2)
							}
		MAX-ACCESS		read-write
		STATUS			current
		DESCRIPTION
				"TYPE: - RadiobuttonList
				 PAGE: - GPIO
					GPI/O 2 Mode  cmdID= 40601 
					Unused  value= 0  
					Input (GPI2)  value= 1  
					Output (GPO2)  value= 2  "
		::= { iqudc32CmdEntry 40601 }


	iqudc32MetadataCh2GPIOGPI2ipSelect OBJECT-TYPE
		SYNTAX		INTEGER {
							val-Unused(255),
							val-Freeze-Ch1(0),
							val-Black-Ch-1(1),
							val-Pattern-Ch1(2),
							val-Freeze-Ch2(3),
							val-Black-Ch-2(4),
							val-Pattern-Ch2(5),
							val-User-Memory-1(6),
							val-User-Memory-2(7),
							val-User-Memory-3(8),
							val-User-Memory-4(9),
							val-User-Memory-5(10),
							val-User-Memory-6(11),
							val-User-Memory-7(12),
							val-User-Memory-8(13),
							val-User-Memory-9(14),
							val-User-Memory-10(15),
							val-User-Memory-11(16),
							val-User-Memory-12(17),
							val-User-Memory-13(18),
							val-User-Memory-14(19),
							val-User-Memory-15(20),
							val-User-Memory-16(21)
							}
		MAX-ACCESS		read-write
		STATUS			current
		DESCRIPTION
				"TYPE: - RadiobuttonList
				 PAGE: - GPIO
					GPI 2-i/p Select  cmdID= 40604 
					Unused  value= 255  
					Freeze Ch1  value= 0  
					Black Ch 1  value= 1  
					Pattern Ch1  value= 2  
					Freeze Ch2  value= 3  
					Black Ch 2  value= 4  
					Pattern Ch2  value= 5  
					User Memory 1  value= 6  
					User Memory 2  value= 7  
					User Memory 3  value= 8  
					User Memory 4  value= 9  
					User Memory 5  value= 10  
					User Memory 6  value= 11  
					User Memory 7  value= 12  
					User Memory 8  value= 13  
					User Memory 9  value= 14  
					User Memory 10  value= 15  
					User Memory 11  value= 16  
					User Memory 12  value= 17  
					User Memory 13  value= 18  
					User Memory 14  value= 19  
					User Memory 15  value= 20  
					User Memory 16  value= 21  "
		::= { iqudc32CmdEntry 40604 }


	iqudc32MetadataCh2GPIOGPO2opSelect OBJECT-TYPE
		SYNTAX		INTEGER {
							val-Unused(255),
							val-Freeze-Ch1(0),
							val-Black-Ch1(1),
							val-Pattern-Ch1(2),
							val-Freeze-Ch2(3),
							val-Black-Ch2(4),
							val-Pattern-Ch2(5)
							}
		MAX-ACCESS		read-write
		STATUS			current
		DESCRIPTION
				"TYPE: - RadiobuttonList
				 PAGE: - GPIO
					GPO 2-o/p Select  cmdID= 40605 
					Unused  value= 255  
					Freeze Ch1  value= 0  
					Black Ch1  value= 1  
					Pattern Ch1  value= 2  
					Freeze Ch2  value= 3  
					Black Ch2  value= 4  
					Pattern Ch2  value= 5  "
		::= { iqudc32CmdEntry 40605 }


	iqudc32MetadataCh2GPIONewDisplay OBJECT-TYPE
		SYNTAX		RollCallString
		MAX-ACCESS		read-only
		STATUS			current
		DESCRIPTION
				"TYPE: - Display
				 PAGE: - GPIO
					New Display  cmdID= 44453  format=   "
		::= { iqudc32CmdEntry 44453 }


	iqudc32MetadataCh2RollCallUnitName OBJECT-TYPE
		SYNTAX		RollCallString
		MAX-ACCESS		read-write
		STATUS			current
		DESCRIPTION
				"TYPE: - Editstring
				 PAGE: - RollCall
					Unit Name  cmdID= 51101  "
		::= { iqudc32CmdEntry 51101 }


	iqudc32MetadataCh2RollCallIPSharePort OBJECT-TYPE
		SYNTAX		INTEGER
		MAX-ACCESS		read-write
		STATUS			current
		DESCRIPTION
				"TYPE: - Number
				 PAGE: - RollCall
					IP Share Port  cmdID= 51105  min= 1024  max= 65535  step= 1  format= %d  div_scale= 1 
					Min = 1024  Max = -1  Step = 1 "
		::= { iqudc32CmdEntry 51105 }


	iqudc32MetadataCh2RollCallIPBridgingPort OBJECT-TYPE
		SYNTAX		INTEGER
		MAX-ACCESS		read-write
		STATUS			current
		DESCRIPTION
				"TYPE: - Number
				 PAGE: - RollCall
					IP Bridging Port  cmdID= 51106  min= 1024  max= 65535  step= 1  format= %d  div_scale= 1 
					Min = 1024  Max = -1  Step = 1 "
		::= { iqudc32CmdEntry 51106 }


	iqudc32MetadataCh2MemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Recall Memory  cmdID= 55002 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc32CmdEntry 55002 }


	iqudc32MetadataCh2MemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Sel Memory  cmdID= 55000 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqudc32CmdEntry 55000 }


	iqudc32MetadataCh2MemoriesSaveMemory OBJECT-TYPE
		SYNTAX		INTEGER { noAction(0),val-Save-Memory(1) }
		MAX-ACCESS		read-write
		STATUS			current
		DESCRIPTION
				"TYPE: - Button
				 PAGE: - Memories
					Save Memory  cmdID= 55001  value= 1  "
		::= { iqudc32CmdEntry 55001 }


	iqudc32MetadataCh2MemoriesClearMemory OBJECT-TYPE
		SYNTAX		INTEGER { noAction(0),val-Clear-Memory(1) }
		MAX-ACCESS		read-write
		STATUS			current
		DESCRIPTION
				"TYPE: - Button
				 PAGE: - Memories
					Clear Memory  cmdID= 55005  value= 1  "
		::= { iqudc32CmdEntry 55005 }


	iqudc32MemoriesMemoryNameChangeName OBJECT-TYPE
		SYNTAX		RollCallString
		MAX-ACCESS		read-write
		STATUS			current
		DESCRIPTION
				"TYPE: - Editstring
				 PAGE: - Memories
					Change Name  cmdID= 55003  "
		::= { iqudc32CmdEntry 55003 }


	iqudc32MetadataCh2MemoriesLastDisplayMemory OBJECT-TYPE
		SYNTAX		RollCallString
		MAX-ACCESS		read-only
		STATUS			current
		DESCRIPTION
				"TYPE: - Display
				 PAGE: - Memories
					Last Display Memory  cmdID= 55004  format=   "
		::= { iqudc32CmdEntry 55004 }


	iqudc32MetadataCh2RollTrackDisableAll OBJECT-TYPE
		SYNTAX		INTEGER { disable(0), enable(1) }
		MAX-ACCESS		read-write
		STATUS			current
		DESCRIPTION
				"TYPE: - Checkbox
				 PAGE: - RollTrack
					Disable All  cmdID= 60312 "
		::= { iqudc32CmdEntry 60312 }


	iqudc32MetadataCh2RollTrackIndex OBJECT-TYPE
		SYNTAX		INTEGER
		MAX-ACCESS		read-write
		STATUS			current
		DESCRIPTION
				"TYPE: - BarGraph
				 PAGE: - RollTrack
					Index  cmdID= 60313  min= 1  max= 50   step= 1  format= %0.0f  div_scale= 1 
					Min = 1  Max = 50  Step = 1 "
		::= { iqudc32CmdEntry 60313 }


	iqudc32MetadataCh2RollTrackSource OBJECT-TYPE
		SYNTAX		INTEGER {
							val-Unused(-1),
							val-Input-Present-Ch1(0),
							val-Input-Loss-Ch1(1),
							val-Reference-OK(2),
							val-Reference-Lost(3),
							val-Input-Present-Ch2(4),
							val-Input-Loss-Ch2(5)
							}
		MAX-ACCESS		read-write
		STATUS			current
		DESCRIPTION
				"TYPE: - RadiobuttonList
				 PAGE: - RollTrack
					Source  cmdID= 60315 
					Unused  value= -1  
					Input Present Ch1  value= 0  
					Input Loss Ch1  value= 1  
					Reference OK  value= 2  
					Reference Lost  value= 3  
					Input Present Ch2  value= 4  
					Input Loss Ch2  value= 5  "
		::= { iqudc32CmdEntry 60315 }


	iqudc32MetadataCh2RollTrackAddress OBJECT-TYPE
		SYNTAX		RollCallString
		MAX-ACCESS		read-write
		STATUS			current
		DESCRIPTION
				"TYPE: - Editstring
				 PAGE: - RollTrack
					Address  cmdID= 60317  "
		::= { iqudc32CmdEntry 60317 }


	iqudc32MetadataCh2RollTrackCommand OBJECT-TYPE
		SYNTAX		RollCallString
		MAX-ACCESS		read-write
		STATUS			current
		DESCRIPTION
				"TYPE: - Editstring
				 PAGE: - RollTrack
					Command  cmdID= 60318  "
		::= { iqudc32CmdEntry 60318 }


	iqudc32MetadataCh2RollTrackStatus OBJECT-TYPE
		SYNTAX		RollCallString
		MAX-ACCESS		read-only
		STATUS			current
		DESCRIPTION
				"TYPE: - Display
				 PAGE: - RollTrack
					Status  cmdID= 60316  format=   "
		::= { iqudc32CmdEntry 60316 }


	iqudc32MetadataCh2RollTrackSending OBJECT-TYPE
		SYNTAX		RollCallString
		MAX-ACCESS		read-only
		STATUS			current
		DESCRIPTION
				"TYPE: - Display
				 PAGE: - RollTrack
					Sending  cmdID= 60314  format=   "
		::= { iqudc32CmdEntry 60314 }


	iqudc32MetadataCh2MiscLoggingSerialNumberEnabl OBJECT-TYPE
		SYNTAX		INTEGER { disable(0), enable(1) }
		MAX-ACCESS		read-write
		STATUS			current
		DESCRIPTION
				"TYPE: - Checkbox
				 PAGE: - Misc. Logging
					Serial Number Enabl  cmdID= 62000 "
		::= { iqudc32CmdEntry 62000 }


	iqudc32MetadataCh2MiscLoggingSerialNumberStatu OBJECT-TYPE
		SYNTAX		RollCallString
		MAX-ACCESS		read-only
		STATUS			current
		DESCRIPTION
				"TYPE: - Display
				 PAGE: - Misc. Logging
					Serial Number Statu  cmdID= 62001  format=   "
		::= { iqudc32CmdEntry 62001 }


	iqudc32MetadataCh2MiscLoggingUpTimeEnable OBJECT-TYPE
		SYNTAX		INTEGER { disable(0), enable(1) }
		MAX-ACCESS		read-write
		STATUS			current
		DESCRIPTION
				"TYPE: - Checkbox
				 PAGE: - Misc. Logging
					Up Time Enable  cmdID= 62004 "
		::= { iqudc32CmdEntry 62004 }


	iqudc32MetadataCh2MiscLoggingUpTimeStatus OBJECT-TYPE
		SYNTAX		RollCallString
		MAX-ACCESS		read-only
		STATUS			current
		DESCRIPTION
				"TYPE: - Display
				 PAGE: - Misc. Logging
					Up Time Status  cmdID= 62005  format=   "
		::= { iqudc32CmdEntry 62005 }


	iqudc32MetadataCh2MiscLoggingPowerUsageStateE OBJECT-TYPE
		SYNTAX		INTEGER { disable(0), enable(1) }
		MAX-ACCESS		read-write
		STATUS			current
		DESCRIPTION
				"TYPE: - Checkbox
				 PAGE: - Misc. Logging
					Power Usage State E  cmdID= 62006 "
		::= { iqudc32CmdEntry 62006 }


	iqudc32MetadataCh2MiscLoggingPowerUsageStateS OBJECT-TYPE
		SYNTAX		RollCallString
		MAX-ACCESS		read-only
		STATUS			current
		DESCRIPTION
				"TYPE: - Display
				 PAGE: - Misc. Logging
					Power Usage State S  cmdID= 62007  format=   "
		::= { iqudc32CmdEntry 62007 }


	iqudc32MetadataCh2MiscLoggingBuild62011 OBJECT-TYPE
		SYNTAX		INTEGER { disable(0), enable(1) }
		MAX-ACCESS		read-write
		STATUS			current
		DESCRIPTION
				"TYPE: - Checkbox
				 PAGE: - Misc. Logging
					Build  cmdID= 62011 "
		::= { iqudc32CmdEntry 62011 }


	iqudc32MetadataCh2MiscLoggingBuild62010 OBJECT-TYPE
		SYNTAX		RollCallString
		MAX-ACCESS		read-only
		STATUS			current
		DESCRIPTION
				"TYPE: - Display
				 PAGE: - Misc. Logging
					Build  cmdID= 62010  format=   "
		::= { iqudc32CmdEntry 62010 }


	iqudc32MetadataCh2MiscLoggingAESOutput14Place OBJECT-TYPE
		SYNTAX		RollCallString
		MAX-ACCESS		read-only
		STATUS			current
		DESCRIPTION
				"TYPE: - Display
				 PAGE: - Misc. Logging
					AES Output1-4 Place  cmdID= 61009  format=   "
		::= { iqudc32CmdEntry 61009 }


	iqudc32MetadataCh2MiscLoggingAESOutput58Place OBJECT-TYPE
		SYNTAX		RollCallString
		MAX-ACCESS		read-only
		STATUS			current
		DESCRIPTION
				"TYPE: - Display
				 PAGE: - Misc. Logging
					AES Output5-8 Place  cmdID= 61010  format=   "
		::= { iqudc32CmdEntry 61010 }


	iqudc32MetadataCh2MiscLoggingInputADCPlacehold OBJECT-TYPE
		SYNTAX		RollCallString
		MAX-ACCESS		read-only
		STATUS			current
		DESCRIPTION
				"TYPE: - Display
				 PAGE: - Misc. Logging
					Input ADC Placehold  cmdID= 61011  format=   "
		::= { iqudc32CmdEntry 61011 }


	iqudc32MetadataCh2MiscLoggingSourceCh1Ch2Pl OBJECT-TYPE
		SYNTAX		RollCallString
		MAX-ACCESS		read-only
		STATUS			current
		DESCRIPTION
				"TYPE: - Display
				 PAGE: - Misc. Logging
					Source Ch1 & Ch2 Pl  cmdID= 61012  format=   "
		::= { iqudc32CmdEntry 61012 }


	iqudc32MetadataCh2MiscLoggingCVBSDecoderPlaceh OBJECT-TYPE
		SYNTAX		RollCallString
		MAX-ACCESS		read-only
		STATUS			current
		DESCRIPTION
				"TYPE: - Display
				 PAGE: - Misc. Logging
					CVBS Decoder Placeh  cmdID= 20500  format=   "
		::= { iqudc32CmdEntry 20500 }


	iqudc32MetadataCh2MiscLoggingFanSpeedPlacehold OBJECT-TYPE
		SYNTAX		RollCallString
		MAX-ACCESS		read-only
		STATUS			current
		DESCRIPTION
				"TYPE: - Display
				 PAGE: - Misc. Logging
					Fan Speed Placehold  cmdID= 61002  format=   "
		::= { iqudc32CmdEntry 61002 }


	iqudc32MetadataCh2VideoInputLoggingInput1Type62100 OBJECT-TYPE
		SYNTAX		INTEGER { disable(0), enable(1) }
		MAX-ACCESS		read-write
		STATUS			current
		DESCRIPTION
				"TYPE: - Checkbox
				 PAGE: - Video Input Logging
					Input 1 Type  cmdID= 62100 "
		::= { iqudc32CmdEntry 62100 }


	iqudc32MetadataCh2VideoInputLoggingInput1Type62101 OBJECT-TYPE
		SYNTAX		RollCallString
		MAX-ACCESS		read-only
		STATUS			current
		DESCRIPTION
				"TYPE: - Display
				 PAGE: - Video Input Logging
					Input 1 Type=  cmdID= 62101  format=   "
		::= { iqudc32CmdEntry 62101 }


	iqudc32MetadataCh2VideoInputLoggingInput1State62102 OBJECT-TYPE
		SYNTAX		INTEGER { disable(0), enable(1) }
		MAX-ACCESS		read-write
		STATUS			current
		DESCRIPTION
				"TYPE: - Checkbox
				 PAGE: - Video Input Logging
					Input 1 State  cmdID= 62102 "
		::= { iqudc32CmdEntry 62102 }


	iqudc32MetadataCh2VideoInputLoggingInput1State62103 OBJECT-TYPE
		SYNTAX		RollCallString
		MAX-ACCESS		read-only
		STATUS			current
		DESCRIPTION
				"TYPE: - Display
				 PAGE: - Video Input Logging
					Input 1 State=  cmdID= 62103  format=   "
		::= { iqudc32CmdEntry 62103 }


	iqudc32MetadataCh2VideoInputLoggingInput1Std62104 OBJECT-TYPE
		SYNTAX		INTEGER { disable(0), enable(1) }
		MAX-ACCESS		read-write
		STATUS			current
		DESCRIPTION
				"TYPE: - Checkbox
				 PAGE: - Video Input Logging
					Input 1 Std.  cmdID= 62104 "
		::= { iqudc32CmdEntry 62104 }


	iqudc32MetadataCh2VideoInputLoggingInput1Std62105 OBJECT-TYPE
		SYNTAX		RollCallString
		MAX-ACCESS		read-only
		STATUS			current
		DESCRIPTION
				"TYPE: - Display
				 PAGE: - Video Input Logging
					Input 1 Std.=  cmdID= 62105  format=   "
		::= { iqudc32CmdEntry 62105 }


	iqudc32MetadataCh2VideoInputLoggingInput2Type62200 OBJECT-TYPE
		SYNTAX		INTEGER { disable(0), enable(1) }
		MAX-ACCESS		read-write
		STATUS			current
		DESCRIPTION
				"TYPE: - Checkbox
				 PAGE: - Video Input Logging
					Input 2 Type  cmdID= 62200 "
		::= { iqudc32CmdEntry 62200 }


	iqudc32MetadataCh2VideoInputLoggingInput2Type62201 OBJECT-TYPE
		SYNTAX		RollCallString
		MAX-ACCESS		read-only
		STATUS			current
		DESCRIPTION
				"TYPE: - Display
				 PAGE: - Video Input Logging
					Input 2 Type=  cmdID= 62201  format=   "
		::= { iqudc32CmdEntry 62201 }


	iqudc32MetadataCh2VideoInputLoggingInput2State62202 OBJECT-TYPE
		SYNTAX		INTEGER { disable(0), enable(1) }
		MAX-ACCESS		read-write
		STATUS			current
		DESCRIPTION
				"TYPE: - Checkbox
				 PAGE: - Video Input Logging
					Input 2 State  cmdID= 62202 "
		::= { iqudc32CmdEntry 62202 }


	iqudc32MetadataCh2VideoInputLoggingInput2State62203 OBJECT-TYPE
		SYNTAX		RollCallString
		MAX-ACCESS		read-only
		STATUS			current
		DESCRIPTION
				"TYPE: - Display
				 PAGE: - Video Input Logging
					Input 2 State=  cmdID= 62203  format=   "
		::= { iqudc32CmdEntry 62203 }


	iqudc32MetadataCh2VideoInputLoggingInput2Std62204 OBJECT-TYPE
		SYNTAX		INTEGER { disable(0), enable(1) }
		MAX-ACCESS		read-write
		STATUS			current
		DESCRIPTION
				"TYPE: - Checkbox
				 PAGE: - Video Input Logging
					Input 2 Std.  cmdID= 62204 "
		::= { iqudc32CmdEntry 62204 }


	iqudc32MetadataCh2VideoInputLoggingInput2Std62205 OBJECT-TYPE
		SYNTAX		RollCallString
		MAX-ACCESS		read-only
		STATUS			current
		DESCRIPTION
				"TYPE: - Display
				 PAGE: - Video Input Logging
					Input 2 Std.=  cmdID= 62205  format=   "
		::= { iqudc32CmdEntry 62205 }


	iqudc32MetadataCh2VideoInputLoggingInput3Type62300 OBJECT-TYPE
		SYNTAX		INTEGER { disable(0), enable(1) }
		MAX-ACCESS		read-write
		STATUS			current
		DESCRIPTION
				"TYPE: - Checkbox
				 PAGE: - Video Input Logging
					Input 3 Type  cmdID= 62300 "
		::= { iqudc32CmdEntry 62300 }


	iqudc32MetadataCh2VideoInputLoggingInput3Type62301 OBJECT-TYPE
		SYNTAX		RollCallString
		MAX-ACCESS		read-only
		STATUS			current
		DESCRIPTION
				"TYPE: - Display
				 PAGE: - Video Input Logging
					Input 3 Type=  cmdID= 62301  format=   "
		::= { iqudc32CmdEntry 62301 }


	iqudc32MetadataCh2VideoInputLoggingInput3State62302 OBJECT-TYPE
		SYNTAX		INTEGER { disable(0), enable(1) }
		MAX-ACCESS		read-write
		STATUS			current
		DESCRIPTION
				"TYPE: - Checkbox
				 PAGE: - Video Input Logging
					Input 3 State  cmdID= 62302 "
		::= { iqudc32CmdEntry 62302 }


	iqudc32MetadataCh2VideoInputLoggingInput3State62303 OBJECT-TYPE
		SYNTAX		RollCallString
		MAX-ACCESS		read-only
		STATUS			current
		DESCRIPTION
				"TYPE: - Display
				 PAGE: - Video Input Logging
					Input 3 State=  cmdID= 62303  format=   "
		::= { iqudc32CmdEntry 62303 }


	iqudc32MetadataCh2VideoInputLoggingInput3Std62304 OBJECT-TYPE
		SYNTAX		INTEGER { disable(0), enable(1) }
		MAX-ACCESS		read-write
		STATUS			current
		DESCRIPTION
				"TYPE: - Checkbox
				 PAGE: - Video Input Logging
					Input 3 Std.  cmdID= 62304 "
		::= { iqudc32CmdEntry 62304 }


	iqudc32MetadataCh2VideoInputLoggingInput3Std62305 OBJECT-TYPE
		SYNTAX		RollCallString
		MAX-ACCESS		read-only
		STATUS			current
		DESCRIPTION
				"TYPE: - Display
				 PAGE: - Video Input Logging
					Input 3 Std.=  cmdID= 62305  format=   "
		::= { iqudc32CmdEntry 62305 }


	iqudc32MetadataCh2VideoInputLoggingInput4Type62400 OBJECT-TYPE
		SYNTAX		INTEGER { disable(0), enable(1) }
		MAX-ACCESS		read-write
		STATUS			current
		DESCRIPTION
				"TYPE: - Checkbox
				 PAGE: - Video Input Logging
					Input 4 Type  cmdID= 62400 "
		::= { iqudc32CmdEntry 62400 }


	iqudc32MetadataCh2VideoInputLoggingInput4Type62401 OBJECT-TYPE
		SYNTAX		RollCallString
		MAX-ACCESS		read-only
		STATUS			current
		DESCRIPTION
				"TYPE: - Display
				 PAGE: - Video Input Logging
					Input 4 Type=  cmdID= 62401  format=   "
		::= { iqudc32CmdEntry 62401 }


	iqudc32MetadataCh2VideoInputLoggingInput4State62402 OBJECT-TYPE
		SYNTAX		INTEGER { disable(0), enable(1) }
		MAX-ACCESS		read-write
		STATUS			current
		DESCRIPTION
				"TYPE: - Checkbox
				 PAGE: - Video Input Logging
					Input 4 State  cmdID= 62402 "
		::= { iqudc32CmdEntry 62402 }


	iqudc32MetadataCh2VideoInputLoggingInput4State62403 OBJECT-TYPE
		SYNTAX		RollCallString
		MAX-ACCESS		read-only
		STATUS			current
		DESCRIPTION
				"TYPE: - Display
				 PAGE: - Video Input Logging
					Input 4 State=  cmdID= 62403  format=   "
		::= { iqudc32CmdEntry 62403 }


	iqudc32MetadataCh2VideoInputLoggingInput4Std62404 OBJECT-TYPE
		SYNTAX		INTEGER { disable(0), enable(1) }
		MAX-ACCESS		read-write
		STATUS			current
		DESCRIPTION
				"TYPE: - Checkbox
				 PAGE: - Video Input Logging
					Input 4 Std.  cmdID= 62404 "
		::= { iqudc32CmdEntry 62404 }


	iqudc32MetadataCh2VideoInputLoggingInput4Std62405 OBJECT-TYPE
		SYNTAX		RollCallString
		MAX-ACCESS		read-only
		STATUS			current
		DESCRIPTION
				"TYPE: - Display
				 PAGE: - Video Input Logging
					Input 4 Std.=  cmdID= 62405  format=   "
		::= { iqudc32CmdEntry 62405 }


	iqudc32MetadataCh2VideoInputLoggingInput5Type62500 OBJECT-TYPE
		SYNTAX		INTEGER { disable(0), enable(1) }
		MAX-ACCESS		read-write
		STATUS			current
		DESCRIPTION
				"TYPE: - Checkbox
				 PAGE: - Video Input Logging
					Input 5 Type  cmdID= 62500 "
		::= { iqudc32CmdEntry 62500 }


	iqudc32MetadataCh2VideoInputLoggingInput5Type62501 OBJECT-TYPE
		SYNTAX		RollCallString
		MAX-ACCESS		read-only
		STATUS			current
		DESCRIPTION
				"TYPE: - Display
				 PAGE: - Video Input Logging
					Input 5 Type=  cmdID= 62501  format=   "
		::= { iqudc32CmdEntry 62501 }


	iqudc32MetadataCh2VideoInputLoggingInput5State62502 OBJECT-TYPE
		SYNTAX		INTEGER { disable(0), enable(1) }
		MAX-ACCESS		read-write
		STATUS			current
		DESCRIPTION
				"TYPE: - Checkbox
				 PAGE: - Video Input Logging
					Input 5 State  cmdID= 62502 "
		::= { iqudc32CmdEntry 62502 }


	iqudc32MetadataCh2VideoInputLoggingInput5State62503 OBJECT-TYPE
		SYNTAX		RollCallString
		MAX-ACCESS		read-only
		STATUS			current
		DESCRIPTION
				"TYPE: - Display
				 PAGE: - Video Input Logging
					Input 5 State=  cmdID= 62503  format=   "
		::= { iqudc32CmdEntry 62503 }


	iqudc32MetadataCh2VideoInputLoggingInput5Std62504 OBJECT-TYPE
		SYNTAX		INTEGER { disable(0), enable(1) }
		MAX-ACCESS		read-write
		STATUS			current
		DESCRIPTION
				"TYPE: - Checkbox
				 PAGE: - Video Input Logging
					Input 5 Std.  cmdID= 62504 "
		::= { iqudc32CmdEntry 62504 }


	iqudc32MetadataCh2VideoInputLoggingInput5Std62505 OBJECT-TYPE
		SYNTAX		RollCallString
		MAX-ACCESS		read-only
		STATUS			current
		DESCRIPTION
				"TYPE: - Display
				 PAGE: - Video Input Logging
					Input 5 Std.=  cmdID= 62505  format=   "
		::= { iqudc32CmdEntry 62505 }


	iqudc32MetadataCh2OutputLoggingOutput1Type62600 OBJECT-TYPE
		SYNTAX		INTEGER { disable(0), enable(1) }
		MAX-ACCESS		read-write
		STATUS			current
		DESCRIPTION
				"TYPE: - Checkbox
				 PAGE: - Output Logging
					Output 1 Type  cmdID= 62600 "
		::= { iqudc32CmdEntry 62600 }


	iqudc32MetadataCh2OutputLoggingOutput1Type62601 OBJECT-TYPE
		SYNTAX		RollCallString
		MAX-ACCESS		read-only
		STATUS			current
		DESCRIPTION
				"TYPE: - Display
				 PAGE: - Output Logging
					Output 1 Type=  cmdID= 62601  format=   "
		::= { iqudc32CmdEntry 62601 }


	iqudc32MetadataCh2OutputLoggingOutput1State62602 OBJECT-TYPE
		SYNTAX		INTEGER { disable(0), enable(1) }
		MAX-ACCESS		read-write
		STATUS			current
		DESCRIPTION
				"TYPE: - Checkbox
				 PAGE: - Output Logging
					Output 1 State  cmdID= 62602 "
		::= { iqudc32CmdEntry 62602 }


	iqudc32MetadataCh2OutputLoggingOutput1State62603 OBJECT-TYPE
		SYNTAX		RollCallString
		MAX-ACCESS		read-only
		STATUS			current
		DESCRIPTION
				"TYPE: - Display
				 PAGE: - Output Logging
					Output 1 State=  cmdID= 62603  format=   "
		::= { iqudc32CmdEntry 62603 }


	iqudc32MetadataCh2OutputLoggingOutput1Std62604 OBJECT-TYPE
		SYNTAX		INTEGER { disable(0), enable(1) }
		MAX-ACCESS		read-write
		STATUS			current
		DESCRIPTION
				"TYPE: - Checkbox
				 PAGE: - Output Logging
					Output 1 Std.  cmdID= 62604 "
		::= { iqudc32CmdEntry 62604 }


	iqudc32MetadataCh2OutputLoggingOutput1Std62605 OBJECT-TYPE
		SYNTAX		RollCallString
		MAX-ACCESS		read-only
		STATUS			current
		DESCRIPTION
				"TYPE: - Display
				 PAGE: - Output Logging
					Output 1 Std.=  cmdID= 62605  format=   "
		::= { iqudc32CmdEntry 62605 }


	iqudc32MetadataCh2OutputLoggingOutput2Type62612 OBJECT-TYPE
		SYNTAX		INTEGER { disable(0), enable(1) }
		MAX-ACCESS		read-write
		STATUS			current
		DESCRIPTION
				"TYPE: - Checkbox
				 PAGE: - Output Logging
					Output 2 Type  cmdID= 62612 "
		::= { iqudc32CmdEntry 62612 }


	iqudc32MetadataCh2OutputLoggingOutput2Type62613 OBJECT-TYPE
		SYNTAX		RollCallString
		MAX-ACCESS		read-only
		STATUS			current
		DESCRIPTION
				"TYPE: - Display
				 PAGE: - Output Logging
					Output 2 Type=  cmdID= 62613  format=   "
		::= { iqudc32CmdEntry 62613 }


	iqudc32MetadataCh2OutputLoggingOutput2State62614 OBJECT-TYPE
		SYNTAX		INTEGER { disable(0), enable(1) }
		MAX-ACCESS		read-write
		STATUS			current
		DESCRIPTION
				"TYPE: - Checkbox
				 PAGE: - Output Logging
					Output 2 State  cmdID= 62614 "
		::= { iqudc32CmdEntry 62614 }


	iqudc32MetadataCh2OutputLoggingOutput2State62615 OBJECT-TYPE
		SYNTAX		RollCallString
		MAX-ACCESS		read-only
		STATUS			current
		DESCRIPTION
				"TYPE: - Display
				 PAGE: - Output Logging
					Output 2 State=  cmdID= 62615  format=   "
		::= { iqudc32CmdEntry 62615 }


	iqudc32MetadataCh2OutputLoggingOutput2Std62616 OBJECT-TYPE
		SYNTAX		INTEGER { disable(0), enable(1) }
		MAX-ACCESS		read-write
		STATUS			current
		DESCRIPTION
				"TYPE: - Checkbox
				 PAGE: - Output Logging
					Output 2 Std.  cmdID= 62616 "
		::= { iqudc32CmdEntry 62616 }


	iqudc32MetadataCh2OutputLoggingOutput2Std62617 OBJECT-TYPE
		SYNTAX		RollCallString
		MAX-ACCESS		read-only
		STATUS			current
		DESCRIPTION
				"TYPE: - Display
				 PAGE: - Output Logging
					Output 2 Std.=  cmdID= 62617  format=   "
		::= { iqudc32CmdEntry 62617 }


	iqudc32MetadataCh2OPAudioStateCh1OutputEmbPair1s62620 OBJECT-TYPE
		SYNTAX		INTEGER { disable(0), enable(1) }
		MAX-ACCESS		read-write
		STATUS			current
		DESCRIPTION
				"TYPE: - Checkbox
				 PAGE: - O/P Audio State Ch1
					Output Emb.Pair 1 s  cmdID= 62620 "
		::= { iqudc32CmdEntry 62620 }


	iqudc32MetadataCh2OPAudioStateCh1OutputEmbPair1s62621 OBJECT-TYPE
		SYNTAX		RollCallString
		MAX-ACCESS		read-only
		STATUS			current
		DESCRIPTION
				"TYPE: - Display
				 PAGE: - O/P Audio State Ch1
					Output Emb.Pair 1 s  cmdID= 62621  format=   "
		::= { iqudc32CmdEntry 62621 }


	iqudc32MetadataCh2OPAudioStateCh1OutputEmbPair2s62622 OBJECT-TYPE
		SYNTAX		INTEGER { disable(0), enable(1) }
		MAX-ACCESS		read-write
		STATUS			current
		DESCRIPTION
				"TYPE: - Checkbox
				 PAGE: - O/P Audio State Ch1
					Output Emb.Pair 2 s  cmdID= 62622 "
		::= { iqudc32CmdEntry 62622 }


	iqudc32MetadataCh2OPAudioStateCh1OutputEmbPair2s62623 OBJECT-TYPE
		SYNTAX		RollCallString
		MAX-ACCESS		read-only
		STATUS			current
		DESCRIPTION
				"TYPE: - Display
				 PAGE: - O/P Audio State Ch1
					Output Emb.Pair 2 s  cmdID= 62623  format=   "
		::= { iqudc32CmdEntry 62623 }


	iqudc32MetadataCh2OPAudioStateCh1OutputEmbPair3s62624 OBJECT-TYPE
		SYNTAX		INTEGER { disable(0), enable(1) }
		MAX-ACCESS		read-write
		STATUS			current
		DESCRIPTION
				"TYPE: - Checkbox
				 PAGE: - O/P Audio State Ch1
					Output Emb.Pair 3 s  cmdID= 62624 "
		::= { iqudc32CmdEntry 62624 }


	iqudc32MetadataCh2OPAudioStateCh1OutputEmbPair3s62625 OBJECT-TYPE
		SYNTAX		RollCallString
		MAX-ACCESS		read-only
		STATUS			current
		DESCRIPTION
				"TYPE: - Display
				 PAGE: - O/P Audio State Ch1
					Output Emb.Pair 3 s  cmdID= 62625  format=   "
		::= { iqudc32CmdEntry 62625 }


	iqudc32MetadataCh2OPAudioStateCh1OutputEmbPair4s62626 OBJECT-TYPE
		SYNTAX		INTEGER { disable(0), enable(1) }
		MAX-ACCESS		read-write
		STATUS			current
		DESCRIPTION
				"TYPE: - Checkbox
				 PAGE: - O/P Audio State Ch1
					Output Emb.Pair 4 s  cmdID= 62626 "
		::= { iqudc32CmdEntry 62626 }


	iqudc32MetadataCh2OPAudioStateCh1OutputEmbPair4s62627 OBJECT-TYPE
		SYNTAX		RollCallString
		MAX-ACCESS		read-only
		STATUS			current
		DESCRIPTION
				"TYPE: - Display
				 PAGE: - O/P Audio State Ch1
					Output Emb.Pair 4 s  cmdID= 62627  format=   "
		::= { iqudc32CmdEntry 62627 }


	iqudc32MetadataCh2OPAudioStateCh1OutputEmbPair5s62628 OBJECT-TYPE
		SYNTAX		INTEGER { disable(0), enable(1) }
		MAX-ACCESS		read-write
		STATUS			current
		DESCRIPTION
				"TYPE: - Checkbox
				 PAGE: - O/P Audio State Ch1
					Output Emb.Pair 5 s  cmdID= 62628 "
		::= { iqudc32CmdEntry 62628 }


	iqudc32MetadataCh2OPAudioStateCh1OutputEmbPair5s62629 OBJECT-TYPE
		SYNTAX		RollCallString
		MAX-ACCESS		read-only
		STATUS			current
		DESCRIPTION
				"TYPE: - Display
				 PAGE: - O/P Audio State Ch1
					Output Emb.Pair 5 s  cmdID= 62629  format=   "
		::= { iqudc32CmdEntry 62629 }


	iqudc32MetadataCh2OPAudioStateCh1OutputEmbPair6s62630 OBJECT-TYPE
		SYNTAX		INTEGER { disable(0), enable(1) }
		MAX-ACCESS		read-write
		STATUS			current
		DESCRIPTION
				"TYPE: - Checkbox
				 PAGE: - O/P Audio State Ch1
					Output Emb.Pair 6 s  cmdID= 62630 "
		::= { iqudc32CmdEntry 62630 }


	iqudc32MetadataCh2OPAudioStateCh1OutputEmbPair6s62631 OBJECT-TYPE
		SYNTAX		RollCallString
		MAX-ACCESS		read-only
		STATUS			current
		DESCRIPTION
				"TYPE: - Display
				 PAGE: - O/P Audio State Ch1
					Output Emb.Pair 6 s  cmdID= 62631  format=   "
		::= { iqudc32CmdEntry 62631 }


	iqudc32MetadataCh2OPAudioStateCh1OutputEmbPair7s62632 OBJECT-TYPE
		SYNTAX		INTEGER { disable(0), enable(1) }
		MAX-ACCESS		read-write
		STATUS			current
		DESCRIPTION
				"TYPE: - Checkbox
				 PAGE: - O/P Audio State Ch1
					Output Emb.Pair 7 s  cmdID= 62632 "
		::= { iqudc32CmdEntry 62632 }


	iqudc32MetadataCh2OPAudioStateCh1OutputEmbPair7s62633 OBJECT-TYPE
		SYNTAX		RollCallString
		MAX-ACCESS		read-only
		STATUS			current
		DESCRIPTION
				"TYPE: - Display
				 PAGE: - O/P Audio State Ch1
					Output Emb.Pair 7 s  cmdID= 62633  format=   "
		::= { iqudc32CmdEntry 62633 }


	iqudc32MetadataCh2OPAudioStateCh1OutputEmbPair8s62634 OBJECT-TYPE
		SYNTAX		INTEGER { disable(0), enable(1) }
		MAX-ACCESS		read-write
		STATUS			current
		DESCRIPTION
				"TYPE: - Checkbox
				 PAGE: - O/P Audio State Ch1
					Output Emb.Pair 8 s  cmdID= 62634 "
		::= { iqudc32CmdEntry 62634 }


	iqudc32MetadataCh2OPAudioStateCh1OutputEmbPair8s62635 OBJECT-TYPE
		SYNTAX		RollCallString
		MAX-ACCESS		read-only
		STATUS			current
		DESCRIPTION
				"TYPE: - Display
				 PAGE: - O/P Audio State Ch1
					Output Emb.Pair 8 s  cmdID= 62635  format=   "
		::= { iqudc32CmdEntry 62635 }


	iqudc32MetadataCh2OPAudioStateCh2OutputEmbPair1s62636 OBJECT-TYPE
		SYNTAX		INTEGER { disable(0), enable(1) }
		MAX-ACCESS		read-write
		STATUS			current
		DESCRIPTION
				"TYPE: - Checkbox
				 PAGE: - O/P Audio State Ch2
					Output Emb.Pair 1 s  cmdID= 62636 "
		::= { iqudc32CmdEntry 62636 }


	iqudc32MetadataCh2OPAudioStateCh2OutputEmbPair1s62637 OBJECT-TYPE
		SYNTAX		RollCallString
		MAX-ACCESS		read-only
		STATUS			current
		DESCRIPTION
				"TYPE: - Display
				 PAGE: - O/P Audio State Ch2
					Output Emb.Pair 1 s  cmdID= 62637  format=   "
		::= { iqudc32CmdEntry 62637 }


	iqudc32MetadataCh2OPAudioStateCh2OutputEmbPair2s62638 OBJECT-TYPE
		SYNTAX		INTEGER { disable(0), enable(1) }
		MAX-ACCESS		read-write
		STATUS			current
		DESCRIPTION
				"TYPE: - Checkbox
				 PAGE: - O/P Audio State Ch2
					Output Emb.Pair 2 s  cmdID= 62638 "
		::= { iqudc32CmdEntry 62638 }


	iqudc32MetadataCh2OPAudioStateCh2OutputEmbPair2s62639 OBJECT-TYPE
		SYNTAX		RollCallString
		MAX-ACCESS		read-only
		STATUS			current
		DESCRIPTION
				"TYPE: - Display
				 PAGE: - O/P Audio State Ch2
					Output Emb.Pair 2 s  cmdID= 62639  format=   "
		::= { iqudc32CmdEntry 62639 }


	iqudc32MetadataCh2OPAudioStateCh2OutputEmbPair3s62640 OBJECT-TYPE
		SYNTAX		INTEGER { disable(0), enable(1) }
		MAX-ACCESS		read-write
		STATUS			current
		DESCRIPTION
				"TYPE: - Checkbox
				 PAGE: - O/P Audio State Ch2
					Output Emb.Pair 3 s  cmdID= 62640 "
		::= { iqudc32CmdEntry 62640 }


	iqudc32MetadataCh2OPAudioStateCh2OutputEmbPair3s62641 OBJECT-TYPE
		SYNTAX		RollCallString
		MAX-ACCESS		read-only
		STATUS			current
		DESCRIPTION
				"TYPE: - Display
				 PAGE: - O/P Audio State Ch2
					Output Emb.Pair 3 s  cmdID= 62641  format=   "
		::= { iqudc32CmdEntry 62641 }


	iqudc32MetadataCh2OPAudioStateCh2OutputEmbPair4s62642 OBJECT-TYPE
		SYNTAX		INTEGER { disable(0), enable(1) }
		MAX-ACCESS		read-write
		STATUS			current
		DESCRIPTION
				"TYPE: - Checkbox
				 PAGE: - O/P Audio State Ch2
					Output Emb.Pair 4 s  cmdID= 62642 "
		::= { iqudc32CmdEntry 62642 }


	iqudc32MetadataCh2OPAudioStateCh2OutputEmbPair4s62643 OBJECT-TYPE
		SYNTAX		RollCallString
		MAX-ACCESS		read-only
		STATUS			current
		DESCRIPTION
				"TYPE: - Display
				 PAGE: - O/P Audio State Ch2
					Output Emb.Pair 4 s  cmdID= 62643  format=   "
		::= { iqudc32CmdEntry 62643 }


	iqudc32MetadataCh2OPAudioStateCh2OutputEmbPair5s62644 OBJECT-TYPE
		SYNTAX		INTEGER { disable(0), enable(1) }
		MAX-ACCESS		read-write
		STATUS			current
		DESCRIPTION
				"TYPE: - Checkbox
				 PAGE: - O/P Audio State Ch2
					Output Emb.Pair 5 s  cmdID= 62644 "
		::= { iqudc32CmdEntry 62644 }


	iqudc32MetadataCh2OPAudioStateCh2OutputEmbPair5s62645 OBJECT-TYPE
		SYNTAX		RollCallString
		MAX-ACCESS		read-only
		STATUS			current
		DESCRIPTION
				"TYPE: - Display
				 PAGE: - O/P Audio State Ch2
					Output Emb.Pair 5 s  cmdID= 62645  format=   "
		::= { iqudc32CmdEntry 62645 }


	iqudc32MetadataCh2OPAudioStateCh2OutputEmbPair6s62646 OBJECT-TYPE
		SYNTAX		INTEGER { disable(0), enable(1) }
		MAX-ACCESS		read-write
		STATUS			current
		DESCRIPTION
				"TYPE: - Checkbox
				 PAGE: - O/P Audio State Ch2
					Output Emb.Pair 6 s  cmdID= 62646 "
		::= { iqudc32CmdEntry 62646 }


	iqudc32MetadataCh2OPAudioStateCh2OutputEmbPair6s62647 OBJECT-TYPE
		SYNTAX		RollCallString
		MAX-ACCESS		read-only
		STATUS			current
		DESCRIPTION
				"TYPE: - Display
				 PAGE: - O/P Audio State Ch2
					Output Emb.Pair 6 s  cmdID= 62647  format=   "
		::= { iqudc32CmdEntry 62647 }


	iqudc32MetadataCh2OPAudioStateCh2OutputEmbPair7s62648 OBJECT-TYPE
		SYNTAX		INTEGER { disable(0), enable(1) }
		MAX-ACCESS		read-write
		STATUS			current
		DESCRIPTION
				"TYPE: - Checkbox
				 PAGE: - O/P Audio State Ch2
					Output Emb.Pair 7 s  cmdID= 62648 "
		::= { iqudc32CmdEntry 62648 }


	iqudc32MetadataCh2OPAudioStateCh2OutputEmbPair7s62649 OBJECT-TYPE
		SYNTAX		RollCallString
		MAX-ACCESS		read-only
		STATUS			current
		DESCRIPTION
				"TYPE: - Display
				 PAGE: - O/P Audio State Ch2
					Output Emb.Pair 7 s  cmdID= 62649  format=   "
		::= { iqudc32CmdEntry 62649 }


	iqudc32MetadataCh2OPAudioStateCh2OutputEmbPair8s62650 OBJECT-TYPE
		SYNTAX		INTEGER { disable(0), enable(1) }
		MAX-ACCESS		read-write
		STATUS			current
		DESCRIPTION
				"TYPE: - Checkbox
				 PAGE: - O/P Audio State Ch2
					Output Emb.Pair 8 s  cmdID= 62650 "
		::= { iqudc32CmdEntry 62650 }


	iqudc32MetadataCh2OPAudioStateCh2OutputEmbPair8s62651 OBJECT-TYPE
		SYNTAX		RollCallString
		MAX-ACCESS		read-only
		STATUS			current
		DESCRIPTION
				"TYPE: - Display
				 PAGE: - O/P Audio State Ch2
					Output Emb.Pair 8 s  cmdID= 62651  format=   "
		::= { iqudc32CmdEntry 62651 }


	iqudc32MetadataCh2OPAudioStateCh2NewDisplay OBJECT-TYPE
		SYNTAX		RollCallString
		MAX-ACCESS		read-only
		STATUS			current
		DESCRIPTION
				"TYPE: - Display
				 PAGE: - O/P Audio State Ch2
					New Display  cmdID= 62652  format=   "
		::= { iqudc32CmdEntry 62652 }


	iqudc32MetadataCh2OPAudioTypeCh1OutputEmbPair1t62653 OBJECT-TYPE
		SYNTAX		INTEGER { disable(0), enable(1) }
		MAX-ACCESS		read-write
		STATUS			current
		DESCRIPTION
				"TYPE: - Checkbox
				 PAGE: - O/P Audio Type Ch1 
					Output Emb.Pair 1 t  cmdID= 62653 "
		::= { iqudc32CmdEntry 62653 }


	iqudc32MetadataCh2OPAudioTypeCh1OutputEmbPair1t62654 OBJECT-TYPE
		SYNTAX		RollCallString
		MAX-ACCESS		read-only
		STATUS			current
		DESCRIPTION
				"TYPE: - Display
				 PAGE: - O/P Audio Type Ch1 
					Output Emb.Pair 1 t  cmdID= 62654  format=   "
		::= { iqudc32CmdEntry 62654 }


	iqudc32MetadataCh2OPAudioTypeCh1OutputEmbPair2t OBJECT-TYPE
		SYNTAX		INTEGER { disable(0), enable(1) }
		MAX-ACCESS		read-write
		STATUS			current
		DESCRIPTION
				"TYPE: - Checkbox
				 PAGE: - O/P Audio Type Ch1 
					Output Emb.Pair 2 t  cmdID= 62655 "
		::= { iqudc32CmdEntry 62655 }


	iqudc32MetadataCh2OPAudioTypeCh1OutputEmbPair2s OBJECT-TYPE
		SYNTAX		RollCallString
		MAX-ACCESS		read-only
		STATUS			current
		DESCRIPTION
				"TYPE: - Display
				 PAGE: - O/P Audio Type Ch1 
					Output Emb.Pair 2 s  cmdID= 62656  format=   "
		::= { iqudc32CmdEntry 62656 }


	iqudc32MetadataCh2OPAudioTypeCh1OutputEmbPair3t62657 OBJECT-TYPE
		SYNTAX		INTEGER { disable(0), enable(1) }
		MAX-ACCESS		read-write
		STATUS			current
		DESCRIPTION
				"TYPE: - Checkbox
				 PAGE: - O/P Audio Type Ch1 
					Output Emb.Pair 3 t  cmdID= 62657 "
		::= { iqudc32CmdEntry 62657 }


	iqudc32MetadataCh2OPAudioTypeCh1OutputEmbPair3t62658 OBJECT-TYPE
		SYNTAX		RollCallString
		MAX-ACCESS		read-only
		STATUS			current
		DESCRIPTION
				"TYPE: - Display
				 PAGE: - O/P Audio Type Ch1 
					Output Emb.Pair 3 t  cmdID= 62658  format=   "
		::= { iqudc32CmdEntry 62658 }


	iqudc32MetadataCh2OPAudioTypeCh1OutputEmbPair4t62659 OBJECT-TYPE
		SYNTAX		INTEGER { disable(0), enable(1) }
		MAX-ACCESS		read-write
		STATUS			current
		DESCRIPTION
				"TYPE: - Checkbox
				 PAGE: - O/P Audio Type Ch1 
					Output Emb.Pair 4 t  cmdID= 62659 "
		::= { iqudc32CmdEntry 62659 }


	iqudc32MetadataCh2OPAudioTypeCh1OutputEmbPair4t62660 OBJECT-TYPE
		SYNTAX		RollCallString
		MAX-ACCESS		read-only
		STATUS			current
		DESCRIPTION
				"TYPE: - Display
				 PAGE: - O/P Audio Type Ch1 
					Output Emb.Pair 4 t  cmdID= 62660  format=   "
		::= { iqudc32CmdEntry 62660 }


	iqudc32MetadataCh2OPAudioTypeCh1OutputEmbPair5t62661 OBJECT-TYPE
		SYNTAX		INTEGER { disable(0), enable(1) }
		MAX-ACCESS		read-write
		STATUS			current
		DESCRIPTION
				"TYPE: - Checkbox
				 PAGE: - O/P Audio Type Ch1 
					Output Emb.Pair 5 t  cmdID= 62661 "
		::= { iqudc32CmdEntry 62661 }


	iqudc32MetadataCh2OPAudioTypeCh1OutputEmbPair5t62662 OBJECT-TYPE
		SYNTAX		RollCallString
		MAX-ACCESS		read-only
		STATUS			current
		DESCRIPTION
				"TYPE: - Display
				 PAGE: - O/P Audio Type Ch1 
					Output Emb.Pair 5 t  cmdID= 62662  format=   "
		::= { iqudc32CmdEntry 62662 }


	iqudc32MetadataCh2OPAudioTypeCh1OutputEmbPair6t62663 OBJECT-TYPE
		SYNTAX		INTEGER { disable(0), enable(1) }
		MAX-ACCESS		read-write
		STATUS			current
		DESCRIPTION
				"TYPE: - Checkbox
				 PAGE: - O/P Audio Type Ch1 
					Output Emb.Pair 6 t  cmdID= 62663 "
		::= { iqudc32CmdEntry 62663 }


	iqudc32MetadataCh2OPAudioTypeCh1OutputEmbPair6t62664 OBJECT-TYPE
		SYNTAX		RollCallString
		MAX-ACCESS		read-only
		STATUS			current
		DESCRIPTION
				"TYPE: - Display
				 PAGE: - O/P Audio Type Ch1 
					Output Emb.Pair 6 t  cmdID= 62664  format=   "
		::= { iqudc32CmdEntry 62664 }


	iqudc32MetadataCh2OPAudioTypeCh1OutputEmbPair7t62665 OBJECT-TYPE
		SYNTAX		INTEGER { disable(0), enable(1) }
		MAX-ACCESS		read-write
		STATUS			current
		DESCRIPTION
				"TYPE: - Checkbox
				 PAGE: - O/P Audio Type Ch1 
					Output Emb.Pair 7 t  cmdID= 62665 "
		::= { iqudc32CmdEntry 62665 }


	iqudc32MetadataCh2OPAudioTypeCh1OutputEmbPair7t62666 OBJECT-TYPE
		SYNTAX		RollCallString
		MAX-ACCESS		read-only
		STATUS			current
		DESCRIPTION
				"TYPE: - Display
				 PAGE: - O/P Audio Type Ch1 
					Output Emb.Pair 7 t  cmdID= 62666  format=   "
		::= { iqudc32CmdEntry 62666 }


	iqudc32MetadataCh2OPAudioTypeCh1OutputEmbPair8t62667 OBJECT-TYPE
		SYNTAX		INTEGER { disable(0), enable(1) }
		MAX-ACCESS		read-write
		STATUS			current
		DESCRIPTION
				"TYPE: - Checkbox
				 PAGE: - O/P Audio Type Ch1 
					Output Emb.Pair 8 t  cmdID= 62667 "
		::= { iqudc32CmdEntry 62667 }


	iqudc32MetadataCh2OPAudioTypeCh1OutputEmbPair8t62668 OBJECT-TYPE
		SYNTAX		RollCallString
		MAX-ACCESS		read-only
		STATUS			current
		DESCRIPTION
				"TYPE: - Display
				 PAGE: - O/P Audio Type Ch1 
					Output Emb.Pair 8 t  cmdID= 62668  format=   "
		::= { iqudc32CmdEntry 62668 }


	iqudc32MetadataCh2OPAudioTypeCh2OutputEmbPair1t62669 OBJECT-TYPE
		SYNTAX		INTEGER { disable(0), enable(1) }
		MAX-ACCESS		read-write
		STATUS			current
		DESCRIPTION
				"TYPE: - Checkbox
				 PAGE: - O/P Audio Type Ch2 
					Output Emb.Pair 1 t  cmdID= 62669 "
		::= { iqudc32CmdEntry 62669 }


	iqudc32MetadataCh2OPAudioTypeCh2OutputEmbPair1t62670 OBJECT-TYPE
		SYNTAX		RollCallString
		MAX-ACCESS		read-only
		STATUS			current
		DESCRIPTION
				"TYPE: - Display
				 PAGE: - O/P Audio Type Ch2 
					Output Emb.Pair 1 t  cmdID= 62670  format=   "
		::= { iqudc32CmdEntry 62670 }


	iqudc32MetadataCh2OPAudioTypeCh2OutputEmbPair2t62671 OBJECT-TYPE
		SYNTAX		INTEGER { disable(0), enable(1) }
		MAX-ACCESS		read-write
		STATUS			current
		DESCRIPTION
				"TYPE: - Checkbox
				 PAGE: - O/P Audio Type Ch2 
					Output Emb.Pair 2 t  cmdID= 62671 "
		::= { iqudc32CmdEntry 62671 }


	iqudc32MetadataCh2OPAudioTypeCh2OutputEmbPair2t62672 OBJECT-TYPE
		SYNTAX		RollCallString
		MAX-ACCESS		read-only
		STATUS			current
		DESCRIPTION
				"TYPE: - Display
				 PAGE: - O/P Audio Type Ch2 
					Output Emb.Pair 2 t  cmdID= 62672  format=   "
		::= { iqudc32CmdEntry 62672 }


	iqudc32MetadataCh2OPAudioTypeCh2OutputEmbPair3t62673 OBJECT-TYPE
		SYNTAX		INTEGER { disable(0), enable(1) }
		MAX-ACCESS		read-write
		STATUS			current
		DESCRIPTION
				"TYPE: - Checkbox
				 PAGE: - O/P Audio Type Ch2 
					Output Emb.Pair 3 t  cmdID= 62673 "
		::= { iqudc32CmdEntry 62673 }


	iqudc32MetadataCh2OPAudioTypeCh2OutputEmbPair3t62674 OBJECT-TYPE
		SYNTAX		RollCallString
		MAX-ACCESS		read-only
		STATUS			current
		DESCRIPTION
				"TYPE: - Display
				 PAGE: - O/P Audio Type Ch2 
					Output Emb.Pair 3 t  cmdID= 62674  format=   "
		::= { iqudc32CmdEntry 62674 }


	iqudc32MetadataCh2OPAudioTypeCh2OutputEmbPair4t62675 OBJECT-TYPE
		SYNTAX		INTEGER { disable(0), enable(1) }
		MAX-ACCESS		read-write
		STATUS			current
		DESCRIPTION
				"TYPE: - Checkbox
				 PAGE: - O/P Audio Type Ch2 
					Output Emb.Pair 4 t  cmdID= 62675 "
		::= { iqudc32CmdEntry 62675 }


	iqudc32MetadataCh2OPAudioTypeCh2OutputEmbPair4t62676 OBJECT-TYPE
		SYNTAX		RollCallString
		MAX-ACCESS		read-only
		STATUS			current
		DESCRIPTION
				"TYPE: - Display
				 PAGE: - O/P Audio Type Ch2 
					Output Emb.Pair 4 t  cmdID= 62676  format=   "
		::= { iqudc32CmdEntry 62676 }


	iqudc32MetadataCh2OPAudioTypeCh2OutputEmbPair5t62677 OBJECT-TYPE
		SYNTAX		INTEGER { disable(0), enable(1) }
		MAX-ACCESS		read-write
		STATUS			current
		DESCRIPTION
				"TYPE: - Checkbox
				 PAGE: - O/P Audio Type Ch2 
					Output Emb.Pair 5 t  cmdID= 62677 "
		::= { iqudc32CmdEntry 62677 }


	iqudc32MetadataCh2OPAudioTypeCh2OutputEmbPair5t62678 OBJECT-TYPE
		SYNTAX		RollCallString
		MAX-ACCESS		read-only
		STATUS			current
		DESCRIPTION
				"TYPE: - Display
				 PAGE: - O/P Audio Type Ch2 
					Output Emb.Pair 5 t  cmdID= 62678  format=   "
		::= { iqudc32CmdEntry 62678 }


	iqudc32MetadataCh2OPAudioTypeCh2OutputEmbPair6t62679 OBJECT-TYPE
		SYNTAX		INTEGER { disable(0), enable(1) }
		MAX-ACCESS		read-write
		STATUS			current
		DESCRIPTION
				"TYPE: - Checkbox
				 PAGE: - O/P Audio Type Ch2 
					Output Emb.Pair 6 t  cmdID= 62679 "
		::= { iqudc32CmdEntry 62679 }


	iqudc32MetadataCh2OPAudioTypeCh2OutputEmbPair6t62680 OBJECT-TYPE
		SYNTAX		RollCallString
		MAX-ACCESS		read-only
		STATUS			current
		DESCRIPTION
				"TYPE: - Display
				 PAGE: - O/P Audio Type Ch2 
					Output Emb.Pair 6 t  cmdID= 62680  format=   "
		::= { iqudc32CmdEntry 62680 }


	iqudc32MetadataCh2OPAudioTypeCh2OutputEmbPair7t62681 OBJECT-TYPE
		SYNTAX		INTEGER { disable(0), enable(1) }
		MAX-ACCESS		read-write
		STATUS			current
		DESCRIPTION
				"TYPE: - Checkbox
				 PAGE: - O/P Audio Type Ch2 
					Output Emb.Pair 7 t  cmdID= 62681 "
		::= { iqudc32CmdEntry 62681 }


	iqudc32MetadataCh2OPAudioTypeCh2OutputEmbPair7t62682 OBJECT-TYPE
		SYNTAX		RollCallString
		MAX-ACCESS		read-only
		STATUS			current
		DESCRIPTION
				"TYPE: - Display
				 PAGE: - O/P Audio Type Ch2 
					Output Emb.Pair 7 t  cmdID= 62682  format=   "
		::= { iqudc32CmdEntry 62682 }


	iqudc32MetadataCh2OPAudioTypeCh2OutputEmbPair8t62683 OBJECT-TYPE
		SYNTAX		INTEGER { disable(0), enable(1) }
		MAX-ACCESS		read-write
		STATUS			current
		DESCRIPTION
				"TYPE: - Checkbox
				 PAGE: - O/P Audio Type Ch2 
					Output Emb.Pair 8 t  cmdID= 62683 "
		::= { iqudc32CmdEntry 62683 }


	iqudc32MetadataCh2OPAudioTypeCh2OutputEmbPair8t62684 OBJECT-TYPE
		SYNTAX		RollCallString
		MAX-ACCESS		read-only
		STATUS			current
		DESCRIPTION
				"TYPE: - Display
				 PAGE: - O/P Audio Type Ch2 
					Output Emb.Pair 8 t  cmdID= 62684  format=   "
		::= { iqudc32CmdEntry 62684 }


	iqudc32MetadataCh2OPAudioTypeCh2NewDisplay OBJECT-TYPE
		SYNTAX		RollCallString
		MAX-ACCESS		read-only
		STATUS			current
		DESCRIPTION
				"TYPE: - Display
				 PAGE: - O/P Audio Type Ch2 
					New Display  cmdID= 62685  format=   "
		::= { iqudc32CmdEntry 62685 }


	iqudc32MetadataCh2SetupSoftwareVersion OBJECT-TYPE
		SYNTAX		RollCallString
		MAX-ACCESS		read-only
		STATUS			current
		DESCRIPTION
				"TYPE: - Display
				 PAGE: - Setup
					Software Version  cmdID= 2  format=   "
		::= { iqudc32CmdEntry 2 }


	iqudc32MetadataCh2SetupSerialNumber OBJECT-TYPE
		SYNTAX		RollCallString
		MAX-ACCESS		read-only
		STATUS			current
		DESCRIPTION
				"TYPE: - Display
				 PAGE: - Setup
					Serial Number  cmdID= 1  format=   "
		::= { iqudc32CmdEntry 1 }


	iqudc32MetadataCh2SetupNumberOfChannels OBJECT-TYPE
		SYNTAX		RollCallString
		MAX-ACCESS		read-only
		STATUS			current
		DESCRIPTION
				"TYPE: - Display
				 PAGE: - Setup
					Number Of Channels  cmdID= 44456  format=   "
		::= { iqudc32CmdEntry 44456 }


	iqudc32MetadataCh2SetupFrameSlotNumber OBJECT-TYPE
		SYNTAX		RollCallString
		MAX-ACCESS		read-only
		STATUS			current
		DESCRIPTION
				"TYPE: - Display
				 PAGE: - Setup
					Frame Slot Number  cmdID= 44455  format=   "
		::= { iqudc32CmdEntry 44455 }


	iqudc32MetadataCh2SetupRearId OBJECT-TYPE
		SYNTAX		RollCallString
		MAX-ACCESS		read-only
		STATUS			current
		DESCRIPTION
				"TYPE: - Display
				 PAGE: - Setup
					Rear Id  cmdID= 44444  format=   "
		::= { iqudc32CmdEntry 44444 }


	iqudc32MetadataCh2SetupFanSpeed OBJECT-TYPE
		SYNTAX		RollCallString
		MAX-ACCESS		read-only
		STATUS			current
		DESCRIPTION
				"TYPE: - Display
				 PAGE: - Setup
					Fan Speed  cmdID= 61003  format=   "
		::= { iqudc32CmdEntry 61003 }


	iqudc32MetadataCh2SetupIQOPTMNR OBJECT-TYPE
		SYNTAX		RollCallString
		MAX-ACCESS		read-only
		STATUS			current
		DESCRIPTION
				"TYPE: - Display
				 PAGE: - Setup
					IQOPTM-NR  cmdID= 62687  format=   "
		::= { iqudc32CmdEntry 62687 }


	iqudc32MetadataCh2SetupIQOPTMSBK OBJECT-TYPE
		SYNTAX		RollCallString
		MAX-ACCESS		read-only
		STATUS			current
		DESCRIPTION
				"TYPE: - Display
				 PAGE: - Setup
					IQOPTM-SBK  cmdID= 62688  format=   "
		::= { iqudc32CmdEntry 62688 }


	iqudc32MetadataCh2SetupIQOPTMLFR OBJECT-TYPE
		SYNTAX		RollCallString
		MAX-ACCESS		read-only
		STATUS			current
		DESCRIPTION
				"TYPE: - Display
				 PAGE: - Setup
					IQOPTM-LFR  cmdID= 62691  format=   "
		::= { iqudc32CmdEntry 62691 }


	iqudc32MetadataCh2SetupIQOPTMLOG OBJECT-TYPE
		SYNTAX		RollCallString
		MAX-ACCESS		read-only
		STATUS			current
		DESCRIPTION
				"TYPE: - Display
				 PAGE: - Setup
					IQOPTM-LOG  cmdID= 62692  format=   "
		::= { iqudc32CmdEntry 62692 }


	iqudc32MetadataCh2SetupIQOPTMLC OBJECT-TYPE
		SYNTAX		RollCallString
		MAX-ACCESS		read-only
		STATUS			current
		DESCRIPTION
				"TYPE: - Display
				 PAGE: - Setup
					IQOPTM-LC  cmdID= 62693  format=   "
		::= { iqudc32CmdEntry 62693 }


	iqudc32MetadataCh2SetupIQOPTMDBD OBJECT-TYPE
		SYNTAX		RollCallString
		MAX-ACCESS		read-only
		STATUS			current
		DESCRIPTION
				"TYPE: - Display
				 PAGE: - Setup
					IQOPTM-DBD  cmdID= 62694  format=   "
		::= { iqudc32CmdEntry 62694 }


	iqudc32MetadataCh2SetupIQOPTMDBEE OBJECT-TYPE
		SYNTAX		RollCallString
		MAX-ACCESS		read-only
		STATUS			current
		DESCRIPTION
				"TYPE: - Display
				 PAGE: - Setup
					IQOPTM-DBE-E  cmdID= 62695  format=   "
		::= { iqudc32CmdEntry 62695 }


	iqudc32MetadataCh2SetupIQOPTMDBED OBJECT-TYPE
		SYNTAX		RollCallString
		MAX-ACCESS		read-only
		STATUS			current
		DESCRIPTION
				"TYPE: - Display
				 PAGE: - Setup
					IQOPTM-DBE-D  cmdID= 62696  format=   "
		::= { iqudc32CmdEntry 62696 }


	iqudc32MetadataCh2SetupIQOPTMLOUDJ OBJECT-TYPE
		SYNTAX		RollCallString
		MAX-ACCESS		read-only
		STATUS			current
		DESCRIPTION
				"TYPE: - Display
				 PAGE: - Setup
					IQOPTM-LOUD-J  cmdID= 62697  format=   "
		::= { iqudc32CmdEntry 62697 }


	iqudc32MetadataCh2SetupIQOPTMLOUDMC OBJECT-TYPE
		SYNTAX		RollCallString
		MAX-ACCESS		read-only
		STATUS			current
		DESCRIPTION
				"TYPE: - Display
				 PAGE: - Setup
					IQOPTM-LOUD-MC  cmdID= 62698  format=   "
		::= { iqudc32CmdEntry 62698 }


	iqudc32MetadataCh2SetupBuild OBJECT-TYPE
		SYNTAX		RollCallString
		MAX-ACCESS		read-only
		STATUS			current
		DESCRIPTION
				"TYPE: - Display
				 PAGE: - Setup
					Build  cmdID= 62689  format=   "
		::= { iqudc32CmdEntry 62689 }


	iqudc32MetadataCh2SetupLicencedOptionsH OBJECT-TYPE
		SYNTAX		RollCallString
		MAX-ACCESS		read-only
		STATUS			current
		DESCRIPTION
				"TYPE: - Display
				 PAGE: - Setup
					Licenced Options (H  cmdID= 62690  format=   "
		::= { iqudc32CmdEntry 62690 }


	iqudc32MetadataCh2SetupFactoryDefaults OBJECT-TYPE
		SYNTAX		INTEGER { noAction(0),val-Factory-Defaults(1) }
		MAX-ACCESS		read-write
		STATUS			current
		DESCRIPTION
				"TYPE: - Button
				 PAGE: - Setup
					Factory Defaults  cmdID= 55555  value= 1  "
		::= { iqudc32CmdEntry 55555 }


	iqudc32MetadataCh2SetupDefaultSettings OBJECT-TYPE
		SYNTAX		INTEGER { noAction(0),val-Default-Settings(1) }
		MAX-ACCESS		read-write
		STATUS			current
		DESCRIPTION
				"TYPE: - Button
				 PAGE: - Setup
					Default Settings  cmdID= 55054  value= 1  "
		::= { iqudc32CmdEntry 55054 }


	iqudc32MetadataCh2SetupRestart OBJECT-TYPE
		SYNTAX		INTEGER { noAction(0),val-Restart(1) }
		MAX-ACCESS		read-write
		STATUS			current
		DESCRIPTION
				"TYPE: - Button
				 PAGE: - Setup
					Restart  cmdID= 4  value= 1  "
		::= { iqudc32CmdEntry 4 }


	iqudc32MetadataCh2SetupUpgradeStartHide OBJECT-TYPE
		SYNTAX		INTEGER { noAction(0),val-Upgrade-Start-Hide(1) }
		MAX-ACCESS		read-write
		STATUS			current
		DESCRIPTION
				"TYPE: - Button
				 PAGE: - Setup
					Upgrade Start (Hide  cmdID= 5  value= 1  "
		::= { iqudc32CmdEntry 5 }


	iqudc32MetadataCh2SetupUpgradeFinishHid OBJECT-TYPE
		SYNTAX		INTEGER { noAction(0),val-Upgrade-Finish-Hid(1) }
		MAX-ACCESS		read-write
		STATUS			current
		DESCRIPTION
				"TYPE: - Button
				 PAGE: - Setup
					Upgrade Finish (Hid  cmdID= 6  value= 1  "
		::= { iqudc32CmdEntry 6 }


	iqudc32MetadataCh2Displaymenu OBJECT-TYPE
		SYNTAX		INTEGER {
							val-Video-Input(0),
							val-Video-Output(1),
							val-Audio(2),
							val-Metadata(3),
							val-Reference(4)
							}
		MAX-ACCESS		read-write
		STATUS			current
		DESCRIPTION
				"TYPE: - RadiobuttonList
				 PAGE: - Displaymenu
					Display  cmdID= 62686 
					Video Input  value= 0  
					Video Output  value= 1  
					Audio  value= 2  
					Metadata  value= 3  
					Reference  value= 4  "
		::= { iqudc32CmdEntry 62686 }


	iqudc32MetadataCh2PlaceholderCh1ScrollingCaptionG OBJECT-TYPE
		SYNTAX		RollCallString
		MAX-ACCESS		read-only
		STATUS			current
		DESCRIPTION
				"TYPE: - Display
				 PAGE: - Placeholder-Ch1
					Scrolling Caption G  cmdID= 44459  format=   "
		::= { iqudc32CmdEntry 44459 }


	iqudc32MetadataCh2PlaceholderCh1SFPOutputRouting OBJECT-TYPE
		SYNTAX		RollCallString
		MAX-ACCESS		read-only
		STATUS			current
		DESCRIPTION
				"TYPE: - Display
				 PAGE: - Placeholder-Ch1
					SFP Output Routing   cmdID= 20515  format=   "
		::= { iqudc32CmdEntry 20515 }


	iqudc32MetadataCh2PlaceholderCh1CVBSEncoderPlaceh OBJECT-TYPE
		SYNTAX		RollCallString
		MAX-ACCESS		read-only
		STATUS			current
		DESCRIPTION
				"TYPE: - Display
				 PAGE: - Placeholder-Ch1
					CVBS Encoder Placeh  cmdID= 20507  format=   "
		::= { iqudc32CmdEntry 20507 }


	iqudc32MetadataCh2PlaceholderCh1LogoControlPlaceh OBJECT-TYPE
		SYNTAX		RollCallString
		MAX-ACCESS		read-only
		STATUS			current
		DESCRIPTION
				"TYPE: - Display
				 PAGE: - Placeholder-Ch1
					Logo Control Placeh  cmdID= 20316  format=   "
		::= { iqudc32CmdEntry 20316 }


	iqudc32MetadataCh2PlaceholderCh1NonlinearEnhancer OBJECT-TYPE
		SYNTAX		RollCallString
		MAX-ACCESS		read-only
		STATUS			current
		DESCRIPTION
				"TYPE: - Display
				 PAGE: - Placeholder-Ch1
					Nonlinear Enhancer   cmdID= 64120  format=   "
		::= { iqudc32CmdEntry 64120 }


	iqudc32MetadataCh2PlaceholderCh1ConversionAperture OBJECT-TYPE
		SYNTAX		RollCallString
		MAX-ACCESS		read-only
		STATUS			current
		DESCRIPTION
				"TYPE: - Display
				 PAGE: - Placeholder-Ch1
					Conversion Aperture  cmdID= 64121  format=   "
		::= { iqudc32CmdEntry 64121 }


	iqudc32MetadataCh2PlaceholderCh1NoiseReducerPlace OBJECT-TYPE
		SYNTAX		RollCallString
		MAX-ACCESS		read-only
		STATUS			current
		DESCRIPTION
				"TYPE: - Display
				 PAGE: - Placeholder-Ch1
					Noise Reducer Place  cmdID= 64102  format=   "
		::= { iqudc32CmdEntry 64102 }


	iqudc32MetadataCh2PlaceholderCh1UpConversionPlace OBJECT-TYPE
		SYNTAX		RollCallString
		MAX-ACCESS		read-only
		STATUS			current
		DESCRIPTION
				"TYPE: - Display
				 PAGE: - Placeholder-Ch1
					Up Conversion Place  cmdID= 64103  format=   "
		::= { iqudc32CmdEntry 64103 }


	iqudc32MetadataCh2PlaceholderCh1GenlockTimingPlac OBJECT-TYPE
		SYNTAX		RollCallString
		MAX-ACCESS		read-only
		STATUS			current
		DESCRIPTION
				"TYPE: - Display
				 PAGE: - Placeholder-Ch1
					Genlock Timing Plac  cmdID= 64201  format=   "
		::= { iqudc32CmdEntry 64201 }


	iqudc32MetadataCh2PlaceholderCh1SMPTERDD8Placehol OBJECT-TYPE
		SYNTAX		RollCallString
		MAX-ACCESS		read-only
		STATUS			current
		DESCRIPTION
				"TYPE: - Display
				 PAGE: - Placeholder-Ch1
					SMPTE RDD8 Placehol  cmdID= 60464  format=   "
		::= { iqudc32CmdEntry 60464 }


	iqudc32MetadataCh2PlaceholderCh1SMPTE2031Placehol OBJECT-TYPE
		SYNTAX		RollCallString
		MAX-ACCESS		read-only
		STATUS			current
		DESCRIPTION
				"TYPE: - Display
				 PAGE: - Placeholder-Ch1
					SMPTE 2031 Placehol  cmdID= 60465  format=   "
		::= { iqudc32CmdEntry 60465 }


	iqudc32MetadataCh2PlaceholderCh2InputSourcePlaceh OBJECT-TYPE
		SYNTAX		RollCallString
		MAX-ACCESS		read-only
		STATUS			current
		DESCRIPTION
				"TYPE: - Display
				 PAGE: - Placeholder-Ch2
					Input Source Placeh  cmdID= 44445  format=   "
		::= { iqudc32CmdEntry 44445 }


	iqudc32MetadataCh2PlaceholderCh2ScrollingCaptionG OBJECT-TYPE
		SYNTAX		RollCallString
		MAX-ACCESS		read-only
		STATUS			current
		DESCRIPTION
				"TYPE: - Display
				 PAGE: - Placeholder-Ch2
					Scrolling Caption G  cmdID= 44460  format=   "
		::= { iqudc32CmdEntry 44460 }


	iqudc32MetadataCh2PlaceholderCh2SFPOutputRouting OBJECT-TYPE
		SYNTAX		RollCallString
		MAX-ACCESS		read-only
		STATUS			current
		DESCRIPTION
				"TYPE: - Display
				 PAGE: - Placeholder-Ch2
					SFP Output Routing   cmdID= 20518  format=   "
		::= { iqudc32CmdEntry 20518 }


	iqudc32MetadataCh2PlaceholderCh2CVBSEncoderPlaceh OBJECT-TYPE
		SYNTAX		RollCallString
		MAX-ACCESS		read-only
		STATUS			current
		DESCRIPTION
				"TYPE: - Display
				 PAGE: - Placeholder-Ch2
					CVBS Encoder Placeh  cmdID= 20511  format=   "
		::= { iqudc32CmdEntry 20511 }


	iqudc32MetadataCh2PlaceholderCh2LogoControlPlaceh OBJECT-TYPE
		SYNTAX		RollCallString
		MAX-ACCESS		read-only
		STATUS			current
		DESCRIPTION
				"TYPE: - Display
				 PAGE: - Placeholder-Ch2
					Logo Control Placeh  cmdID= 20416  format=   "
		::= { iqudc32CmdEntry 20416 }


	iqudc32MetadataCh2PlaceholderCh2NonlinearEnhancer OBJECT-TYPE
		SYNTAX		RollCallString
		MAX-ACCESS		read-only
		STATUS			current
		DESCRIPTION
				"TYPE: - Display
				 PAGE: - Placeholder-Ch2
					Nonlinear Enhancer   cmdID= 64122  format=   "
		::= { iqudc32CmdEntry 64122 }


	iqudc32MetadataCh2PlaceholderCh2ConversionAperture OBJECT-TYPE
		SYNTAX		RollCallString
		MAX-ACCESS		read-only
		STATUS			current
		DESCRIPTION
				"TYPE: - Display
				 PAGE: - Placeholder-Ch2
					Conversion Aperture  cmdID= 64123  format=   "
		::= { iqudc32CmdEntry 64123 }


	iqudc32MetadataCh2PlaceholderCh2NoiseReducerPlace OBJECT-TYPE
		SYNTAX		RollCallString
		MAX-ACCESS		read-only
		STATUS			current
		DESCRIPTION
				"TYPE: - Display
				 PAGE: - Placeholder-Ch2
					Noise Reducer Place  cmdID= 64202  format=   "
		::= { iqudc32CmdEntry 64202 }


	iqudc32MetadataCh2PlaceholderCh2UpConversionPlace OBJECT-TYPE
		SYNTAX		RollCallString
		MAX-ACCESS		read-only
		STATUS			current
		DESCRIPTION
				"TYPE: - Display
				 PAGE: - Placeholder-Ch2
					Up Conversion Place  cmdID= 64203  format=   "
		::= { iqudc32CmdEntry 64203 }


	iqudc32MetadataCh2PlaceholderCh2GenlockTimingPlac OBJECT-TYPE
		SYNTAX		RollCallString
		MAX-ACCESS		read-only
		STATUS			current
		DESCRIPTION
				"TYPE: - Display
				 PAGE: - Placeholder-Ch2
					Genlock Timing Plac  cmdID= 64210  format=   "
		::= { iqudc32CmdEntry 64210 }


	iqudc32MetadataCh2PlaceholderCh2SMPTERDD8Placehol OBJECT-TYPE
		SYNTAX		RollCallString
		MAX-ACCESS		read-only
		STATUS			current
		DESCRIPTION
				"TYPE: - Display
				 PAGE: - Placeholder-Ch2
					SMPTE RDD8 Placehol  cmdID= 60664  format=   "
		::= { iqudc32CmdEntry 60664 }


	iqudc32MetadataCh2PlaceholderCh2SMPTE2031Placehol OBJECT-TYPE
		SYNTAX		RollCallString
		MAX-ACCESS		read-only
		STATUS			current
		DESCRIPTION
				"TYPE: - Display
				 PAGE: - Placeholder-Ch2
					SMPTE 2031 Placehol  cmdID= 60665  format=   "
		::= { iqudc32CmdEntry 60665 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 14030209
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: POWER_USAGE
--
-- MIB ref		: swCardEventLogSlotXX       .11.80.79.87.69.82.95.85.83.65.71.69
-- absolute OID	: 1.3.6.1.4.1.7995.2.6.1.1.XX.11.80.79.87.69.82.95.85.83.65.71.69
-- Vary			: YES
--
-- Value(s)		: 
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: 
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: 
--				: 
-- Comments		: 
--
---------------------------------------------------------------------------------------------------
-- Header		: INPUT_3_TYPE
--
-- MIB ref		: swCardEventLogSlotXX       .12.73.78.80.85.84.95.51.95.84.89.80.69
-- absolute OID	: 1.3.6.1.4.1.7995.2.6.1.1.XX.12.73.78.80.85.84.95.51.95.84.89.80.69
-- Vary			: YES
--
-- Value(s)		: 
--				: 
-- Comments		: 
--
---------------------------------------------------------------------------------------------------
-- Header		: INPUT_4_TYPE
--
-- MIB ref		: swCardEventLogSlotXX       .12.73.78.80.85.84.95.52.95.84.89.80.69
-- absolute OID	: 1.3.6.1.4.1.7995.2.6.1.1.XX.12.73.78.80.85.84.95.52.95.84.89.80.69
-- Vary			: YES
--
-- Value(s)		: 
--				: 
-- Comments		: 
--
---------------------------------------------------------------------------------------------------
-- Header		: INPUT_5_TYPE
--
-- MIB ref		: swCardEventLogSlotXX       .12.73.78.80.85.84.95.53.95.84.89.80.69
-- absolute OID	: 1.3.6.1.4.1.7995.2.6.1.1.XX.12.73.78.80.85.84.95.53.95.84.89.80.69
-- Vary			: YES
--
-- Value(s)		: 
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2015-02-19T14:18:53Z
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: 
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: 
--				: 
-- Comments		: 
--
---------------------------------------------------------------------------------------------------
-- Header		: INPUT_3_STATE
--
-- MIB ref		: swCardEventLogSlotXX       .13.73.78.80.85.84.95.51.95.83.84.65.84.69
-- absolute OID	: 1.3.6.1.4.1.7995.2.6.1.1.XX.13.73.78.80.85.84.95.51.95.83.84.65.84.69
-- Vary			: YES
--
-- Value(s)		: 
--				: 
-- Comments		: 
--
---------------------------------------------------------------------------------------------------
-- Header		: INPUT_4_STATE
--
-- MIB ref		: swCardEventLogSlotXX       .13.73.78.80.85.84.95.52.95.83.84.65.84.69
-- absolute OID	: 1.3.6.1.4.1.7995.2.6.1.1.XX.13.73.78.80.85.84.95.52.95.83.84.65.84.69
-- Vary			: YES
--
-- Value(s)		: 
--				: 
-- Comments		: 
--
---------------------------------------------------------------------------------------------------
-- Header		: INPUT_5_STATE
--
-- MIB ref		: swCardEventLogSlotXX       .13.73.78.80.85.84.95.53.95.83.84.65.84.69
-- absolute OID	: 1.3.6.1.4.1.7995.2.6.1.1.XX.13.73.78.80.85.84.95.53.95.83.84.65.84.69
-- Vary			: YES
--
-- Value(s)		: 
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
-- Vary			: YES
--
-- Value(s)		: 
--				: 
-- Comments		: 
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
-- Vary			: YES
--
-- Value(s)		: 
--				: 
-- Comments		: 
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
-- Vary			: YES
--
-- Value(s)		: 
--				: 
-- Comments		: 
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
-- Vary			: YES
--
-- Value(s)		: 
--				: 
-- Comments		: 
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
-- Vary			: YES
--
-- Value(s)		: 
--				: 
-- Comments		: 
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
-- Vary			: YES
--
-- Value(s)		: 
--				: 
-- Comments		: 
--
---------------------------------------------------------------------------------------------------
-- Header		: INPUT_3_STANDARD
--
-- MIB ref		: swCardEventLogSlotXX       .16.73.78.80.85.84.95.51.95.83.84.65.78.68.65.82.68
-- absolute OID	: 1.3.6.1.4.1.7995.2.6.1.1.XX.16.73.78.80.85.84.95.51.95.83.84.65.78.68.65.82.68
-- Vary			: YES
--
-- Value(s)		: 
--				: 
-- Comments		: 
--
---------------------------------------------------------------------------------------------------
-- Header		: INPUT_4_STANDARD
--
-- MIB ref		: swCardEventLogSlotXX       .16.73.78.80.85.84.95.52.95.83.84.65.78.68.65.82.68
-- absolute OID	: 1.3.6.1.4.1.7995.2.6.1.1.XX.16.73.78.80.85.84.95.52.95.83.84.65.78.68.65.82.68
-- Vary			: YES
--
-- Value(s)		: 
--				: 
-- Comments		: 
--
---------------------------------------------------------------------------------------------------
-- Header		: INPUT_5_STANDARD
--
-- MIB ref		: swCardEventLogSlotXX       .16.73.78.80.85.84.95.53.95.83.84.65.78.68.65.82.68
-- absolute OID	: 1.3.6.1.4.1.7995.2.6.1.1.XX.16.73.78.80.85.84.95.53.95.83.84.65.78.68.65.82.68
-- Vary			: YES
--
-- Value(s)		: 
--				: 
-- Comments		: 
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
-- Vary			: YES
--
-- Value(s)		: 
--				: 
-- Comments		: 
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
-- Vary			: YES
--
-- Value(s)		: 
--				: 
-- Comments		: 
--
---------------------------------------------------------------------------------------------------
-- Header		: OUTPUT_1_EMBEDDED_AUDIO_1_TYPE
--
-- MIB ref		: swCardEventLogSlotXX       .30.79.85.84.80.85.84.95.49.95.69.77.66.69.68.68.69.68.95.65.85.68.73.79.95.49.95.84.89.80.69
-- absolute OID	: 1.3.6.1.4.1.7995.2.6.1.1.XX.30.79.85.84.80.85.84.95.49.95.69.77.66.69.68.68.69.68.95.65.85.68.73.79.95.49.95.84.89.80.69
-- Vary			: YES
--
-- Value(s)		: 
--				: 
-- Comments		: 
--
---------------------------------------------------------------------------------------------------
-- Header		: OUTPUT_1_EMBEDDED_AUDIO_2_TYPE
--
-- MIB ref		: swCardEventLogSlotXX       .30.79.85.84.80.85.84.95.49.95.69.77.66.69.68.68.69.68.95.65.85.68.73.79.95.50.95.84.89.80.69
-- absolute OID	: 1.3.6.1.4.1.7995.2.6.1.1.XX.30.79.85.84.80.85.84.95.49.95.69.77.66.69.68.68.69.68.95.65.85.68.73.79.95.50.95.84.89.80.69
-- Vary			: YES
--
-- Value(s)		: 
--				: 
-- Comments		: 
--
---------------------------------------------------------------------------------------------------
-- Header		: OUTPUT_1_EMBEDDED_AUDIO_3_TYPE
--
-- MIB ref		: swCardEventLogSlotXX       .30.79.85.84.80.85.84.95.49.95.69.77.66.69.68.68.69.68.95.65.85.68.73.79.95.51.95.84.89.80.69
-- absolute OID	: 1.3.6.1.4.1.7995.2.6.1.1.XX.30.79.85.84.80.85.84.95.49.95.69.77.66.69.68.68.69.68.95.65.85.68.73.79.95.51.95.84.89.80.69
-- Vary			: YES
--
-- Value(s)		: 
--				: 
-- Comments		: 
--
---------------------------------------------------------------------------------------------------
-- Header		: OUTPUT_1_EMBEDDED_AUDIO_4_TYPE
--
-- MIB ref		: swCardEventLogSlotXX       .30.79.85.84.80.85.84.95.49.95.69.77.66.69.68.68.69.68.95.65.85.68.73.79.95.52.95.84.89.80.69
-- absolute OID	: 1.3.6.1.4.1.7995.2.6.1.1.XX.30.79.85.84.80.85.84.95.49.95.69.77.66.69.68.68.69.68.95.65.85.68.73.79.95.52.95.84.89.80.69
-- Vary			: YES
--
-- Value(s)		: 
--				: 
-- Comments		: 
--
---------------------------------------------------------------------------------------------------
-- Header		: OUTPUT_1_EMBEDDED_AUDIO_5_TYPE
--
-- MIB ref		: swCardEventLogSlotXX       .30.79.85.84.80.85.84.95.49.95.69.77.66.69.68.68.69.68.95.65.85.68.73.79.95.53.95.84.89.80.69
-- absolute OID	: 1.3.6.1.4.1.7995.2.6.1.1.XX.30.79.85.84.80.85.84.95.49.95.69.77.66.69.68.68.69.68.95.65.85.68.73.79.95.53.95.84.89.80.69
-- Vary			: YES
--
-- Value(s)		: 
--				: 
-- Comments		: 
--
---------------------------------------------------------------------------------------------------
-- Header		: OUTPUT_1_EMBEDDED_AUDIO_6_TYPE
--
-- MIB ref		: swCardEventLogSlotXX       .30.79.85.84.80.85.84.95.49.95.69.77.66.69.68.68.69.68.95.65.85.68.73.79.95.54.95.84.89.80.69
-- absolute OID	: 1.3.6.1.4.1.7995.2.6.1.1.XX.30.79.85.84.80.85.84.95.49.95.69.77.66.69.68.68.69.68.95.65.85.68.73.79.95.54.95.84.89.80.69
-- Vary			: YES
--
-- Value(s)		: 
--				: 
-- Comments		: 
--
---------------------------------------------------------------------------------------------------
-- Header		: OUTPUT_1_EMBEDDED_AUDIO_7_TYPE
--
-- MIB ref		: swCardEventLogSlotXX       .30.79.85.84.80.85.84.95.49.95.69.77.66.69.68.68.69.68.95.65.85.68.73.79.95.55.95.84.89.80.69
-- absolute OID	: 1.3.6.1.4.1.7995.2.6.1.1.XX.30.79.85.84.80.85.84.95.49.95.69.77.66.69.68.68.69.68.95.65.85.68.73.79.95.55.95.84.89.80.69
-- Vary			: YES
--
-- Value(s)		: 
--				: 
-- Comments		: 
--
---------------------------------------------------------------------------------------------------
-- Header		: OUTPUT_1_EMBEDDED_AUDIO_8_TYPE
--
-- MIB ref		: swCardEventLogSlotXX       .30.79.85.84.80.85.84.95.49.95.69.77.66.69.68.68.69.68.95.65.85.68.73.79.95.56.95.84.89.80.69
-- absolute OID	: 1.3.6.1.4.1.7995.2.6.1.1.XX.30.79.85.84.80.85.84.95.49.95.69.77.66.69.68.68.69.68.95.65.85.68.73.79.95.56.95.84.89.80.69
-- Vary			: YES
--
-- Value(s)		: 
--				: 
-- Comments		: 
--
---------------------------------------------------------------------------------------------------
-- Header		: OUTPUT_2_EMBEDDED_AUDIO_1_TYPE
--
-- MIB ref		: swCardEventLogSlotXX       .30.79.85.84.80.85.84.95.50.95.69.77.66.69.68.68.69.68.95.65.85.68.73.79.95.49.95.84.89.80.69
-- absolute OID	: 1.3.6.1.4.1.7995.2.6.1.1.XX.30.79.85.84.80.85.84.95.50.95.69.77.66.69.68.68.69.68.95.65.85.68.73.79.95.49.95.84.89.80.69
-- Vary			: YES
--
-- Value(s)		: 
--				: 
-- Comments		: 
--
---------------------------------------------------------------------------------------------------
-- Header		: OUTPUT_2_EMBEDDED_AUDIO_2_TYPE
--
-- MIB ref		: swCardEventLogSlotXX       .30.79.85.84.80.85.84.95.50.95.69.77.66.69.68.68.69.68.95.65.85.68.73.79.95.50.95.84.89.80.69
-- absolute OID	: 1.3.6.1.4.1.7995.2.6.1.1.XX.30.79.85.84.80.85.84.95.50.95.69.77.66.69.68.68.69.68.95.65.85.68.73.79.95.50.95.84.89.80.69
-- Vary			: YES
--
-- Value(s)		: 
--				: 
-- Comments		: 
--
---------------------------------------------------------------------------------------------------
-- Header		: OUTPUT_2_EMBEDDED_AUDIO_3_TYPE
--
-- MIB ref		: swCardEventLogSlotXX       .30.79.85.84.80.85.84.95.50.95.69.77.66.69.68.68.69.68.95.65.85.68.73.79.95.51.95.84.89.80.69
-- absolute OID	: 1.3.6.1.4.1.7995.2.6.1.1.XX.30.79.85.84.80.85.84.95.50.95.69.77.66.69.68.68.69.68.95.65.85.68.73.79.95.51.95.84.89.80.69
-- Vary			: YES
--
-- Value(s)		: 
--				: 
-- Comments		: 
--
---------------------------------------------------------------------------------------------------
-- Header		: OUTPUT_2_EMBEDDED_AUDIO_4_TYPE
--
-- MIB ref		: swCardEventLogSlotXX       .30.79.85.84.80.85.84.95.50.95.69.77.66.69.68.68.69.68.95.65.85.68.73.79.95.52.95.84.89.80.69
-- absolute OID	: 1.3.6.1.4.1.7995.2.6.1.1.XX.30.79.85.84.80.85.84.95.50.95.69.77.66.69.68.68.69.68.95.65.85.68.73.79.95.52.95.84.89.80.69
-- Vary			: YES
--
-- Value(s)		: 
--				: 
-- Comments		: 
--
---------------------------------------------------------------------------------------------------
-- Header		: OUTPUT_2_EMBEDDED_AUDIO_5_TYPE
--
-- MIB ref		: swCardEventLogSlotXX       .30.79.85.84.80.85.84.95.50.95.69.77.66.69.68.68.69.68.95.65.85.68.73.79.95.53.95.84.89.80.69
-- absolute OID	: 1.3.6.1.4.1.7995.2.6.1.1.XX.30.79.85.84.80.85.84.95.50.95.69.77.66.69.68.68.69.68.95.65.85.68.73.79.95.53.95.84.89.80.69
-- Vary			: YES
--
-- Value(s)		: 
--				: 
-- Comments		: 
--
---------------------------------------------------------------------------------------------------
-- Header		: OUTPUT_2_EMBEDDED_AUDIO_6_TYPE
--
-- MIB ref		: swCardEventLogSlotXX       .30.79.85.84.80.85.84.95.50.95.69.77.66.69.68.68.69.68.95.65.85.68.73.79.95.54.95.84.89.80.69
-- absolute OID	: 1.3.6.1.4.1.7995.2.6.1.1.XX.30.79.85.84.80.85.84.95.50.95.69.77.66.69.68.68.69.68.95.65.85.68.73.79.95.54.95.84.89.80.69
-- Vary			: YES
--
-- Value(s)		: 
--				: 
-- Comments		: 
--
---------------------------------------------------------------------------------------------------
-- Header		: OUTPUT_2_EMBEDDED_AUDIO_7_TYPE
--
-- MIB ref		: swCardEventLogSlotXX       .30.79.85.84.80.85.84.95.50.95.69.77.66.69.68.68.69.68.95.65.85.68.73.79.95.55.95.84.89.80.69
-- absolute OID	: 1.3.6.1.4.1.7995.2.6.1.1.XX.30.79.85.84.80.85.84.95.50.95.69.77.66.69.68.68.69.68.95.65.85.68.73.79.95.55.95.84.89.80.69
-- Vary			: YES
--
-- Value(s)		: 
--				: 
-- Comments		: 
--
---------------------------------------------------------------------------------------------------
-- Header		: OUTPUT_2_EMBEDDED_AUDIO_8_TYPE
--
-- MIB ref		: swCardEventLogSlotXX       .30.79.85.84.80.85.84.95.50.95.69.77.66.69.68.68.69.68.95.65.85.68.73.79.95.56.95.84.89.80.69
-- absolute OID	: 1.3.6.1.4.1.7995.2.6.1.1.XX.30.79.85.84.80.85.84.95.50.95.69.77.66.69.68.68.69.68.95.65.85.68.73.79.95.56.95.84.89.80.69
-- Vary			: YES
--
-- Value(s)		: 
--				: 
-- Comments		: 
--
---------------------------------------------------------------------------------------------------
-- Header		: OUTPUT_1_EMBEDDED_AUDIO_1_STATE
--
-- MIB ref		: swCardEventLogSlotXX       .31.79.85.84.80.85.84.95.49.95.69.77.66.69.68.68.69.68.95.65.85.68.73.79.95.49.95.83.84.65.84.69
-- absolute OID	: 1.3.6.1.4.1.7995.2.6.1.1.XX.31.79.85.84.80.85.84.95.49.95.69.77.66.69.68.68.69.68.95.65.85.68.73.79.95.49.95.83.84.65.84.69
-- Vary			: YES
--
-- Value(s)		: 
--				: 
-- Comments		: 
--
---------------------------------------------------------------------------------------------------
-- Header		: OUTPUT_1_EMBEDDED_AUDIO_2_STATE
--
-- MIB ref		: swCardEventLogSlotXX       .31.79.85.84.80.85.84.95.49.95.69.77.66.69.68.68.69.68.95.65.85.68.73.79.95.50.95.83.84.65.84.69
-- absolute OID	: 1.3.6.1.4.1.7995.2.6.1.1.XX.31.79.85.84.80.85.84.95.49.95.69.77.66.69.68.68.69.68.95.65.85.68.73.79.95.50.95.83.84.65.84.69
-- Vary			: YES
--
-- Value(s)		: 
--				: 
-- Comments		: 
--
---------------------------------------------------------------------------------------------------
-- Header		: OUTPUT_1_EMBEDDED_AUDIO_3_STATE
--
-- MIB ref		: swCardEventLogSlotXX       .31.79.85.84.80.85.84.95.49.95.69.77.66.69.68.68.69.68.95.65.85.68.73.79.95.51.95.83.84.65.84.69
-- absolute OID	: 1.3.6.1.4.1.7995.2.6.1.1.XX.31.79.85.84.80.85.84.95.49.95.69.77.66.69.68.68.69.68.95.65.85.68.73.79.95.51.95.83.84.65.84.69
-- Vary			: YES
--
-- Value(s)		: 
--				: 
-- Comments		: 
--
---------------------------------------------------------------------------------------------------
-- Header		: OUTPUT_1_EMBEDDED_AUDIO_4_STATE
--
-- MIB ref		: swCardEventLogSlotXX       .31.79.85.84.80.85.84.95.49.95.69.77.66.69.68.68.69.68.95.65.85.68.73.79.95.52.95.83.84.65.84.69
-- absolute OID	: 1.3.6.1.4.1.7995.2.6.1.1.XX.31.79.85.84.80.85.84.95.49.95.69.77.66.69.68.68.69.68.95.65.85.68.73.79.95.52.95.83.84.65.84.69
-- Vary			: YES
--
-- Value(s)		: 
--				: 
-- Comments		: 
--
---------------------------------------------------------------------------------------------------
-- Header		: OUTPUT_1_EMBEDDED_AUDIO_5_STATE
--
-- MIB ref		: swCardEventLogSlotXX       .31.79.85.84.80.85.84.95.49.95.69.77.66.69.68.68.69.68.95.65.85.68.73.79.95.53.95.83.84.65.84.69
-- absolute OID	: 1.3.6.1.4.1.7995.2.6.1.1.XX.31.79.85.84.80.85.84.95.49.95.69.77.66.69.68.68.69.68.95.65.85.68.73.79.95.53.95.83.84.65.84.69
-- Vary			: YES
--
-- Value(s)		: 
--				: 
-- Comments		: 
--
---------------------------------------------------------------------------------------------------
-- Header		: OUTPUT_1_EMBEDDED_AUDIO_6_STATE
--
-- MIB ref		: swCardEventLogSlotXX       .31.79.85.84.80.85.84.95.49.95.69.77.66.69.68.68.69.68.95.65.85.68.73.79.95.54.95.83.84.65.84.69
-- absolute OID	: 1.3.6.1.4.1.7995.2.6.1.1.XX.31.79.85.84.80.85.84.95.49.95.69.77.66.69.68.68.69.68.95.65.85.68.73.79.95.54.95.83.84.65.84.69
-- Vary			: YES
--
-- Value(s)		: 
--				: 
-- Comments		: 
--
---------------------------------------------------------------------------------------------------
-- Header		: OUTPUT_1_EMBEDDED_AUDIO_7_STATE
--
-- MIB ref		: swCardEventLogSlotXX       .31.79.85.84.80.85.84.95.49.95.69.77.66.69.68.68.69.68.95.65.85.68.73.79.95.55.95.83.84.65.84.69
-- absolute OID	: 1.3.6.1.4.1.7995.2.6.1.1.XX.31.79.85.84.80.85.84.95.49.95.69.77.66.69.68.68.69.68.95.65.85.68.73.79.95.55.95.83.84.65.84.69
-- Vary			: YES
--
-- Value(s)		: 
--				: 
-- Comments		: 
--
---------------------------------------------------------------------------------------------------
-- Header		: OUTPUT_1_EMBEDDED_AUDIO_8_STATE
--
-- MIB ref		: swCardEventLogSlotXX       .31.79.85.84.80.85.84.95.49.95.69.77.66.69.68.68.69.68.95.65.85.68.73.79.95.56.95.83.84.65.84.69
-- absolute OID	: 1.3.6.1.4.1.7995.2.6.1.1.XX.31.79.85.84.80.85.84.95.49.95.69.77.66.69.68.68.69.68.95.65.85.68.73.79.95.56.95.83.84.65.84.69
-- Vary			: YES
--
-- Value(s)		: 
--				: 
-- Comments		: 
--
---------------------------------------------------------------------------------------------------
-- Header		: OUTPUT_2_EMBEDDED_AUDIO_1_STATE
--
-- MIB ref		: swCardEventLogSlotXX       .31.79.85.84.80.85.84.95.50.95.69.77.66.69.68.68.69.68.95.65.85.68.73.79.95.49.95.83.84.65.84.69
-- absolute OID	: 1.3.6.1.4.1.7995.2.6.1.1.XX.31.79.85.84.80.85.84.95.50.95.69.77.66.69.68.68.69.68.95.65.85.68.73.79.95.49.95.83.84.65.84.69
-- Vary			: YES
--
-- Value(s)		: 
--				: 
-- Comments		: 
--
---------------------------------------------------------------------------------------------------
-- Header		: OUTPUT_2_EMBEDDED_AUDIO_2_STATE
--
-- MIB ref		: swCardEventLogSlotXX       .31.79.85.84.80.85.84.95.50.95.69.77.66.69.68.68.69.68.95.65.85.68.73.79.95.50.95.83.84.65.84.69
-- absolute OID	: 1.3.6.1.4.1.7995.2.6.1.1.XX.31.79.85.84.80.85.84.95.50.95.69.77.66.69.68.68.69.68.95.65.85.68.73.79.95.50.95.83.84.65.84.69
-- Vary			: YES
--
-- Value(s)		: 
--				: 
-- Comments		: 
--
---------------------------------------------------------------------------------------------------
-- Header		: OUTPUT_2_EMBEDDED_AUDIO_3_STATE
--
-- MIB ref		: swCardEventLogSlotXX       .31.79.85.84.80.85.84.95.50.95.69.77.66.69.68.68.69.68.95.65.85.68.73.79.95.51.95.83.84.65.84.69
-- absolute OID	: 1.3.6.1.4.1.7995.2.6.1.1.XX.31.79.85.84.80.85.84.95.50.95.69.77.66.69.68.68.69.68.95.65.85.68.73.79.95.51.95.83.84.65.84.69
-- Vary			: YES
--
-- Value(s)		: 
--				: 
-- Comments		: 
--
---------------------------------------------------------------------------------------------------
-- Header		: OUTPUT_2_EMBEDDED_AUDIO_4_STATE
--
-- MIB ref		: swCardEventLogSlotXX       .31.79.85.84.80.85.84.95.50.95.69.77.66.69.68.68.69.68.95.65.85.68.73.79.95.52.95.83.84.65.84.69
-- absolute OID	: 1.3.6.1.4.1.7995.2.6.1.1.XX.31.79.85.84.80.85.84.95.50.95.69.77.66.69.68.68.69.68.95.65.85.68.73.79.95.52.95.83.84.65.84.69
-- Vary			: YES
--
-- Value(s)		: 
--				: 
-- Comments		: 
--
---------------------------------------------------------------------------------------------------
-- Header		: OUTPUT_2_EMBEDDED_AUDIO_5_STATE
--
-- MIB ref		: swCardEventLogSlotXX       .31.79.85.84.80.85.84.95.50.95.69.77.66.69.68.68.69.68.95.65.85.68.73.79.95.53.95.83.84.65.84.69
-- absolute OID	: 1.3.6.1.4.1.7995.2.6.1.1.XX.31.79.85.84.80.85.84.95.50.95.69.77.66.69.68.68.69.68.95.65.85.68.73.79.95.53.95.83.84.65.84.69
-- Vary			: YES
--
-- Value(s)		: 
--				: 
-- Comments		: 
--
---------------------------------------------------------------------------------------------------
-- Header		: OUTPUT_2_EMBEDDED_AUDIO_6_STATE
--
-- MIB ref		: swCardEventLogSlotXX       .31.79.85.84.80.85.84.95.50.95.69.77.66.69.68.68.69.68.95.65.85.68.73.79.95.54.95.83.84.65.84.69
-- absolute OID	: 1.3.6.1.4.1.7995.2.6.1.1.XX.31.79.85.84.80.85.84.95.50.95.69.77.66.69.68.68.69.68.95.65.85.68.73.79.95.54.95.83.84.65.84.69
-- Vary			: YES
--
-- Value(s)		: 
--				: 
-- Comments		: 
--
---------------------------------------------------------------------------------------------------
-- Header		: OUTPUT_2_EMBEDDED_AUDIO_7_STATE
--
-- MIB ref		: swCardEventLogSlotXX       .31.79.85.84.80.85.84.95.50.95.69.77.66.69.68.68.69.68.95.65.85.68.73.79.95.55.95.83.84.65.84.69
-- absolute OID	: 1.3.6.1.4.1.7995.2.6.1.1.XX.31.79.85.84.80.85.84.95.50.95.69.77.66.69.68.68.69.68.95.65.85.68.73.79.95.55.95.83.84.65.84.69
-- Vary			: YES
--
-- Value(s)		: 
--				: 
-- Comments		: 
--
---------------------------------------------------------------------------------------------------
-- Header		: OUTPUT_2_EMBEDDED_AUDIO_8_STATE
--
-- MIB ref		: swCardEventLogSlotXX       .31.79.85.84.80.85.84.95.50.95.69.77.66.69.68.68.69.68.95.65.85.68.73.79.95.56.95.83.84.65.84.69
-- absolute OID	: 1.3.6.1.4.1.7995.2.6.1.1.XX.31.79.85.84.80.85.84.95.50.95.69.77.66.69.68.68.69.68.95.65.85.68.73.79.95.56.95.83.84.65.84.69
-- Vary			: YES
--
-- Value(s)		: 
--				: 
-- Comments		: 
--
---------------------------------------------------------------------------------------------------
