-- ************************************************************************************
--        Snell Card:IQOTR40
--        Module Id#:588
--       Command Set:7
--          Filename:SNELL-IQOTR40-CMD-MIB.mib
--            Author:r english
--              Date:24/02/2015
--              Time:16:45
--
-- Copyright (c) 2010 Snell Ltd
-- All rights reserved.
--
-- ************************************************************************************

SNELL-IQOTR40-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQOTR40,
    moduleIQOTR40MIB
        FROM SNELL-WILCOX-PRODUCT-REG;

 moduleIQOTR40CmdMi MODULE-IDENTITY
    LAST-UPDATED "1502241645Z"
    ORGANIZATION "Snell Ltd"
    CONTACT-INFO
        "Primary Author:r english

         postal:    Southleigh Park House
                    Eastleigh Road
                    Havant, Hants
                    PO9 2PE
         phone:     +44 (0)23 92489000
         email:     snmp.support@snellgroup.com"
    DESCRIPTION
        "This file defines the Snell card, command set  translations."
    ::= { moduleIQOTR40MIB 1 }




--********************************************************************************
--*
--*  Snell Card:
--*  command set:
--*  list commands/menus:
--*
--******************************************************************************
	iqotr40CmdTable OBJECT-TYPE
		SYNTAX			SEQUENCE OF Iqotr40CmdEntry
		MAX-ACCESS		not-accessible
		STATUS			current
		DESCRIPTION
				"Note the instance of this table is relected in the command set Version"
		::= { moduleIQOTR40 1 }

	iqotr40CmdEntry OBJECT-TYPE
		SYNTAX		Iqotr40CmdEntry
		MAX-ACCESS		not-accessible
		STATUS			current
		DESCRIPTION
				"Entry in command table."
		INDEX	{ iqotr40SlotIndex }
		::= { iqotr40CmdTable 1 }

	Iqotr40CmdEntry ::=
		SEQUENCE {
			iqotr40SlotIndex
				Unsigned32,
			iqotr40InputsInput1SD270
				INTEGER,
			iqotr40InputsInput1HD15G
				INTEGER,
			iqotr40InputsInput13G
				INTEGER,
			iqotr40InputsInput1Others
				INTEGER,
			iqotr40InputsInput1ReclockBypass
				INTEGER,
			iqotr40InputsInput2SD270
				INTEGER,
			iqotr40InputsInput2HD15G
				INTEGER,
			iqotr40InputsInput23G
				INTEGER,
			iqotr40InputsInput2Others
				INTEGER,
			iqotr40InputsInput2ReclockBypass
				INTEGER,
			iqotr40InputsInput3SD270
				INTEGER,
			iqotr40InputsInput3HD15G
				INTEGER,
			iqotr40InputsInput33G
				INTEGER,
			iqotr40InputsInput3Others
				INTEGER,
			iqotr40InputsInput3ReclockBypass
				INTEGER,
			iqotr40InputsInput4SD270
				INTEGER,
			iqotr40InputsInput4HD15G
				INTEGER,
			iqotr40InputsInput43G
				INTEGER,
			iqotr40InputsInput4Others
				INTEGER,
			iqotr40InputsInput4ReclockBypass
				INTEGER,
			iqotr40InputsInput5SD270
				INTEGER,
			iqotr40InputsInput5HD15G
				INTEGER,
			iqotr40InputsInput53G
				INTEGER,
			iqotr40InputsInput5Others
				INTEGER,
			iqotr40InputsInput5ReclockBypass
				INTEGER,
			iqotr40InputsInput6SD270
				INTEGER,
			iqotr40InputsInput6HD15G
				INTEGER,
			iqotr40InputsInput63G
				INTEGER,
			iqotr40InputsInput6Others
				INTEGER,
			iqotr40InputsInput6ReclockBypass
				INTEGER,
			iqotr40InputsInput7SD270
				INTEGER,
			iqotr40InputsInput7HD15G
				INTEGER,
			iqotr40InputsInput73G
				INTEGER,
			iqotr40InputsInput7Others
				INTEGER,
			iqotr40InputsInput7ReclockBypass
				INTEGER,
			iqotr40InputsInput8SD270
				INTEGER,
			iqotr40InputsInput8HD15G
				INTEGER,
			iqotr40InputsInput83G
				INTEGER,
			iqotr40InputsInput8Others
				INTEGER,
			iqotr40InputsInput8ReclockBypass
				INTEGER,
			iqotr40InputsPrimarySecondaryPrimaryInput4127
				INTEGER,
			iqotr40InputsPrimarySecondarySecondaryInput4126
				INTEGER,
			iqotr40InputsPrimaryInput14OKTimer
				INTEGER,
			iqotr40InputsPrimaryInput14ErrorTimer
				INTEGER,
			iqotr40InputsSecondaryInput14OKTimer
				INTEGER,
			iqotr40InputsSecondaryInput14ErrorTimer
				INTEGER,
			iqotr40InputsPrimarySecondaryPrimaryInput4295
				INTEGER,
			iqotr40InputsPrimarySecondarySecondaryInput4296
				INTEGER,
			iqotr40InputsPrimaryInput58OKTimer
				INTEGER,
			iqotr40InputsPrimaryInput58ErrorTimer
				INTEGER,
			iqotr40InputsSecondaryInput58OKTimer
				INTEGER,
			iqotr40InputsSecondaryInput58ErrorTimer
				INTEGER,
			iqotr40Config141Output1Inputselect
				INTEGER,
			iqotr40Config141Output1MuteonInputErr
				INTEGER,
			iqotr40Config141Output1Mute
				INTEGER,
			iqotr40Config141Output2Inputselect
				INTEGER,
			iqotr40Config141Output2MuteonInputErr
				INTEGER,
			iqotr40Config141Output2Mute
				INTEGER,
			iqotr40Config141Output3Inputselect
				INTEGER,
			iqotr40Config141Output3MuteonInputErr
				INTEGER,
			iqotr40Config141Output3Mute
				INTEGER,
			iqotr40Config141Output4Inputselect
				INTEGER,
			iqotr40Config141Output4MuteonInputErr
				INTEGER,
			iqotr40Config141Output4Mute
				INTEGER,
			iqotr40OutputsConfig141Conf1Selected
				RollCallString,
			iqotr40Config142Output1Inputselect
				INTEGER,
			iqotr40Config142Output1MuteonInputErr
				INTEGER,
			iqotr40Config142Output1Mute
				INTEGER,
			iqotr40Config142Output2Inputselect
				INTEGER,
			iqotr40Config142Output2MuteonInputErr
				INTEGER,
			iqotr40Config142Output2Mute
				INTEGER,
			iqotr40Config142Output3Inputselect
				INTEGER,
			iqotr40Config142Output3MuteonInputErr
				INTEGER,
			iqotr40Config142Output3Mute
				INTEGER,
			iqotr40Config142Output4Inputselect
				INTEGER,
			iqotr40Config142Output4MuteonInputErr
				INTEGER,
			iqotr40Config142Output4Mute
				INTEGER,
			iqotr40OutputsConfig142Conf2Selected
				RollCallString,
			iqotr40OutputsMode14
				INTEGER,
			iqotr40OutputsMode14SwapConfig12
				INTEGER,
			iqotr40OutputsRules14Config1PrimOK
				INTEGER,
			iqotr40OutputsRules14Config2PrimErr
				INTEGER,
			iqotr40OutputsRules14Config1SecErr
				INTEGER,
			iqotr40Config581Output5Inputselect
				INTEGER,
			iqotr40Config581Output5MuteonInputErr
				INTEGER,
			iqotr40Config581Output5Mute
				INTEGER,
			iqotr40Config581Output6Inputselect
				INTEGER,
			iqotr40Config581Output6MuteonInputErr
				INTEGER,
			iqotr40Config581Output6Mute
				INTEGER,
			iqotr40Config581Output7Inputselect
				INTEGER,
			iqotr40Config581Output7MuteonInputErr
				INTEGER,
			iqotr40Config581Output7Mute
				INTEGER,
			iqotr40Config581Output8Inputselect
				INTEGER,
			iqotr40Config581Output8MuteonInputErr
				INTEGER,
			iqotr40Config581Output8Mute
				INTEGER,
			iqotr40OutputsConfig581Conf1Selected
				RollCallString,
			iqotr40Config582Output5Inputselect
				INTEGER,
			iqotr40Config582Output5MuteonInputErr
				INTEGER,
			iqotr40Config582Output5Mute
				INTEGER,
			iqotr40Config582Output6Inputselect
				INTEGER,
			iqotr40Config582Output6MuteonInputErr
				INTEGER,
			iqotr40Config582Output6Mute
				INTEGER,
			iqotr40Config582Output7Inputselect
				INTEGER,
			iqotr40Config582Output7MuteonInputErr
				INTEGER,
			iqotr40Config582Output7Mute
				INTEGER,
			iqotr40Config582Output8Inputselect
				INTEGER,
			iqotr40Config582Output8MuteonInputErr
				INTEGER,
			iqotr40Config582Output8Mute
				INTEGER,
			iqotr40OutputsConfig582Conf2Selected
				RollCallString,
			iqotr40OutputsMode58
				INTEGER,
			iqotr40OutputsMode58SwapConfig12
				INTEGER,
			iqotr40OutputsRules58Config1PrimOK
				INTEGER,
			iqotr40OutputsRules58Config2PrimErr
				INTEGER,
			iqotr40OutputsRules58Config1SecErr
				INTEGER,
			iqotr40MenuMemoriesRecallMemory
				INTEGER,
			iqotr40MenuMemoriesSelMemory
				INTEGER,
			iqotr40MenuMemoriesSaveMemory
				INTEGER,
			iqotr40MenuMemoriesClearMemory
				INTEGER,
			iqotr40MemoriesMemoryNameChangeName
				RollCallString,
			iqotr40MenuMemoriesLastUserMemory
				RollCallString,
			iqotr40MenuMemoriesMemoryName1
				RollCallString,
			iqotr40MenuMemoriesMemoryName2
				RollCallString,
			iqotr40MenuMemoriesMemoryName3
				RollCallString,
			iqotr40MenuMemoriesMemoryName4
				RollCallString,
			iqotr40MenuMemoriesMemoryName5
				RollCallString,
			iqotr40MenuMemoriesMemoryName6
				RollCallString,
			iqotr40MenuMemoriesMemoryName7
				RollCallString,
			iqotr40MenuMemoriesMemoryName8
				RollCallString,
			iqotr40MenuMemoriesMemoryName9
				RollCallString,
			iqotr40MenuMemoriesMemoryName10
				RollCallString,
			iqotr40MenuMemoriesMemoryName11
				RollCallString,
			iqotr40MenuMemoriesMemoryName12
				RollCallString,
			iqotr40MenuMemoriesMemoryName13
				RollCallString,
			iqotr40MenuMemoriesMemoryName14
				RollCallString,
			iqotr40MenuMemoriesMemoryName15
				RollCallString,
			iqotr40MenuMemoriesMemoryName16
				RollCallString,
			iqotr40Logging1MiscLogSerialNo
				INTEGER,
			iqotr40Logging1MiscSerialNo
				RollCallString,
			iqotr40Logging1MiscLogOSVersion
				INTEGER,
			iqotr40Logging1MiscOSVersion
				RollCallString,
			iqotr40Logging1MiscLogBuildNo
				INTEGER,
			iqotr40Logging1MiscBuildNo
				RollCallString,
			iqotr40Logging1MiscLogHardwareVer
				INTEGER,
			iqotr40Logging1MiscHardwareVer
				RollCallString,
			iqotr40Logging1MiscLogFirmwareVer
				INTEGER,
			iqotr40Logging1MiscFirmwareVer
				RollCallString,
			iqotr40Logging1MiscLogRearID
				INTEGER,
			iqotr40Logging1MiscRearID
				RollCallString,
			iqotr40Logging1MiscLogRearStatus
				INTEGER,
			iqotr40Logging1MiscRearStatus
				RollCallString,
			iqotr40Logging1MiscLogSlotWidth
				INTEGER,
			iqotr40Logging1MiscSlotWidth
				RollCallString,
			iqotr40Logging1MiscLogSlotStart
				INTEGER,
			iqotr40Logging1MiscSlotStart
				RollCallString,
			iqotr40Logging1MiscLogIOMod1ID
				INTEGER,
			iqotr40Logging1MiscIOMod1ID
				RollCallString,
			iqotr40Logging1MiscLogIOMod2ID
				INTEGER,
			iqotr40Logging1MiscIOMod2ID
				RollCallString,
			iqotr40Logging1MiscLogProcModID
				INTEGER,
			iqotr40Logging1MiscProcModID
				RollCallString,
			iqotr40Logging1MiscLogUpTime
				INTEGER,
			iqotr40Logging1MiscUpTime
				RollCallString,
			iqotr40Logging1MiscLogLicensedOpt
				INTEGER,
			iqotr40Logging1MiscLicensedOptions
				RollCallString,
			iqotr40Logging1MiscLogConfig14InU
				INTEGER,
			iqotr40Logging1MiscConfig14InUse
				RollCallString,
			iqotr40Logging1MiscLogConfig58InU
				INTEGER,
			iqotr40Logging1MiscConfig58InUse
				RollCallString,
			iqotr40Logging1Input1LogIdent
				INTEGER,
			iqotr40Logging1Input1Ident
				RollCallString,
			iqotr40Logging1Input1LogName
				INTEGER,
			iqotr40Logging1Input1Name
				RollCallString,
			iqotr40Logging1Input1LogType
				INTEGER,
			iqotr40Logging1Input1Type
				RollCallString,
			iqotr40Logging1Input1LogState
				INTEGER,
			iqotr40Logging1Input1State
				RollCallString,
			iqotr40Logging1Input1LogSDIBitrate
				INTEGER,
			iqotr40Logging1Input1Bitrate
				RollCallString,
			iqotr40Logging1Input2LogIdent
				INTEGER,
			iqotr40Logging1Input2Ident
				RollCallString,
			iqotr40Logging1Input2LogName
				INTEGER,
			iqotr40Logging1Input2Name
				RollCallString,
			iqotr40Logging1Input2LogType
				INTEGER,
			iqotr40Logging1Input2Type
				RollCallString,
			iqotr40Logging1Input2LogState
				INTEGER,
			iqotr40Logging1Input2State
				RollCallString,
			iqotr40Logging1Input2LogSDIBitrate
				INTEGER,
			iqotr40Logging1Input2Bitrate
				RollCallString,
			iqotr40Logging1Input3LogIdent
				INTEGER,
			iqotr40Logging1Input3Ident
				RollCallString,
			iqotr40Logging1Input3LogName
				INTEGER,
			iqotr40Logging1Input3Name
				RollCallString,
			iqotr40Logging1Input3LogType
				INTEGER,
			iqotr40Logging1Input3Type
				RollCallString,
			iqotr40Logging1Input3LogState
				INTEGER,
			iqotr40Logging1Input3State
				RollCallString,
			iqotr40Logging1Input3LogSDIBitrate
				INTEGER,
			iqotr40Logging1Input3Bitrate
				RollCallString,
			iqotr40Logging1Input4LogIdent
				INTEGER,
			iqotr40Logging1Input4Ident
				RollCallString,
			iqotr40Logging1Input4LogName
				INTEGER,
			iqotr40Logging1Input4Name
				RollCallString,
			iqotr40Logging1Input4LogType
				INTEGER,
			iqotr40Logging1Input4Type
				RollCallString,
			iqotr40Logging1Input4LogState
				INTEGER,
			iqotr40Logging1Input4State
				RollCallString,
			iqotr40Logging1Input4LogSDIBitrate
				INTEGER,
			iqotr40Logging1Input4Bitrate
				RollCallString,
			iqotr40Logging1Input5LogIdent
				INTEGER,
			iqotr40Logging1Input5Ident
				RollCallString,
			iqotr40Logging1Input5LogName
				INTEGER,
			iqotr40Logging1Input5Name
				RollCallString,
			iqotr40Logging1Input5LogType
				INTEGER,
			iqotr40Logging1Input5Type
				RollCallString,
			iqotr40Logging1Input5LogState
				INTEGER,
			iqotr40Logging1Input5State
				RollCallString,
			iqotr40Logging1Input5LogSDIBitrate
				INTEGER,
			iqotr40Logging1Input5Bitrate
				RollCallString,
			iqotr40Logging1Input6LogIdent
				INTEGER,
			iqotr40Logging1Input6Ident
				RollCallString,
			iqotr40Logging1Input6LogName
				INTEGER,
			iqotr40Logging1Input6Name
				RollCallString,
			iqotr40Logging1Input6LogType
				INTEGER,
			iqotr40Logging1Input6Type
				RollCallString,
			iqotr40Logging1Input6LogState
				INTEGER,
			iqotr40Logging1Input6State
				RollCallString,
			iqotr40Logging1Input6LogSDIBitrate
				INTEGER,
			iqotr40Logging1Input6Bitrate
				RollCallString,
			iqotr40Logging1Input7LogIdent
				INTEGER,
			iqotr40Logging1Input7Ident
				RollCallString,
			iqotr40Logging1Input7LogName
				INTEGER,
			iqotr40Logging1Input7Name
				RollCallString,
			iqotr40Logging1Input7LogType
				INTEGER,
			iqotr40Logging1Input7Type
				RollCallString,
			iqotr40Logging1Input7LogState
				INTEGER,
			iqotr40Logging1Input7State
				RollCallString,
			iqotr40Logging1Input7LogSDIBitrate
				INTEGER,
			iqotr40Logging1Input7Bitrate
				RollCallString,
			iqotr40Logging1Input8LogIdent
				INTEGER,
			iqotr40Logging1Input8Ident
				RollCallString,
			iqotr40Logging1Input8LogName
				INTEGER,
			iqotr40Logging1Input8Name
				RollCallString,
			iqotr40Logging1Input8LogType
				INTEGER,
			iqotr40Logging1Input8Type
				RollCallString,
			iqotr40Logging1Input8LogState
				INTEGER,
			iqotr40Logging1Input8State
				RollCallString,
			iqotr40Logging1Input8LogSDIBitrate
				INTEGER,
			iqotr40Logging1Input8Bitrate
				RollCallString,
			iqotr40Logging2FiberTx1LaserBiasState35100
				INTEGER,
			iqotr40Logging2FiberTx1LaserBiasState35280
				RollCallString,
			iqotr40Logging2FiberTx1TxPowerState35110
				INTEGER,
			iqotr40Logging2FiberTx1TxPowerState35290
				RollCallString,
			iqotr40Logging2FiberTx1LaserBias35090
				INTEGER,
			iqotr40Logging2FiberTx1LaserBias35300
				RollCallString,
			iqotr40Logging2FiberTx1TxPower35130
				INTEGER,
			iqotr40Logging2FiberTx1TxPower35310
				RollCallString,
			iqotr40Logging2FiberTx1Wavelength35120
				INTEGER,
			iqotr40Logging2FiberTx1Wavelength35270
				RollCallString,
			iqotr40Logging2FiberTx1TxSFP35170
				INTEGER,
			iqotr40Logging2FiberTx1TxSFP35350
				RollCallString,
			iqotr40Logging2FiberTx2LaserBiasState35101
				INTEGER,
			iqotr40Logging2FiberTx2LaserBiasState35281
				RollCallString,
			iqotr40Logging2FiberTx2TxPowerState35111
				INTEGER,
			iqotr40Logging2FiberTx2TxPowerState35291
				RollCallString,
			iqotr40Logging2FiberTx2LaserBias35091
				INTEGER,
			iqotr40Logging2FiberTx2LaserBias35301
				RollCallString,
			iqotr40Logging2FiberTx2TxPower35131
				INTEGER,
			iqotr40Logging2FiberTx2TxPower35311
				RollCallString,
			iqotr40Logging2FiberTx2Wavelength35121
				INTEGER,
			iqotr40Logging2FiberTx2Wavelength35271
				RollCallString,
			iqotr40Logging2FiberTx2TxSFP35171
				INTEGER,
			iqotr40Logging2FiberTx2TxSFP35351
				RollCallString,
			iqotr40Logging2FiberTx3LaserBiasState35102
				INTEGER,
			iqotr40Logging2FiberTx3LaserBiasState35282
				RollCallString,
			iqotr40Logging2FiberTx3TxPowerState35112
				INTEGER,
			iqotr40Logging2FiberTx3TxPowerState35292
				RollCallString,
			iqotr40Logging2FiberTx3LaserBias35092
				INTEGER,
			iqotr40Logging2FiberTx3LaserBias35302
				RollCallString,
			iqotr40Logging2FiberTx3TxPower35132
				INTEGER,
			iqotr40Logging2FiberTx3TxPower35312
				RollCallString,
			iqotr40Logging2FiberTx3Wavelength35122
				INTEGER,
			iqotr40Logging2FiberTx3Wavelength35272
				RollCallString,
			iqotr40Logging2FiberTx3TxSFP35172
				INTEGER,
			iqotr40Logging2FiberTx3TxSFP35352
				RollCallString,
			iqotr40Logging2FiberTx4LaserBiasState35103
				INTEGER,
			iqotr40Logging2FiberTx4LaserBiasState35283
				RollCallString,
			iqotr40Logging2FiberTx4TxPowerState35113
				INTEGER,
			iqotr40Logging2FiberTx4TxPowerState35293
				RollCallString,
			iqotr40Logging2FiberTx4LaserBias35093
				INTEGER,
			iqotr40Logging2FiberTx4LaserBias35303
				RollCallString,
			iqotr40Logging2FiberTx4TxPower35133
				INTEGER,
			iqotr40Logging2FiberTx4TxPower35313
				RollCallString,
			iqotr40Logging2FiberTx4Wavelength35123
				INTEGER,
			iqotr40Logging2FiberTx4Wavelength35273
				RollCallString,
			iqotr40Logging2FiberTx4TxSFP35173
				INTEGER,
			iqotr40Logging2FiberTx4TxSFP35353
				RollCallString,
			iqotr40Logging2FiberTx5LaserBiasState35104
				INTEGER,
			iqotr40Logging2FiberTx5LaserBiasState35284
				RollCallString,
			iqotr40Logging2FiberTx5TxPowerState35114
				INTEGER,
			iqotr40Logging2FiberTx5TxPowerState35294
				RollCallString,
			iqotr40Logging2FiberTx5LaserBias35094
				INTEGER,
			iqotr40Logging2FiberTx5LaserBias35304
				RollCallString,
			iqotr40Logging2FiberTx5TxPower35134
				INTEGER,
			iqotr40Logging2FiberTx5TxPower35314
				RollCallString,
			iqotr40Logging2FiberTx5Wavelength35124
				INTEGER,
			iqotr40Logging2FiberTx5Wavelength35274
				RollCallString,
			iqotr40Logging2FiberTx5TxSFP35174
				INTEGER,
			iqotr40Logging2FiberTx5TxSFP35354
				RollCallString,
			iqotr40Logging2FiberTx6LaserBiasState35105
				INTEGER,
			iqotr40Logging2FiberTx6LaserBiasState35285
				RollCallString,
			iqotr40Logging2FiberTx6TxPowerState35115
				INTEGER,
			iqotr40Logging2FiberTx6TxPowerState35295
				RollCallString,
			iqotr40Logging2FiberTx6LaserBias35095
				INTEGER,
			iqotr40Logging2FiberTx6LaserBias35305
				RollCallString,
			iqotr40Logging2FiberTx6TxPower35135
				INTEGER,
			iqotr40Logging2FiberTx6TxPower35315
				RollCallString,
			iqotr40Logging2FiberTx6Wavelength35125
				INTEGER,
			iqotr40Logging2FiberTx6Wavelength35275
				RollCallString,
			iqotr40Logging2FiberTx6TxSFP35175
				INTEGER,
			iqotr40Logging2FiberTx6TxSFP35355
				RollCallString,
			iqotr40Logging2FiberTx7LaserBiasState35106
				INTEGER,
			iqotr40Logging2FiberTx7LaserBiasState35286
				RollCallString,
			iqotr40Logging2FiberTx7TxPowerState35116
				INTEGER,
			iqotr40Logging2FiberTx7TxPowerState35296
				RollCallString,
			iqotr40Logging2FiberTx7LaserBias35096
				INTEGER,
			iqotr40Logging2FiberTx7LaserBias35306
				RollCallString,
			iqotr40Logging2FiberTx7TxPower35136
				INTEGER,
			iqotr40Logging2FiberTx7TxPower35316
				RollCallString,
			iqotr40Logging2FiberTx7Wavelength35126
				INTEGER,
			iqotr40Logging2FiberTx7Wavelength35276
				RollCallString,
			iqotr40Logging2FiberTx7TxSFP35176
				INTEGER,
			iqotr40Logging2FiberTx7TxSFP35356
				RollCallString,
			iqotr40Logging2FiberTx8LaserBiasState35107
				INTEGER,
			iqotr40Logging2FiberTx8LaserBiasState35287
				RollCallString,
			iqotr40Logging2FiberTx8TxPowerState35117
				INTEGER,
			iqotr40Logging2FiberTx8TxPowerState35297
				RollCallString,
			iqotr40Logging2FiberTx8LaserBias35097
				INTEGER,
			iqotr40Logging2FiberTx8LaserBias35307
				RollCallString,
			iqotr40Logging2FiberTx8TxPower35137
				INTEGER,
			iqotr40Logging2FiberTx8TxPower35317
				RollCallString,
			iqotr40Logging2FiberTx8Wavelength35127
				INTEGER,
			iqotr40Logging2FiberTx8Wavelength35277
				RollCallString,
			iqotr40Logging2FiberTx8TxSFP35177
				INTEGER,
			iqotr40Logging2FiberTx8TxSFP35357
				RollCallString,
			iqotr40Logging2FiberRx1RxPowerState35140
				INTEGER,
			iqotr40Logging2FiberRx1RxPowerState35320
				RollCallString,
			iqotr40Logging2FiberRx1RxPower35150
				INTEGER,
			iqotr40Logging2FiberRx1RxPower35330
				RollCallString,
			iqotr40Logging2FiberRx1RxSFP35160
				INTEGER,
			iqotr40Logging2FiberRx1RxSFP35340
				RollCallString,
			iqotr40Logging2FiberRx2RxPowerState35141
				INTEGER,
			iqotr40Logging2FiberRx2RxPowerState35321
				RollCallString,
			iqotr40Logging2FiberRx2RxPower35151
				INTEGER,
			iqotr40Logging2FiberRx2RxPower35331
				RollCallString,
			iqotr40Logging2FiberRx2RxSFP35161
				INTEGER,
			iqotr40Logging2FiberRx2RxSFP35341
				RollCallString,
			iqotr40Logging2FiberRx3RxPowerState35142
				INTEGER,
			iqotr40Logging2FiberRx3RxPowerState35322
				RollCallString,
			iqotr40Logging2FiberRx3RxPower35152
				INTEGER,
			iqotr40Logging2FiberRx3RxPower35332
				RollCallString,
			iqotr40Logging2FiberRx3RxSFP35162
				INTEGER,
			iqotr40Logging2FiberRx3RxSFP35342
				RollCallString,
			iqotr40Logging2FiberRx4RxPowerState35143
				INTEGER,
			iqotr40Logging2FiberRx4RxPowerState35323
				RollCallString,
			iqotr40Logging2FiberRx4RxPower35153
				INTEGER,
			iqotr40Logging2FiberRx4RxPower35333
				RollCallString,
			iqotr40Logging2FiberRx4RxSFP35163
				INTEGER,
			iqotr40Logging2FiberRx4RxSFP35343
				RollCallString,
			iqotr40Logging2FiberRx5RxPowerState35144
				INTEGER,
			iqotr40Logging2FiberRx5RxPowerState35324
				RollCallString,
			iqotr40Logging2FiberRx5RxPower35154
				INTEGER,
			iqotr40Logging2FiberRx5RxPower35334
				RollCallString,
			iqotr40Logging2FiberRx5RxSFP35164
				INTEGER,
			iqotr40Logging2FiberRx5RxSFP35344
				RollCallString,
			iqotr40Logging2FiberRx6RxPowerState35145
				INTEGER,
			iqotr40Logging2FiberRx6RxPowerState35325
				RollCallString,
			iqotr40Logging2FiberRx6RxPower35155
				INTEGER,
			iqotr40Logging2FiberRx6RxPower35335
				RollCallString,
			iqotr40Logging2FiberRx6RxSFP35165
				INTEGER,
			iqotr40Logging2FiberRx6RxSFP35345
				RollCallString,
			iqotr40Logging2FiberRx7RxPowerState35146
				INTEGER,
			iqotr40Logging2FiberRx7RxPowerState35326
				RollCallString,
			iqotr40Logging2FiberRx7RxPower35156
				INTEGER,
			iqotr40Logging2FiberRx7RxPower35336
				RollCallString,
			iqotr40Logging2FiberRx7RxSFP35166
				INTEGER,
			iqotr40Logging2FiberRx7RxSFP35346
				RollCallString,
			iqotr40Logging2FiberRx8RxPowerState35147
				INTEGER,
			iqotr40Logging2FiberRx8RxPowerState35327
				RollCallString,
			iqotr40Logging2FiberRx8RxPower35157
				INTEGER,
			iqotr40Logging2FiberRx8RxPower35337
				RollCallString,
			iqotr40Logging2FiberRx8RxSFP35167
				INTEGER,
			iqotr40Logging2FiberRx8RxSFP35347
				RollCallString,
			iqotr40MenuRollTrackDisableAll
				INTEGER,
			iqotr40MenuRollTrackIndex
				INTEGER,
			iqotr40MenuRollTrackSource
				INTEGER,
			iqotr40MenuRollTrackAddress
				RollCallString,
			iqotr40MenuRollTrackCommand
				RollCallString,
			iqotr40MenuRollTrackStatus
				RollCallString,
			iqotr40MenuRollTrackSending
				RollCallString,
			iqotr40MenuSetupDisplay
				INTEGER,
			iqotr40MenuSetupProduct
				RollCallString,
			iqotr40MenuSetupLicensedProduct
				RollCallString,
			iqotr40MenuSetupRelease
				RollCallString,
			iqotr40MenuSetupBuild
				RollCallString,
			iqotr40MenuSetupKOS
				RollCallString,
			iqotr40MenuSetupSerialNo
				RollCallString,
			iqotr40MenuSetupPCB
				RollCallString,
			iqotr40MenuSetupRearID
				RollCallString,
			iqotr40MenuSetupInput1Name
				RollCallString,
			iqotr40MenuSetupInput2Name
				RollCallString,
			iqotr40MenuSetupInput3Name
				RollCallString,
			iqotr40MenuSetupInput4Name
				RollCallString,
			iqotr40MenuSetupInput5Name
				RollCallString,
			iqotr40MenuSetupInput6Name
				RollCallString,
			iqotr40MenuSetupInput7Name
				RollCallString,
			iqotr40MenuSetupInput8Name
				RollCallString,
			iqotr40MenuSetupFactoryDefault
				INTEGER,
			iqotr40MenuSetupDefaultsSettings
				INTEGER,
			iqotr40MenuSetupRestart
				INTEGER,
			iqotr40MenuSetupSerialNumber
				RollCallString,
			iqotr40SetupSFP1Ident
				RollCallString,
			iqotr40SetupSFP1Vendor
				RollCallString,
			iqotr40SetupSFP1PartNo
				RollCallString,
			iqotr40SetupSFP1Status
				RollCallString,
			iqotr40SetupSFP2Ident
				RollCallString,
			iqotr40SetupSFP2Vendor
				RollCallString,
			iqotr40SetupSFP2PartNo
				RollCallString,
			iqotr40SetupSFP2Status
				RollCallString,
			iqotr40SetupSFP3Ident
				RollCallString,
			iqotr40SetupSFP3Vendor
				RollCallString,
			iqotr40SetupSFP3PartNo
				RollCallString,
			iqotr40SetupSFP3Status
				RollCallString,
			iqotr40SetupSFP4Ident
				RollCallString,
			iqotr40SetupSFP4Vendor
				RollCallString,
			iqotr40SetupSFP4PartNo
				RollCallString,
			iqotr40SetupSFP4Status
				RollCallString,
			iqotr40SetupSFP5Ident
				RollCallString,
			iqotr40SetupSFP5Vendor
				RollCallString,
			iqotr40SetupSFP5PartNo
				RollCallString,
			iqotr40SetupSFP5Status
				RollCallString,
			iqotr40SetupSFP6Ident
				RollCallString,
			iqotr40SetupSFP6Vendor
				RollCallString,
			iqotr40SetupSFP6PartNo
				RollCallString,
			iqotr40SetupSFP6Status
				RollCallString,
			iqotr40SetupSFP7Ident
				RollCallString,
			iqotr40SetupSFP7Vendor
				RollCallString,
			iqotr40SetupSFP7PartNo
				RollCallString,
			iqotr40SetupSFP7Status
				RollCallString,
			iqotr40SetupSFP8Ident
				RollCallString,
			iqotr40SetupSFP8Vendor
				RollCallString,
			iqotr40SetupSFP8PartNo
				RollCallString,
			iqotr40SetupSFP8Status
				RollCallString,
			iqotr40MenuSetupHideFiberOPDlg
				RollCallString
		}

	iqotr40SlotIndex OBJECT-TYPE
		SYNTAX		Unsigned32
		MAX-ACCESS		not-accessible
		STATUS			current
		DESCRIPTION
				"The unique Index value for each slot.  Its value
					ranges between 1 and the value of slotNumber."
		::= { iqotr40CmdEntry 0 }


	iqotr40InputsInput1SD270 OBJECT-TYPE
		SYNTAX		INTEGER { disable(0), enable(1) }
		MAX-ACCESS		read-write
		STATUS			current
		DESCRIPTION
				"TYPE: - Checkbox
				 PAGE: - Inputs
					SD 270  cmdID= 4130 "
		::= { iqotr40CmdEntry 4130 }


	iqotr40InputsInput1HD15G OBJECT-TYPE
		SYNTAX		INTEGER { disable(0), enable(1) }
		MAX-ACCESS		read-write
		STATUS			current
		DESCRIPTION
				"TYPE: - Checkbox
				 PAGE: - Inputs
					HD 1.5G  cmdID= 4128 "
		::= { iqotr40CmdEntry 4128 }


	iqotr40InputsInput13G OBJECT-TYPE
		SYNTAX		INTEGER { disable(0), enable(1) }
		MAX-ACCESS		read-write
		STATUS			current
		DESCRIPTION
				"TYPE: - Checkbox
				 PAGE: - Inputs
					3G  cmdID= 4129 "
		::= { iqotr40CmdEntry 4129 }


	iqotr40InputsInput1Others OBJECT-TYPE
		SYNTAX		INTEGER { disable(0), enable(1) }
		MAX-ACCESS		read-write
		STATUS			current
		DESCRIPTION
				"TYPE: - Checkbox
				 PAGE: - Inputs
					Others  cmdID= 4123 "
		::= { iqotr40CmdEntry 4123 }


	iqotr40InputsInput1ReclockBypass OBJECT-TYPE
		SYNTAX		INTEGER { disable(0), enable(1) }
		MAX-ACCESS		read-write
		STATUS			current
		DESCRIPTION
				"TYPE: - Checkbox
				 PAGE: - Inputs
					Reclock Bypass  cmdID= 4125 "
		::= { iqotr40CmdEntry 4125 }


	iqotr40InputsInput2SD270 OBJECT-TYPE
		SYNTAX		INTEGER { disable(0), enable(1) }
		MAX-ACCESS		read-write
		STATUS			current
		DESCRIPTION
				"TYPE: - Checkbox
				 PAGE: - Inputs
					SD 270  cmdID= 4137 "
		::= { iqotr40CmdEntry 4137 }


	iqotr40InputsInput2HD15G OBJECT-TYPE
		SYNTAX		INTEGER { disable(0), enable(1) }
		MAX-ACCESS		read-write
		STATUS			current
		DESCRIPTION
				"TYPE: - Checkbox
				 PAGE: - Inputs
					HD 1.5G  cmdID= 4124 "
		::= { iqotr40CmdEntry 4124 }


	iqotr40InputsInput23G OBJECT-TYPE
		SYNTAX		INTEGER { disable(0), enable(1) }
		MAX-ACCESS		read-write
		STATUS			current
		DESCRIPTION
				"TYPE: - Checkbox
				 PAGE: - Inputs
					3G  cmdID= 4136 "
		::= { iqotr40CmdEntry 4136 }


	iqotr40InputsInput2Others OBJECT-TYPE
		SYNTAX		INTEGER { disable(0), enable(1) }
		MAX-ACCESS		read-write
		STATUS			current
		DESCRIPTION
				"TYPE: - Checkbox
				 PAGE: - Inputs
					Others  cmdID= 4139 "
		::= { iqotr40CmdEntry 4139 }


	iqotr40InputsInput2ReclockBypass OBJECT-TYPE
		SYNTAX		INTEGER { disable(0), enable(1) }
		MAX-ACCESS		read-write
		STATUS			current
		DESCRIPTION
				"TYPE: - Checkbox
				 PAGE: - Inputs
					Reclock Bypass  cmdID= 4132 "
		::= { iqotr40CmdEntry 4132 }


	iqotr40InputsInput3SD270 OBJECT-TYPE
		SYNTAX		INTEGER { disable(0), enable(1) }
		MAX-ACCESS		read-write
		STATUS			current
		DESCRIPTION
				"TYPE: - Checkbox
				 PAGE: - Inputs
					SD 270  cmdID= 4133 "
		::= { iqotr40CmdEntry 4133 }


	iqotr40InputsInput3HD15G OBJECT-TYPE
		SYNTAX		INTEGER { disable(0), enable(1) }
		MAX-ACCESS		read-write
		STATUS			current
		DESCRIPTION
				"TYPE: - Checkbox
				 PAGE: - Inputs
					HD 1.5G  cmdID= 4131 "
		::= { iqotr40CmdEntry 4131 }


	iqotr40InputsInput33G OBJECT-TYPE
		SYNTAX		INTEGER { disable(0), enable(1) }
		MAX-ACCESS		read-write
		STATUS			current
		DESCRIPTION
				"TYPE: - Checkbox
				 PAGE: - Inputs
					3G  cmdID= 4135 "
		::= { iqotr40CmdEntry 4135 }


	iqotr40InputsInput3Others OBJECT-TYPE
		SYNTAX		INTEGER { disable(0), enable(1) }
		MAX-ACCESS		read-write
		STATUS			current
		DESCRIPTION
				"TYPE: - Checkbox
				 PAGE: - Inputs
					Others  cmdID= 4134 "
		::= { iqotr40CmdEntry 4134 }


	iqotr40InputsInput3ReclockBypass OBJECT-TYPE
		SYNTAX		INTEGER { disable(0), enable(1) }
		MAX-ACCESS		read-write
		STATUS			current
		DESCRIPTION
				"TYPE: - Checkbox
				 PAGE: - Inputs
					Reclock Bypass  cmdID= 4120 "
		::= { iqotr40CmdEntry 4120 }


	iqotr40InputsInput4SD270 OBJECT-TYPE
		SYNTAX		INTEGER { disable(0), enable(1) }
		MAX-ACCESS		read-write
		STATUS			current
		DESCRIPTION
				"TYPE: - Checkbox
				 PAGE: - Inputs
					SD 270  cmdID= 4105 "
		::= { iqotr40CmdEntry 4105 }


	iqotr40InputsInput4HD15G OBJECT-TYPE
		SYNTAX		INTEGER { disable(0), enable(1) }
		MAX-ACCESS		read-write
		STATUS			current
		DESCRIPTION
				"TYPE: - Checkbox
				 PAGE: - Inputs
					HD 1.5G  cmdID= 4106 "
		::= { iqotr40CmdEntry 4106 }


	iqotr40InputsInput43G OBJECT-TYPE
		SYNTAX		INTEGER { disable(0), enable(1) }
		MAX-ACCESS		read-write
		STATUS			current
		DESCRIPTION
				"TYPE: - Checkbox
				 PAGE: - Inputs
					3G  cmdID= 4107 "
		::= { iqotr40CmdEntry 4107 }


	iqotr40InputsInput4Others OBJECT-TYPE
		SYNTAX		INTEGER { disable(0), enable(1) }
		MAX-ACCESS		read-write
		STATUS			current
		DESCRIPTION
				"TYPE: - Checkbox
				 PAGE: - Inputs
					Others  cmdID= 4109 "
		::= { iqotr40CmdEntry 4109 }


	iqotr40InputsInput4ReclockBypass OBJECT-TYPE
		SYNTAX		INTEGER { disable(0), enable(1) }
		MAX-ACCESS		read-write
		STATUS			current
		DESCRIPTION
				"TYPE: - Checkbox
				 PAGE: - Inputs
					Reclock Bypass  cmdID= 4108 "
		::= { iqotr40CmdEntry 4108 }


	iqotr40InputsInput5SD270 OBJECT-TYPE
		SYNTAX		INTEGER { disable(0), enable(1) }
		MAX-ACCESS		read-write
		STATUS			current
		DESCRIPTION
				"TYPE: - Checkbox
				 PAGE: - Inputs
					SD 270  cmdID= 4210 "
		::= { iqotr40CmdEntry 4210 }


	iqotr40InputsInput5HD15G OBJECT-TYPE
		SYNTAX		INTEGER { disable(0), enable(1) }
		MAX-ACCESS		read-write
		STATUS			current
		DESCRIPTION
				"TYPE: - Checkbox
				 PAGE: - Inputs
					HD 1.5G  cmdID= 4211 "
		::= { iqotr40CmdEntry 4211 }


	iqotr40InputsInput53G OBJECT-TYPE
		SYNTAX		INTEGER { disable(0), enable(1) }
		MAX-ACCESS		read-write
		STATUS			current
		DESCRIPTION
				"TYPE: - Checkbox
				 PAGE: - Inputs
					3G  cmdID= 4214 "
		::= { iqotr40CmdEntry 4214 }


	iqotr40InputsInput5Others OBJECT-TYPE
		SYNTAX		INTEGER { disable(0), enable(1) }
		MAX-ACCESS		read-write
		STATUS			current
		DESCRIPTION
				"TYPE: - Checkbox
				 PAGE: - Inputs
					Others  cmdID= 4213 "
		::= { iqotr40CmdEntry 4213 }


	iqotr40InputsInput5ReclockBypass OBJECT-TYPE
		SYNTAX		INTEGER { disable(0), enable(1) }
		MAX-ACCESS		read-write
		STATUS			current
		DESCRIPTION
				"TYPE: - Checkbox
				 PAGE: - Inputs
					Reclock Bypass  cmdID= 4209 "
		::= { iqotr40CmdEntry 4209 }


	iqotr40InputsInput6SD270 OBJECT-TYPE
		SYNTAX		INTEGER { disable(0), enable(1) }
		MAX-ACCESS		read-write
		STATUS			current
		DESCRIPTION
				"TYPE: - Checkbox
				 PAGE: - Inputs
					SD 270  cmdID= 4203 "
		::= { iqotr40CmdEntry 4203 }


	iqotr40InputsInput6HD15G OBJECT-TYPE
		SYNTAX		INTEGER { disable(0), enable(1) }
		MAX-ACCESS		read-write
		STATUS			current
		DESCRIPTION
				"TYPE: - Checkbox
				 PAGE: - Inputs
					HD 1.5G  cmdID= 4202 "
		::= { iqotr40CmdEntry 4202 }


	iqotr40InputsInput63G OBJECT-TYPE
		SYNTAX		INTEGER { disable(0), enable(1) }
		MAX-ACCESS		read-write
		STATUS			current
		DESCRIPTION
				"TYPE: - Checkbox
				 PAGE: - Inputs
					3G  cmdID= 4200 "
		::= { iqotr40CmdEntry 4200 }


	iqotr40InputsInput6Others OBJECT-TYPE
		SYNTAX		INTEGER { disable(0), enable(1) }
		MAX-ACCESS		read-write
		STATUS			current
		DESCRIPTION
				"TYPE: - Checkbox
				 PAGE: - Inputs
					Others  cmdID= 4201 "
		::= { iqotr40CmdEntry 4201 }


	iqotr40InputsInput6ReclockBypass OBJECT-TYPE
		SYNTAX		INTEGER { disable(0), enable(1) }
		MAX-ACCESS		read-write
		STATUS			current
		DESCRIPTION
				"TYPE: - Checkbox
				 PAGE: - Inputs
					Reclock Bypass  cmdID= 4204 "
		::= { iqotr40CmdEntry 4204 }


	iqotr40InputsInput7SD270 OBJECT-TYPE
		SYNTAX		INTEGER { disable(0), enable(1) }
		MAX-ACCESS		read-write
		STATUS			current
		DESCRIPTION
				"TYPE: - Checkbox
				 PAGE: - Inputs
					SD 270  cmdID= 4208 "
		::= { iqotr40CmdEntry 4208 }


	iqotr40InputsInput7HD15G OBJECT-TYPE
		SYNTAX		INTEGER { disable(0), enable(1) }
		MAX-ACCESS		read-write
		STATUS			current
		DESCRIPTION
				"TYPE: - Checkbox
				 PAGE: - Inputs
					HD 1.5G  cmdID= 4207 "
		::= { iqotr40CmdEntry 4207 }


	iqotr40InputsInput73G OBJECT-TYPE
		SYNTAX		INTEGER { disable(0), enable(1) }
		MAX-ACCESS		read-write
		STATUS			current
		DESCRIPTION
				"TYPE: - Checkbox
				 PAGE: - Inputs
					3G  cmdID= 4206 "
		::= { iqotr40CmdEntry 4206 }


	iqotr40InputsInput7Others OBJECT-TYPE
		SYNTAX		INTEGER { disable(0), enable(1) }
		MAX-ACCESS		read-write
		STATUS			current
		DESCRIPTION
				"TYPE: - Checkbox
				 PAGE: - Inputs
					Others  cmdID= 4205 "
		::= { iqotr40CmdEntry 4205 }


	iqotr40InputsInput7ReclockBypass OBJECT-TYPE
		SYNTAX		INTEGER { disable(0), enable(1) }
		MAX-ACCESS		read-write
		STATUS			current
		DESCRIPTION
				"TYPE: - Checkbox
				 PAGE: - Inputs
					Reclock Bypass  cmdID= 4212 "
		::= { iqotr40CmdEntry 4212 }


	iqotr40InputsInput8SD270 OBJECT-TYPE
		SYNTAX		INTEGER { disable(0), enable(1) }
		MAX-ACCESS		read-write
		STATUS			current
		DESCRIPTION
				"TYPE: - Checkbox
				 PAGE: - Inputs
					SD 270  cmdID= 4292 "
		::= { iqotr40CmdEntry 4292 }


	iqotr40InputsInput8HD15G OBJECT-TYPE
		SYNTAX		INTEGER { disable(0), enable(1) }
		MAX-ACCESS		read-write
		STATUS			current
		DESCRIPTION
				"TYPE: - Checkbox
				 PAGE: - Inputs
					HD 1.5G  cmdID= 4290 "
		::= { iqotr40CmdEntry 4290 }


	iqotr40InputsInput83G OBJECT-TYPE
		SYNTAX		INTEGER { disable(0), enable(1) }
		MAX-ACCESS		read-write
		STATUS			current
		DESCRIPTION
				"TYPE: - Checkbox
				 PAGE: - Inputs
					3G  cmdID= 4294 "
		::= { iqotr40CmdEntry 4294 }


	iqotr40InputsInput8Others OBJECT-TYPE
		SYNTAX		INTEGER { disable(0), enable(1) }
		MAX-ACCESS		read-write
		STATUS			current
		DESCRIPTION
				"TYPE: - Checkbox
				 PAGE: - Inputs
					Others  cmdID= 4293 "
		::= { iqotr40CmdEntry 4293 }


	iqotr40InputsInput8ReclockBypass OBJECT-TYPE
		SYNTAX		INTEGER { disable(0), enable(1) }
		MAX-ACCESS		read-write
		STATUS			current
		DESCRIPTION
				"TYPE: - Checkbox
				 PAGE: - Inputs
					Reclock Bypass  cmdID= 4291 "
		::= { iqotr40CmdEntry 4291 }


	iqotr40InputsPrimarySecondaryPrimaryInput4127 OBJECT-TYPE
		SYNTAX		INTEGER {
							val-1(0),
							val-2(1),
							val-3(2),
							val-4(3)
							}
		MAX-ACCESS		read-write
		STATUS			current
		DESCRIPTION
				"TYPE: - RadiobuttonList
				 PAGE: - Inputs
					Primary Input  cmdID= 4127 
					1  value= 0  
					2  value= 1  
					3  value= 2  
					4  value= 3  "
		::= { iqotr40CmdEntry 4127 }


	iqotr40InputsPrimarySecondarySecondaryInput4126 OBJECT-TYPE
		SYNTAX		INTEGER {
							val-1(0),
							val-2(1),
							val-3(2),
							val-4(3)
							}
		MAX-ACCESS		read-write
		STATUS			current
		DESCRIPTION
				"TYPE: - RadiobuttonList
				 PAGE: - Inputs
					Secondary Input  cmdID= 4126 
					1  value= 0  
					2  value= 1  
					3  value= 2  
					4  value= 3  "
		::= { iqotr40CmdEntry 4126 }


	iqotr40InputsPrimaryInput14OKTimer OBJECT-TYPE
		SYNTAX		INTEGER
		MAX-ACCESS		read-write
		STATUS			current
		DESCRIPTION
				"TYPE: - Number
				 PAGE: - Inputs
					OK Timer  cmdID= 4158  min= 0  max= 50  step= 1  format= %0.1f sec  div_scale= 10 
					Min = 0.0 sec  Max = 5.0 sec  Step = 0.1 sec "
		::= { iqotr40CmdEntry 4158 }


	iqotr40InputsPrimaryInput14ErrorTimer OBJECT-TYPE
		SYNTAX		INTEGER
		MAX-ACCESS		read-write
		STATUS			current
		DESCRIPTION
				"TYPE: - Number
				 PAGE: - Inputs
					Error Timer  cmdID= 4160  min= 0  max= 50  step= 1  format= %0.1f sec  div_scale= 10 
					Min = 0.0 sec  Max = 5.0 sec  Step = 0.1 sec "
		::= { iqotr40CmdEntry 4160 }


	iqotr40InputsSecondaryInput14OKTimer OBJECT-TYPE
		SYNTAX		INTEGER
		MAX-ACCESS		read-write
		STATUS			current
		DESCRIPTION
				"TYPE: - Number
				 PAGE: - Inputs
					OK Timer  cmdID= 4161  min= 0  max= 50  step= 1  format= %0.1f sec  div_scale= 10 
					Min = 0.0 sec  Max = 5.0 sec  Step = 0.1 sec "
		::= { iqotr40CmdEntry 4161 }


	iqotr40InputsSecondaryInput14ErrorTimer OBJECT-TYPE
		SYNTAX		INTEGER
		MAX-ACCESS		read-write
		STATUS			current
		DESCRIPTION
				"TYPE: - Number
				 PAGE: - Inputs
					Error Timer  cmdID= 4159  min= 0  max= 50  step= 1  format= %0.1f sec  div_scale= 10 
					Min = 0.0 sec  Max = 5.0 sec  Step = 0.1 sec "
		::= { iqotr40CmdEntry 4159 }


	iqotr40InputsPrimarySecondaryPrimaryInput4295 OBJECT-TYPE
		SYNTAX		INTEGER {
							val-5(4),
							val-6(5),
							val-7(6),
							val-8(7)
							}
		MAX-ACCESS		read-write
		STATUS			current
		DESCRIPTION
				"TYPE: - RadiobuttonList
				 PAGE: - Inputs
					Primary Input  cmdID= 4295 
					5  value= 4  
					6  value= 5  
					7  value= 6  
					8  value= 7  "
		::= { iqotr40CmdEntry 4295 }


	iqotr40InputsPrimarySecondarySecondaryInput4296 OBJECT-TYPE
		SYNTAX		INTEGER {
							val-5(4),
							val-6(5),
							val-7(6),
							val-8(7)
							}
		MAX-ACCESS		read-write
		STATUS			current
		DESCRIPTION
				"TYPE: - RadiobuttonList
				 PAGE: - Inputs
					Secondary Input  cmdID= 4296 
					5  value= 4  
					6  value= 5  
					7  value= 6  
					8  value= 7  "
		::= { iqotr40CmdEntry 4296 }


	iqotr40InputsPrimaryInput58OKTimer OBJECT-TYPE
		SYNTAX		INTEGER
		MAX-ACCESS		read-write
		STATUS			current
		DESCRIPTION
				"TYPE: - Number
				 PAGE: - Inputs
					OK Timer  cmdID= 4255  min= 0  max= 50  step= 1  format= %0.1f sec  div_scale= 10 
					Min = 0.0 sec  Max = 5.0 sec  Step = 0.1 sec "
		::= { iqotr40CmdEntry 4255 }


	iqotr40InputsPrimaryInput58ErrorTimer OBJECT-TYPE
		SYNTAX		INTEGER
		MAX-ACCESS		read-write
		STATUS			current
		DESCRIPTION
				"TYPE: - Number
				 PAGE: - Inputs
					Error Timer  cmdID= 4254  min= 0  max= 50  step= 1  format= %0.1f sec  div_scale= 10 
					Min = 0.0 sec  Max = 5.0 sec  Step = 0.1 sec "
		::= { iqotr40CmdEntry 4254 }


	iqotr40InputsSecondaryInput58OKTimer OBJECT-TYPE
		SYNTAX		INTEGER
		MAX-ACCESS		read-write
		STATUS			current
		DESCRIPTION
				"TYPE: - Number
				 PAGE: - Inputs
					OK Timer  cmdID= 4265  min= 0  max= 50  step= 1  format= %0.1f sec  div_scale= 10 
					Min = 0.0 sec  Max = 5.0 sec  Step = 0.1 sec "
		::= { iqotr40CmdEntry 4265 }


	iqotr40InputsSecondaryInput58ErrorTimer OBJECT-TYPE
		SYNTAX		INTEGER
		MAX-ACCESS		read-write
		STATUS			current
		DESCRIPTION
				"TYPE: - Number
				 PAGE: - Inputs
					Error Timer  cmdID= 4256  min= 0  max= 50  step= 1  format= %0.1f sec  div_scale= 10 
					Min = 0.0 sec  Max = 5.0 sec  Step = 0.1 sec "
		::= { iqotr40CmdEntry 4256 }


	iqotr40Config141Output1Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4234 
					Input 1  value= 0  
					Input 2  value= 1  
					Input 3  value= 2  
					Input 4  value= 3  "
		::= { iqotr40CmdEntry 4234 }


	iqotr40Config141Output1MuteonInputErr OBJECT-TYPE
		SYNTAX		INTEGER { disable(0), enable(1) }
		MAX-ACCESS		read-write
		STATUS			current
		DESCRIPTION
				"TYPE: - Checkbox
				 PAGE: - Outputs
					Mute on Input Err  cmdID= 4232 "
		::= { iqotr40CmdEntry 4232 }


	iqotr40Config141Output1Mute OBJECT-TYPE
		SYNTAX		INTEGER { disable(0), enable(1) }
		MAX-ACCESS		read-write
		STATUS			current
		DESCRIPTION
				"TYPE: - Checkbox
				 PAGE: - Outputs
					Mute  cmdID= 4233 "
		::= { iqotr40CmdEntry 4233 }


	iqotr40Config141Output2Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4240 
					Input 1  value= 0  
					Input 2  value= 1  
					Input 3  value= 2  
					Input 4  value= 3  "
		::= { iqotr40CmdEntry 4240 }


	iqotr40Config141Output2MuteonInputErr OBJECT-TYPE
		SYNTAX		INTEGER { disable(0), enable(1) }
		MAX-ACCESS		read-write
		STATUS			current
		DESCRIPTION
				"TYPE: - Checkbox
				 PAGE: - Outputs
					Mute on Input Err  cmdID= 4238 "
		::= { iqotr40CmdEntry 4238 }


	iqotr40Config141Output2Mute OBJECT-TYPE
		SYNTAX		INTEGER { disable(0), enable(1) }
		MAX-ACCESS		read-write
		STATUS			current
		DESCRIPTION
				"TYPE: - Checkbox
				 PAGE: - Outputs
					Mute  cmdID= 4239 "
		::= { iqotr40CmdEntry 4239 }


	iqotr40Config141Output3Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4224 
					Input 1  value= 0  
					Input 2  value= 1  
					Input 3  value= 2  
					Input 4  value= 3  "
		::= { iqotr40CmdEntry 4224 }


	iqotr40Config141Output3MuteonInputErr OBJECT-TYPE
		SYNTAX		INTEGER { disable(0), enable(1) }
		MAX-ACCESS		read-write
		STATUS			current
		DESCRIPTION
				"TYPE: - Checkbox
				 PAGE: - Outputs
					Mute on Input Err  cmdID= 4225 "
		::= { iqotr40CmdEntry 4225 }


	iqotr40Config141Output3Mute OBJECT-TYPE
		SYNTAX		INTEGER { disable(0), enable(1) }
		MAX-ACCESS		read-write
		STATUS			current
		DESCRIPTION
				"TYPE: - Checkbox
				 PAGE: - Outputs
					Mute  cmdID= 4220 "
		::= { iqotr40CmdEntry 4220 }


	iqotr40Config141Output4Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4230 
					Input 1  value= 0  
					Input 2  value= 1  
					Input 3  value= 2  
					Input 4  value= 3  "
		::= { iqotr40CmdEntry 4230 }


	iqotr40Config141Output4MuteonInputErr OBJECT-TYPE
		SYNTAX		INTEGER { disable(0), enable(1) }
		MAX-ACCESS		read-write
		STATUS			current
		DESCRIPTION
				"TYPE: - Checkbox
				 PAGE: - Outputs
					Mute on Input Err  cmdID= 4243 "
		::= { iqotr40CmdEntry 4243 }


	iqotr40Config141Output4Mute OBJECT-TYPE
		SYNTAX		INTEGER { disable(0), enable(1) }
		MAX-ACCESS		read-write
		STATUS			current
		DESCRIPTION
				"TYPE: - Checkbox
				 PAGE: - Outputs
					Mute  cmdID= 4226 "
		::= { iqotr40CmdEntry 4226 }


	iqotr40OutputsConfig141Conf1Selected OBJECT-TYPE
		SYNTAX		RollCallString
		MAX-ACCESS		read-only
		STATUS			current
		DESCRIPTION
				"TYPE: - Display
				 PAGE: - Outputs
					Conf 1 Selected  cmdID= 4297  format=   "
		::= { iqotr40CmdEntry 4297 }


	iqotr40Config142Output1Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4235 
					Input 1  value= 0  
					Input 2  value= 1  
					Input 3  value= 2  
					Input 4  value= 3  "
		::= { iqotr40CmdEntry 4235 }


	iqotr40Config142Output1MuteonInputErr OBJECT-TYPE
		SYNTAX		INTEGER { disable(0), enable(1) }
		MAX-ACCESS		read-write
		STATUS			current
		DESCRIPTION
				"TYPE: - Checkbox
				 PAGE: - Outputs
					Mute on Input Err  cmdID= 4236 "
		::= { iqotr40CmdEntry 4236 }


	iqotr40Config142Output1Mute OBJECT-TYPE
		SYNTAX		INTEGER { disable(0), enable(1) }
		MAX-ACCESS		read-write
		STATUS			current
		DESCRIPTION
				"TYPE: - Checkbox
				 PAGE: - Outputs
					Mute  cmdID= 4231 "
		::= { iqotr40CmdEntry 4231 }


	iqotr40Config142Output2Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4241 
					Input 1  value= 0  
					Input 2  value= 1  
					Input 3  value= 2  
					Input 4  value= 3  "
		::= { iqotr40CmdEntry 4241 }


	iqotr40Config142Output2MuteonInputErr OBJECT-TYPE
		SYNTAX		INTEGER { disable(0), enable(1) }
		MAX-ACCESS		read-write
		STATUS			current
		DESCRIPTION
				"TYPE: - Checkbox
				 PAGE: - Outputs
					Mute on Input Err  cmdID= 4223 "
		::= { iqotr40CmdEntry 4223 }


	iqotr40Config142Output2Mute OBJECT-TYPE
		SYNTAX		INTEGER { disable(0), enable(1) }
		MAX-ACCESS		read-write
		STATUS			current
		DESCRIPTION
				"TYPE: - Checkbox
				 PAGE: - Outputs
					Mute  cmdID= 4237 "
		::= { iqotr40CmdEntry 4237 }


	iqotr40Config142Output3Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4222 
					Input 1  value= 0  
					Input 2  value= 1  
					Input 3  value= 2  
					Input 4  value= 3  "
		::= { iqotr40CmdEntry 4222 }


	iqotr40Config142Output3MuteonInputErr OBJECT-TYPE
		SYNTAX		INTEGER { disable(0), enable(1) }
		MAX-ACCESS		read-write
		STATUS			current
		DESCRIPTION
				"TYPE: - Checkbox
				 PAGE: - Outputs
					Mute on Input Err  cmdID= 4229 "
		::= { iqotr40CmdEntry 4229 }


	iqotr40Config142Output3Mute OBJECT-TYPE
		SYNTAX		INTEGER { disable(0), enable(1) }
		MAX-ACCESS		read-write
		STATUS			current
		DESCRIPTION
				"TYPE: - Checkbox
				 PAGE: - Outputs
					Mute  cmdID= 4221 "
		::= { iqotr40CmdEntry 4221 }


	iqotr40Config142Output4Inputselect OBJECT-TYPE
		SYNTAX		INTEGER {
							val-Input-1(0),
							val-Input-2(1),
							val-Input-3(2),
							val-Input-4(3)
							}
		MAX-ACCESS		read-write
		STATUS			current
		DESCRIPTION
				"TYPE: - RadiobuttonList
				 PAGE: - Outputs
					Input select  cmdID= 4228 
					Input 1  value= 0  
					Input 2  value= 1  
					Input 3  value= 2  
					Input 4  value= 3  "
		::= { iqotr40CmdEntry 4228 }


	iqotr40Config142Output4MuteonInputErr OBJECT-TYPE
		SYNTAX		INTEGER { disable(0), enable(1) }
		MAX-ACCESS		read-write
		STATUS			current
		DESCRIPTION
				"TYPE: - Checkbox
				 PAGE: - Outputs
					Mute on Input Err  cmdID= 4242 "
		::= { iqotr40CmdEntry 4242 }


	iqotr40Config142Output4Mute OBJECT-TYPE
		SYNTAX		INTEGER { disable(0), enable(1) }
		MAX-ACCESS		read-write
		STATUS			current
		DESCRIPTION
				"TYPE: - Checkbox
				 PAGE: - Outputs
					Mute  cmdID= 4227 "
		::= { iqotr40CmdEntry 4227 }


	iqotr40OutputsConfig142Conf2Selected OBJECT-TYPE
		SYNTAX		RollCallString
		MAX-ACCESS		read-only
		STATUS			current
		DESCRIPTION
				"TYPE: - Display
				 PAGE: - Outputs
					Conf 2 Selected  cmdID= 4298  format=   "
		::= { iqotr40CmdEntry 4298 }


	iqotr40OutputsMode14 OBJECT-TYPE
		SYNTAX		INTEGER {
							val-Use-Config-1(0),
							val-Use-Config-2(1),
							val-Use-Rules(2)
							}
		MAX-ACCESS		read-write
		STATUS			current
		DESCRIPTION
				"TYPE: - RadiobuttonList
				 PAGE: - Outputs
					Mode 1-4  cmdID= 4100 
					Use Config 1  value= 0  
					Use Config 2  value= 1  
					Use Rules  value= 2  "
		::= { iqotr40CmdEntry 4100 }


	iqotr40OutputsMode14SwapConfig12 OBJECT-TYPE
		SYNTAX		INTEGER { noAction(0),val-Swap-Config-1-2(1) }
		MAX-ACCESS		read-write
		STATUS			current
		DESCRIPTION
				"TYPE: - Button
				 PAGE: - Outputs
					Swap Config 1<>2  cmdID= 4101  value= 1  "
		::= { iqotr40CmdEntry 4101 }


	iqotr40OutputsRules14Config1PrimOK OBJECT-TYPE
		SYNTAX		INTEGER { disable(0), enable(1) }
		MAX-ACCESS		read-write
		STATUS			current
		DESCRIPTION
				"TYPE: - Checkbox
				 PAGE: - Outputs
					Config 1 Prim OK  cmdID= 4104 "
		::= { iqotr40CmdEntry 4104 }


	iqotr40OutputsRules14Config2PrimErr OBJECT-TYPE
		SYNTAX		INTEGER { disable(0), enable(1) }
		MAX-ACCESS		read-write
		STATUS			current
		DESCRIPTION
				"TYPE: - Checkbox
				 PAGE: - Outputs
					Config 2 Prim Err  cmdID= 4102 "
		::= { iqotr40CmdEntry 4102 }


	iqotr40OutputsRules14Config1SecErr OBJECT-TYPE
		SYNTAX		INTEGER { disable(0), enable(1) }
		MAX-ACCESS		read-write
		STATUS			current
		DESCRIPTION
				"TYPE: - Checkbox
				 PAGE: - Outputs
					Config 1 Sec Err  cmdID= 4103 "
		::= { iqotr40CmdEntry 4103 }


	iqotr40Config581Output5Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4257 
					Input 5  value= 4  
					Input 6  value= 5  
					Input 7  value= 6  
					Input 8  value= 7  "
		::= { iqotr40CmdEntry 4257 }


	iqotr40Config581Output5MuteonInputErr OBJECT-TYPE
		SYNTAX		INTEGER { disable(0), enable(1) }
		MAX-ACCESS		read-write
		STATUS			current
		DESCRIPTION
				"TYPE: - Checkbox
				 PAGE: - Outputs
					Mute on Input Err  cmdID= 4263 "
		::= { iqotr40CmdEntry 4263 }


	iqotr40Config581Output5Mute OBJECT-TYPE
		SYNTAX		INTEGER { disable(0), enable(1) }
		MAX-ACCESS		read-write
		STATUS			current
		DESCRIPTION
				"TYPE: - Checkbox
				 PAGE: - Outputs
					Mute  cmdID= 4262 "
		::= { iqotr40CmdEntry 4262 }


	iqotr40Config581Output6Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4264 
					Input 5  value= 4  
					Input 6  value= 5  
					Input 7  value= 6  
					Input 8  value= 7  "
		::= { iqotr40CmdEntry 4264 }


	iqotr40Config581Output6MuteonInputErr OBJECT-TYPE
		SYNTAX		INTEGER { disable(0), enable(1) }
		MAX-ACCESS		read-write
		STATUS			current
		DESCRIPTION
				"TYPE: - Checkbox
				 PAGE: - Outputs
					Mute on Input Err  cmdID= 4258 "
		::= { iqotr40CmdEntry 4258 }


	iqotr40Config581Output6Mute OBJECT-TYPE
		SYNTAX		INTEGER { disable(0), enable(1) }
		MAX-ACCESS		read-write
		STATUS			current
		DESCRIPTION
				"TYPE: - Checkbox
				 PAGE: - Outputs
					Mute  cmdID= 4261 "
		::= { iqotr40CmdEntry 4261 }


	iqotr40Config581Output7Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4259 
					Input 5  value= 4  
					Input 6  value= 5  
					Input 7  value= 6  
					Input 8  value= 7  "
		::= { iqotr40CmdEntry 4259 }


	iqotr40Config581Output7MuteonInputErr OBJECT-TYPE
		SYNTAX		INTEGER { disable(0), enable(1) }
		MAX-ACCESS		read-write
		STATUS			current
		DESCRIPTION
				"TYPE: - Checkbox
				 PAGE: - Outputs
					Mute on Input Err  cmdID= 4252 "
		::= { iqotr40CmdEntry 4252 }


	iqotr40Config581Output7Mute OBJECT-TYPE
		SYNTAX		INTEGER { disable(0), enable(1) }
		MAX-ACCESS		read-write
		STATUS			current
		DESCRIPTION
				"TYPE: - Checkbox
				 PAGE: - Outputs
					Mute  cmdID= 4260 "
		::= { iqotr40CmdEntry 4260 }


	iqotr40Config581Output8Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4251 
					Input 5  value= 4  
					Input 6  value= 5  
					Input 7  value= 6  
					Input 8  value= 7  "
		::= { iqotr40CmdEntry 4251 }


	iqotr40Config581Output8MuteonInputErr OBJECT-TYPE
		SYNTAX		INTEGER { disable(0), enable(1) }
		MAX-ACCESS		read-write
		STATUS			current
		DESCRIPTION
				"TYPE: - Checkbox
				 PAGE: - Outputs
					Mute on Input Err  cmdID= 4253 "
		::= { iqotr40CmdEntry 4253 }


	iqotr40Config581Output8Mute OBJECT-TYPE
		SYNTAX		INTEGER { disable(0), enable(1) }
		MAX-ACCESS		read-write
		STATUS			current
		DESCRIPTION
				"TYPE: - Checkbox
				 PAGE: - Outputs
					Mute  cmdID= 4250 "
		::= { iqotr40CmdEntry 4250 }


	iqotr40OutputsConfig581Conf1Selected OBJECT-TYPE
		SYNTAX		RollCallString
		MAX-ACCESS		read-only
		STATUS			current
		DESCRIPTION
				"TYPE: - Display
				 PAGE: - Outputs
					Conf 1 Selected  cmdID= 4299  format=   "
		::= { iqotr40CmdEntry 4299 }


	iqotr40Config582Output5Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4280 
					Input 5  value= 4  
					Input 6  value= 5  
					Input 7  value= 6  
					Input 8  value= 7  "
		::= { iqotr40CmdEntry 4280 }


	iqotr40Config582Output5MuteonInputErr OBJECT-TYPE
		SYNTAX		INTEGER { disable(0), enable(1) }
		MAX-ACCESS		read-write
		STATUS			current
		DESCRIPTION
				"TYPE: - Checkbox
				 PAGE: - Outputs
					Mute on Input Err  cmdID= 4278 "
		::= { iqotr40CmdEntry 4278 }


	iqotr40Config582Output5Mute OBJECT-TYPE
		SYNTAX		INTEGER { disable(0), enable(1) }
		MAX-ACCESS		read-write
		STATUS			current
		DESCRIPTION
				"TYPE: - Checkbox
				 PAGE: - Outputs
					Mute  cmdID= 4281 "
		::= { iqotr40CmdEntry 4281 }


	iqotr40Config582Output6Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4272 
					Input 5  value= 4  
					Input 6  value= 5  
					Input 7  value= 6  
					Input 8  value= 7  "
		::= { iqotr40CmdEntry 4272 }


	iqotr40Config582Output6MuteonInputErr OBJECT-TYPE
		SYNTAX		INTEGER { disable(0), enable(1) }
		MAX-ACCESS		read-write
		STATUS			current
		DESCRIPTION
				"TYPE: - Checkbox
				 PAGE: - Outputs
					Mute on Input Err  cmdID= 4270 "
		::= { iqotr40CmdEntry 4270 }


	iqotr40Config582Output6Mute OBJECT-TYPE
		SYNTAX		INTEGER { disable(0), enable(1) }
		MAX-ACCESS		read-write
		STATUS			current
		DESCRIPTION
				"TYPE: - Checkbox
				 PAGE: - Outputs
					Mute  cmdID= 4273 "
		::= { iqotr40CmdEntry 4273 }


	iqotr40Config582Output7Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4271 
					Input 5  value= 4  
					Input 6  value= 5  
					Input 7  value= 6  
					Input 8  value= 7  "
		::= { iqotr40CmdEntry 4271 }


	iqotr40Config582Output7MuteonInputErr OBJECT-TYPE
		SYNTAX		INTEGER { disable(0), enable(1) }
		MAX-ACCESS		read-write
		STATUS			current
		DESCRIPTION
				"TYPE: - Checkbox
				 PAGE: - Outputs
					Mute on Input Err  cmdID= 4277 "
		::= { iqotr40CmdEntry 4277 }


	iqotr40Config582Output7Mute OBJECT-TYPE
		SYNTAX		INTEGER { disable(0), enable(1) }
		MAX-ACCESS		read-write
		STATUS			current
		DESCRIPTION
				"TYPE: - Checkbox
				 PAGE: - Outputs
					Mute  cmdID= 4276 "
		::= { iqotr40CmdEntry 4276 }


	iqotr40Config582Output8Inputselect OBJECT-TYPE
		SYNTAX		INTEGER {
							val-Input-5(4),
							val-Input-6(5),
							val-Input-7(6),
							val-Input-8(7)
							}
		MAX-ACCESS		read-write
		STATUS			current
		DESCRIPTION
				"TYPE: - RadiobuttonList
				 PAGE: - Outputs
					Input select  cmdID= 4274 
					Input 5  value= 4  
					Input 6  value= 5  
					Input 7  value= 6  
					Input 8  value= 7  "
		::= { iqotr40CmdEntry 4274 }


	iqotr40Config582Output8MuteonInputErr OBJECT-TYPE
		SYNTAX		INTEGER { disable(0), enable(1) }
		MAX-ACCESS		read-write
		STATUS			current
		DESCRIPTION
				"TYPE: - Checkbox
				 PAGE: - Outputs
					Mute on Input Err  cmdID= 4279 "
		::= { iqotr40CmdEntry 4279 }


	iqotr40Config582Output8Mute OBJECT-TYPE
		SYNTAX		INTEGER { disable(0), enable(1) }
		MAX-ACCESS		read-write
		STATUS			current
		DESCRIPTION
				"TYPE: - Checkbox
				 PAGE: - Outputs
					Mute  cmdID= 4275 "
		::= { iqotr40CmdEntry 4275 }


	iqotr40OutputsConfig582Conf2Selected OBJECT-TYPE
		SYNTAX		RollCallString
		MAX-ACCESS		read-only
		STATUS			current
		DESCRIPTION
				"TYPE: - Display
				 PAGE: - Outputs
					Conf 2 Selected  cmdID= 4300  format=   "
		::= { iqotr40CmdEntry 4300 }


	iqotr40OutputsMode58 OBJECT-TYPE
		SYNTAX		INTEGER {
							val-Use-Config-1(0),
							val-Use-Config-2(1),
							val-Use-Rules(2)
							}
		MAX-ACCESS		read-write
		STATUS			current
		DESCRIPTION
				"TYPE: - RadiobuttonList
				 PAGE: - Outputs
					Mode 5-8  cmdID= 4282 
					Use Config 1  value= 0  
					Use Config 2  value= 1  
					Use Rules  value= 2  "
		::= { iqotr40CmdEntry 4282 }


	iqotr40OutputsMode58SwapConfig12 OBJECT-TYPE
		SYNTAX		INTEGER { noAction(0),val-Swap-Config-1-2(1) }
		MAX-ACCESS		read-write
		STATUS			current
		DESCRIPTION
				"TYPE: - Button
				 PAGE: - Outputs
					Swap Config 1<>2  cmdID= 4283  value= 1  "
		::= { iqotr40CmdEntry 4283 }


	iqotr40OutputsRules58Config1PrimOK OBJECT-TYPE
		SYNTAX		INTEGER { disable(0), enable(1) }
		MAX-ACCESS		read-write
		STATUS			current
		DESCRIPTION
				"TYPE: - Checkbox
				 PAGE: - Outputs
					Config 1 Prim OK  cmdID= 4286 "
		::= { iqotr40CmdEntry 4286 }


	iqotr40OutputsRules58Config2PrimErr OBJECT-TYPE
		SYNTAX		INTEGER { disable(0), enable(1) }
		MAX-ACCESS		read-write
		STATUS			current
		DESCRIPTION
				"TYPE: - Checkbox
				 PAGE: - Outputs
					Config 2 Prim Err  cmdID= 4285 "
		::= { iqotr40CmdEntry 4285 }


	iqotr40OutputsRules58Config1SecErr OBJECT-TYPE
		SYNTAX		INTEGER { disable(0), enable(1) }
		MAX-ACCESS		read-write
		STATUS			current
		DESCRIPTION
				"TYPE: - Checkbox
				 PAGE: - Outputs
					Config 1 Sec Err  cmdID= 4284 "
		::= { iqotr40CmdEntry 4284 }


	iqotr40MenuMemoriesRecallMemory OBJECT-TYPE
		SYNTAX		INTEGER {
							val-None-Selected(0),
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Recall Memory  cmdID= 37100 
					None Selected  value= 0  
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqotr40CmdEntry 37100 }


	iqotr40MenuMemoriesSelMemory OBJECT-TYPE
		SYNTAX		INTEGER {
							val-User-Memory-1(1),
							val-User-Memory-2(2),
							val-User-Memory-3(3),
							val-User-Memory-4(4),
							val-User-Memory-5(5),
							val-User-Memory-6(6),
							val-User-Memory-7(7),
							val-User-Memory-8(8),
							val-User-Memory-9(9),
							val-User-Memory-10(10),
							val-User-Memory-11(11),
							val-User-Memory-12(12),
							val-User-Memory-13(13),
							val-User-Memory-14(14),
							val-User-Memory-15(15),
							val-User-Memory-16(16)
							}
		MAX-ACCESS		read-write
		STATUS			current
		DESCRIPTION
				"TYPE: - RadiobuttonList
				 PAGE: - Memories
					Sel Memory  cmdID= 37101 
					User Memory 1  value= 1  
					User Memory 2  value= 2  
					User Memory 3  value= 3  
					User Memory 4  value= 4  
					User Memory 5  value= 5  
					User Memory 6  value= 6  
					User Memory 7  value= 7  
					User Memory 8  value= 8  
					User Memory 9  value= 9  
					User Memory 10  value= 10  
					User Memory 11  value= 11  
					User Memory 12  value= 12  
					User Memory 13  value= 13  
					User Memory 14  value= 14  
					User Memory 15  value= 15  
					User Memory 16  value= 16  "
		::= { iqotr40CmdEntry 37101 }


	iqotr40MenuMemoriesSaveMemory OBJECT-TYPE
		SYNTAX		INTEGER { noAction(0),val-Save-Memory(1) }
		MAX-ACCESS		read-write
		STATUS			current
		DESCRIPTION
				"TYPE: - Button
				 PAGE: - Memories
					Save Memory  cmdID= 37102  value= 1  "
		::= { iqotr40CmdEntry 37102 }


	iqotr40MenuMemoriesClearMemory OBJECT-TYPE
		SYNTAX		INTEGER { noAction(0),val-Clear-Memory(1) }
		MAX-ACCESS		read-write
		STATUS			current
		DESCRIPTION
				"TYPE: - Button
				 PAGE: - Memories
					Clear Memory  cmdID= 37105  value= 1  "
		::= { iqotr40CmdEntry 37105 }


	iqotr40MemoriesMemoryNameChangeName OBJECT-TYPE
		SYNTAX		RollCallString
		MAX-ACCESS		read-write
		STATUS			current
		DESCRIPTION
				"TYPE: - Editstring
				 PAGE: - Memories
					Change Name  cmdID= 37103  "
		::= { iqotr40CmdEntry 37103 }


	iqotr40MenuMemoriesLastUserMemory OBJECT-TYPE
		SYNTAX		RollCallString
		MAX-ACCESS		read-only
		STATUS			current
		DESCRIPTION
				"TYPE: - Display
				 PAGE: - Memories
					Last User Memory  cmdID= 37104  format=   "
		::= { iqotr40CmdEntry 37104 }


	iqotr40MenuMemoriesMemoryName1 OBJECT-TYPE
		SYNTAX		RollCallString
		MAX-ACCESS		read-only
		STATUS			current
		DESCRIPTION
				"TYPE: - Display
				 PAGE: - Memories
					Memory Name1  cmdID= 37106  format=   "
		::= { iqotr40CmdEntry 37106 }


	iqotr40MenuMemoriesMemoryName2 OBJECT-TYPE
		SYNTAX		RollCallString
		MAX-ACCESS		read-only
		STATUS			current
		DESCRIPTION
				"TYPE: - Display
				 PAGE: - Memories
					Memory Name2  cmdID= 37107  format=   "
		::= { iqotr40CmdEntry 37107 }


	iqotr40MenuMemoriesMemoryName3 OBJECT-TYPE
		SYNTAX		RollCallString
		MAX-ACCESS		read-only
		STATUS			current
		DESCRIPTION
				"TYPE: - Display
				 PAGE: - Memories
					Memory Name3  cmdID= 37108  format=   "
		::= { iqotr40CmdEntry 37108 }


	iqotr40MenuMemoriesMemoryName4 OBJECT-TYPE
		SYNTAX		RollCallString
		MAX-ACCESS		read-only
		STATUS			current
		DESCRIPTION
				"TYPE: - Display
				 PAGE: - Memories
					Memory Name4  cmdID= 37109  format=   "
		::= { iqotr40CmdEntry 37109 }


	iqotr40MenuMemoriesMemoryName5 OBJECT-TYPE
		SYNTAX		RollCallString
		MAX-ACCESS		read-only
		STATUS			current
		DESCRIPTION
				"TYPE: - Display
				 PAGE: - Memories
					Memory Name5  cmdID= 37110  format=   "
		::= { iqotr40CmdEntry 37110 }


	iqotr40MenuMemoriesMemoryName6 OBJECT-TYPE
		SYNTAX		RollCallString
		MAX-ACCESS		read-only
		STATUS			current
		DESCRIPTION
				"TYPE: - Display
				 PAGE: - Memories
					Memory Name6  cmdID= 37111  format=   "
		::= { iqotr40CmdEntry 37111 }


	iqotr40MenuMemoriesMemoryName7 OBJECT-TYPE
		SYNTAX		RollCallString
		MAX-ACCESS		read-only
		STATUS			current
		DESCRIPTION
				"TYPE: - Display
				 PAGE: - Memories
					Memory Name7  cmdID= 37112  format=   "
		::= { iqotr40CmdEntry 37112 }


	iqotr40MenuMemoriesMemoryName8 OBJECT-TYPE
		SYNTAX		RollCallString
		MAX-ACCESS		read-only
		STATUS			current
		DESCRIPTION
				"TYPE: - Display
				 PAGE: - Memories
					Memory Name8  cmdID= 37113  format=   "
		::= { iqotr40CmdEntry 37113 }


	iqotr40MenuMemoriesMemoryName9 OBJECT-TYPE
		SYNTAX		RollCallString
		MAX-ACCESS		read-only
		STATUS			current
		DESCRIPTION
				"TYPE: - Display
				 PAGE: - Memories
					Memory Name9  cmdID= 37114  format=   "
		::= { iqotr40CmdEntry 37114 }


	iqotr40MenuMemoriesMemoryName10 OBJECT-TYPE
		SYNTAX		RollCallString
		MAX-ACCESS		read-only
		STATUS			current
		DESCRIPTION
				"TYPE: - Display
				 PAGE: - Memories
					Memory Name10  cmdID= 37115  format=   "
		::= { iqotr40CmdEntry 37115 }


	iqotr40MenuMemoriesMemoryName11 OBJECT-TYPE
		SYNTAX		RollCallString
		MAX-ACCESS		read-only
		STATUS			current
		DESCRIPTION
				"TYPE: - Display
				 PAGE: - Memories
					Memory Name11  cmdID= 37116  format=   "
		::= { iqotr40CmdEntry 37116 }


	iqotr40MenuMemoriesMemoryName12 OBJECT-TYPE
		SYNTAX		RollCallString
		MAX-ACCESS		read-only
		STATUS			current
		DESCRIPTION
				"TYPE: - Display
				 PAGE: - Memories
					Memory Name12  cmdID= 37117  format=   "
		::= { iqotr40CmdEntry 37117 }


	iqotr40MenuMemoriesMemoryName13 OBJECT-TYPE
		SYNTAX		RollCallString
		MAX-ACCESS		read-only
		STATUS			current
		DESCRIPTION
				"TYPE: - Display
				 PAGE: - Memories
					Memory Name13  cmdID= 37118  format=   "
		::= { iqotr40CmdEntry 37118 }


	iqotr40MenuMemoriesMemoryName14 OBJECT-TYPE
		SYNTAX		RollCallString
		MAX-ACCESS		read-only
		STATUS			current
		DESCRIPTION
				"TYPE: - Display
				 PAGE: - Memories
					Memory Name14  cmdID= 37119  format=   "
		::= { iqotr40CmdEntry 37119 }


	iqotr40MenuMemoriesMemoryName15 OBJECT-TYPE
		SYNTAX		RollCallString
		MAX-ACCESS		read-only
		STATUS			current
		DESCRIPTION
				"TYPE: - Display
				 PAGE: - Memories
					Memory Name15  cmdID= 37120  format=   "
		::= { iqotr40CmdEntry 37120 }


	iqotr40MenuMemoriesMemoryName16 OBJECT-TYPE
		SYNTAX		RollCallString
		MAX-ACCESS		read-only
		STATUS			current
		DESCRIPTION
				"TYPE: - Display
				 PAGE: - Memories
					Memory Name16  cmdID= 37121  format=   "
		::= { iqotr40CmdEntry 37121 }


	iqotr40Logging1MiscLogSerialNo OBJECT-TYPE
		SYNTAX		INTEGER { disable(0), enable(1) }
		MAX-ACCESS		read-write
		STATUS			current
		DESCRIPTION
				"TYPE: - Checkbox
				 PAGE: - Logging 1
					Log Serial No.  cmdID= 35015 "
		::= { iqotr40CmdEntry 35015 }


	iqotr40Logging1MiscSerialNo OBJECT-TYPE
		SYNTAX		RollCallString
		MAX-ACCESS		read-only
		STATUS			current
		DESCRIPTION
				"TYPE: - Display
				 PAGE: - Logging 1
					Serial No.=  cmdID= 35215  format=   "
		::= { iqotr40CmdEntry 35215 }


	iqotr40Logging1MiscLogOSVersion OBJECT-TYPE
		SYNTAX		INTEGER { disable(0), enable(1) }
		MAX-ACCESS		read-write
		STATUS			current
		DESCRIPTION
				"TYPE: - Checkbox
				 PAGE: - Logging 1
					Log OS Version  cmdID= 35993 "
		::= { iqotr40CmdEntry 35993 }


	iqotr40Logging1MiscOSVersion OBJECT-TYPE
		SYNTAX		RollCallString
		MAX-ACCESS		read-only
		STATUS			current
		DESCRIPTION
				"TYPE: - Display
				 PAGE: - Logging 1
					OS Version=  cmdID= 36993  format=   "
		::= { iqotr40CmdEntry 36993 }


	iqotr40Logging1MiscLogBuildNo OBJECT-TYPE
		SYNTAX		INTEGER { disable(0), enable(1) }
		MAX-ACCESS		read-write
		STATUS			current
		DESCRIPTION
				"TYPE: - Checkbox
				 PAGE: - Logging 1
					Log Build No.  cmdID= 35990 "
		::= { iqotr40CmdEntry 35990 }


	iqotr40Logging1MiscBuildNo OBJECT-TYPE
		SYNTAX		RollCallString
		MAX-ACCESS		read-only
		STATUS			current
		DESCRIPTION
				"TYPE: - Display
				 PAGE: - Logging 1
					Build No.=  cmdID= 36990  format=   "
		::= { iqotr40CmdEntry 36990 }


	iqotr40Logging1MiscLogHardwareVer OBJECT-TYPE
		SYNTAX		INTEGER { disable(0), enable(1) }
		MAX-ACCESS		read-write
		STATUS			current
		DESCRIPTION
				"TYPE: - Checkbox
				 PAGE: - Logging 1
					Log Hardware Ver.  cmdID= 35992 "
		::= { iqotr40CmdEntry 35992 }


	iqotr40Logging1MiscHardwareVer OBJECT-TYPE
		SYNTAX		RollCallString
		MAX-ACCESS		read-only
		STATUS			current
		DESCRIPTION
				"TYPE: - Display
				 PAGE: - Logging 1
					Hardware Ver.=  cmdID= 36992  format=   "
		::= { iqotr40CmdEntry 36992 }


	iqotr40Logging1MiscLogFirmwareVer OBJECT-TYPE
		SYNTAX		INTEGER { disable(0), enable(1) }
		MAX-ACCESS		read-write
		STATUS			current
		DESCRIPTION
				"TYPE: - Checkbox
				 PAGE: - Logging 1
					Log Firmware Ver.  cmdID= 35996 "
		::= { iqotr40CmdEntry 35996 }


	iqotr40Logging1MiscFirmwareVer OBJECT-TYPE
		SYNTAX		RollCallString
		MAX-ACCESS		read-only
		STATUS			current
		DESCRIPTION
				"TYPE: - Display
				 PAGE: - Logging 1
					Firmware Ver.=  cmdID= 36996  format=   "
		::= { iqotr40CmdEntry 36996 }


	iqotr40Logging1MiscLogRearID OBJECT-TYPE
		SYNTAX		INTEGER { disable(0), enable(1) }
		MAX-ACCESS		read-write
		STATUS			current
		DESCRIPTION
				"TYPE: - Checkbox
				 PAGE: - Logging 1
					Log Rear ID  cmdID= 35997 "
		::= { iqotr40CmdEntry 35997 }


	iqotr40Logging1MiscRearID OBJECT-TYPE
		SYNTAX		RollCallString
		MAX-ACCESS		read-only
		STATUS			current
		DESCRIPTION
				"TYPE: - Display
				 PAGE: - Logging 1
					Rear ID.=  cmdID= 36997  format=   "
		::= { iqotr40CmdEntry 36997 }


	iqotr40Logging1MiscLogRearStatus OBJECT-TYPE
		SYNTAX		INTEGER { disable(0), enable(1) }
		MAX-ACCESS		read-write
		STATUS			current
		DESCRIPTION
				"TYPE: - Checkbox
				 PAGE: - Logging 1
					Log Rear Status  cmdID= 36000 "
		::= { iqotr40CmdEntry 36000 }


	iqotr40Logging1MiscRearStatus OBJECT-TYPE
		SYNTAX		RollCallString
		MAX-ACCESS		read-only
		STATUS			current
		DESCRIPTION
				"TYPE: - Display
				 PAGE: - Logging 1
					Rear Status=  cmdID= 35358  format=   "
		::= { iqotr40CmdEntry 35358 }


	iqotr40Logging1MiscLogSlotWidth OBJECT-TYPE
		SYNTAX		INTEGER { disable(0), enable(1) }
		MAX-ACCESS		read-write
		STATUS			current
		DESCRIPTION
				"TYPE: - Checkbox
				 PAGE: - Logging 1
					Log Slot Width  cmdID= 36001 "
		::= { iqotr40CmdEntry 36001 }


	iqotr40Logging1MiscSlotWidth OBJECT-TYPE
		SYNTAX		RollCallString
		MAX-ACCESS		read-only
		STATUS			current
		DESCRIPTION
				"TYPE: - Display
				 PAGE: - Logging 1
					Slot Width=  cmdID= 35359  format=   "
		::= { iqotr40CmdEntry 35359 }


	iqotr40Logging1MiscLogSlotStart OBJECT-TYPE
		SYNTAX		INTEGER { disable(0), enable(1) }
		MAX-ACCESS		read-write
		STATUS			current
		DESCRIPTION
				"TYPE: - Checkbox
				 PAGE: - Logging 1
					Log Slot Start  cmdID= 36002 "
		::= { iqotr40CmdEntry 36002 }


	iqotr40Logging1MiscSlotStart OBJECT-TYPE
		SYNTAX		RollCallString
		MAX-ACCESS		read-only
		STATUS			current
		DESCRIPTION
				"TYPE: - Display
				 PAGE: - Logging 1
					Slot Start=  cmdID= 35360  format=   "
		::= { iqotr40CmdEntry 35360 }


	iqotr40Logging1MiscLogIOMod1ID OBJECT-TYPE
		SYNTAX		INTEGER { disable(0), enable(1) }
		MAX-ACCESS		read-write
		STATUS			current
		DESCRIPTION
				"TYPE: - Checkbox
				 PAGE: - Logging 1
					Log IO Mod 1 ID  cmdID= 35998 "
		::= { iqotr40CmdEntry 35998 }


	iqotr40Logging1MiscIOMod1ID OBJECT-TYPE
		SYNTAX		RollCallString
		MAX-ACCESS		read-only
		STATUS			current
		DESCRIPTION
				"TYPE: - Display
				 PAGE: - Logging 1
					IO Mod 1 ID.=  cmdID= 36998  format=   "
		::= { iqotr40CmdEntry 36998 }


	iqotr40Logging1MiscLogIOMod2ID OBJECT-TYPE
		SYNTAX		INTEGER { disable(0), enable(1) }
		MAX-ACCESS		read-write
		STATUS			current
		DESCRIPTION
				"TYPE: - Checkbox
				 PAGE: - Logging 1
					Log IO Mod 2 ID  cmdID= 35999 "
		::= { iqotr40CmdEntry 35999 }


	iqotr40Logging1MiscIOMod2ID OBJECT-TYPE
		SYNTAX		RollCallString
		MAX-ACCESS		read-only
		STATUS			current
		DESCRIPTION
				"TYPE: - Display
				 PAGE: - Logging 1
					IO Mod 2 ID.=  cmdID= 36999  format=   "
		::= { iqotr40CmdEntry 36999 }


	iqotr40Logging1MiscLogProcModID OBJECT-TYPE
		SYNTAX		INTEGER { disable(0), enable(1) }
		MAX-ACCESS		read-write
		STATUS			current
		DESCRIPTION
				"TYPE: - Checkbox
				 PAGE: - Logging 1
					Log Proc Mod ID  cmdID= 36003 "
		::= { iqotr40CmdEntry 36003 }


	iqotr40Logging1MiscProcModID OBJECT-TYPE
		SYNTAX		RollCallString
		MAX-ACCESS		read-only
		STATUS			current
		DESCRIPTION
				"TYPE: - Display
				 PAGE: - Logging 1
					Proc Mod ID.=  cmdID= 37000  format=   "
		::= { iqotr40CmdEntry 37000 }


	iqotr40Logging1MiscLogUpTime OBJECT-TYPE
		SYNTAX		INTEGER { disable(0), enable(1) }
		MAX-ACCESS		read-write
		STATUS			current
		DESCRIPTION
				"TYPE: - Checkbox
				 PAGE: - Logging 1
					Log Up Time  cmdID= 35994 "
		::= { iqotr40CmdEntry 35994 }


	iqotr40Logging1MiscUpTime OBJECT-TYPE
		SYNTAX		RollCallString
		MAX-ACCESS		read-only
		STATUS			current
		DESCRIPTION
				"TYPE: - Display
				 PAGE: - Logging 1
					Up Time=  cmdID= 36994  format=   "
		::= { iqotr40CmdEntry 36994 }


	iqotr40Logging1MiscLogLicensedOpt OBJECT-TYPE
		SYNTAX		INTEGER { disable(0), enable(1) }
		MAX-ACCESS		read-write
		STATUS			current
		DESCRIPTION
				"TYPE: - Checkbox
				 PAGE: - Logging 1
					Log Licensed Opt.  cmdID= 35995 "
		::= { iqotr40CmdEntry 35995 }


	iqotr40Logging1MiscLicensedOptions OBJECT-TYPE
		SYNTAX		RollCallString
		MAX-ACCESS		read-only
		STATUS			current
		DESCRIPTION
				"TYPE: - Display
				 PAGE: - Logging 1
					Licensed Options=  cmdID= 36995  format=   "
		::= { iqotr40CmdEntry 36995 }


	iqotr40Logging1MiscLogConfig14InU OBJECT-TYPE
		SYNTAX		INTEGER { disable(0), enable(1) }
		MAX-ACCESS		read-write
		STATUS			current
		DESCRIPTION
				"TYPE: - Checkbox
				 PAGE: - Logging 1
					Log Config 1-4 In U  cmdID= 35178 "
		::= { iqotr40CmdEntry 35178 }


	iqotr40Logging1MiscConfig14InUse OBJECT-TYPE
		SYNTAX		RollCallString
		MAX-ACCESS		read-only
		STATUS			current
		DESCRIPTION
				"TYPE: - Display
				 PAGE: - Logging 1
					Config 1-4 In Use=  cmdID= 35361  format=   "
		::= { iqotr40CmdEntry 35361 }


	iqotr40Logging1MiscLogConfig58InU OBJECT-TYPE
		SYNTAX		INTEGER { disable(0), enable(1) }
		MAX-ACCESS		read-write
		STATUS			current
		DESCRIPTION
				"TYPE: - Checkbox
				 PAGE: - Logging 1
					Log Config 5-8 In U  cmdID= 35179 "
		::= { iqotr40CmdEntry 35179 }


	iqotr40Logging1MiscConfig58InUse OBJECT-TYPE
		SYNTAX		RollCallString
		MAX-ACCESS		read-only
		STATUS			current
		DESCRIPTION
				"TYPE: - Display
				 PAGE: - Logging 1
					Config 5-8 In Use=  cmdID= 35362  format=   "
		::= { iqotr40CmdEntry 35362 }


	iqotr40Logging1Input1LogIdent OBJECT-TYPE
		SYNTAX		INTEGER { disable(0), enable(1) }
		MAX-ACCESS		read-write
		STATUS			current
		DESCRIPTION
				"TYPE: - Checkbox
				 PAGE: - Logging 1
					Log Ident  cmdID= 35041 "
		::= { iqotr40CmdEntry 35041 }


	iqotr40Logging1Input1Ident OBJECT-TYPE
		SYNTAX		RollCallString
		MAX-ACCESS		read-only
		STATUS			current
		DESCRIPTION
				"TYPE: - Display
				 PAGE: - Logging 1
					Ident=  cmdID= 35240  format=   "
		::= { iqotr40CmdEntry 35240 }


	iqotr40Logging1Input1LogName OBJECT-TYPE
		SYNTAX		INTEGER { disable(0), enable(1) }
		MAX-ACCESS		read-write
		STATUS			current
		DESCRIPTION
				"TYPE: - Checkbox
				 PAGE: - Logging 1
					Log Name  cmdID= 35080 "
		::= { iqotr40CmdEntry 35080 }


	iqotr40Logging1Input1Name OBJECT-TYPE
		SYNTAX		RollCallString
		MAX-ACCESS		read-only
		STATUS			current
		DESCRIPTION
				"TYPE: - Display
				 PAGE: - Logging 1
					Name=  cmdID= 35260  format=   "
		::= { iqotr40CmdEntry 35260 }


	iqotr40Logging1Input1LogType OBJECT-TYPE
		SYNTAX		INTEGER { disable(0), enable(1) }
		MAX-ACCESS		read-write
		STATUS			current
		DESCRIPTION
				"TYPE: - Checkbox
				 PAGE: - Logging 1
					LogType  cmdID= 35031 "
		::= { iqotr40CmdEntry 35031 }


	iqotr40Logging1Input1Type OBJECT-TYPE
		SYNTAX		RollCallString
		MAX-ACCESS		read-only
		STATUS			current
		DESCRIPTION
				"TYPE: - Display
				 PAGE: - Logging 1
					Type=  cmdID= 35230  format=   "
		::= { iqotr40CmdEntry 35230 }


	iqotr40Logging1Input1LogState OBJECT-TYPE
		SYNTAX		INTEGER { disable(0), enable(1) }
		MAX-ACCESS		read-write
		STATUS			current
		DESCRIPTION
				"TYPE: - Checkbox
				 PAGE: - Logging 1
					Log State  cmdID= 35020 "
		::= { iqotr40CmdEntry 35020 }


	iqotr40Logging1Input1State OBJECT-TYPE
		SYNTAX		RollCallString
		MAX-ACCESS		read-only
		STATUS			current
		DESCRIPTION
				"TYPE: - Display
				 PAGE: - Logging 1
					State=  cmdID= 35220  format=   "
		::= { iqotr40CmdEntry 35220 }


	iqotr40Logging1Input1LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35051 "
		::= { iqotr40CmdEntry 35051 }


	iqotr40Logging1Input1Bitrate OBJECT-TYPE
		SYNTAX		RollCallString
		MAX-ACCESS		read-only
		STATUS			current
		DESCRIPTION
				"TYPE: - Display
				 PAGE: - Logging 1
					Bitrate=  cmdID= 35250  format=   "
		::= { iqotr40CmdEntry 35250 }


	iqotr40Logging1Input2LogIdent OBJECT-TYPE
		SYNTAX		INTEGER { disable(0), enable(1) }
		MAX-ACCESS		read-write
		STATUS			current
		DESCRIPTION
				"TYPE: - Checkbox
				 PAGE: - Logging 1
					Log Ident  cmdID= 35042 "
		::= { iqotr40CmdEntry 35042 }


	iqotr40Logging1Input2Ident OBJECT-TYPE
		SYNTAX		RollCallString
		MAX-ACCESS		read-only
		STATUS			current
		DESCRIPTION
				"TYPE: - Display
				 PAGE: - Logging 1
					Ident=  cmdID= 35241  format=   "
		::= { iqotr40CmdEntry 35241 }


	iqotr40Logging1Input2LogName OBJECT-TYPE
		SYNTAX		INTEGER { disable(0), enable(1) }
		MAX-ACCESS		read-write
		STATUS			current
		DESCRIPTION
				"TYPE: - Checkbox
				 PAGE: - Logging 1
					Log Name  cmdID= 35081 "
		::= { iqotr40CmdEntry 35081 }


	iqotr40Logging1Input2Name OBJECT-TYPE
		SYNTAX		RollCallString
		MAX-ACCESS		read-only
		STATUS			current
		DESCRIPTION
				"TYPE: - Display
				 PAGE: - Logging 1
					Name=  cmdID= 35261  format=   "
		::= { iqotr40CmdEntry 35261 }


	iqotr40Logging1Input2LogType OBJECT-TYPE
		SYNTAX		INTEGER { disable(0), enable(1) }
		MAX-ACCESS		read-write
		STATUS			current
		DESCRIPTION
				"TYPE: - Checkbox
				 PAGE: - Logging 1
					LogType  cmdID= 35032 "
		::= { iqotr40CmdEntry 35032 }


	iqotr40Logging1Input2Type OBJECT-TYPE
		SYNTAX		RollCallString
		MAX-ACCESS		read-only
		STATUS			current
		DESCRIPTION
				"TYPE: - Display
				 PAGE: - Logging 1
					Type=  cmdID= 35231  format=   "
		::= { iqotr40CmdEntry 35231 }


	iqotr40Logging1Input2LogState OBJECT-TYPE
		SYNTAX		INTEGER { disable(0), enable(1) }
		MAX-ACCESS		read-write
		STATUS			current
		DESCRIPTION
				"TYPE: - Checkbox
				 PAGE: - Logging 1
					Log State  cmdID= 35021 "
		::= { iqotr40CmdEntry 35021 }


	iqotr40Logging1Input2State OBJECT-TYPE
		SYNTAX		RollCallString
		MAX-ACCESS		read-only
		STATUS			current
		DESCRIPTION
				"TYPE: - Display
				 PAGE: - Logging 1
					State=  cmdID= 35221  format=   "
		::= { iqotr40CmdEntry 35221 }


	iqotr40Logging1Input2LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35052 "
		::= { iqotr40CmdEntry 35052 }


	iqotr40Logging1Input2Bitrate OBJECT-TYPE
		SYNTAX		RollCallString
		MAX-ACCESS		read-only
		STATUS			current
		DESCRIPTION
				"TYPE: - Display
				 PAGE: - Logging 1
					Bitrate=  cmdID= 35251  format=   "
		::= { iqotr40CmdEntry 35251 }


	iqotr40Logging1Input3LogIdent OBJECT-TYPE
		SYNTAX		INTEGER { disable(0), enable(1) }
		MAX-ACCESS		read-write
		STATUS			current
		DESCRIPTION
				"TYPE: - Checkbox
				 PAGE: - Logging 1
					Log Ident  cmdID= 35043 "
		::= { iqotr40CmdEntry 35043 }


	iqotr40Logging1Input3Ident OBJECT-TYPE
		SYNTAX		RollCallString
		MAX-ACCESS		read-only
		STATUS			current
		DESCRIPTION
				"TYPE: - Display
				 PAGE: - Logging 1
					Ident=  cmdID= 35242  format=   "
		::= { iqotr40CmdEntry 35242 }


	iqotr40Logging1Input3LogName OBJECT-TYPE
		SYNTAX		INTEGER { disable(0), enable(1) }
		MAX-ACCESS		read-write
		STATUS			current
		DESCRIPTION
				"TYPE: - Checkbox
				 PAGE: - Logging 1
					Log Name  cmdID= 35082 "
		::= { iqotr40CmdEntry 35082 }


	iqotr40Logging1Input3Name OBJECT-TYPE
		SYNTAX		RollCallString
		MAX-ACCESS		read-only
		STATUS			current
		DESCRIPTION
				"TYPE: - Display
				 PAGE: - Logging 1
					Name=  cmdID= 35262  format=   "
		::= { iqotr40CmdEntry 35262 }


	iqotr40Logging1Input3LogType OBJECT-TYPE
		SYNTAX		INTEGER { disable(0), enable(1) }
		MAX-ACCESS		read-write
		STATUS			current
		DESCRIPTION
				"TYPE: - Checkbox
				 PAGE: - Logging 1
					LogType  cmdID= 35033 "
		::= { iqotr40CmdEntry 35033 }


	iqotr40Logging1Input3Type OBJECT-TYPE
		SYNTAX		RollCallString
		MAX-ACCESS		read-only
		STATUS			current
		DESCRIPTION
				"TYPE: - Display
				 PAGE: - Logging 1
					Type=  cmdID= 35232  format=   "
		::= { iqotr40CmdEntry 35232 }


	iqotr40Logging1Input3LogState OBJECT-TYPE
		SYNTAX		INTEGER { disable(0), enable(1) }
		MAX-ACCESS		read-write
		STATUS			current
		DESCRIPTION
				"TYPE: - Checkbox
				 PAGE: - Logging 1
					Log State  cmdID= 35022 "
		::= { iqotr40CmdEntry 35022 }


	iqotr40Logging1Input3State OBJECT-TYPE
		SYNTAX		RollCallString
		MAX-ACCESS		read-only
		STATUS			current
		DESCRIPTION
				"TYPE: - Display
				 PAGE: - Logging 1
					State=  cmdID= 35222  format=   "
		::= { iqotr40CmdEntry 35222 }


	iqotr40Logging1Input3LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35053 "
		::= { iqotr40CmdEntry 35053 }


	iqotr40Logging1Input3Bitrate OBJECT-TYPE
		SYNTAX		RollCallString
		MAX-ACCESS		read-only
		STATUS			current
		DESCRIPTION
				"TYPE: - Display
				 PAGE: - Logging 1
					Bitrate=  cmdID= 35252  format=   "
		::= { iqotr40CmdEntry 35252 }


	iqotr40Logging1Input4LogIdent OBJECT-TYPE
		SYNTAX		INTEGER { disable(0), enable(1) }
		MAX-ACCESS		read-write
		STATUS			current
		DESCRIPTION
				"TYPE: - Checkbox
				 PAGE: - Logging 1
					Log Ident  cmdID= 35044 "
		::= { iqotr40CmdEntry 35044 }


	iqotr40Logging1Input4Ident OBJECT-TYPE
		SYNTAX		RollCallString
		MAX-ACCESS		read-only
		STATUS			current
		DESCRIPTION
				"TYPE: - Display
				 PAGE: - Logging 1
					Ident=  cmdID= 35243  format=   "
		::= { iqotr40CmdEntry 35243 }


	iqotr40Logging1Input4LogName OBJECT-TYPE
		SYNTAX		INTEGER { disable(0), enable(1) }
		MAX-ACCESS		read-write
		STATUS			current
		DESCRIPTION
				"TYPE: - Checkbox
				 PAGE: - Logging 1
					Log Name  cmdID= 35083 "
		::= { iqotr40CmdEntry 35083 }


	iqotr40Logging1Input4Name OBJECT-TYPE
		SYNTAX		RollCallString
		MAX-ACCESS		read-only
		STATUS			current
		DESCRIPTION
				"TYPE: - Display
				 PAGE: - Logging 1
					Name=  cmdID= 35263  format=   "
		::= { iqotr40CmdEntry 35263 }


	iqotr40Logging1Input4LogType OBJECT-TYPE
		SYNTAX		INTEGER { disable(0), enable(1) }
		MAX-ACCESS		read-write
		STATUS			current
		DESCRIPTION
				"TYPE: - Checkbox
				 PAGE: - Logging 1
					LogType  cmdID= 35034 "
		::= { iqotr40CmdEntry 35034 }


	iqotr40Logging1Input4Type OBJECT-TYPE
		SYNTAX		RollCallString
		MAX-ACCESS		read-only
		STATUS			current
		DESCRIPTION
				"TYPE: - Display
				 PAGE: - Logging 1
					Type=  cmdID= 35233  format=   "
		::= { iqotr40CmdEntry 35233 }


	iqotr40Logging1Input4LogState OBJECT-TYPE
		SYNTAX		INTEGER { disable(0), enable(1) }
		MAX-ACCESS		read-write
		STATUS			current
		DESCRIPTION
				"TYPE: - Checkbox
				 PAGE: - Logging 1
					Log State  cmdID= 35023 "
		::= { iqotr40CmdEntry 35023 }


	iqotr40Logging1Input4State OBJECT-TYPE
		SYNTAX		RollCallString
		MAX-ACCESS		read-only
		STATUS			current
		DESCRIPTION
				"TYPE: - Display
				 PAGE: - Logging 1
					State=  cmdID= 35223  format=   "
		::= { iqotr40CmdEntry 35223 }


	iqotr40Logging1Input4LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35054 "
		::= { iqotr40CmdEntry 35054 }


	iqotr40Logging1Input4Bitrate OBJECT-TYPE
		SYNTAX		RollCallString
		MAX-ACCESS		read-only
		STATUS			current
		DESCRIPTION
				"TYPE: - Display
				 PAGE: - Logging 1
					Bitrate=  cmdID= 35253  format=   "
		::= { iqotr40CmdEntry 35253 }


	iqotr40Logging1Input5LogIdent OBJECT-TYPE
		SYNTAX		INTEGER { disable(0), enable(1) }
		MAX-ACCESS		read-write
		STATUS			current
		DESCRIPTION
				"TYPE: - Checkbox
				 PAGE: - Logging 1
					Log Ident  cmdID= 35045 "
		::= { iqotr40CmdEntry 35045 }


	iqotr40Logging1Input5Ident OBJECT-TYPE
		SYNTAX		RollCallString
		MAX-ACCESS		read-only
		STATUS			current
		DESCRIPTION
				"TYPE: - Display
				 PAGE: - Logging 1
					Ident=  cmdID= 35244  format=   "
		::= { iqotr40CmdEntry 35244 }


	iqotr40Logging1Input5LogName OBJECT-TYPE
		SYNTAX		INTEGER { disable(0), enable(1) }
		MAX-ACCESS		read-write
		STATUS			current
		DESCRIPTION
				"TYPE: - Checkbox
				 PAGE: - Logging 1
					Log Name  cmdID= 35084 "
		::= { iqotr40CmdEntry 35084 }


	iqotr40Logging1Input5Name OBJECT-TYPE
		SYNTAX		RollCallString
		MAX-ACCESS		read-only
		STATUS			current
		DESCRIPTION
				"TYPE: - Display
				 PAGE: - Logging 1
					Name=  cmdID= 35264  format=   "
		::= { iqotr40CmdEntry 35264 }


	iqotr40Logging1Input5LogType OBJECT-TYPE
		SYNTAX		INTEGER { disable(0), enable(1) }
		MAX-ACCESS		read-write
		STATUS			current
		DESCRIPTION
				"TYPE: - Checkbox
				 PAGE: - Logging 1
					LogType  cmdID= 35035 "
		::= { iqotr40CmdEntry 35035 }


	iqotr40Logging1Input5Type OBJECT-TYPE
		SYNTAX		RollCallString
		MAX-ACCESS		read-only
		STATUS			current
		DESCRIPTION
				"TYPE: - Display
				 PAGE: - Logging 1
					Type=  cmdID= 35234  format=   "
		::= { iqotr40CmdEntry 35234 }


	iqotr40Logging1Input5LogState OBJECT-TYPE
		SYNTAX		INTEGER { disable(0), enable(1) }
		MAX-ACCESS		read-write
		STATUS			current
		DESCRIPTION
				"TYPE: - Checkbox
				 PAGE: - Logging 1
					Log State  cmdID= 35024 "
		::= { iqotr40CmdEntry 35024 }


	iqotr40Logging1Input5State OBJECT-TYPE
		SYNTAX		RollCallString
		MAX-ACCESS		read-only
		STATUS			current
		DESCRIPTION
				"TYPE: - Display
				 PAGE: - Logging 1
					State=  cmdID= 35224  format=   "
		::= { iqotr40CmdEntry 35224 }


	iqotr40Logging1Input5LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35055 "
		::= { iqotr40CmdEntry 35055 }


	iqotr40Logging1Input5Bitrate OBJECT-TYPE
		SYNTAX		RollCallString
		MAX-ACCESS		read-only
		STATUS			current
		DESCRIPTION
				"TYPE: - Display
				 PAGE: - Logging 1
					Bitrate=  cmdID= 35254  format=   "
		::= { iqotr40CmdEntry 35254 }


	iqotr40Logging1Input6LogIdent OBJECT-TYPE
		SYNTAX		INTEGER { disable(0), enable(1) }
		MAX-ACCESS		read-write
		STATUS			current
		DESCRIPTION
				"TYPE: - Checkbox
				 PAGE: - Logging 1
					Log Ident  cmdID= 35046 "
		::= { iqotr40CmdEntry 35046 }


	iqotr40Logging1Input6Ident OBJECT-TYPE
		SYNTAX		RollCallString
		MAX-ACCESS		read-only
		STATUS			current
		DESCRIPTION
				"TYPE: - Display
				 PAGE: - Logging 1
					Ident=  cmdID= 35245  format=   "
		::= { iqotr40CmdEntry 35245 }


	iqotr40Logging1Input6LogName OBJECT-TYPE
		SYNTAX		INTEGER { disable(0), enable(1) }
		MAX-ACCESS		read-write
		STATUS			current
		DESCRIPTION
				"TYPE: - Checkbox
				 PAGE: - Logging 1
					Log Name  cmdID= 35085 "
		::= { iqotr40CmdEntry 35085 }


	iqotr40Logging1Input6Name OBJECT-TYPE
		SYNTAX		RollCallString
		MAX-ACCESS		read-only
		STATUS			current
		DESCRIPTION
				"TYPE: - Display
				 PAGE: - Logging 1
					Name=  cmdID= 35265  format=   "
		::= { iqotr40CmdEntry 35265 }


	iqotr40Logging1Input6LogType OBJECT-TYPE
		SYNTAX		INTEGER { disable(0), enable(1) }
		MAX-ACCESS		read-write
		STATUS			current
		DESCRIPTION
				"TYPE: - Checkbox
				 PAGE: - Logging 1
					LogType  cmdID= 35036 "
		::= { iqotr40CmdEntry 35036 }


	iqotr40Logging1Input6Type OBJECT-TYPE
		SYNTAX		RollCallString
		MAX-ACCESS		read-only
		STATUS			current
		DESCRIPTION
				"TYPE: - Display
				 PAGE: - Logging 1
					Type=  cmdID= 35235  format=   "
		::= { iqotr40CmdEntry 35235 }


	iqotr40Logging1Input6LogState OBJECT-TYPE
		SYNTAX		INTEGER { disable(0), enable(1) }
		MAX-ACCESS		read-write
		STATUS			current
		DESCRIPTION
				"TYPE: - Checkbox
				 PAGE: - Logging 1
					Log State  cmdID= 35025 "
		::= { iqotr40CmdEntry 35025 }


	iqotr40Logging1Input6State OBJECT-TYPE
		SYNTAX		RollCallString
		MAX-ACCESS		read-only
		STATUS			current
		DESCRIPTION
				"TYPE: - Display
				 PAGE: - Logging 1
					State=  cmdID= 35225  format=   "
		::= { iqotr40CmdEntry 35225 }


	iqotr40Logging1Input6LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35056 "
		::= { iqotr40CmdEntry 35056 }


	iqotr40Logging1Input6Bitrate OBJECT-TYPE
		SYNTAX		RollCallString
		MAX-ACCESS		read-only
		STATUS			current
		DESCRIPTION
				"TYPE: - Display
				 PAGE: - Logging 1
					Bitrate=  cmdID= 35255  format=   "
		::= { iqotr40CmdEntry 35255 }


	iqotr40Logging1Input7LogIdent OBJECT-TYPE
		SYNTAX		INTEGER { disable(0), enable(1) }
		MAX-ACCESS		read-write
		STATUS			current
		DESCRIPTION
				"TYPE: - Checkbox
				 PAGE: - Logging 1
					Log Ident  cmdID= 35047 "
		::= { iqotr40CmdEntry 35047 }


	iqotr40Logging1Input7Ident OBJECT-TYPE
		SYNTAX		RollCallString
		MAX-ACCESS		read-only
		STATUS			current
		DESCRIPTION
				"TYPE: - Display
				 PAGE: - Logging 1
					Ident=  cmdID= 35246  format=   "
		::= { iqotr40CmdEntry 35246 }


	iqotr40Logging1Input7LogName OBJECT-TYPE
		SYNTAX		INTEGER { disable(0), enable(1) }
		MAX-ACCESS		read-write
		STATUS			current
		DESCRIPTION
				"TYPE: - Checkbox
				 PAGE: - Logging 1
					Log Name  cmdID= 35086 "
		::= { iqotr40CmdEntry 35086 }


	iqotr40Logging1Input7Name OBJECT-TYPE
		SYNTAX		RollCallString
		MAX-ACCESS		read-only
		STATUS			current
		DESCRIPTION
				"TYPE: - Display
				 PAGE: - Logging 1
					Name=  cmdID= 35266  format=   "
		::= { iqotr40CmdEntry 35266 }


	iqotr40Logging1Input7LogType OBJECT-TYPE
		SYNTAX		INTEGER { disable(0), enable(1) }
		MAX-ACCESS		read-write
		STATUS			current
		DESCRIPTION
				"TYPE: - Checkbox
				 PAGE: - Logging 1
					LogType  cmdID= 35037 "
		::= { iqotr40CmdEntry 35037 }


	iqotr40Logging1Input7Type OBJECT-TYPE
		SYNTAX		RollCallString
		MAX-ACCESS		read-only
		STATUS			current
		DESCRIPTION
				"TYPE: - Display
				 PAGE: - Logging 1
					Type=  cmdID= 35236  format=   "
		::= { iqotr40CmdEntry 35236 }


	iqotr40Logging1Input7LogState OBJECT-TYPE
		SYNTAX		INTEGER { disable(0), enable(1) }
		MAX-ACCESS		read-write
		STATUS			current
		DESCRIPTION
				"TYPE: - Checkbox
				 PAGE: - Logging 1
					Log State  cmdID= 35026 "
		::= { iqotr40CmdEntry 35026 }


	iqotr40Logging1Input7State OBJECT-TYPE
		SYNTAX		RollCallString
		MAX-ACCESS		read-only
		STATUS			current
		DESCRIPTION
				"TYPE: - Display
				 PAGE: - Logging 1
					State=  cmdID= 35226  format=   "
		::= { iqotr40CmdEntry 35226 }


	iqotr40Logging1Input7LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35057 "
		::= { iqotr40CmdEntry 35057 }


	iqotr40Logging1Input7Bitrate OBJECT-TYPE
		SYNTAX		RollCallString
		MAX-ACCESS		read-only
		STATUS			current
		DESCRIPTION
				"TYPE: - Display
				 PAGE: - Logging 1
					Bitrate=  cmdID= 35256  format=   "
		::= { iqotr40CmdEntry 35256 }


	iqotr40Logging1Input8LogIdent OBJECT-TYPE
		SYNTAX		INTEGER { disable(0), enable(1) }
		MAX-ACCESS		read-write
		STATUS			current
		DESCRIPTION
				"TYPE: - Checkbox
				 PAGE: - Logging 1
					Log Ident  cmdID= 35048 "
		::= { iqotr40CmdEntry 35048 }


	iqotr40Logging1Input8Ident OBJECT-TYPE
		SYNTAX		RollCallString
		MAX-ACCESS		read-only
		STATUS			current
		DESCRIPTION
				"TYPE: - Display
				 PAGE: - Logging 1
					Ident=  cmdID= 35247  format=   "
		::= { iqotr40CmdEntry 35247 }


	iqotr40Logging1Input8LogName OBJECT-TYPE
		SYNTAX		INTEGER { disable(0), enable(1) }
		MAX-ACCESS		read-write
		STATUS			current
		DESCRIPTION
				"TYPE: - Checkbox
				 PAGE: - Logging 1
					Log Name  cmdID= 35087 "
		::= { iqotr40CmdEntry 35087 }


	iqotr40Logging1Input8Name OBJECT-TYPE
		SYNTAX		RollCallString
		MAX-ACCESS		read-only
		STATUS			current
		DESCRIPTION
				"TYPE: - Display
				 PAGE: - Logging 1
					Name=  cmdID= 35267  format=   "
		::= { iqotr40CmdEntry 35267 }


	iqotr40Logging1Input8LogType OBJECT-TYPE
		SYNTAX		INTEGER { disable(0), enable(1) }
		MAX-ACCESS		read-write
		STATUS			current
		DESCRIPTION
				"TYPE: - Checkbox
				 PAGE: - Logging 1
					LogType  cmdID= 35038 "
		::= { iqotr40CmdEntry 35038 }


	iqotr40Logging1Input8Type OBJECT-TYPE
		SYNTAX		RollCallString
		MAX-ACCESS		read-only
		STATUS			current
		DESCRIPTION
				"TYPE: - Display
				 PAGE: - Logging 1
					Type=  cmdID= 35237  format=   "
		::= { iqotr40CmdEntry 35237 }


	iqotr40Logging1Input8LogState OBJECT-TYPE
		SYNTAX		INTEGER { disable(0), enable(1) }
		MAX-ACCESS		read-write
		STATUS			current
		DESCRIPTION
				"TYPE: - Checkbox
				 PAGE: - Logging 1
					Log State  cmdID= 35027 "
		::= { iqotr40CmdEntry 35027 }


	iqotr40Logging1Input8State OBJECT-TYPE
		SYNTAX		RollCallString
		MAX-ACCESS		read-only
		STATUS			current
		DESCRIPTION
				"TYPE: - Display
				 PAGE: - Logging 1
					State=  cmdID= 35227  format=   "
		::= { iqotr40CmdEntry 35227 }


	iqotr40Logging1Input8LogSDIBitrate OBJECT-TYPE
		SYNTAX		INTEGER { disable(0), enable(1) }
		MAX-ACCESS		read-write
		STATUS			current
		DESCRIPTION
				"TYPE: - Checkbox
				 PAGE: - Logging 1
					Log SDI Bitrate  cmdID= 35058 "
		::= { iqotr40CmdEntry 35058 }


	iqotr40Logging1Input8Bitrate OBJECT-TYPE
		SYNTAX		RollCallString
		MAX-ACCESS		read-only
		STATUS			current
		DESCRIPTION
				"TYPE: - Display
				 PAGE: - Logging 1
					Bitrate=  cmdID= 35257  format=   "
		::= { iqotr40CmdEntry 35257 }


	iqotr40Logging2FiberTx1LaserBiasState35100 OBJECT-TYPE
		SYNTAX		INTEGER { disable(0), enable(1) }
		MAX-ACCESS		read-write
		STATUS			current
		DESCRIPTION
				"TYPE: - Checkbox
				 PAGE: - Logging 2
					Laser Bias State  cmdID= 35100 "
		::= { iqotr40CmdEntry 35100 }


	iqotr40Logging2FiberTx1LaserBiasState35280 OBJECT-TYPE
		SYNTAX		RollCallString
		MAX-ACCESS		read-only
		STATUS			current
		DESCRIPTION
				"TYPE: - Display
				 PAGE: - Logging 2
					Laser Bias State=  cmdID= 35280  format=   "
		::= { iqotr40CmdEntry 35280 }


	iqotr40Logging2FiberTx1TxPowerState35110 OBJECT-TYPE
		SYNTAX		INTEGER { disable(0), enable(1) }
		MAX-ACCESS		read-write
		STATUS			current
		DESCRIPTION
				"TYPE: - Checkbox
				 PAGE: - Logging 2
					Tx Power State  cmdID= 35110 "
		::= { iqotr40CmdEntry 35110 }


	iqotr40Logging2FiberTx1TxPowerState35290 OBJECT-TYPE
		SYNTAX		RollCallString
		MAX-ACCESS		read-only
		STATUS			current
		DESCRIPTION
				"TYPE: - Display
				 PAGE: - Logging 2
					Tx Power State=  cmdID= 35290  format=   "
		::= { iqotr40CmdEntry 35290 }


	iqotr40Logging2FiberTx1LaserBias35090 OBJECT-TYPE
		SYNTAX		INTEGER { disable(0), enable(1) }
		MAX-ACCESS		read-write
		STATUS			current
		DESCRIPTION
				"TYPE: - Checkbox
				 PAGE: - Logging 2
					Laser Bias  cmdID= 35090 "
		::= { iqotr40CmdEntry 35090 }


	iqotr40Logging2FiberTx1LaserBias35300 OBJECT-TYPE
		SYNTAX		RollCallString
		MAX-ACCESS		read-only
		STATUS			current
		DESCRIPTION
				"TYPE: - Display
				 PAGE: - Logging 2
					Laser Bias=  cmdID= 35300  format=   "
		::= { iqotr40CmdEntry 35300 }


	iqotr40Logging2FiberTx1TxPower35130 OBJECT-TYPE
		SYNTAX		INTEGER { disable(0), enable(1) }
		MAX-ACCESS		read-write
		STATUS			current
		DESCRIPTION
				"TYPE: - Checkbox
				 PAGE: - Logging 2
					Tx Power  cmdID= 35130 "
		::= { iqotr40CmdEntry 35130 }


	iqotr40Logging2FiberTx1TxPower35310 OBJECT-TYPE
		SYNTAX		RollCallString
		MAX-ACCESS		read-only
		STATUS			current
		DESCRIPTION
				"TYPE: - Display
				 PAGE: - Logging 2
					Tx Power=  cmdID= 35310  format=   "
		::= { iqotr40CmdEntry 35310 }


	iqotr40Logging2FiberTx1Wavelength35120 OBJECT-TYPE
		SYNTAX		INTEGER { disable(0), enable(1) }
		MAX-ACCESS		read-write
		STATUS			current
		DESCRIPTION
				"TYPE: - Checkbox
				 PAGE: - Logging 2
					Wavelength  cmdID= 35120 "
		::= { iqotr40CmdEntry 35120 }


	iqotr40Logging2FiberTx1Wavelength35270 OBJECT-TYPE
		SYNTAX		RollCallString
		MAX-ACCESS		read-only
		STATUS			current
		DESCRIPTION
				"TYPE: - Display
				 PAGE: - Logging 2
					Wavelength=  cmdID= 35270  format=   "
		::= { iqotr40CmdEntry 35270 }


	iqotr40Logging2FiberTx1TxSFP35170 OBJECT-TYPE
		SYNTAX		INTEGER { disable(0), enable(1) }
		MAX-ACCESS		read-write
		STATUS			current
		DESCRIPTION
				"TYPE: - Checkbox
				 PAGE: - Logging 2
					Tx SFP  cmdID= 35170 "
		::= { iqotr40CmdEntry 35170 }


	iqotr40Logging2FiberTx1TxSFP35350 OBJECT-TYPE
		SYNTAX		RollCallString
		MAX-ACCESS		read-only
		STATUS			current
		DESCRIPTION
				"TYPE: - Display
				 PAGE: - Logging 2
					Tx SFP=  cmdID= 35350  format=   "
		::= { iqotr40CmdEntry 35350 }


	iqotr40Logging2FiberTx2LaserBiasState35101 OBJECT-TYPE
		SYNTAX		INTEGER { disable(0), enable(1) }
		MAX-ACCESS		read-write
		STATUS			current
		DESCRIPTION
				"TYPE: - Checkbox
				 PAGE: - Logging 2
					Laser Bias State  cmdID= 35101 "
		::= { iqotr40CmdEntry 35101 }


	iqotr40Logging2FiberTx2LaserBiasState35281 OBJECT-TYPE
		SYNTAX		RollCallString
		MAX-ACCESS		read-only
		STATUS			current
		DESCRIPTION
				"TYPE: - Display
				 PAGE: - Logging 2
					Laser Bias State=  cmdID= 35281  format=   "
		::= { iqotr40CmdEntry 35281 }


	iqotr40Logging2FiberTx2TxPowerState35111 OBJECT-TYPE
		SYNTAX		INTEGER { disable(0), enable(1) }
		MAX-ACCESS		read-write
		STATUS			current
		DESCRIPTION
				"TYPE: - Checkbox
				 PAGE: - Logging 2
					Tx Power State  cmdID= 35111 "
		::= { iqotr40CmdEntry 35111 }


	iqotr40Logging2FiberTx2TxPowerState35291 OBJECT-TYPE
		SYNTAX		RollCallString
		MAX-ACCESS		read-only
		STATUS			current
		DESCRIPTION
				"TYPE: - Display
				 PAGE: - Logging 2
					Tx Power State=  cmdID= 35291  format=   "
		::= { iqotr40CmdEntry 35291 }


	iqotr40Logging2FiberTx2LaserBias35091 OBJECT-TYPE
		SYNTAX		INTEGER { disable(0), enable(1) }
		MAX-ACCESS		read-write
		STATUS			current
		DESCRIPTION
				"TYPE: - Checkbox
				 PAGE: - Logging 2
					Laser Bias  cmdID= 35091 "
		::= { iqotr40CmdEntry 35091 }


	iqotr40Logging2FiberTx2LaserBias35301 OBJECT-TYPE
		SYNTAX		RollCallString
		MAX-ACCESS		read-only
		STATUS			current
		DESCRIPTION
				"TYPE: - Display
				 PAGE: - Logging 2
					Laser Bias=  cmdID= 35301  format=   "
		::= { iqotr40CmdEntry 35301 }


	iqotr40Logging2FiberTx2TxPower35131 OBJECT-TYPE
		SYNTAX		INTEGER { disable(0), enable(1) }
		MAX-ACCESS		read-write
		STATUS			current
		DESCRIPTION
				"TYPE: - Checkbox
				 PAGE: - Logging 2
					Tx Power  cmdID= 35131 "
		::= { iqotr40CmdEntry 35131 }


	iqotr40Logging2FiberTx2TxPower35311 OBJECT-TYPE
		SYNTAX		RollCallString
		MAX-ACCESS		read-only
		STATUS			current
		DESCRIPTION
				"TYPE: - Display
				 PAGE: - Logging 2
					Tx Power=  cmdID= 35311  format=   "
		::= { iqotr40CmdEntry 35311 }


	iqotr40Logging2FiberTx2Wavelength35121 OBJECT-TYPE
		SYNTAX		INTEGER { disable(0), enable(1) }
		MAX-ACCESS		read-write
		STATUS			current
		DESCRIPTION
				"TYPE: - Checkbox
				 PAGE: - Logging 2
					Wavelength  cmdID= 35121 "
		::= { iqotr40CmdEntry 35121 }


	iqotr40Logging2FiberTx2Wavelength35271 OBJECT-TYPE
		SYNTAX		RollCallString
		MAX-ACCESS		read-only
		STATUS			current
		DESCRIPTION
				"TYPE: - Display
				 PAGE: - Logging 2
					Wavelength=  cmdID= 35271  format=   "
		::= { iqotr40CmdEntry 35271 }


	iqotr40Logging2FiberTx2TxSFP35171 OBJECT-TYPE
		SYNTAX		INTEGER { disable(0), enable(1) }
		MAX-ACCESS		read-write
		STATUS			current
		DESCRIPTION
				"TYPE: - Checkbox
				 PAGE: - Logging 2
					Tx SFP  cmdID= 35171 "
		::= { iqotr40CmdEntry 35171 }


	iqotr40Logging2FiberTx2TxSFP35351 OBJECT-TYPE
		SYNTAX		RollCallString
		MAX-ACCESS		read-only
		STATUS			current
		DESCRIPTION
				"TYPE: - Display
				 PAGE: - Logging 2
					Tx SFP=  cmdID= 35351  format=   "
		::= { iqotr40CmdEntry 35351 }


	iqotr40Logging2FiberTx3LaserBiasState35102 OBJECT-TYPE
		SYNTAX		INTEGER { disable(0), enable(1) }
		MAX-ACCESS		read-write
		STATUS			current
		DESCRIPTION
				"TYPE: - Checkbox
				 PAGE: - Logging 2
					Laser Bias State  cmdID= 35102 "
		::= { iqotr40CmdEntry 35102 }


	iqotr40Logging2FiberTx3LaserBiasState35282 OBJECT-TYPE
		SYNTAX		RollCallString
		MAX-ACCESS		read-only
		STATUS			current
		DESCRIPTION
				"TYPE: - Display
				 PAGE: - Logging 2
					Laser Bias State=  cmdID= 35282  format=   "
		::= { iqotr40CmdEntry 35282 }


	iqotr40Logging2FiberTx3TxPowerState35112 OBJECT-TYPE
		SYNTAX		INTEGER { disable(0), enable(1) }
		MAX-ACCESS		read-write
		STATUS			current
		DESCRIPTION
				"TYPE: - Checkbox
				 PAGE: - Logging 2
					Tx Power State  cmdID= 35112 "
		::= { iqotr40CmdEntry 35112 }


	iqotr40Logging2FiberTx3TxPowerState35292 OBJECT-TYPE
		SYNTAX		RollCallString
		MAX-ACCESS		read-only
		STATUS			current
		DESCRIPTION
				"TYPE: - Display
				 PAGE: - Logging 2
					Tx Power State=  cmdID= 35292  format=   "
		::= { iqotr40CmdEntry 35292 }


	iqotr40Logging2FiberTx3LaserBias35092 OBJECT-TYPE
		SYNTAX		INTEGER { disable(0), enable(1) }
		MAX-ACCESS		read-write
		STATUS			current
		DESCRIPTION
				"TYPE: - Checkbox
				 PAGE: - Logging 2
					Laser Bias  cmdID= 35092 "
		::= { iqotr40CmdEntry 35092 }


	iqotr40Logging2FiberTx3LaserBias35302 OBJECT-TYPE
		SYNTAX		RollCallString
		MAX-ACCESS		read-only
		STATUS			current
		DESCRIPTION
				"TYPE: - Display
				 PAGE: - Logging 2
					Laser Bias=  cmdID= 35302  format=   "
		::= { iqotr40CmdEntry 35302 }


	iqotr40Logging2FiberTx3TxPower35132 OBJECT-TYPE
		SYNTAX		INTEGER { disable(0), enable(1) }
		MAX-ACCESS		read-write
		STATUS			current
		DESCRIPTION
				"TYPE: - Checkbox
				 PAGE: - Logging 2
					Tx Power  cmdID= 35132 "
		::= { iqotr40CmdEntry 35132 }


	iqotr40Logging2FiberTx3TxPower35312 OBJECT-TYPE
		SYNTAX		RollCallString
		MAX-ACCESS		read-only
		STATUS			current
		DESCRIPTION
				"TYPE: - Display
				 PAGE: - Logging 2
					Tx Power=  cmdID= 35312  format=   "
		::= { iqotr40CmdEntry 35312 }


	iqotr40Logging2FiberTx3Wavelength35122 OBJECT-TYPE
		SYNTAX		INTEGER { disable(0), enable(1) }
		MAX-ACCESS		read-write
		STATUS			current
		DESCRIPTION
				"TYPE: - Checkbox
				 PAGE: - Logging 2
					Wavelength  cmdID= 35122 "
		::= { iqotr40CmdEntry 35122 }


	iqotr40Logging2FiberTx3Wavelength35272 OBJECT-TYPE
		SYNTAX		RollCallString
		MAX-ACCESS		read-only
		STATUS			current
		DESCRIPTION
				"TYPE: - Display
				 PAGE: - Logging 2
					Wavelength=  cmdID= 35272  format=   "
		::= { iqotr40CmdEntry 35272 }


	iqotr40Logging2FiberTx3TxSFP35172 OBJECT-TYPE
		SYNTAX		INTEGER { disable(0), enable(1) }
		MAX-ACCESS		read-write
		STATUS			current
		DESCRIPTION
				"TYPE: - Checkbox
				 PAGE: - Logging 2
					Tx SFP  cmdID= 35172 "
		::= { iqotr40CmdEntry 35172 }


	iqotr40Logging2FiberTx3TxSFP35352 OBJECT-TYPE
		SYNTAX		RollCallString
		MAX-ACCESS		read-only
		STATUS			current
		DESCRIPTION
				"TYPE: - Display
				 PAGE: - Logging 2
					Tx SFP=  cmdID= 35352  format=   "
		::= { iqotr40CmdEntry 35352 }


	iqotr40Logging2FiberTx4LaserBiasState35103 OBJECT-TYPE
		SYNTAX		INTEGER { disable(0), enable(1) }
		MAX-ACCESS		read-write
		STATUS			current
		DESCRIPTION
				"TYPE: - Checkbox
				 PAGE: - Logging 2
					Laser Bias State  cmdID= 35103 "
		::= { iqotr40CmdEntry 35103 }


	iqotr40Logging2FiberTx4LaserBiasState35283 OBJECT-TYPE
		SYNTAX		RollCallString
		MAX-ACCESS		read-only
		STATUS			current
		DESCRIPTION
				"TYPE: - Display
				 PAGE: - Logging 2
					Laser Bias State=  cmdID= 35283  format=   "
		::= { iqotr40CmdEntry 35283 }


	iqotr40Logging2FiberTx4TxPowerState35113 OBJECT-TYPE
		SYNTAX		INTEGER { disable(0), enable(1) }
		MAX-ACCESS		read-write
		STATUS			current
		DESCRIPTION
				"TYPE: - Checkbox
				 PAGE: - Logging 2
					Tx Power State  cmdID= 35113 "
		::= { iqotr40CmdEntry 35113 }


	iqotr40Logging2FiberTx4TxPowerState35293 OBJECT-TYPE
		SYNTAX		RollCallString
		MAX-ACCESS		read-only
		STATUS			current
		DESCRIPTION
				"TYPE: - Display
				 PAGE: - Logging 2
					Tx Power State=  cmdID= 35293  format=   "
		::= { iqotr40CmdEntry 35293 }


	iqotr40Logging2FiberTx4LaserBias35093 OBJECT-TYPE
		SYNTAX		INTEGER { disable(0), enable(1) }
		MAX-ACCESS		read-write
		STATUS			current
		DESCRIPTION
				"TYPE: - Checkbox
				 PAGE: - Logging 2
					Laser Bias  cmdID= 35093 "
		::= { iqotr40CmdEntry 35093 }


	iqotr40Logging2FiberTx4LaserBias35303 OBJECT-TYPE
		SYNTAX		RollCallString
		MAX-ACCESS		read-only
		STATUS			current
		DESCRIPTION
				"TYPE: - Display
				 PAGE: - Logging 2
					Laser Bias=  cmdID= 35303  format=   "
		::= { iqotr40CmdEntry 35303 }


	iqotr40Logging2FiberTx4TxPower35133 OBJECT-TYPE
		SYNTAX		INTEGER { disable(0), enable(1) }
		MAX-ACCESS		read-write
		STATUS			current
		DESCRIPTION
				"TYPE: - Checkbox
				 PAGE: - Logging 2
					Tx Power  cmdID= 35133 "
		::= { iqotr40CmdEntry 35133 }


	iqotr40Logging2FiberTx4TxPower35313 OBJECT-TYPE
		SYNTAX		RollCallString
		MAX-ACCESS		read-only
		STATUS			current
		DESCRIPTION
				"TYPE: - Display
				 PAGE: - Logging 2
					Tx Power=  cmdID= 35313  format=   "
		::= { iqotr40CmdEntry 35313 }


	iqotr40Logging2FiberTx4Wavelength35123 OBJECT-TYPE
		SYNTAX		INTEGER { disable(0), enable(1) }
		MAX-ACCESS		read-write
		STATUS			current
		DESCRIPTION
				"TYPE: - Checkbox
				 PAGE: - Logging 2
					Wavelength  cmdID= 35123 "
		::= { iqotr40CmdEntry 35123 }


	iqotr40Logging2FiberTx4Wavelength35273 OBJECT-TYPE
		SYNTAX		RollCallString
		MAX-ACCESS		read-only
		STATUS			current
		DESCRIPTION
				"TYPE: - Display
				 PAGE: - Logging 2
					Wavelength=  cmdID= 35273  format=   "
		::= { iqotr40CmdEntry 35273 }


	iqotr40Logging2FiberTx4TxSFP35173 OBJECT-TYPE
		SYNTAX		INTEGER { disable(0), enable(1) }
		MAX-ACCESS		read-write
		STATUS			current
		DESCRIPTION
				"TYPE: - Checkbox
				 PAGE: - Logging 2
					Tx SFP  cmdID= 35173 "
		::= { iqotr40CmdEntry 35173 }


	iqotr40Logging2FiberTx4TxSFP35353 OBJECT-TYPE
		SYNTAX		RollCallString
		MAX-ACCESS		read-only
		STATUS			current
		DESCRIPTION
				"TYPE: - Display
				 PAGE: - Logging 2
					Tx SFP=  cmdID= 35353  format=   "
		::= { iqotr40CmdEntry 35353 }


	iqotr40Logging2FiberTx5LaserBiasState35104 OBJECT-TYPE
		SYNTAX		INTEGER { disable(0), enable(1) }
		MAX-ACCESS		read-write
		STATUS			current
		DESCRIPTION
				"TYPE: - Checkbox
				 PAGE: - Logging 2
					Laser Bias State  cmdID= 35104 "
		::= { iqotr40CmdEntry 35104 }


	iqotr40Logging2FiberTx5LaserBiasState35284 OBJECT-TYPE
		SYNTAX		RollCallString
		MAX-ACCESS		read-only
		STATUS			current
		DESCRIPTION
				"TYPE: - Display
				 PAGE: - Logging 2
					Laser Bias State=  cmdID= 35284  format=   "
		::= { iqotr40CmdEntry 35284 }


	iqotr40Logging2FiberTx5TxPowerState35114 OBJECT-TYPE
		SYNTAX		INTEGER { disable(0), enable(1) }
		MAX-ACCESS		read-write
		STATUS			current
		DESCRIPTION
				"TYPE: - Checkbox
				 PAGE: - Logging 2
					Tx Power State  cmdID= 35114 "
		::= { iqotr40CmdEntry 35114 }


	iqotr40Logging2FiberTx5TxPowerState35294 OBJECT-TYPE
		SYNTAX		RollCallString
		MAX-ACCESS		read-only
		STATUS			current
		DESCRIPTION
				"TYPE: - Display
				 PAGE: - Logging 2
					Tx Power State=  cmdID= 35294  format=   "
		::= { iqotr40CmdEntry 35294 }


	iqotr40Logging2FiberTx5LaserBias35094 OBJECT-TYPE
		SYNTAX		INTEGER { disable(0), enable(1) }
		MAX-ACCESS		read-write
		STATUS			current
		DESCRIPTION
				"TYPE: - Checkbox
				 PAGE: - Logging 2
					Laser Bias  cmdID= 35094 "
		::= { iqotr40CmdEntry 35094 }


	iqotr40Logging2FiberTx5LaserBias35304 OBJECT-TYPE
		SYNTAX		RollCallString
		MAX-ACCESS		read-only
		STATUS			current
		DESCRIPTION
				"TYPE: - Display
				 PAGE: - Logging 2
					Laser Bias=  cmdID= 35304  format=   "
		::= { iqotr40CmdEntry 35304 }


	iqotr40Logging2FiberTx5TxPower35134 OBJECT-TYPE
		SYNTAX		INTEGER { disable(0), enable(1) }
		MAX-ACCESS		read-write
		STATUS			current
		DESCRIPTION
				"TYPE: - Checkbox
				 PAGE: - Logging 2
					Tx Power  cmdID= 35134 "
		::= { iqotr40CmdEntry 35134 }


	iqotr40Logging2FiberTx5TxPower35314 OBJECT-TYPE
		SYNTAX		RollCallString
		MAX-ACCESS		read-only
		STATUS			current
		DESCRIPTION
				"TYPE: - Display
				 PAGE: - Logging 2
					Tx Power=  cmdID= 35314  format=   "
		::= { iqotr40CmdEntry 35314 }


	iqotr40Logging2FiberTx5Wavelength35124 OBJECT-TYPE
		SYNTAX		INTEGER { disable(0), enable(1) }
		MAX-ACCESS		read-write
		STATUS			current
		DESCRIPTION
				"TYPE: - Checkbox
				 PAGE: - Logging 2
					Wavelength  cmdID= 35124 "
		::= { iqotr40CmdEntry 35124 }


	iqotr40Logging2FiberTx5Wavelength35274 OBJECT-TYPE
		SYNTAX		RollCallString
		MAX-ACCESS		read-only
		STATUS			current
		DESCRIPTION
				"TYPE: - Display
				 PAGE: - Logging 2
					Wavelength=  cmdID= 35274  format=   "
		::= { iqotr40CmdEntry 35274 }


	iqotr40Logging2FiberTx5TxSFP35174 OBJECT-TYPE
		SYNTAX		INTEGER { disable(0), enable(1) }
		MAX-ACCESS		read-write
		STATUS			current
		DESCRIPTION
				"TYPE: - Checkbox
				 PAGE: - Logging 2
					Tx SFP  cmdID= 35174 "
		::= { iqotr40CmdEntry 35174 }


	iqotr40Logging2FiberTx5TxSFP35354 OBJECT-TYPE
		SYNTAX		RollCallString
		MAX-ACCESS		read-only
		STATUS			current
		DESCRIPTION
				"TYPE: - Display
				 PAGE: - Logging 2
					Tx SFP=  cmdID= 35354  format=   "
		::= { iqotr40CmdEntry 35354 }


	iqotr40Logging2FiberTx6LaserBiasState35105 OBJECT-TYPE
		SYNTAX		INTEGER { disable(0), enable(1) }
		MAX-ACCESS		read-write
		STATUS			current
		DESCRIPTION
				"TYPE: - Checkbox
				 PAGE: - Logging 2
					Laser Bias State  cmdID= 35105 "
		::= { iqotr40CmdEntry 35105 }


	iqotr40Logging2FiberTx6LaserBiasState35285 OBJECT-TYPE
		SYNTAX		RollCallString
		MAX-ACCESS		read-only
		STATUS			current
		DESCRIPTION
				"TYPE: - Display
				 PAGE: - Logging 2
					Laser Bias State=  cmdID= 35285  format=   "
		::= { iqotr40CmdEntry 35285 }


	iqotr40Logging2FiberTx6TxPowerState35115 OBJECT-TYPE
		SYNTAX		INTEGER { disable(0), enable(1) }
		MAX-ACCESS		read-write
		STATUS			current
		DESCRIPTION
				"TYPE: - Checkbox
				 PAGE: - Logging 2
					Tx Power State  cmdID= 35115 "
		::= { iqotr40CmdEntry 35115 }


	iqotr40Logging2FiberTx6TxPowerState35295 OBJECT-TYPE
		SYNTAX		RollCallString
		MAX-ACCESS		read-only
		STATUS			current
		DESCRIPTION
				"TYPE: - Display
				 PAGE: - Logging 2
					Tx Power State=  cmdID= 35295  format=   "
		::= { iqotr40CmdEntry 35295 }


	iqotr40Logging2FiberTx6LaserBias35095 OBJECT-TYPE
		SYNTAX		INTEGER { disable(0), enable(1) }
		MAX-ACCESS		read-write
		STATUS			current
		DESCRIPTION
				"TYPE: - Checkbox
				 PAGE: - Logging 2
					Laser Bias  cmdID= 35095 "
		::= { iqotr40CmdEntry 35095 }


	iqotr40Logging2FiberTx6LaserBias35305 OBJECT-TYPE
		SYNTAX		RollCallString
		MAX-ACCESS		read-only
		STATUS			current
		DESCRIPTION
				"TYPE: - Display
				 PAGE: - Logging 2
					Laser Bias=  cmdID= 35305  format=   "
		::= { iqotr40CmdEntry 35305 }


	iqotr40Logging2FiberTx6TxPower35135 OBJECT-TYPE
		SYNTAX		INTEGER { disable(0), enable(1) }
		MAX-ACCESS		read-write
		STATUS			current
		DESCRIPTION
				"TYPE: - Checkbox
				 PAGE: - Logging 2
					Tx Power  cmdID= 35135 "
		::= { iqotr40CmdEntry 35135 }


	iqotr40Logging2FiberTx6TxPower35315 OBJECT-TYPE
		SYNTAX		RollCallString
		MAX-ACCESS		read-only
		STATUS			current
		DESCRIPTION
				"TYPE: - Display
				 PAGE: - Logging 2
					Tx Power=  cmdID= 35315  format=   "
		::= { iqotr40CmdEntry 35315 }


	iqotr40Logging2FiberTx6Wavelength35125 OBJECT-TYPE
		SYNTAX		INTEGER { disable(0), enable(1) }
		MAX-ACCESS		read-write
		STATUS			current
		DESCRIPTION
				"TYPE: - Checkbox
				 PAGE: - Logging 2
					Wavelength  cmdID= 35125 "
		::= { iqotr40CmdEntry 35125 }


	iqotr40Logging2FiberTx6Wavelength35275 OBJECT-TYPE
		SYNTAX		RollCallString
		MAX-ACCESS		read-only
		STATUS			current
		DESCRIPTION
				"TYPE: - Display
				 PAGE: - Logging 2
					Wavelength=  cmdID= 35275  format=   "
		::= { iqotr40CmdEntry 35275 }


	iqotr40Logging2FiberTx6TxSFP35175 OBJECT-TYPE
		SYNTAX		INTEGER { disable(0), enable(1) }
		MAX-ACCESS		read-write
		STATUS			current
		DESCRIPTION
				"TYPE: - Checkbox
				 PAGE: - Logging 2
					Tx SFP  cmdID= 35175 "
		::= { iqotr40CmdEntry 35175 }


	iqotr40Logging2FiberTx6TxSFP35355 OBJECT-TYPE
		SYNTAX		RollCallString
		MAX-ACCESS		read-only
		STATUS			current
		DESCRIPTION
				"TYPE: - Display
				 PAGE: - Logging 2
					Tx SFP=  cmdID= 35355  format=   "
		::= { iqotr40CmdEntry 35355 }


	iqotr40Logging2FiberTx7LaserBiasState35106 OBJECT-TYPE
		SYNTAX		INTEGER { disable(0), enable(1) }
		MAX-ACCESS		read-write
		STATUS			current
		DESCRIPTION
				"TYPE: - Checkbox
				 PAGE: - Logging 2
					Laser Bias State  cmdID= 35106 "
		::= { iqotr40CmdEntry 35106 }


	iqotr40Logging2FiberTx7LaserBiasState35286 OBJECT-TYPE
		SYNTAX		RollCallString
		MAX-ACCESS		read-only
		STATUS			current
		DESCRIPTION
				"TYPE: - Display
				 PAGE: - Logging 2
					Laser Bias State=  cmdID= 35286  format=   "
		::= { iqotr40CmdEntry 35286 }


	iqotr40Logging2FiberTx7TxPowerState35116 OBJECT-TYPE
		SYNTAX		INTEGER { disable(0), enable(1) }
		MAX-ACCESS		read-write
		STATUS			current
		DESCRIPTION
				"TYPE: - Checkbox
				 PAGE: - Logging 2
					Tx Power State  cmdID= 35116 "
		::= { iqotr40CmdEntry 35116 }


	iqotr40Logging2FiberTx7TxPowerState35296 OBJECT-TYPE
		SYNTAX		RollCallString
		MAX-ACCESS		read-only
		STATUS			current
		DESCRIPTION
				"TYPE: - Display
				 PAGE: - Logging 2
					Tx Power State=  cmdID= 35296  format=   "
		::= { iqotr40CmdEntry 35296 }


	iqotr40Logging2FiberTx7LaserBias35096 OBJECT-TYPE
		SYNTAX		INTEGER { disable(0), enable(1) }
		MAX-ACCESS		read-write
		STATUS			current
		DESCRIPTION
				"TYPE: - Checkbox
				 PAGE: - Logging 2
					Laser Bias  cmdID= 35096 "
		::= { iqotr40CmdEntry 35096 }


	iqotr40Logging2FiberTx7LaserBias35306 OBJECT-TYPE
		SYNTAX		RollCallString
		MAX-ACCESS		read-only
		STATUS			current
		DESCRIPTION
				"TYPE: - Display
				 PAGE: - Logging 2
					Laser Bias=  cmdID= 35306  format=   "
		::= { iqotr40CmdEntry 35306 }


	iqotr40Logging2FiberTx7TxPower35136 OBJECT-TYPE
		SYNTAX		INTEGER { disable(0), enable(1) }
		MAX-ACCESS		read-write
		STATUS			current
		DESCRIPTION
				"TYPE: - Checkbox
				 PAGE: - Logging 2
					Tx Power  cmdID= 35136 "
		::= { iqotr40CmdEntry 35136 }


	iqotr40Logging2FiberTx7TxPower35316 OBJECT-TYPE
		SYNTAX		RollCallString
		MAX-ACCESS		read-only
		STATUS			current
		DESCRIPTION
				"TYPE: - Display
				 PAGE: - Logging 2
					Tx Power=  cmdID= 35316  format=   "
		::= { iqotr40CmdEntry 35316 }


	iqotr40Logging2FiberTx7Wavelength35126 OBJECT-TYPE
		SYNTAX		INTEGER { disable(0), enable(1) }
		MAX-ACCESS		read-write
		STATUS			current
		DESCRIPTION
				"TYPE: - Checkbox
				 PAGE: - Logging 2
					Wavelength  cmdID= 35126 "
		::= { iqotr40CmdEntry 35126 }


	iqotr40Logging2FiberTx7Wavelength35276 OBJECT-TYPE
		SYNTAX		RollCallString
		MAX-ACCESS		read-only
		STATUS			current
		DESCRIPTION
				"TYPE: - Display
				 PAGE: - Logging 2
					Wavelength=  cmdID= 35276  format=   "
		::= { iqotr40CmdEntry 35276 }


	iqotr40Logging2FiberTx7TxSFP35176 OBJECT-TYPE
		SYNTAX		INTEGER { disable(0), enable(1) }
		MAX-ACCESS		read-write
		STATUS			current
		DESCRIPTION
				"TYPE: - Checkbox
				 PAGE: - Logging 2
					Tx SFP  cmdID= 35176 "
		::= { iqotr40CmdEntry 35176 }


	iqotr40Logging2FiberTx7TxSFP35356 OBJECT-TYPE
		SYNTAX		RollCallString
		MAX-ACCESS		read-only
		STATUS			current
		DESCRIPTION
				"TYPE: - Display
				 PAGE: - Logging 2
					Tx SFP=  cmdID= 35356  format=   "
		::= { iqotr40CmdEntry 35356 }


	iqotr40Logging2FiberTx8LaserBiasState35107 OBJECT-TYPE
		SYNTAX		INTEGER { disable(0), enable(1) }
		MAX-ACCESS		read-write
		STATUS			current
		DESCRIPTION
				"TYPE: - Checkbox
				 PAGE: - Logging 2
					Laser Bias State  cmdID= 35107 "
		::= { iqotr40CmdEntry 35107 }


	iqotr40Logging2FiberTx8LaserBiasState35287 OBJECT-TYPE
		SYNTAX		RollCallString
		MAX-ACCESS		read-only
		STATUS			current
		DESCRIPTION
				"TYPE: - Display
				 PAGE: - Logging 2
					Laser Bias State=  cmdID= 35287  format=   "
		::= { iqotr40CmdEntry 35287 }


	iqotr40Logging2FiberTx8TxPowerState35117 OBJECT-TYPE
		SYNTAX		INTEGER { disable(0), enable(1) }
		MAX-ACCESS		read-write
		STATUS			current
		DESCRIPTION
				"TYPE: - Checkbox
				 PAGE: - Logging 2
					Tx Power State  cmdID= 35117 "
		::= { iqotr40CmdEntry 35117 }


	iqotr40Logging2FiberTx8TxPowerState35297 OBJECT-TYPE
		SYNTAX		RollCallString
		MAX-ACCESS		read-only
		STATUS			current
		DESCRIPTION
				"TYPE: - Display
				 PAGE: - Logging 2
					Tx Power State=  cmdID= 35297  format=   "
		::= { iqotr40CmdEntry 35297 }


	iqotr40Logging2FiberTx8LaserBias35097 OBJECT-TYPE
		SYNTAX		INTEGER { disable(0), enable(1) }
		MAX-ACCESS		read-write
		STATUS			current
		DESCRIPTION
				"TYPE: - Checkbox
				 PAGE: - Logging 2
					Laser Bias  cmdID= 35097 "
		::= { iqotr40CmdEntry 35097 }


	iqotr40Logging2FiberTx8LaserBias35307 OBJECT-TYPE
		SYNTAX		RollCallString
		MAX-ACCESS		read-only
		STATUS			current
		DESCRIPTION
				"TYPE: - Display
				 PAGE: - Logging 2
					Laser Bias=  cmdID= 35307  format=   "
		::= { iqotr40CmdEntry 35307 }


	iqotr40Logging2FiberTx8TxPower35137 OBJECT-TYPE
		SYNTAX		INTEGER { disable(0), enable(1) }
		MAX-ACCESS		read-write
		STATUS			current
		DESCRIPTION
				"TYPE: - Checkbox
				 PAGE: - Logging 2
					Tx Power  cmdID= 35137 "
		::= { iqotr40CmdEntry 35137 }


	iqotr40Logging2FiberTx8TxPower35317 OBJECT-TYPE
		SYNTAX		RollCallString
		MAX-ACCESS		read-only
		STATUS			current
		DESCRIPTION
				"TYPE: - Display
				 PAGE: - Logging 2
					Tx Power=  cmdID= 35317  format=   "
		::= { iqotr40CmdEntry 35317 }


	iqotr40Logging2FiberTx8Wavelength35127 OBJECT-TYPE
		SYNTAX		INTEGER { disable(0), enable(1) }
		MAX-ACCESS		read-write
		STATUS			current
		DESCRIPTION
				"TYPE: - Checkbox
				 PAGE: - Logging 2
					Wavelength  cmdID= 35127 "
		::= { iqotr40CmdEntry 35127 }


	iqotr40Logging2FiberTx8Wavelength35277 OBJECT-TYPE
		SYNTAX		RollCallString
		MAX-ACCESS		read-only
		STATUS			current
		DESCRIPTION
				"TYPE: - Display
				 PAGE: - Logging 2
					Wavelength=  cmdID= 35277  format=   "
		::= { iqotr40CmdEntry 35277 }


	iqotr40Logging2FiberTx8TxSFP35177 OBJECT-TYPE
		SYNTAX		INTEGER { disable(0), enable(1) }
		MAX-ACCESS		read-write
		STATUS			current
		DESCRIPTION
				"TYPE: - Checkbox
				 PAGE: - Logging 2
					Tx SFP  cmdID= 35177 "
		::= { iqotr40CmdEntry 35177 }


	iqotr40Logging2FiberTx8TxSFP35357 OBJECT-TYPE
		SYNTAX		RollCallString
		MAX-ACCESS		read-only
		STATUS			current
		DESCRIPTION
				"TYPE: - Display
				 PAGE: - Logging 2
					Tx SFP=  cmdID= 35357  format=   "
		::= { iqotr40CmdEntry 35357 }


	iqotr40Logging2FiberRx1RxPowerState35140 OBJECT-TYPE
		SYNTAX		INTEGER { disable(0), enable(1) }
		MAX-ACCESS		read-write
		STATUS			current
		DESCRIPTION
				"TYPE: - Checkbox
				 PAGE: - Logging 2
					Rx Power State  cmdID= 35140 "
		::= { iqotr40CmdEntry 35140 }


	iqotr40Logging2FiberRx1RxPowerState35320 OBJECT-TYPE
		SYNTAX		RollCallString
		MAX-ACCESS		read-only
		STATUS			current
		DESCRIPTION
				"TYPE: - Display
				 PAGE: - Logging 2
					Rx Power State=  cmdID= 35320  format=   "
		::= { iqotr40CmdEntry 35320 }


	iqotr40Logging2FiberRx1RxPower35150 OBJECT-TYPE
		SYNTAX		INTEGER { disable(0), enable(1) }
		MAX-ACCESS		read-write
		STATUS			current
		DESCRIPTION
				"TYPE: - Checkbox
				 PAGE: - Logging 2
					Rx Power  cmdID= 35150 "
		::= { iqotr40CmdEntry 35150 }


	iqotr40Logging2FiberRx1RxPower35330 OBJECT-TYPE
		SYNTAX		RollCallString
		MAX-ACCESS		read-only
		STATUS			current
		DESCRIPTION
				"TYPE: - Display
				 PAGE: - Logging 2
					Rx Power=  cmdID= 35330  format=   "
		::= { iqotr40CmdEntry 35330 }


	iqotr40Logging2FiberRx1RxSFP35160 OBJECT-TYPE
		SYNTAX		INTEGER { disable(0), enable(1) }
		MAX-ACCESS		read-write
		STATUS			current
		DESCRIPTION
				"TYPE: - Checkbox
				 PAGE: - Logging 2
					Rx SFP  cmdID= 35160 "
		::= { iqotr40CmdEntry 35160 }


	iqotr40Logging2FiberRx1RxSFP35340 OBJECT-TYPE
		SYNTAX		RollCallString
		MAX-ACCESS		read-only
		STATUS			current
		DESCRIPTION
				"TYPE: - Display
				 PAGE: - Logging 2
					Rx SFP=  cmdID= 35340  format=   "
		::= { iqotr40CmdEntry 35340 }


	iqotr40Logging2FiberRx2RxPowerState35141 OBJECT-TYPE
		SYNTAX		INTEGER { disable(0), enable(1) }
		MAX-ACCESS		read-write
		STATUS			current
		DESCRIPTION
				"TYPE: - Checkbox
				 PAGE: - Logging 2
					Rx Power State  cmdID= 35141 "
		::= { iqotr40CmdEntry 35141 }


	iqotr40Logging2FiberRx2RxPowerState35321 OBJECT-TYPE
		SYNTAX		RollCallString
		MAX-ACCESS		read-only
		STATUS			current
		DESCRIPTION
				"TYPE: - Display
				 PAGE: - Logging 2
					Rx Power State=  cmdID= 35321  format=   "
		::= { iqotr40CmdEntry 35321 }


	iqotr40Logging2FiberRx2RxPower35151 OBJECT-TYPE
		SYNTAX		INTEGER { disable(0), enable(1) }
		MAX-ACCESS		read-write
		STATUS			current
		DESCRIPTION
				"TYPE: - Checkbox
				 PAGE: - Logging 2
					Rx Power  cmdID= 35151 "
		::= { iqotr40CmdEntry 35151 }


	iqotr40Logging2FiberRx2RxPower35331 OBJECT-TYPE
		SYNTAX		RollCallString
		MAX-ACCESS		read-only
		STATUS			current
		DESCRIPTION
				"TYPE: - Display
				 PAGE: - Logging 2
					Rx Power=  cmdID= 35331  format=   "
		::= { iqotr40CmdEntry 35331 }


	iqotr40Logging2FiberRx2RxSFP35161 OBJECT-TYPE
		SYNTAX		INTEGER { disable(0), enable(1) }
		MAX-ACCESS		read-write
		STATUS			current
		DESCRIPTION
				"TYPE: - Checkbox
				 PAGE: - Logging 2
					Rx SFP  cmdID= 35161 "
		::= { iqotr40CmdEntry 35161 }


	iqotr40Logging2FiberRx2RxSFP35341 OBJECT-TYPE
		SYNTAX		RollCallString
		MAX-ACCESS		read-only
		STATUS			current
		DESCRIPTION
				"TYPE: - Display
				 PAGE: - Logging 2
					Rx SFP=  cmdID= 35341  format=   "
		::= { iqotr40CmdEntry 35341 }


	iqotr40Logging2FiberRx3RxPowerState35142 OBJECT-TYPE
		SYNTAX		INTEGER { disable(0), enable(1) }
		MAX-ACCESS		read-write
		STATUS			current
		DESCRIPTION
				"TYPE: - Checkbox
				 PAGE: - Logging 2
					Rx Power State  cmdID= 35142 "
		::= { iqotr40CmdEntry 35142 }


	iqotr40Logging2FiberRx3RxPowerState35322 OBJECT-TYPE
		SYNTAX		RollCallString
		MAX-ACCESS		read-only
		STATUS			current
		DESCRIPTION
				"TYPE: - Display
				 PAGE: - Logging 2
					Rx Power State=  cmdID= 35322  format=   "
		::= { iqotr40CmdEntry 35322 }


	iqotr40Logging2FiberRx3RxPower35152 OBJECT-TYPE
		SYNTAX		INTEGER { disable(0), enable(1) }
		MAX-ACCESS		read-write
		STATUS			current
		DESCRIPTION
				"TYPE: - Checkbox
				 PAGE: - Logging 2
					Rx Power  cmdID= 35152 "
		::= { iqotr40CmdEntry 35152 }


	iqotr40Logging2FiberRx3RxPower35332 OBJECT-TYPE
		SYNTAX		RollCallString
		MAX-ACCESS		read-only
		STATUS			current
		DESCRIPTION
				"TYPE: - Display
				 PAGE: - Logging 2
					Rx Power=  cmdID= 35332  format=   "
		::= { iqotr40CmdEntry 35332 }


	iqotr40Logging2FiberRx3RxSFP35162 OBJECT-TYPE
		SYNTAX		INTEGER { disable(0), enable(1) }
		MAX-ACCESS		read-write
		STATUS			current
		DESCRIPTION
				"TYPE: - Checkbox
				 PAGE: - Logging 2
					Rx SFP  cmdID= 35162 "
		::= { iqotr40CmdEntry 35162 }


	iqotr40Logging2FiberRx3RxSFP35342 OBJECT-TYPE
		SYNTAX		RollCallString
		MAX-ACCESS		read-only
		STATUS			current
		DESCRIPTION
				"TYPE: - Display
				 PAGE: - Logging 2
					Rx SFP=  cmdID= 35342  format=   "
		::= { iqotr40CmdEntry 35342 }


	iqotr40Logging2FiberRx4RxPowerState35143 OBJECT-TYPE
		SYNTAX		INTEGER { disable(0), enable(1) }
		MAX-ACCESS		read-write
		STATUS			current
		DESCRIPTION
				"TYPE: - Checkbox
				 PAGE: - Logging 2
					Rx Power State  cmdID= 35143 "
		::= { iqotr40CmdEntry 35143 }


	iqotr40Logging2FiberRx4RxPowerState35323 OBJECT-TYPE
		SYNTAX		RollCallString
		MAX-ACCESS		read-only
		STATUS			current
		DESCRIPTION
				"TYPE: - Display
				 PAGE: - Logging 2
					Rx Power State=  cmdID= 35323  format=   "
		::= { iqotr40CmdEntry 35323 }


	iqotr40Logging2FiberRx4RxPower35153 OBJECT-TYPE
		SYNTAX		INTEGER { disable(0), enable(1) }
		MAX-ACCESS		read-write
		STATUS			current
		DESCRIPTION
				"TYPE: - Checkbox
				 PAGE: - Logging 2
					Rx Power  cmdID= 35153 "
		::= { iqotr40CmdEntry 35153 }


	iqotr40Logging2FiberRx4RxPower35333 OBJECT-TYPE
		SYNTAX		RollCallString
		MAX-ACCESS		read-only
		STATUS			current
		DESCRIPTION
				"TYPE: - Display
				 PAGE: - Logging 2
					Rx Power=  cmdID= 35333  format=   "
		::= { iqotr40CmdEntry 35333 }


	iqotr40Logging2FiberRx4RxSFP35163 OBJECT-TYPE
		SYNTAX		INTEGER { disable(0), enable(1) }
		MAX-ACCESS		read-write
		STATUS			current
		DESCRIPTION
				"TYPE: - Checkbox
				 PAGE: - Logging 2
					Rx SFP  cmdID= 35163 "
		::= { iqotr40CmdEntry 35163 }


	iqotr40Logging2FiberRx4RxSFP35343 OBJECT-TYPE
		SYNTAX		RollCallString
		MAX-ACCESS		read-only
		STATUS			current
		DESCRIPTION
				"TYPE: - Display
				 PAGE: - Logging 2
					Rx SFP=  cmdID= 35343  format=   "
		::= { iqotr40CmdEntry 35343 }


	iqotr40Logging2FiberRx5RxPowerState35144 OBJECT-TYPE
		SYNTAX		INTEGER { disable(0), enable(1) }
		MAX-ACCESS		read-write
		STATUS			current
		DESCRIPTION
				"TYPE: - Checkbox
				 PAGE: - Logging 2
					Rx Power State  cmdID= 35144 "
		::= { iqotr40CmdEntry 35144 }


	iqotr40Logging2FiberRx5RxPowerState35324 OBJECT-TYPE
		SYNTAX		RollCallString
		MAX-ACCESS		read-only
		STATUS			current
		DESCRIPTION
				"TYPE: - Display
				 PAGE: - Logging 2
					Rx Power State=  cmdID= 35324  format=   "
		::= { iqotr40CmdEntry 35324 }


	iqotr40Logging2FiberRx5RxPower35154 OBJECT-TYPE
		SYNTAX		INTEGER { disable(0), enable(1) }
		MAX-ACCESS		read-write
		STATUS			current
		DESCRIPTION
				"TYPE: - Checkbox
				 PAGE: - Logging 2
					Rx Power  cmdID= 35154 "
		::= { iqotr40CmdEntry 35154 }


	iqotr40Logging2FiberRx5RxPower35334 OBJECT-TYPE
		SYNTAX		RollCallString
		MAX-ACCESS		read-only
		STATUS			current
		DESCRIPTION
				"TYPE: - Display
				 PAGE: - Logging 2
					Rx Power=  cmdID= 35334  format=   "
		::= { iqotr40CmdEntry 35334 }


	iqotr40Logging2FiberRx5RxSFP35164 OBJECT-TYPE
		SYNTAX		INTEGER { disable(0), enable(1) }
		MAX-ACCESS		read-write
		STATUS			current
		DESCRIPTION
				"TYPE: - Checkbox
				 PAGE: - Logging 2
					Rx SFP  cmdID= 35164 "
		::= { iqotr40CmdEntry 35164 }


	iqotr40Logging2FiberRx5RxSFP35344 OBJECT-TYPE
		SYNTAX		RollCallString
		MAX-ACCESS		read-only
		STATUS			current
		DESCRIPTION
				"TYPE: - Display
				 PAGE: - Logging 2
					Rx SFP=  cmdID= 35344  format=   "
		::= { iqotr40CmdEntry 35344 }


	iqotr40Logging2FiberRx6RxPowerState35145 OBJECT-TYPE
		SYNTAX		INTEGER { disable(0), enable(1) }
		MAX-ACCESS		read-write
		STATUS			current
		DESCRIPTION
				"TYPE: - Checkbox
				 PAGE: - Logging 2
					Rx Power State  cmdID= 35145 "
		::= { iqotr40CmdEntry 35145 }


	iqotr40Logging2FiberRx6RxPowerState35325 OBJECT-TYPE
		SYNTAX		RollCallString
		MAX-ACCESS		read-only
		STATUS			current
		DESCRIPTION
				"TYPE: - Display
				 PAGE: - Logging 2
					Rx Power State=  cmdID= 35325  format=   "
		::= { iqotr40CmdEntry 35325 }


	iqotr40Logging2FiberRx6RxPower35155 OBJECT-TYPE
		SYNTAX		INTEGER { disable(0), enable(1) }
		MAX-ACCESS		read-write
		STATUS			current
		DESCRIPTION
				"TYPE: - Checkbox
				 PAGE: - Logging 2
					Rx Power  cmdID= 35155 "
		::= { iqotr40CmdEntry 35155 }


	iqotr40Logging2FiberRx6RxPower35335 OBJECT-TYPE
		SYNTAX		RollCallString
		MAX-ACCESS		read-only
		STATUS			current
		DESCRIPTION
				"TYPE: - Display
				 PAGE: - Logging 2
					Rx Power=  cmdID= 35335  format=   "
		::= { iqotr40CmdEntry 35335 }


	iqotr40Logging2FiberRx6RxSFP35165 OBJECT-TYPE
		SYNTAX		INTEGER { disable(0), enable(1) }
		MAX-ACCESS		read-write
		STATUS			current
		DESCRIPTION
				"TYPE: - Checkbox
				 PAGE: - Logging 2
					Rx SFP  cmdID= 35165 "
		::= { iqotr40CmdEntry 35165 }


	iqotr40Logging2FiberRx6RxSFP35345 OBJECT-TYPE
		SYNTAX		RollCallString
		MAX-ACCESS		read-only
		STATUS			current
		DESCRIPTION
				"TYPE: - Display
				 PAGE: - Logging 2
					Rx SFP=  cmdID= 35345  format=   "
		::= { iqotr40CmdEntry 35345 }


	iqotr40Logging2FiberRx7RxPowerState35146 OBJECT-TYPE
		SYNTAX		INTEGER { disable(0), enable(1) }
		MAX-ACCESS		read-write
		STATUS			current
		DESCRIPTION
				"TYPE: - Checkbox
				 PAGE: - Logging 2
					Rx Power State  cmdID= 35146 "
		::= { iqotr40CmdEntry 35146 }


	iqotr40Logging2FiberRx7RxPowerState35326 OBJECT-TYPE
		SYNTAX		RollCallString
		MAX-ACCESS		read-only
		STATUS			current
		DESCRIPTION
				"TYPE: - Display
				 PAGE: - Logging 2
					Rx Power State=  cmdID= 35326  format=   "
		::= { iqotr40CmdEntry 35326 }


	iqotr40Logging2FiberRx7RxPower35156 OBJECT-TYPE
		SYNTAX		INTEGER { disable(0), enable(1) }
		MAX-ACCESS		read-write
		STATUS			current
		DESCRIPTION
				"TYPE: - Checkbox
				 PAGE: - Logging 2
					Rx Power  cmdID= 35156 "
		::= { iqotr40CmdEntry 35156 }


	iqotr40Logging2FiberRx7RxPower35336 OBJECT-TYPE
		SYNTAX		RollCallString
		MAX-ACCESS		read-only
		STATUS			current
		DESCRIPTION
				"TYPE: - Display
				 PAGE: - Logging 2
					Rx Power=  cmdID= 35336  format=   "
		::= { iqotr40CmdEntry 35336 }


	iqotr40Logging2FiberRx7RxSFP35166 OBJECT-TYPE
		SYNTAX		INTEGER { disable(0), enable(1) }
		MAX-ACCESS		read-write
		STATUS			current
		DESCRIPTION
				"TYPE: - Checkbox
				 PAGE: - Logging 2
					Rx SFP  cmdID= 35166 "
		::= { iqotr40CmdEntry 35166 }


	iqotr40Logging2FiberRx7RxSFP35346 OBJECT-TYPE
		SYNTAX		RollCallString
		MAX-ACCESS		read-only
		STATUS			current
		DESCRIPTION
				"TYPE: - Display
				 PAGE: - Logging 2
					Rx SFP=  cmdID= 35346  format=   "
		::= { iqotr40CmdEntry 35346 }


	iqotr40Logging2FiberRx8RxPowerState35147 OBJECT-TYPE
		SYNTAX		INTEGER { disable(0), enable(1) }
		MAX-ACCESS		read-write
		STATUS			current
		DESCRIPTION
				"TYPE: - Checkbox
				 PAGE: - Logging 2
					Rx Power State  cmdID= 35147 "
		::= { iqotr40CmdEntry 35147 }


	iqotr40Logging2FiberRx8RxPowerState35327 OBJECT-TYPE
		SYNTAX		RollCallString
		MAX-ACCESS		read-only
		STATUS			current
		DESCRIPTION
				"TYPE: - Display
				 PAGE: - Logging 2
					Rx Power State=  cmdID= 35327  format=   "
		::= { iqotr40CmdEntry 35327 }


	iqotr40Logging2FiberRx8RxPower35157 OBJECT-TYPE
		SYNTAX		INTEGER { disable(0), enable(1) }
		MAX-ACCESS		read-write
		STATUS			current
		DESCRIPTION
				"TYPE: - Checkbox
				 PAGE: - Logging 2
					Rx Power  cmdID= 35157 "
		::= { iqotr40CmdEntry 35157 }


	iqotr40Logging2FiberRx8RxPower35337 OBJECT-TYPE
		SYNTAX		RollCallString
		MAX-ACCESS		read-only
		STATUS			current
		DESCRIPTION
				"TYPE: - Display
				 PAGE: - Logging 2
					Rx Power=  cmdID= 35337  format=   "
		::= { iqotr40CmdEntry 35337 }


	iqotr40Logging2FiberRx8RxSFP35167 OBJECT-TYPE
		SYNTAX		INTEGER { disable(0), enable(1) }
		MAX-ACCESS		read-write
		STATUS			current
		DESCRIPTION
				"TYPE: - Checkbox
				 PAGE: - Logging 2
					Rx SFP  cmdID= 35167 "
		::= { iqotr40CmdEntry 35167 }


	iqotr40Logging2FiberRx8RxSFP35347 OBJECT-TYPE
		SYNTAX		RollCallString
		MAX-ACCESS		read-only
		STATUS			current
		DESCRIPTION
				"TYPE: - Display
				 PAGE: - Logging 2
					Rx SFP=  cmdID= 35347  format=   "
		::= { iqotr40CmdEntry 35347 }


	iqotr40MenuRollTrackDisableAll OBJECT-TYPE
		SYNTAX		INTEGER { disable(0), enable(1) }
		MAX-ACCESS		read-write
		STATUS			current
		DESCRIPTION
				"TYPE: - Checkbox
				 PAGE: - RollTrack
					Disable All  cmdID= 36104 "
		::= { iqotr40CmdEntry 36104 }


	iqotr40MenuRollTrackIndex OBJECT-TYPE
		SYNTAX		INTEGER
		MAX-ACCESS		read-write
		STATUS			current
		DESCRIPTION
				"TYPE: - BarGraph
				 PAGE: - RollTrack
					Index  cmdID= 36100  min= 1  max= 32   step= 1  format= %0.0f  div_scale= 1 
					Min = 1  Max = 32  Step = 1 "
		::= { iqotr40CmdEntry 36100 }


	iqotr40MenuRollTrackSource OBJECT-TYPE
		SYNTAX		INTEGER {
							val-Unused(-1),
							val-Input-1-OK(0),
							val-Input-1-None(1),
							val-Input-1-Bitrate-270(2),
							val-Input-1-Bitrate-1-5(3),
							val-Input-1-Bitrate-3G(4),
							val-Input-1-Bitrate-Un(5),
							val-Rx-1-Power-OK(6),
							val-Rx-1-Power-High(7),
							val-Rx-1-Power-Low(8),
							val-Tx-1-Bias-OK(9),
							val-Tx-1-Bias-High(10),
							val-Tx-1-Bias-Low(11),
							val-Input-2-OK(12),
							val-Input-2-None(13),
							val-Input-2-Bitrate-270(14),
							val-Input-2-Bitrate-1-5(15),
							val-Input-2-Bitrate-3G(16),
							val-Input-2-Bitrate-Un(17),
							val-Rx-2-Power-OK(18),
							val-Rx-2-Power-High(19),
							val-Rx-2-Power-Low(20),
							val-Tx-2-Bias-OK(21),
							val-Tx-2-Bias-High(22),
							val-Tx-2-Bias-Low(23),
							val-Input-3-OK(24),
							val-Input-3-None(25),
							val-Input-3-Bitrate-270(26),
							val-Input-3-Bitrate-1-5(27),
							val-Input-3-Bitrate-3G(28),
							val-Input-3-Bitrate-Un(29),
							val-Rx-3-Power-OK(30),
							val-Rx-3-Power-High(31),
							val-Rx-3-Power-Low(32),
							val-Tx-3-Bias-OK(33),
							val-Tx-3-Bias-High(34),
							val-Tx-3-Bias-Low(35),
							val-Input-4-OK(36),
							val-Input-4-None(37),
							val-Input-4-Bitrate-270(38),
							val-Input-4-Bitrate-1-5(39),
							val-Input-4-Bitrate-3G(40),
							val-Input-4-Bitrate-Un(41),
							val-Rx-4-Power-OK(42),
							val-Rx-4-Power-High(43),
							val-Rx-4-Power-Low(44),
							val-Tx-4-Bias-OK(45),
							val-Tx-4-Bias-High(46),
							val-Tx-4-Bias-Low(47),
							val-Inp-1-4-Config-1(96),
							val-Inp-1-4-Config-2(97),
							val-Input-5-OK(48),
							val-Input-5-None(49),
							val-Input-5-Bitrate-270(50),
							val-Input-5-Bitrate-1-5(51),
							val-Input-5-Bitrate-3G(52),
							val-Input-5-Bitrate-Un(53),
							val-Rx-5-Power-OK(54),
							val-Rx-5-Power-High(55),
							val-Rx-5-Power-Low(56),
							val-Tx-5-Bias-OK(57),
							val-Tx-5-Bias-High(58),
							val-Tx-5-Bias-Low(59),
							val-Input-6-OK(60),
							val-Input-6-None(61),
							val-Input-6-Bitrate-270(62),
							val-Input-6-Bitrate-1-5(63),
							val-Input-6-Bitrate-3G(64),
							val-Input-6-Bitrate-Un(65),
							val-Rx-6-Power-OK(66),
							val-Rx-6-Power-High(67),
							val-Rx-6-Power-Low(68),
							val-Tx-6-Bias-OK(69),
							val-Tx-6-Bias-High(70),
							val-Tx-6-Bias-Low(71),
							val-Input-7-OK(72),
							val-Input-7-None(73),
							val-Input-7-Bitrate-270(74),
							val-Input-7-Bitrate-1-5(75),
							val-Input-7-Bitrate-3G(76),
							val-Input-7-Bitrate-Un(77),
							val-Rx-7-Power-OK(78),
							val-Rx-7-Power-High(79),
							val-Rx-7-Power-Low(80),
							val-Tx-7-Bias-OK(81),
							val-Tx-7-Bias-High(82),
							val-Tx-7-Bias-Low(83),
							val-Input-8-OK(84),
							val-Input-8-None(85),
							val-Input-8-Bitrate-270(86),
							val-Input-8-Bitrate-1-5(87),
							val-Input-8-Bitrate-3G(88),
							val-Input-8-Bitrate-Un(89),
							val-Rx-8-Power-OK(90),
							val-Rx-8-Power-High(91),
							val-Rx-8-Power-Low(92),
							val-Tx-8-Bias-OK(93),
							val-Tx-8-Bias-High(94),
							val-Tx-8-Bias-Low(95),
							val-Inp-5-8-Config-1(98),
							val-Inp-5-8-Config-2(99)
							}
		MAX-ACCESS		read-write
		STATUS			current
		DESCRIPTION
				"TYPE: - RadiobuttonList
				 PAGE: - RollTrack
					Source  cmdID= 36101 
					Unused  value= -1  
					Input 1 OK  value= 0  
					Input 1 None  value= 1  
					Input 1 Bitrate 270  value= 2  
					Input 1 Bitrate 1.5  value= 3  
					Input 1 Bitrate 3G  value= 4  
					Input 1 Bitrate Un.  value= 5  
					Rx 1 Power OK  value= 6  
					Rx 1 Power High  value= 7  
					Rx 1 Power Low  value= 8  
					Tx 1 Bias OK  value= 9  
					Tx 1 Bias High  value= 10  
					Tx 1 Bias Low  value= 11  
					Input 2 OK  value= 12  
					Input 2 None  value= 13  
					Input 2 Bitrate 270  value= 14  
					Input 2 Bitrate 1.5  value= 15  
					Input 2 Bitrate 3G  value= 16  
					Input 2 Bitrate Un  value= 17  
					Rx 2 Power OK  value= 18  
					Rx 2 Power High  value= 19  
					Rx 2 Power Low  value= 20  
					Tx 2 Bias OK  value= 21  
					Tx 2 Bias High  value= 22  
					Tx 2 Bias Low  value= 23  
					Input 3 OK  value= 24  
					Input 3 None  value= 25  
					Input 3 Bitrate 270  value= 26  
					Input 3 Bitrate 1.5  value= 27  
					Input 3 Bitrate 3G  value= 28  
					Input 3 Bitrate Un  value= 29  
					Rx 3 Power OK  value= 30  
					Rx 3 Power High  value= 31  
					Rx 3 Power Low  value= 32  
					Tx 3 Bias OK  value= 33  
					Tx 3 Bias High  value= 34  
					Tx 3 Bias Low  value= 35  
					Input 4 OK  value= 36  
					Input 4 None  value= 37  
					Input 4 Bitrate 270  value= 38  
					Input 4 Bitrate 1.5  value= 39  
					Input 4 Bitrate 3G  value= 40  
					Input 4 Bitrate Un  value= 41  
					Rx 4 Power OK  value= 42  
					Rx 4 Power High  value= 43  
					Rx 4 Power Low  value= 44  
					Tx 4 Bias OK  value= 45  
					Tx 4 Bias High  value= 46  
					Tx 4 Bias Low  value= 47  
					Inp 1-4 Config 1  value= 96  
					Inp 1-4 Config 2  value= 97  
					Input 5 OK  value= 48  
					Input 5 None  value= 49  
					Input 5 Bitrate 270  value= 50  
					Input 5 Bitrate 1.5  value= 51  
					Input 5 Bitrate 3G  value= 52  
					Input 5 Bitrate Un  value= 53  
					Rx 5 Power OK  value= 54  
					Rx 5 Power High  value= 55  
					Rx 5 Power Low  value= 56  
					Tx 5 Bias OK  value= 57  
					Tx 5 Bias High  value= 58  
					Tx 5 Bias Low  value= 59  
					Input 6 OK  value= 60  
					Input 6 None  value= 61  
					Input 6 Bitrate 270  value= 62  
					Input 6 Bitrate 1.5  value= 63  
					Input 6 Bitrate 3G  value= 64  
					Input 6 Bitrate Un  value= 65  
					Rx 6 Power OK  value= 66  
					Rx 6 Power High  value= 67  
					Rx 6 Power Low  value= 68  
					Tx 6 Bias OK  value= 69  
					Tx 6 Bias High  value= 70  
					Tx 6 Bias Low  value= 71  
					Input 7 OK  value= 72  
					Input 7 None  value= 73  
					Input 7 Bitrate 270  value= 74  
					Input 7 Bitrate 1.5  value= 75  
					Input 7 Bitrate 3G  value= 76  
					Input 7 Bitrate Un  value= 77  
					Rx 7 Power OK  value= 78  
					Rx 7 Power High  value= 79  
					Rx 7 Power Low  value= 80  
					Tx 7 Bias OK  value= 81  
					Tx 7 Bias High  value= 82  
					Tx 7 Bias Low  value= 83  
					Input 8 OK  value= 84  
					Input 8 None  value= 85  
					Input 8 Bitrate 270  value= 86  
					Input 8 Bitrate 1.5  value= 87  
					Input 8 Bitrate 3G  value= 88  
					Input 8 Bitrate Un  value= 89  
					Rx 8 Power OK  value= 90  
					Rx 8 Power High  value= 91  
					Rx 8 Power Low  value= 92  
					Tx 8 Bias OK  value= 93  
					Tx 8 Bias High  value= 94  
					Tx 8 Bias Low  value= 95  
					Inp 5-8 Config 1  value= 98  
					Inp 5-8 Config 2  value= 99  "
		::= { iqotr40CmdEntry 36101 }


	iqotr40MenuRollTrackAddress OBJECT-TYPE
		SYNTAX		RollCallString
		MAX-ACCESS		read-write
		STATUS			current
		DESCRIPTION
				"TYPE: - Editstring
				 PAGE: - RollTrack
					Address  cmdID= 36102  "
		::= { iqotr40CmdEntry 36102 }


	iqotr40MenuRollTrackCommand OBJECT-TYPE
		SYNTAX		RollCallString
		MAX-ACCESS		read-write
		STATUS			current
		DESCRIPTION
				"TYPE: - Editstring
				 PAGE: - RollTrack
					Command  cmdID= 36103  "
		::= { iqotr40CmdEntry 36103 }


	iqotr40MenuRollTrackStatus OBJECT-TYPE
		SYNTAX		RollCallString
		MAX-ACCESS		read-only
		STATUS			current
		DESCRIPTION
				"TYPE: - Display
				 PAGE: - RollTrack
					Status  cmdID= 36105  format=   "
		::= { iqotr40CmdEntry 36105 }


	iqotr40MenuRollTrackSending OBJECT-TYPE
		SYNTAX		RollCallString
		MAX-ACCESS		read-only
		STATUS			current
		DESCRIPTION
				"TYPE: - Display
				 PAGE: - RollTrack
					Sending  cmdID= 36106  format=   "
		::= { iqotr40CmdEntry 36106 }


	iqotr40MenuSetupDisplay OBJECT-TYPE
		SYNTAX		INTEGER {
							val-Inputs-1-4(0),
							val-Inputs-5-8(1),
							val-Output-Status(2),
							val-Fiber-Status(3),
							val-Summary(4)
							}
		MAX-ACCESS		read-write
		STATUS			current
		DESCRIPTION
				"TYPE: - RadiobuttonList
				 PAGE: - Setup
					Display  cmdID= 32773 
					Inputs 1-4  value= 0  
					Inputs 5-8  value= 1  
					Output Status  value= 2  
					Fiber Status  value= 3  
					Summary  value= 4  "
		::= { iqotr40CmdEntry 32773 }


	iqotr40MenuSetupProduct OBJECT-TYPE
		SYNTAX		RollCallString
		MAX-ACCESS		read-only
		STATUS			current
		DESCRIPTION
				"TYPE: - Display
				 PAGE: - Setup
					Product  cmdID= 32771  format=   "
		::= { iqotr40CmdEntry 32771 }


	iqotr40MenuSetupLicensedProduct OBJECT-TYPE
		SYNTAX		RollCallString
		MAX-ACCESS		read-only
		STATUS			current
		DESCRIPTION
				"TYPE: - Display
				 PAGE: - Setup
					Licensed Product  cmdID= 32777  format=   "
		::= { iqotr40CmdEntry 32777 }


	iqotr40MenuSetupRelease OBJECT-TYPE
		SYNTAX		RollCallString
		MAX-ACCESS		read-only
		STATUS			current
		DESCRIPTION
				"TYPE: - Display
				 PAGE: - Setup
					Release  cmdID= 2  format=   "
		::= { iqotr40CmdEntry 2 }


	iqotr40MenuSetupBuild OBJECT-TYPE
		SYNTAX		RollCallString
		MAX-ACCESS		read-only
		STATUS			current
		DESCRIPTION
				"TYPE: - Display
				 PAGE: - Setup
					Build  cmdID= 5  format=   "
		::= { iqotr40CmdEntry 5 }


	iqotr40MenuSetupKOS OBJECT-TYPE
		SYNTAX		RollCallString
		MAX-ACCESS		read-only
		STATUS			current
		DESCRIPTION
				"TYPE: - Display
				 PAGE: - Setup
					KOS  cmdID= 32772  format=   "
		::= { iqotr40CmdEntry 32772 }


	iqotr40MenuSetupSerialNo OBJECT-TYPE
		SYNTAX		RollCallString
		MAX-ACCESS		read-only
		STATUS			current
		DESCRIPTION
				"TYPE: - Display
				 PAGE: - Setup
					Serial No.  cmdID= 1  format=   "
		::= { iqotr40CmdEntry 1 }


	iqotr40MenuSetupPCB OBJECT-TYPE
		SYNTAX		RollCallString
		MAX-ACCESS		read-only
		STATUS			current
		DESCRIPTION
				"TYPE: - Display
				 PAGE: - Setup
					PCB  cmdID= 32770  format=   "
		::= { iqotr40CmdEntry 32770 }


	iqotr40MenuSetupRearID OBJECT-TYPE
		SYNTAX		RollCallString
		MAX-ACCESS		read-only
		STATUS			current
		DESCRIPTION
				"TYPE: - Display
				 PAGE: - Setup
					RearID  cmdID= 1000  format=   "
		::= { iqotr40CmdEntry 1000 }


	iqotr40MenuSetupInput1Name OBJECT-TYPE
		SYNTAX		RollCallString
		MAX-ACCESS		read-write
		STATUS			current
		DESCRIPTION
				"TYPE: - Editstring
				 PAGE: - Setup
					Input 1 Name  cmdID= 4050  "
		::= { iqotr40CmdEntry 4050 }


	iqotr40MenuSetupInput2Name OBJECT-TYPE
		SYNTAX		RollCallString
		MAX-ACCESS		read-write
		STATUS			current
		DESCRIPTION
				"TYPE: - Editstring
				 PAGE: - Setup
					Input 2 Name  cmdID= 4051  "
		::= { iqotr40CmdEntry 4051 }


	iqotr40MenuSetupInput3Name OBJECT-TYPE
		SYNTAX		RollCallString
		MAX-ACCESS		read-write
		STATUS			current
		DESCRIPTION
				"TYPE: - Editstring
				 PAGE: - Setup
					Input 3 Name  cmdID= 4052  "
		::= { iqotr40CmdEntry 4052 }


	iqotr40MenuSetupInput4Name OBJECT-TYPE
		SYNTAX		RollCallString
		MAX-ACCESS		read-write
		STATUS			current
		DESCRIPTION
				"TYPE: - Editstring
				 PAGE: - Setup
					Input 4 Name  cmdID= 4053  "
		::= { iqotr40CmdEntry 4053 }


	iqotr40MenuSetupInput5Name OBJECT-TYPE
		SYNTAX		RollCallString
		MAX-ACCESS		read-write
		STATUS			current
		DESCRIPTION
				"TYPE: - Editstring
				 PAGE: - Setup
					Input 5 Name  cmdID= 4054  "
		::= { iqotr40CmdEntry 4054 }


	iqotr40MenuSetupInput6Name OBJECT-TYPE
		SYNTAX		RollCallString
		MAX-ACCESS		read-write
		STATUS			current
		DESCRIPTION
				"TYPE: - Editstring
				 PAGE: - Setup
					Input 6 Name  cmdID= 4055  "
		::= { iqotr40CmdEntry 4055 }


	iqotr40MenuSetupInput7Name OBJECT-TYPE
		SYNTAX		RollCallString
		MAX-ACCESS		read-write
		STATUS			current
		DESCRIPTION
				"TYPE: - Editstring
				 PAGE: - Setup
					Input 7 Name  cmdID= 4056  "
		::= { iqotr40CmdEntry 4056 }


	iqotr40MenuSetupInput8Name OBJECT-TYPE
		SYNTAX		RollCallString
		MAX-ACCESS		read-write
		STATUS			current
		DESCRIPTION
				"TYPE: - Editstring
				 PAGE: - Setup
					Input 8 Name  cmdID= 4057  "
		::= { iqotr40CmdEntry 4057 }


	iqotr40MenuSetupFactoryDefault OBJECT-TYPE
		SYNTAX		INTEGER { noAction(0),val-Factory-Default(1) }
		MAX-ACCESS		read-write
		STATUS			current
		DESCRIPTION
				"TYPE: - Button
				 PAGE: - Setup
					Factory Default  cmdID= 37002  value= 1  "
		::= { iqotr40CmdEntry 37002 }


	iqotr40MenuSetupDefaultsSettings OBJECT-TYPE
		SYNTAX		INTEGER { noAction(0),val-Defaults-Settings(1) }
		MAX-ACCESS		read-write
		STATUS			current
		DESCRIPTION
				"TYPE: - Button
				 PAGE: - Setup
					Defaults Settings  cmdID= 37001  value= 1  "
		::= { iqotr40CmdEntry 37001 }


	iqotr40MenuSetupRestart OBJECT-TYPE
		SYNTAX		INTEGER { noAction(0),val-Restart(1) }
		MAX-ACCESS		read-write
		STATUS			current
		DESCRIPTION
				"TYPE: - Button
				 PAGE: - Setup
					Restart  cmdID= 4  value= 1  "
		::= { iqotr40CmdEntry 4 }


	iqotr40MenuSetupSerialNumber OBJECT-TYPE
		SYNTAX		RollCallString
		MAX-ACCESS		read-write
		STATUS			current
		DESCRIPTION
				"TYPE: - Editstring
				 PAGE: - Setup
					Serial Number  cmdID= 3  "
		::= { iqotr40CmdEntry 3 }


	iqotr40SetupSFP1Ident OBJECT-TYPE
		SYNTAX		RollCallString
		MAX-ACCESS		read-only
		STATUS			current
		DESCRIPTION
				"TYPE: - Display
				 PAGE: - Setup
					Ident  cmdID= 4070  format=   "
		::= { iqotr40CmdEntry 4070 }


	iqotr40SetupSFP1Vendor OBJECT-TYPE
		SYNTAX		RollCallString
		MAX-ACCESS		read-only
		STATUS			current
		DESCRIPTION
				"TYPE: - Display
				 PAGE: - Setup
					Vendor  cmdID= 4060  format=   "
		::= { iqotr40CmdEntry 4060 }


	iqotr40SetupSFP1PartNo OBJECT-TYPE
		SYNTAX		RollCallString
		MAX-ACCESS		read-only
		STATUS			current
		DESCRIPTION
				"TYPE: - Display
				 PAGE: - Setup
					PartNo  cmdID= 4080  format=   "
		::= { iqotr40CmdEntry 4080 }


	iqotr40SetupSFP1Status OBJECT-TYPE
		SYNTAX		RollCallString
		MAX-ACCESS		read-only
		STATUS			current
		DESCRIPTION
				"TYPE: - Display
				 PAGE: - Setup
					Status  cmdID= 4090  format=   "
		::= { iqotr40CmdEntry 4090 }


	iqotr40SetupSFP2Ident OBJECT-TYPE
		SYNTAX		RollCallString
		MAX-ACCESS		read-only
		STATUS			current
		DESCRIPTION
				"TYPE: - Display
				 PAGE: - Setup
					Ident  cmdID= 4071  format=   "
		::= { iqotr40CmdEntry 4071 }


	iqotr40SetupSFP2Vendor OBJECT-TYPE
		SYNTAX		RollCallString
		MAX-ACCESS		read-only
		STATUS			current
		DESCRIPTION
				"TYPE: - Display
				 PAGE: - Setup
					Vendor  cmdID= 4061  format=   "
		::= { iqotr40CmdEntry 4061 }


	iqotr40SetupSFP2PartNo OBJECT-TYPE
		SYNTAX		RollCallString
		MAX-ACCESS		read-only
		STATUS			current
		DESCRIPTION
				"TYPE: - Display
				 PAGE: - Setup
					PartNo  cmdID= 4081  format=   "
		::= { iqotr40CmdEntry 4081 }


	iqotr40SetupSFP2Status OBJECT-TYPE
		SYNTAX		RollCallString
		MAX-ACCESS		read-only
		STATUS			current
		DESCRIPTION
				"TYPE: - Display
				 PAGE: - Setup
					Status  cmdID= 4091  format=   "
		::= { iqotr40CmdEntry 4091 }


	iqotr40SetupSFP3Ident OBJECT-TYPE
		SYNTAX		RollCallString
		MAX-ACCESS		read-only
		STATUS			current
		DESCRIPTION
				"TYPE: - Display
				 PAGE: - Setup
					Ident  cmdID= 4072  format=   "
		::= { iqotr40CmdEntry 4072 }


	iqotr40SetupSFP3Vendor OBJECT-TYPE
		SYNTAX		RollCallString
		MAX-ACCESS		read-only
		STATUS			current
		DESCRIPTION
				"TYPE: - Display
				 PAGE: - Setup
					Vendor  cmdID= 4062  format=   "
		::= { iqotr40CmdEntry 4062 }


	iqotr40SetupSFP3PartNo OBJECT-TYPE
		SYNTAX		RollCallString
		MAX-ACCESS		read-only
		STATUS			current
		DESCRIPTION
				"TYPE: - Display
				 PAGE: - Setup
					PartNo  cmdID= 4082  format=   "
		::= { iqotr40CmdEntry 4082 }


	iqotr40SetupSFP3Status OBJECT-TYPE
		SYNTAX		RollCallString
		MAX-ACCESS		read-only
		STATUS			current
		DESCRIPTION
				"TYPE: - Display
				 PAGE: - Setup
					Status  cmdID= 4092  format=   "
		::= { iqotr40CmdEntry 4092 }


	iqotr40SetupSFP4Ident OBJECT-TYPE
		SYNTAX		RollCallString
		MAX-ACCESS		read-only
		STATUS			current
		DESCRIPTION
				"TYPE: - Display
				 PAGE: - Setup
					Ident  cmdID= 4073  format=   "
		::= { iqotr40CmdEntry 4073 }


	iqotr40SetupSFP4Vendor OBJECT-TYPE
		SYNTAX		RollCallString
		MAX-ACCESS		read-only
		STATUS			current
		DESCRIPTION
				"TYPE: - Display
				 PAGE: - Setup
					Vendor  cmdID= 4063  format=   "
		::= { iqotr40CmdEntry 4063 }


	iqotr40SetupSFP4PartNo OBJECT-TYPE
		SYNTAX		RollCallString
		MAX-ACCESS		read-only
		STATUS			current
		DESCRIPTION
				"TYPE: - Display
				 PAGE: - Setup
					PartNo  cmdID= 4083  format=   "
		::= { iqotr40CmdEntry 4083 }


	iqotr40SetupSFP4Status OBJECT-TYPE
		SYNTAX		RollCallString
		MAX-ACCESS		read-only
		STATUS			current
		DESCRIPTION
				"TYPE: - Display
				 PAGE: - Setup
					Status  cmdID= 4093  format=   "
		::= { iqotr40CmdEntry 4093 }


	iqotr40SetupSFP5Ident OBJECT-TYPE
		SYNTAX		RollCallString
		MAX-ACCESS		read-only
		STATUS			current
		DESCRIPTION
				"TYPE: - Display
				 PAGE: - Setup
					Ident  cmdID= 4074  format=   "
		::= { iqotr40CmdEntry 4074 }


	iqotr40SetupSFP5Vendor OBJECT-TYPE
		SYNTAX		RollCallString
		MAX-ACCESS		read-only
		STATUS			current
		DESCRIPTION
				"TYPE: - Display
				 PAGE: - Setup
					Vendor  cmdID= 4064  format=   "
		::= { iqotr40CmdEntry 4064 }


	iqotr40SetupSFP5PartNo OBJECT-TYPE
		SYNTAX		RollCallString
		MAX-ACCESS		read-only
		STATUS			current
		DESCRIPTION
				"TYPE: - Display
				 PAGE: - Setup
					PartNo  cmdID= 4084  format=   "
		::= { iqotr40CmdEntry 4084 }


	iqotr40SetupSFP5Status OBJECT-TYPE
		SYNTAX		RollCallString
		MAX-ACCESS		read-only
		STATUS			current
		DESCRIPTION
				"TYPE: - Display
				 PAGE: - Setup
					Status  cmdID= 4094  format=   "
		::= { iqotr40CmdEntry 4094 }


	iqotr40SetupSFP6Ident OBJECT-TYPE
		SYNTAX		RollCallString
		MAX-ACCESS		read-only
		STATUS			current
		DESCRIPTION
				"TYPE: - Display
				 PAGE: - Setup
					Ident  cmdID= 4075  format=   "
		::= { iqotr40CmdEntry 4075 }


	iqotr40SetupSFP6Vendor OBJECT-TYPE
		SYNTAX		RollCallString
		MAX-ACCESS		read-only
		STATUS			current
		DESCRIPTION
				"TYPE: - Display
				 PAGE: - Setup
					Vendor  cmdID= 4065  format=   "
		::= { iqotr40CmdEntry 4065 }


	iqotr40SetupSFP6PartNo OBJECT-TYPE
		SYNTAX		RollCallString
		MAX-ACCESS		read-only
		STATUS			current
		DESCRIPTION
				"TYPE: - Display
				 PAGE: - Setup
					PartNo  cmdID= 4085  format=   "
		::= { iqotr40CmdEntry 4085 }


	iqotr40SetupSFP6Status OBJECT-TYPE
		SYNTAX		RollCallString
		MAX-ACCESS		read-only
		STATUS			current
		DESCRIPTION
				"TYPE: - Display
				 PAGE: - Setup
					Status  cmdID= 4095  format=   "
		::= { iqotr40CmdEntry 4095 }


	iqotr40SetupSFP7Ident OBJECT-TYPE
		SYNTAX		RollCallString
		MAX-ACCESS		read-only
		STATUS			current
		DESCRIPTION
				"TYPE: - Display
				 PAGE: - Setup
					Ident  cmdID= 4076  format=   "
		::= { iqotr40CmdEntry 4076 }


	iqotr40SetupSFP7Vendor OBJECT-TYPE
		SYNTAX		RollCallString
		MAX-ACCESS		read-only
		STATUS			current
		DESCRIPTION
				"TYPE: - Display
				 PAGE: - Setup
					Vendor  cmdID= 4066  format=   "
		::= { iqotr40CmdEntry 4066 }


	iqotr40SetupSFP7PartNo OBJECT-TYPE
		SYNTAX		RollCallString
		MAX-ACCESS		read-only
		STATUS			current
		DESCRIPTION
				"TYPE: - Display
				 PAGE: - Setup
					PartNo  cmdID= 4086  format=   "
		::= { iqotr40CmdEntry 4086 }


	iqotr40SetupSFP7Status OBJECT-TYPE
		SYNTAX		RollCallString
		MAX-ACCESS		read-only
		STATUS			current
		DESCRIPTION
				"TYPE: - Display
				 PAGE: - Setup
					Status  cmdID= 4096  format=   "
		::= { iqotr40CmdEntry 4096 }


	iqotr40SetupSFP8Ident OBJECT-TYPE
		SYNTAX		RollCallString
		MAX-ACCESS		read-only
		STATUS			current
		DESCRIPTION
				"TYPE: - Display
				 PAGE: - Setup
					Ident  cmdID= 4077  format=   "
		::= { iqotr40CmdEntry 4077 }


	iqotr40SetupSFP8Vendor OBJECT-TYPE
		SYNTAX		RollCallString
		MAX-ACCESS		read-only
		STATUS			current
		DESCRIPTION
				"TYPE: - Display
				 PAGE: - Setup
					Vendor  cmdID= 4067  format=   "
		::= { iqotr40CmdEntry 4067 }


	iqotr40SetupSFP8PartNo OBJECT-TYPE
		SYNTAX		RollCallString
		MAX-ACCESS		read-only
		STATUS			current
		DESCRIPTION
				"TYPE: - Display
				 PAGE: - Setup
					PartNo  cmdID= 4087  format=   "
		::= { iqotr40CmdEntry 4087 }


	iqotr40SetupSFP8Status OBJECT-TYPE
		SYNTAX		RollCallString
		MAX-ACCESS		read-only
		STATUS			current
		DESCRIPTION
				"TYPE: - Display
				 PAGE: - Setup
					Status  cmdID= 4097  format=   "
		::= { iqotr40CmdEntry 4097 }


	iqotr40MenuSetupHideFiberOPDlg OBJECT-TYPE
		SYNTAX		RollCallString
		MAX-ACCESS		read-only
		STATUS			current
		DESCRIPTION
				"TYPE: - Display
				 PAGE: - Setup
					Hide Fiber O/P Dlg  cmdID= 4301  format=   "
		::= { iqotr40CmdEntry 4301 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |       base           |Slt|Len| F  A  U  L  T |
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: S53014842
--				: 
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: UPTIME
--
-- MIB ref		: swCardEventLogSlotXX       .6.85.80.84.73.77.69
-- absolute OID	: 1.3.6.1.4.1.7995.2.6.1.1.XX.6.85.80.84.73.77.69
-- Vary			: YES
--
-- Value(s)		: 000:00:09:00
--				: 
-- Comments		: 
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
-- Vary			: YES
--
-- Value(s)		: 8
--				: 
-- Comments		: 
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				: 
-- Comments		: 
--
---------------------------------------------------------------------------------------------------
-- Header		: IOMOD1_ID
--
-- MIB ref		: swCardEventLogSlotXX       .9.73.79.77.79.68.49.95.73.68
-- absolute OID	: 1.3.6.1.4.1.7995.2.6.1.1.XX.9.73.79.77.79.68.49.95.73.68
-- Vary			: YES
--
-- Value(s)		: 2:RKIOM8V4F
--				: 
-- Comments		: 
--
---------------------------------------------------------------------------------------------------
-- Header		: IOMOD2_ID
--
-- MIB ref		: swCardEventLogSlotXX       .9.73.79.77.79.68.50.95.73.68
-- absolute OID	: 1.3.6.1.4.1.7995.2.6.1.1.XX.9.73.79.77.79.68.50.95.73.68
-- Vary			: YES
--
-- Value(s)		: 0:None fitted
--				: 
-- Comments		: 
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
-- Vary			: YES
--
-- Value(s)		: V115 Release
--				: 
-- Comments		: 
--
---------------------------------------------------------------------------------------------------
-- Header		: PROCMOD_ID
--
-- MIB ref		: swCardEventLogSlotXX       .10.80.82.79.67.77.79.68.95.73.68
-- absolute OID	: 1.3.6.1.4.1.7995.2.6.1.1.XX.10.80.82.79.67.77.79.68.95.73.68
-- Vary			: YES
--
-- Value(s)		: SAACS RKPRMLED1A
--				: 
-- Comments		: 
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
-- Vary			: YES
--
-- Value(s)		: 14
--				: 
-- Comments		: 
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
-- Vary			: YES
--
-- Value(s)		: 2
--				: 
-- Comments		: 
--
---------------------------------------------------------------------------------------------------
-- Header		: INPUT_1_SFP
--
-- MIB ref		: swCardEventLogSlotXX       .11.73.78.80.85.84.95.49.95.83.70.80
-- absolute OID	: 1.3.6.1.4.1.7995.2.6.1.1.XX.11.73.78.80.85.84.95.49.95.83.70.80
-- Vary			: YES
--
-- Value(s)		: 
--				: 
-- Comments		: 
--
---------------------------------------------------------------------------------------------------
-- Header		: INPUT_2_SFP
--
-- MIB ref		: swCardEventLogSlotXX       .11.73.78.80.85.84.95.50.95.83.70.80
-- absolute OID	: 1.3.6.1.4.1.7995.2.6.1.1.XX.11.73.78.80.85.84.95.50.95.83.70.80
-- Vary			: YES
--
-- Value(s)		: 
--				: 
-- Comments		: 
--
---------------------------------------------------------------------------------------------------
-- Header		: INPUT_3_SFP
--
-- MIB ref		: swCardEventLogSlotXX       .11.73.78.80.85.84.95.51.95.83.70.80
-- absolute OID	: 1.3.6.1.4.1.7995.2.6.1.1.XX.11.73.78.80.85.84.95.51.95.83.70.80
-- Vary			: YES
--
-- Value(s)		: 
--				: 
-- Comments		: 
--
---------------------------------------------------------------------------------------------------
-- Header		: INPUT_4_SFP
--
-- MIB ref		: swCardEventLogSlotXX       .11.73.78.80.85.84.95.52.95.83.70.80
-- absolute OID	: 1.3.6.1.4.1.7995.2.6.1.1.XX.11.73.78.80.85.84.95.52.95.83.70.80
-- Vary			: YES
--
-- Value(s)		: 
--				: 
-- Comments		: 
--
---------------------------------------------------------------------------------------------------
-- Header		: INPUT_5_SFP
--
-- MIB ref		: swCardEventLogSlotXX       .11.73.78.80.85.84.95.53.95.83.70.80
-- absolute OID	: 1.3.6.1.4.1.7995.2.6.1.1.XX.11.73.78.80.85.84.95.53.95.83.70.80
-- Vary			: YES
--
-- Value(s)		: OK
--				: 
-- Comments		: 
--
---------------------------------------------------------------------------------------------------
-- Header		: INPUT_6_SFP
--
-- MIB ref		: swCardEventLogSlotXX       .11.73.78.80.85.84.95.54.95.83.70.80
-- absolute OID	: 1.3.6.1.4.1.7995.2.6.1.1.XX.11.73.78.80.85.84.95.54.95.83.70.80
-- Vary			: YES
--
-- Value(s)		: OK
--				: 
-- Comments		: 
--
---------------------------------------------------------------------------------------------------
-- Header		: INPUT_7_SFP
--
-- MIB ref		: swCardEventLogSlotXX       .11.73.78.80.85.84.95.55.95.83.70.80
-- absolute OID	: 1.3.6.1.4.1.7995.2.6.1.1.XX.11.73.78.80.85.84.95.55.95.83.70.80
-- Vary			: YES
--
-- Value(s)		: OK
--				: 
-- Comments		: 
--
---------------------------------------------------------------------------------------------------
-- Header		: INPUT_8_SFP
--
-- MIB ref		: swCardEventLogSlotXX       .11.73.78.80.85.84.95.56.95.83.70.80
-- absolute OID	: 1.3.6.1.4.1.7995.2.6.1.1.XX.11.73.78.80.85.84.95.56.95.83.70.80
-- Vary			: YES
--
-- Value(s)		: OK
--				: 
-- Comments		: 
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
-- Vary			: YES
--
-- Value(s)		: OK
--				: 
-- Comments		: 
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
-- Vary			: YES
--
-- Value(s)		: 0004205198
--				: 
-- Comments		: 
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
-- Vary			: YES
--
-- Value(s)		: CHANNEL 1
--				: 
-- Comments		: 
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
-- Vary			: YES
--
-- Value(s)		: SD/HD/3G SDI
--				: 
-- Comments		: 
--
---------------------------------------------------------------------------------------------------
-- Header		: INPUT_2_NAME
--
-- MIB ref		: swCardEventLogSlotXX       .12.73.78.80.85.84.95.50.95.78.65.77.69
-- absolute OID	: 1.3.6.1.4.1.7995.2.6.1.1.XX.12.73.78.80.85.84.95.50.95.78.65.77.69
-- Vary			: YES
--
-- Value(s)		: CHANNEL 2
--				: 
-- Comments		: 
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
-- Vary			: YES
--
-- Value(s)		: SD/HD/3G SDI
--				: 
-- Comments		: 
--
---------------------------------------------------------------------------------------------------
-- Header		: INPUT_3_NAME
--
-- MIB ref		: swCardEventLogSlotXX       .12.73.78.80.85.84.95.51.95.78.65.77.69
-- absolute OID	: 1.3.6.1.4.1.7995.2.6.1.1.XX.12.73.78.80.85.84.95.51.95.78.65.77.69
-- Vary			: YES
--
-- Value(s)		: CHANNEL 3
--				: 
-- Comments		: 
--
---------------------------------------------------------------------------------------------------
-- Header		: INPUT_3_TYPE
--
-- MIB ref		: swCardEventLogSlotXX       .12.73.78.80.85.84.95.51.95.84.89.80.69
-- absolute OID	: 1.3.6.1.4.1.7995.2.6.1.1.XX.12.73.78.80.85.84.95.51.95.84.89.80.69
-- Vary			: YES
--
-- Value(s)		: SD/HD/3G SDI
--				: 
-- Comments		: 
--
---------------------------------------------------------------------------------------------------
-- Header		: INPUT_4_NAME
--
-- MIB ref		: swCardEventLogSlotXX       .12.73.78.80.85.84.95.52.95.78.65.77.69
-- absolute OID	: 1.3.6.1.4.1.7995.2.6.1.1.XX.12.73.78.80.85.84.95.52.95.78.65.77.69
-- Vary			: YES
--
-- Value(s)		: CHANNEL 4
--				: 
-- Comments		: 
--
---------------------------------------------------------------------------------------------------
-- Header		: INPUT_4_TYPE
--
-- MIB ref		: swCardEventLogSlotXX       .12.73.78.80.85.84.95.52.95.84.89.80.69
-- absolute OID	: 1.3.6.1.4.1.7995.2.6.1.1.XX.12.73.78.80.85.84.95.52.95.84.89.80.69
-- Vary			: YES
--
-- Value(s)		: SD/HD/3G SDI
--				: 
-- Comments		: 
--
---------------------------------------------------------------------------------------------------
-- Header		: INPUT_5_NAME
--
-- MIB ref		: swCardEventLogSlotXX       .12.73.78.80.85.84.95.53.95.78.65.77.69
-- absolute OID	: 1.3.6.1.4.1.7995.2.6.1.1.XX.12.73.78.80.85.84.95.53.95.78.65.77.69
-- Vary			: YES
--
-- Value(s)		: CHANNEL 5
--				: 
-- Comments		: 
--
---------------------------------------------------------------------------------------------------
-- Header		: INPUT_5_TYPE
--
-- MIB ref		: swCardEventLogSlotXX       .12.73.78.80.85.84.95.53.95.84.89.80.69
-- absolute OID	: 1.3.6.1.4.1.7995.2.6.1.1.XX.12.73.78.80.85.84.95.53.95.84.89.80.69
-- Vary			: YES
--
-- Value(s)		: SD/HD/3G SDI
--				: 
-- Comments		: 
--
---------------------------------------------------------------------------------------------------
-- Header		: INPUT_6_NAME
--
-- MIB ref		: swCardEventLogSlotXX       .12.73.78.80.85.84.95.54.95.78.65.77.69
-- absolute OID	: 1.3.6.1.4.1.7995.2.6.1.1.XX.12.73.78.80.85.84.95.54.95.78.65.77.69
-- Vary			: YES
--
-- Value(s)		: CHANNEL 6
--				: 
-- Comments		: 
--
---------------------------------------------------------------------------------------------------
-- Header		: INPUT_6_TYPE
--
-- MIB ref		: swCardEventLogSlotXX       .12.73.78.80.85.84.95.54.95.84.89.80.69
-- absolute OID	: 1.3.6.1.4.1.7995.2.6.1.1.XX.12.73.78.80.85.84.95.54.95.84.89.80.69
-- Vary			: YES
--
-- Value(s)		: SD/HD/3G SDI
--				: 
-- Comments		: 
--
---------------------------------------------------------------------------------------------------
-- Header		: INPUT_7_NAME
--
-- MIB ref		: swCardEventLogSlotXX       .12.73.78.80.85.84.95.55.95.78.65.77.69
-- absolute OID	: 1.3.6.1.4.1.7995.2.6.1.1.XX.12.73.78.80.85.84.95.55.95.78.65.77.69
-- Vary			: YES
--
-- Value(s)		: CHANNEL 7
--				: 
-- Comments		: 
--
---------------------------------------------------------------------------------------------------
-- Header		: INPUT_7_TYPE
--
-- MIB ref		: swCardEventLogSlotXX       .12.73.78.80.85.84.95.55.95.84.89.80.69
-- absolute OID	: 1.3.6.1.4.1.7995.2.6.1.1.XX.12.73.78.80.85.84.95.55.95.84.89.80.69
-- Vary			: YES
--
-- Value(s)		: SD/HD/3G SDI
--				: 
-- Comments		: 
--
---------------------------------------------------------------------------------------------------
-- Header		: INPUT_8_NAME
--
-- MIB ref		: swCardEventLogSlotXX       .12.73.78.80.85.84.95.56.95.78.65.77.69
-- absolute OID	: 1.3.6.1.4.1.7995.2.6.1.1.XX.12.73.78.80.85.84.95.56.95.78.65.77.69
-- Vary			: YES
--
-- Value(s)		: CHANNEL 8
--				: 
-- Comments		: 
--
---------------------------------------------------------------------------------------------------
-- Header		: INPUT_8_TYPE
--
-- MIB ref		: swCardEventLogSlotXX       .12.73.78.80.85.84.95.56.95.84.89.80.69
-- absolute OID	: 1.3.6.1.4.1.7995.2.6.1.1.XX.12.73.78.80.85.84.95.56.95.84.89.80.69
-- Vary			: YES
--
-- Value(s)		: SD/HD/3G SDI
--				: 
-- Comments		: 
--
---------------------------------------------------------------------------------------------------
-- Header		: OUTPUT_1_SFP
--
-- MIB ref		: swCardEventLogSlotXX       .12.79.85.84.80.85.84.95.49.95.83.70.80
-- absolute OID	: 1.3.6.1.4.1.7995.2.6.1.1.XX.12.79.85.84.80.85.84.95.49.95.83.70.80
-- Vary			: YES
--
-- Value(s)		: ERR:Rx
--				: 
-- Comments		: 
--
---------------------------------------------------------------------------------------------------
-- Header		: OUTPUT_2_SFP
--
-- MIB ref		: swCardEventLogSlotXX       .12.79.85.84.80.85.84.95.50.95.83.70.80
-- absolute OID	: 1.3.6.1.4.1.7995.2.6.1.1.XX.12.79.85.84.80.85.84.95.50.95.83.70.80
-- Vary			: YES
--
-- Value(s)		: ERR:Rx
--				: 
-- Comments		: 
--
---------------------------------------------------------------------------------------------------
-- Header		: OUTPUT_3_SFP
--
-- MIB ref		: swCardEventLogSlotXX       .12.79.85.84.80.85.84.95.51.95.83.70.80
-- absolute OID	: 1.3.6.1.4.1.7995.2.6.1.1.XX.12.79.85.84.80.85.84.95.51.95.83.70.80
-- Vary			: YES
--
-- Value(s)		: ERR:Rx
--				: 
-- Comments		: 
--
---------------------------------------------------------------------------------------------------
-- Header		: OUTPUT_4_SFP
--
-- MIB ref		: swCardEventLogSlotXX       .12.79.85.84.80.85.84.95.52.95.83.70.80
-- absolute OID	: 1.3.6.1.4.1.7995.2.6.1.1.XX.12.79.85.84.80.85.84.95.52.95.83.70.80
-- Vary			: YES
--
-- Value(s)		: ERR:Rx
--				: 
-- Comments		: 
--
---------------------------------------------------------------------------------------------------
-- Header		: OUTPUT_5_SFP
--
-- MIB ref		: swCardEventLogSlotXX       .12.79.85.84.80.85.84.95.53.95.83.70.80
-- absolute OID	: 1.3.6.1.4.1.7995.2.6.1.1.XX.12.79.85.84.80.85.84.95.53.95.83.70.80
-- Vary			: YES
--
-- Value(s)		: 
--				: 
-- Comments		: 
--
---------------------------------------------------------------------------------------------------
-- Header		: OUTPUT_6_SFP
--
-- MIB ref		: swCardEventLogSlotXX       .12.79.85.84.80.85.84.95.54.95.83.70.80
-- absolute OID	: 1.3.6.1.4.1.7995.2.6.1.1.XX.12.79.85.84.80.85.84.95.54.95.83.70.80
-- Vary			: YES
--
-- Value(s)		: 
--				: 
-- Comments		: 
--
---------------------------------------------------------------------------------------------------
-- Header		: OUTPUT_7_SFP
--
-- MIB ref		: swCardEventLogSlotXX       .12.79.85.84.80.85.84.95.55.95.83.70.80
-- absolute OID	: 1.3.6.1.4.1.7995.2.6.1.1.XX.12.79.85.84.80.85.84.95.55.95.83.70.80
-- Vary			: YES
--
-- Value(s)		: 
--				: 
-- Comments		: 
--
---------------------------------------------------------------------------------------------------
-- Header		: OUTPUT_8_SFP
--
-- MIB ref		: swCardEventLogSlotXX       .12.79.85.84.80.85.84.95.56.95.83.70.80
-- absolute OID	: 1.3.6.1.4.1.7995.2.6.1.1.XX.12.79.85.84.80.85.84.95.56.95.83.70.80
-- Vary			: YES
--
-- Value(s)		: 
--				: 
-- Comments		: 
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2015-02-24T16:42:51Z
--				: 
-- Comments		: 
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
-- Vary			: YES
--
-- Value(s)		: SERIAL IN 1
--				: 
-- Comments		: 
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
-- Vary			: YES
--
-- Value(s)		: FAIL:Lost
--				: 
-- Comments		: 
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
-- Vary			: YES
--
-- Value(s)		: SERIAL IN 2
--				: 
-- Comments		: 
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
-- Vary			: YES
--
-- Value(s)		: FAIL:Lost
--				: 
-- Comments		: 
--
---------------------------------------------------------------------------------------------------
-- Header		: INPUT_3_IDENT
--
-- MIB ref		: swCardEventLogSlotXX       .13.73.78.80.85.84.95.51.95.73.68.69.78.84
-- absolute OID	: 1.3.6.1.4.1.7995.2.6.1.1.XX.13.73.78.80.85.84.95.51.95.73.68.69.78.84
-- Vary			: YES
--
-- Value(s)		: SERIAL IN 3
--				: 
-- Comments		: 
--
---------------------------------------------------------------------------------------------------
-- Header		: INPUT_3_STATE
--
-- MIB ref		: swCardEventLogSlotXX       .13.73.78.80.85.84.95.51.95.83.84.65.84.69
-- absolute OID	: 1.3.6.1.4.1.7995.2.6.1.1.XX.13.73.78.80.85.84.95.51.95.83.84.65.84.69
-- Vary			: YES
--
-- Value(s)		: FAIL:Lost
--				: 
-- Comments		: 
--
---------------------------------------------------------------------------------------------------
-- Header		: INPUT_4_IDENT
--
-- MIB ref		: swCardEventLogSlotXX       .13.73.78.80.85.84.95.52.95.73.68.69.78.84
-- absolute OID	: 1.3.6.1.4.1.7995.2.6.1.1.XX.13.73.78.80.85.84.95.52.95.73.68.69.78.84
-- Vary			: YES
--
-- Value(s)		: SERIAL IN 4
--				: 
-- Comments		: 
--
---------------------------------------------------------------------------------------------------
-- Header		: INPUT_4_STATE
--
-- MIB ref		: swCardEventLogSlotXX       .13.73.78.80.85.84.95.52.95.83.84.65.84.69
-- absolute OID	: 1.3.6.1.4.1.7995.2.6.1.1.XX.13.73.78.80.85.84.95.52.95.83.84.65.84.69
-- Vary			: YES
--
-- Value(s)		: FAIL:Lost
--				: 
-- Comments		: 
--
---------------------------------------------------------------------------------------------------
-- Header		: INPUT_5_IDENT
--
-- MIB ref		: swCardEventLogSlotXX       .13.73.78.80.85.84.95.53.95.73.68.69.78.84
-- absolute OID	: 1.3.6.1.4.1.7995.2.6.1.1.XX.13.73.78.80.85.84.95.53.95.73.68.69.78.84
-- Vary			: YES
--
-- Value(s)		: FIBER IN 1
--				: 
-- Comments		: 
--
---------------------------------------------------------------------------------------------------
-- Header		: INPUT_5_STATE
--
-- MIB ref		: swCardEventLogSlotXX       .13.73.78.80.85.84.95.53.95.83.84.65.84.69
-- absolute OID	: 1.3.6.1.4.1.7995.2.6.1.1.XX.13.73.78.80.85.84.95.53.95.83.84.65.84.69
-- Vary			: YES
--
-- Value(s)		: FAIL:Lost
--				: 
-- Comments		: 
--
---------------------------------------------------------------------------------------------------
-- Header		: INPUT_6_IDENT
--
-- MIB ref		: swCardEventLogSlotXX       .13.73.78.80.85.84.95.54.95.73.68.69.78.84
-- absolute OID	: 1.3.6.1.4.1.7995.2.6.1.1.XX.13.73.78.80.85.84.95.54.95.73.68.69.78.84
-- Vary			: YES
--
-- Value(s)		: FIBER IN 2
--				: 
-- Comments		: 
--
---------------------------------------------------------------------------------------------------
-- Header		: INPUT_6_STATE
--
-- MIB ref		: swCardEventLogSlotXX       .13.73.78.80.85.84.95.54.95.83.84.65.84.69
-- absolute OID	: 1.3.6.1.4.1.7995.2.6.1.1.XX.13.73.78.80.85.84.95.54.95.83.84.65.84.69
-- Vary			: YES
--
-- Value(s)		: FAIL:Lost
--				: 
-- Comments		: 
--
---------------------------------------------------------------------------------------------------
-- Header		: INPUT_7_IDENT
--
-- MIB ref		: swCardEventLogSlotXX       .13.73.78.80.85.84.95.55.95.73.68.69.78.84
-- absolute OID	: 1.3.6.1.4.1.7995.2.6.1.1.XX.13.73.78.80.85.84.95.55.95.73.68.69.78.84
-- Vary			: YES
--
-- Value(s)		: FIBER IN 3
--				: 
-- Comments		: 
--
---------------------------------------------------------------------------------------------------
-- Header		: INPUT_7_STATE
--
-- MIB ref		: swCardEventLogSlotXX       .13.73.78.80.85.84.95.55.95.83.84.65.84.69
-- absolute OID	: 1.3.6.1.4.1.7995.2.6.1.1.XX.13.73.78.80.85.84.95.55.95.83.84.65.84.69
-- Vary			: YES
--
-- Value(s)		: FAIL:Lost
--				: 
-- Comments		: 
--
---------------------------------------------------------------------------------------------------
-- Header		: INPUT_8_IDENT
--
-- MIB ref		: swCardEventLogSlotXX       .13.73.78.80.85.84.95.56.95.73.68.69.78.84
-- absolute OID	: 1.3.6.1.4.1.7995.2.6.1.1.XX.13.73.78.80.85.84.95.56.95.73.68.69.78.84
-- Vary			: YES
--
-- Value(s)		: FIBER IN 4
--				: 
-- Comments		: 
--
---------------------------------------------------------------------------------------------------
-- Header		: INPUT_8_STATE
--
-- MIB ref		: swCardEventLogSlotXX       .13.73.78.80.85.84.95.56.95.83.84.65.84.69
-- absolute OID	: 1.3.6.1.4.1.7995.2.6.1.1.XX.13.73.78.80.85.84.95.56.95.83.84.65.84.69
-- Vary			: YES
--
-- Value(s)		: FAIL:Lost
--				: 
-- Comments		: 
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				: 
-- Comments		: 
--
---------------------------------------------------------------------------------------------------
-- Header		: INPUT_1_SDIRATE
--
-- MIB ref		: swCardEventLogSlotXX       .15.73.78.80.85.84.95.49.95.83.68.73.82.65.84.69
-- absolute OID	: 1.3.6.1.4.1.7995.2.6.1.1.XX.15.73.78.80.85.84.95.49.95.83.68.73.82.65.84.69
-- Vary			: YES
--
-- Value(s)		: UNKNOWN
--				: 
-- Comments		: 
--
---------------------------------------------------------------------------------------------------
-- Header		: INPUT_2_SDIRATE
--
-- MIB ref		: swCardEventLogSlotXX       .15.73.78.80.85.84.95.50.95.83.68.73.82.65.84.69
-- absolute OID	: 1.3.6.1.4.1.7995.2.6.1.1.XX.15.73.78.80.85.84.95.50.95.83.68.73.82.65.84.69
-- Vary			: YES
--
-- Value(s)		: UNKNOWN
--				: 
-- Comments		: 
--
---------------------------------------------------------------------------------------------------
-- Header		: INPUT_3_SDIRATE
--
-- MIB ref		: swCardEventLogSlotXX       .15.73.78.80.85.84.95.51.95.83.68.73.82.65.84.69
-- absolute OID	: 1.3.6.1.4.1.7995.2.6.1.1.XX.15.73.78.80.85.84.95.51.95.83.68.73.82.65.84.69
-- Vary			: YES
--
-- Value(s)		: UNKNOWN
--				: 
-- Comments		: 
--
---------------------------------------------------------------------------------------------------
-- Header		: INPUT_4_SDIRATE
--
-- MIB ref		: swCardEventLogSlotXX       .15.73.78.80.85.84.95.52.95.83.68.73.82.65.84.69
-- absolute OID	: 1.3.6.1.4.1.7995.2.6.1.1.XX.15.73.78.80.85.84.95.52.95.83.68.73.82.65.84.69
-- Vary			: YES
--
-- Value(s)		: UNKNOWN
--				: 
-- Comments		: 
--
---------------------------------------------------------------------------------------------------
-- Header		: INPUT_5_SDIRATE
--
-- MIB ref		: swCardEventLogSlotXX       .15.73.78.80.85.84.95.53.95.83.68.73.82.65.84.69
-- absolute OID	: 1.3.6.1.4.1.7995.2.6.1.1.XX.15.73.78.80.85.84.95.53.95.83.68.73.82.65.84.69
-- Vary			: YES
--
-- Value(s)		: UNKNOWN
--				: 
-- Comments		: 
--
---------------------------------------------------------------------------------------------------
-- Header		: INPUT_6_SDIRATE
--
-- MIB ref		: swCardEventLogSlotXX       .15.73.78.80.85.84.95.54.95.83.68.73.82.65.84.69
-- absolute OID	: 1.3.6.1.4.1.7995.2.6.1.1.XX.15.73.78.80.85.84.95.54.95.83.68.73.82.65.84.69
-- Vary			: YES
--
-- Value(s)		: UNKNOWN
--				: 
-- Comments		: 
--
---------------------------------------------------------------------------------------------------
-- Header		: INPUT_7_SDIRATE
--
-- MIB ref		: swCardEventLogSlotXX       .15.73.78.80.85.84.95.55.95.83.68.73.82.65.84.69
-- absolute OID	: 1.3.6.1.4.1.7995.2.6.1.1.XX.15.73.78.80.85.84.95.55.95.83.68.73.82.65.84.69
-- Vary			: YES
--
-- Value(s)		: UNKNOWN
--				: 
-- Comments		: 
--
---------------------------------------------------------------------------------------------------
-- Header		: INPUT_8_SDIRATE
--
-- MIB ref		: swCardEventLogSlotXX       .15.73.78.80.85.84.95.56.95.83.68.73.82.65.84.69
-- absolute OID	: 1.3.6.1.4.1.7995.2.6.1.1.XX.15.73.78.80.85.84.95.56.95.83.68.73.82.65.84.69
-- Vary			: YES
--
-- Value(s)		: UNKNOWN
--				: 
-- Comments		: 
--
---------------------------------------------------------------------------------------------------
-- Header		: CONFIG_1_4_INUSE
--
-- MIB ref		: swCardEventLogSlotXX       .16.67.79.78.70.73.71.95.49.95.52.95.73.78.85.83.69
-- absolute OID	: 1.3.6.1.4.1.7995.2.6.1.1.XX.16.67.79.78.70.73.71.95.49.95.52.95.73.78.85.83.69
-- Vary			: YES
--
-- Value(s)		: Config(1)
--				: 
-- Comments		: 
--
---------------------------------------------------------------------------------------------------
-- Header		: CONFIG_5_8_INUSE
--
-- MIB ref		: swCardEventLogSlotXX       .16.67.79.78.70.73.71.95.53.95.56.95.73.78.85.83.69
-- absolute OID	: 1.3.6.1.4.1.7995.2.6.1.1.XX.16.67.79.78.70.73.71.95.53.95.56.95.73.78.85.83.69
-- Vary			: YES
--
-- Value(s)		: Config(1)
--				: 
-- Comments		: 
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
-- Vary			: YES
--
-- Value(s)		: 00.001.01 01.000.02
--				: 
-- Comments		: 
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
-- Vary			: YES
--
-- Value(s)		: RKADM1Y
--				: 
-- Comments		: 
--
---------------------------------------------------------------------------------------------------
-- Header		: INPUT_1_RX_POWER
--
-- MIB ref		: swCardEventLogSlotXX       .16.73.78.80.85.84.95.49.95.82.88.95.80.79.87.69.82
-- absolute OID	: 1.3.6.1.4.1.7995.2.6.1.1.XX.16.73.78.80.85.84.95.49.95.82.88.95.80.79.87.69.82
-- Vary			: YES
--
-- Value(s)		: 
--				: 
-- Comments		: 
--
---------------------------------------------------------------------------------------------------
-- Header		: INPUT_2_RX_POWER
--
-- MIB ref		: swCardEventLogSlotXX       .16.73.78.80.85.84.95.50.95.82.88.95.80.79.87.69.82
-- absolute OID	: 1.3.6.1.4.1.7995.2.6.1.1.XX.16.73.78.80.85.84.95.50.95.82.88.95.80.79.87.69.82
-- Vary			: YES
--
-- Value(s)		: 
--				: 
-- Comments		: 
--
---------------------------------------------------------------------------------------------------
-- Header		: INPUT_3_RX_POWER
--
-- MIB ref		: swCardEventLogSlotXX       .16.73.78.80.85.84.95.51.95.82.88.95.80.79.87.69.82
-- absolute OID	: 1.3.6.1.4.1.7995.2.6.1.1.XX.16.73.78.80.85.84.95.51.95.82.88.95.80.79.87.69.82
-- Vary			: YES
--
-- Value(s)		: 
--				: 
-- Comments		: 
--
---------------------------------------------------------------------------------------------------
-- Header		: INPUT_4_RX_POWER
--
-- MIB ref		: swCardEventLogSlotXX       .16.73.78.80.85.84.95.52.95.82.88.95.80.79.87.69.82
-- absolute OID	: 1.3.6.1.4.1.7995.2.6.1.1.XX.16.73.78.80.85.84.95.52.95.82.88.95.80.79.87.69.82
-- Vary			: YES
--
-- Value(s)		: 
--				: 
-- Comments		: 
--
---------------------------------------------------------------------------------------------------
-- Header		: INPUT_5_RX_POWER
--
-- MIB ref		: swCardEventLogSlotXX       .16.73.78.80.85.84.95.53.95.82.88.95.80.79.87.69.82
-- absolute OID	: 1.3.6.1.4.1.7995.2.6.1.1.XX.16.73.78.80.85.84.95.53.95.82.88.95.80.79.87.69.82
-- Vary			: YES
--
-- Value(s)		: < -40.0dBm
--				: 
-- Comments		: 
--
---------------------------------------------------------------------------------------------------
-- Header		: INPUT_6_RX_POWER
--
-- MIB ref		: swCardEventLogSlotXX       .16.73.78.80.85.84.95.54.95.82.88.95.80.79.87.69.82
-- absolute OID	: 1.3.6.1.4.1.7995.2.6.1.1.XX.16.73.78.80.85.84.95.54.95.82.88.95.80.79.87.69.82
-- Vary			: YES
--
-- Value(s)		: < -40.0dBm
--				: 
-- Comments		: 
--
---------------------------------------------------------------------------------------------------
-- Header		: INPUT_7_RX_POWER
--
-- MIB ref		: swCardEventLogSlotXX       .16.73.78.80.85.84.95.55.95.82.88.95.80.79.87.69.82
-- absolute OID	: 1.3.6.1.4.1.7995.2.6.1.1.XX.16.73.78.80.85.84.95.55.95.82.88.95.80.79.87.69.82
-- Vary			: YES
--
-- Value(s)		: < -40.0dBm
--				: 
-- Comments		: 
--
---------------------------------------------------------------------------------------------------
-- Header		: INPUT_8_RX_POWER
--
-- MIB ref		: swCardEventLogSlotXX       .16.73.78.80.85.84.95.56.95.82.88.95.80.79.87.69.82
-- absolute OID	: 1.3.6.1.4.1.7995.2.6.1.1.XX.16.73.78.80.85.84.95.56.95.82.88.95.80.79.87.69.82
-- Vary			: YES
--
-- Value(s)		: < -40.0dBm
--				: 
-- Comments		: 
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
-- Vary			: YES
--
-- Value(s)		: FAIL:Bad File
--				: 
-- Comments		: 
--
---------------------------------------------------------------------------------------------------
-- Header		: OUTPUT_1_TX_POWER
--
-- MIB ref		: swCardEventLogSlotXX       .17.79.85.84.80.85.84.95.49.95.84.88.95.80.79.87.69.82
-- absolute OID	: 1.3.6.1.4.1.7995.2.6.1.1.XX.17.79.85.84.80.85.84.95.49.95.84.88.95.80.79.87.69.82
-- Vary			: YES
--
-- Value(s)		: 
--				: 
-- Comments		: 
--
---------------------------------------------------------------------------------------------------
-- Header		: OUTPUT_2_TX_POWER
--
-- MIB ref		: swCardEventLogSlotXX       .17.79.85.84.80.85.84.95.50.95.84.88.95.80.79.87.69.82
-- absolute OID	: 1.3.6.1.4.1.7995.2.6.1.1.XX.17.79.85.84.80.85.84.95.50.95.84.88.95.80.79.87.69.82
-- Vary			: YES
--
-- Value(s)		: 
--				: 
-- Comments		: 
--
---------------------------------------------------------------------------------------------------
-- Header		: OUTPUT_3_TX_POWER
--
-- MIB ref		: swCardEventLogSlotXX       .17.79.85.84.80.85.84.95.51.95.84.88.95.80.79.87.69.82
-- absolute OID	: 1.3.6.1.4.1.7995.2.6.1.1.XX.17.79.85.84.80.85.84.95.51.95.84.88.95.80.79.87.69.82
-- Vary			: YES
--
-- Value(s)		: 
--				: 
-- Comments		: 
--
---------------------------------------------------------------------------------------------------
-- Header		: OUTPUT_4_TX_POWER
--
-- MIB ref		: swCardEventLogSlotXX       .17.79.85.84.80.85.84.95.52.95.84.88.95.80.79.87.69.82
-- absolute OID	: 1.3.6.1.4.1.7995.2.6.1.1.XX.17.79.85.84.80.85.84.95.52.95.84.88.95.80.79.87.69.82
-- Vary			: YES
--
-- Value(s)		: 
--				: 
-- Comments		: 
--
---------------------------------------------------------------------------------------------------
-- Header		: OUTPUT_5_TX_POWER
--
-- MIB ref		: swCardEventLogSlotXX       .17.79.85.84.80.85.84.95.53.95.84.88.95.80.79.87.69.82
-- absolute OID	: 1.3.6.1.4.1.7995.2.6.1.1.XX.17.79.85.84.80.85.84.95.53.95.84.88.95.80.79.87.69.82
-- Vary			: YES
--
-- Value(s)		: 
--				: 
-- Comments		: 
--
---------------------------------------------------------------------------------------------------
-- Header		: OUTPUT_6_TX_POWER
--
-- MIB ref		: swCardEventLogSlotXX       .17.79.85.84.80.85.84.95.54.95.84.88.95.80.79.87.69.82
-- absolute OID	: 1.3.6.1.4.1.7995.2.6.1.1.XX.17.79.85.84.80.85.84.95.54.95.84.88.95.80.79.87.69.82
-- Vary			: YES
--
-- Value(s)		: 
--				: 
-- Comments		: 
--
---------------------------------------------------------------------------------------------------
-- Header		: OUTPUT_7_TX_POWER
--
-- MIB ref		: swCardEventLogSlotXX       .17.79.85.84.80.85.84.95.55.95.84.88.95.80.79.87.69.82
-- absolute OID	: 1.3.6.1.4.1.7995.2.6.1.1.XX.17.79.85.84.80.85.84.95.55.95.84.88.95.80.79.87.69.82
-- Vary			: YES
--
-- Value(s)		: 
--				: 
-- Comments		: 
--
---------------------------------------------------------------------------------------------------
-- Header		: OUTPUT_8_TX_POWER
--
-- MIB ref		: swCardEventLogSlotXX       .17.79.85.84.80.85.84.95.56.95.84.88.95.80.79.87.69.82
-- absolute OID	: 1.3.6.1.4.1.7995.2.6.1.1.XX.17.79.85.84.80.85.84.95.56.95.84.88.95.80.79.87.69.82
-- Vary			: YES
--
-- Value(s)		: 
--				: 
-- Comments		: 
--
---------------------------------------------------------------------------------------------------
-- Header		: OUTPUT_1_LASER_BIAS
--
-- MIB ref		: swCardEventLogSlotXX       .19.79.85.84.80.85.84.95.49.95.76.65.83.69.82.95.66.73.65.83
-- absolute OID	: 1.3.6.1.4.1.7995.2.6.1.1.XX.19.79.85.84.80.85.84.95.49.95.76.65.83.69.82.95.66.73.65.83
-- Vary			: YES
--
-- Value(s)		: 
--				: 
-- Comments		: 
--
---------------------------------------------------------------------------------------------------
-- Header		: OUTPUT_1_WAVELENGTH
--
-- MIB ref		: swCardEventLogSlotXX       .19.79.85.84.80.85.84.95.49.95.87.65.86.69.76.69.78.71.84.72
-- absolute OID	: 1.3.6.1.4.1.7995.2.6.1.1.XX.19.79.85.84.80.85.84.95.49.95.87.65.86.69.76.69.78.71.84.72
-- Vary			: YES
--
-- Value(s)		: 
--				: 
-- Comments		: 
--
---------------------------------------------------------------------------------------------------
-- Header		: OUTPUT_2_LASER_BIAS
--
-- MIB ref		: swCardEventLogSlotXX       .19.79.85.84.80.85.84.95.50.95.76.65.83.69.82.95.66.73.65.83
-- absolute OID	: 1.3.6.1.4.1.7995.2.6.1.1.XX.19.79.85.84.80.85.84.95.50.95.76.65.83.69.82.95.66.73.65.83
-- Vary			: YES
--
-- Value(s)		: 
--				: 
-- Comments		: 
--
---------------------------------------------------------------------------------------------------
-- Header		: OUTPUT_2_WAVELENGTH
--
-- MIB ref		: swCardEventLogSlotXX       .19.79.85.84.80.85.84.95.50.95.87.65.86.69.76.69.78.71.84.72
-- absolute OID	: 1.3.6.1.4.1.7995.2.6.1.1.XX.19.79.85.84.80.85.84.95.50.95.87.65.86.69.76.69.78.71.84.72
-- Vary			: YES
--
-- Value(s)		: 
--				: 
-- Comments		: 
--
---------------------------------------------------------------------------------------------------
-- Header		: OUTPUT_3_LASER_BIAS
--
-- MIB ref		: swCardEventLogSlotXX       .19.79.85.84.80.85.84.95.51.95.76.65.83.69.82.95.66.73.65.83
-- absolute OID	: 1.3.6.1.4.1.7995.2.6.1.1.XX.19.79.85.84.80.85.84.95.51.95.76.65.83.69.82.95.66.73.65.83
-- Vary			: YES
--
-- Value(s)		: 
--				: 
-- Comments		: 
--
---------------------------------------------------------------------------------------------------
-- Header		: OUTPUT_3_WAVELENGTH
--
-- MIB ref		: swCardEventLogSlotXX       .19.79.85.84.80.85.84.95.51.95.87.65.86.69.76.69.78.71.84.72
-- absolute OID	: 1.3.6.1.4.1.7995.2.6.1.1.XX.19.79.85.84.80.85.84.95.51.95.87.65.86.69.76.69.78.71.84.72
-- Vary			: YES
--
-- Value(s)		: 
--				: 
-- Comments		: 
--
---------------------------------------------------------------------------------------------------
-- Header		: OUTPUT_4_LASER_BIAS
--
-- MIB ref		: swCardEventLogSlotXX       .19.79.85.84.80.85.84.95.52.95.76.65.83.69.82.95.66.73.65.83
-- absolute OID	: 1.3.6.1.4.1.7995.2.6.1.1.XX.19.79.85.84.80.85.84.95.52.95.76.65.83.69.82.95.66.73.65.83
-- Vary			: YES
--
-- Value(s)		: 
--				: 
-- Comments		: 
--
---------------------------------------------------------------------------------------------------
-- Header		: OUTPUT_4_WAVELENGTH
--
-- MIB ref		: swCardEventLogSlotXX       .19.79.85.84.80.85.84.95.52.95.87.65.86.69.76.69.78.71.84.72
-- absolute OID	: 1.3.6.1.4.1.7995.2.6.1.1.XX.19.79.85.84.80.85.84.95.52.95.87.65.86.69.76.69.78.71.84.72
-- Vary			: YES
--
-- Value(s)		: 
--				: 
-- Comments		: 
--
---------------------------------------------------------------------------------------------------
-- Header		: OUTPUT_5_LASER_BIAS
--
-- MIB ref		: swCardEventLogSlotXX       .19.79.85.84.80.85.84.95.53.95.76.65.83.69.82.95.66.73.65.83
-- absolute OID	: 1.3.6.1.4.1.7995.2.6.1.1.XX.19.79.85.84.80.85.84.95.53.95.76.65.83.69.82.95.66.73.65.83
-- Vary			: YES
--
-- Value(s)		: 
--				: 
-- Comments		: 
--
---------------------------------------------------------------------------------------------------
-- Header		: OUTPUT_5_WAVELENGTH
--
-- MIB ref		: swCardEventLogSlotXX       .19.79.85.84.80.85.84.95.53.95.87.65.86.69.76.69.78.71.84.72
-- absolute OID	: 1.3.6.1.4.1.7995.2.6.1.1.XX.19.79.85.84.80.85.84.95.53.95.87.65.86.69.76.69.78.71.84.72
-- Vary			: YES
--
-- Value(s)		: 
--				: 
-- Comments		: 
--
---------------------------------------------------------------------------------------------------
-- Header		: OUTPUT_6_LASER_BIAS
--
-- MIB ref		: swCardEventLogSlotXX       .19.79.85.84.80.85.84.95.54.95.76.65.83.69.82.95.66.73.65.83
-- absolute OID	: 1.3.6.1.4.1.7995.2.6.1.1.XX.19.79.85.84.80.85.84.95.54.95.76.65.83.69.82.95.66.73.65.83
-- Vary			: YES
--
-- Value(s)		: 
--				: 
-- Comments		: 
--
---------------------------------------------------------------------------------------------------
-- Header		: OUTPUT_6_WAVELENGTH
--
-- MIB ref		: swCardEventLogSlotXX       .19.79.85.84.80.85.84.95.54.95.87.65.86.69.76.69.78.71.84.72
-- absolute OID	: 1.3.6.1.4.1.7995.2.6.1.1.XX.19.79.85.84.80.85.84.95.54.95.87.65.86.69.76.69.78.71.84.72
-- Vary			: YES
--
-- Value(s)		: 
--				: 
-- Comments		: 
--
---------------------------------------------------------------------------------------------------
-- Header		: OUTPUT_7_LASER_BIAS
--
-- MIB ref		: swCardEventLogSlotXX       .19.79.85.84.80.85.84.95.55.95.76.65.83.69.82.95.66.73.65.83
-- absolute OID	: 1.3.6.1.4.1.7995.2.6.1.1.XX.19.79.85.84.80.85.84.95.55.95.76.65.83.69.82.95.66.73.65.83
-- Vary			: YES
--
-- Value(s)		: 
--				: 
-- Comments		: 
--
---------------------------------------------------------------------------------------------------
-- Header		: OUTPUT_7_WAVELENGTH
--
-- MIB ref		: swCardEventLogSlotXX       .19.79.85.84.80.85.84.95.55.95.87.65.86.69.76.69.78.71.84.72
-- absolute OID	: 1.3.6.1.4.1.7995.2.6.1.1.XX.19.79.85.84.80.85.84.95.55.95.87.65.86.69.76.69.78.71.84.72
-- Vary			: YES
--
-- Value(s)		: 
--				: 
-- Comments		: 
--
---------------------------------------------------------------------------------------------------
-- Header		: OUTPUT_8_LASER_BIAS
--
-- MIB ref		: swCardEventLogSlotXX       .19.79.85.84.80.85.84.95.56.95.76.65.83.69.82.95.66.73.65.83
-- absolute OID	: 1.3.6.1.4.1.7995.2.6.1.1.XX.19.79.85.84.80.85.84.95.56.95.76.65.83.69.82.95.66.73.65.83
-- Vary			: YES
--
-- Value(s)		: 
--				: 
-- Comments		: 
--
---------------------------------------------------------------------------------------------------
-- Header		: OUTPUT_8_WAVELENGTH
--
-- MIB ref		: swCardEventLogSlotXX       .19.79.85.84.80.85.84.95.56.95.87.65.86.69.76.69.78.71.84.72
-- absolute OID	: 1.3.6.1.4.1.7995.2.6.1.1.XX.19.79.85.84.80.85.84.95.56.95.87.65.86.69.76.69.78.71.84.72
-- Vary			: YES
--
-- Value(s)		: 
--				: 
-- Comments		: 
--
---------------------------------------------------------------------------------------------------
-- Header		: INPUT_1_RX_POWER_STATE
--
-- MIB ref		: swCardEventLogSlotXX       .22.73.78.80.85.84.95.49.95.82.88.95.80.79.87.69.82.95.83.84.65.84.69
-- absolute OID	: 1.3.6.1.4.1.7995.2.6.1.1.XX.22.73.78.80.85.84.95.49.95.82.88.95.80.79.87.69.82.95.83.84.65.84.69
-- Vary			: YES
--
-- Value(s)		: 
--				: 
-- Comments		: 
--
---------------------------------------------------------------------------------------------------
-- Header		: INPUT_2_RX_POWER_STATE
--
-- MIB ref		: swCardEventLogSlotXX       .22.73.78.80.85.84.95.50.95.82.88.95.80.79.87.69.82.95.83.84.65.84.69
-- absolute OID	: 1.3.6.1.4.1.7995.2.6.1.1.XX.22.73.78.80.85.84.95.50.95.82.88.95.80.79.87.69.82.95.83.84.65.84.69
-- Vary			: YES
--
-- Value(s)		: 
--				: 
-- Comments		: 
--
---------------------------------------------------------------------------------------------------
-- Header		: INPUT_3_RX_POWER_STATE
--
-- MIB ref		: swCardEventLogSlotXX       .22.73.78.80.85.84.95.51.95.82.88.95.80.79.87.69.82.95.83.84.65.84.69
-- absolute OID	: 1.3.6.1.4.1.7995.2.6.1.1.XX.22.73.78.80.85.84.95.51.95.82.88.95.80.79.87.69.82.95.83.84.65.84.69
-- Vary			: YES
--
-- Value(s)		: 
--				: 
-- Comments		: 
--
---------------------------------------------------------------------------------------------------
-- Header		: INPUT_4_RX_POWER_STATE
--
-- MIB ref		: swCardEventLogSlotXX       .22.73.78.80.85.84.95.52.95.82.88.95.80.79.87.69.82.95.83.84.65.84.69
-- absolute OID	: 1.3.6.1.4.1.7995.2.6.1.1.XX.22.73.78.80.85.84.95.52.95.82.88.95.80.79.87.69.82.95.83.84.65.84.69
-- Vary			: YES
--
-- Value(s)		: 
--				: 
-- Comments		: 
--
---------------------------------------------------------------------------------------------------
-- Header		: INPUT_5_RX_POWER_STATE
--
-- MIB ref		: swCardEventLogSlotXX       .22.73.78.80.85.84.95.53.95.82.88.95.80.79.87.69.82.95.83.84.65.84.69
-- absolute OID	: 1.3.6.1.4.1.7995.2.6.1.1.XX.22.73.78.80.85.84.95.53.95.82.88.95.80.79.87.69.82.95.83.84.65.84.69
-- Vary			: YES
--
-- Value(s)		: FAIL:LOW
--				: 
-- Comments		: 
--
---------------------------------------------------------------------------------------------------
-- Header		: INPUT_6_RX_POWER_STATE
--
-- MIB ref		: swCardEventLogSlotXX       .22.73.78.80.85.84.95.54.95.82.88.95.80.79.87.69.82.95.83.84.65.84.69
-- absolute OID	: 1.3.6.1.4.1.7995.2.6.1.1.XX.22.73.78.80.85.84.95.54.95.82.88.95.80.79.87.69.82.95.83.84.65.84.69
-- Vary			: YES
--
-- Value(s)		: FAIL:LOW
--				: 
-- Comments		: 
--
---------------------------------------------------------------------------------------------------
-- Header		: INPUT_7_RX_POWER_STATE
--
-- MIB ref		: swCardEventLogSlotXX       .22.73.78.80.85.84.95.55.95.82.88.95.80.79.87.69.82.95.83.84.65.84.69
-- absolute OID	: 1.3.6.1.4.1.7995.2.6.1.1.XX.22.73.78.80.85.84.95.55.95.82.88.95.80.79.87.69.82.95.83.84.65.84.69
-- Vary			: YES
--
-- Value(s)		: FAIL:LOW
--				: 
-- Comments		: 
--
---------------------------------------------------------------------------------------------------
-- Header		: INPUT_8_RX_POWER_STATE
--
-- MIB ref		: swCardEventLogSlotXX       .22.73.78.80.85.84.95.56.95.82.88.95.80.79.87.69.82.95.83.84.65.84.69
-- absolute OID	: 1.3.6.1.4.1.7995.2.6.1.1.XX.22.73.78.80.85.84.95.56.95.82.88.95.80.79.87.69.82.95.83.84.65.84.69
-- Vary			: YES
--
-- Value(s)		: FAIL:LOW
--				: 
-- Comments		: 
--
---------------------------------------------------------------------------------------------------
-- Header		: OUTPUT_1_TX_POWER_STATE
--
-- MIB ref		: swCardEventLogSlotXX       .23.79.85.84.80.85.84.95.49.95.84.88.95.80.79.87.69.82.95.83.84.65.84.69
-- absolute OID	: 1.3.6.1.4.1.7995.2.6.1.1.XX.23.79.85.84.80.85.84.95.49.95.84.88.95.80.79.87.69.82.95.83.84.65.84.69
-- Vary			: YES
--
-- Value(s)		: 
--				: 
-- Comments		: 
--
---------------------------------------------------------------------------------------------------
-- Header		: OUTPUT_2_TX_POWER_STATE
--
-- MIB ref		: swCardEventLogSlotXX       .23.79.85.84.80.85.84.95.50.95.84.88.95.80.79.87.69.82.95.83.84.65.84.69
-- absolute OID	: 1.3.6.1.4.1.7995.2.6.1.1.XX.23.79.85.84.80.85.84.95.50.95.84.88.95.80.79.87.69.82.95.83.84.65.84.69
-- Vary			: YES
--
-- Value(s)		: 
--				: 
-- Comments		: 
--
---------------------------------------------------------------------------------------------------
-- Header		: OUTPUT_3_TX_POWER_STATE
--
-- MIB ref		: swCardEventLogSlotXX       .23.79.85.84.80.85.84.95.51.95.84.88.95.80.79.87.69.82.95.83.84.65.84.69
-- absolute OID	: 1.3.6.1.4.1.7995.2.6.1.1.XX.23.79.85.84.80.85.84.95.51.95.84.88.95.80.79.87.69.82.95.83.84.65.84.69
-- Vary			: YES
--
-- Value(s)		: 
--				: 
-- Comments		: 
--
---------------------------------------------------------------------------------------------------
-- Header		: OUTPUT_4_TX_POWER_STATE
--
-- MIB ref		: swCardEventLogSlotXX       .23.79.85.84.80.85.84.95.52.95.84.88.95.80.79.87.69.82.95.83.84.65.84.69
-- absolute OID	: 1.3.6.1.4.1.7995.2.6.1.1.XX.23.79.85.84.80.85.84.95.52.95.84.88.95.80.79.87.69.82.95.83.84.65.84.69
-- Vary			: YES
--
-- Value(s)		: 
--				: 
-- Comments		: 
--
---------------------------------------------------------------------------------------------------
-- Header		: OUTPUT_5_TX_POWER_STATE
--
-- MIB ref		: swCardEventLogSlotXX       .23.79.85.84.80.85.84.95.53.95.84.88.95.80.79.87.69.82.95.83.84.65.84.69
-- absolute OID	: 1.3.6.1.4.1.7995.2.6.1.1.XX.23.79.85.84.80.85.84.95.53.95.84.88.95.80.79.87.69.82.95.83.84.65.84.69
-- Vary			: YES
--
-- Value(s)		: 
--				: 
-- Comments		: 
--
---------------------------------------------------------------------------------------------------
-- Header		: OUTPUT_6_TX_POWER_STATE
--
-- MIB ref		: swCardEventLogSlotXX       .23.79.85.84.80.85.84.95.54.95.84.88.95.80.79.87.69.82.95.83.84.65.84.69
-- absolute OID	: 1.3.6.1.4.1.7995.2.6.1.1.XX.23.79.85.84.80.85.84.95.54.95.84.88.95.80.79.87.69.82.95.83.84.65.84.69
-- Vary			: YES
--
-- Value(s)		: 
--				: 
-- Comments		: 
--
---------------------------------------------------------------------------------------------------
-- Header		: OUTPUT_7_TX_POWER_STATE
--
-- MIB ref		: swCardEventLogSlotXX       .23.79.85.84.80.85.84.95.55.95.84.88.95.80.79.87.69.82.95.83.84.65.84.69
-- absolute OID	: 1.3.6.1.4.1.7995.2.6.1.1.XX.23.79.85.84.80.85.84.95.55.95.84.88.95.80.79.87.69.82.95.83.84.65.84.69
-- Vary			: YES
--
-- Value(s)		: 
--				: 
-- Comments		: 
--
---------------------------------------------------------------------------------------------------
-- Header		: OUTPUT_8_TX_POWER_STATE
--
-- MIB ref		: swCardEventLogSlotXX       .23.79.85.84.80.85.84.95.56.95.84.88.95.80.79.87.69.82.95.83.84.65.84.69
-- absolute OID	: 1.3.6.1.4.1.7995.2.6.1.1.XX.23.79.85.84.80.85.84.95.56.95.84.88.95.80.79.87.69.82.95.83.84.65.84.69
-- Vary			: YES
--
-- Value(s)		: 
--				: 
-- Comments		: 
--
---------------------------------------------------------------------------------------------------
-- Header		: OUTPUT_1_LASER_BIAS_STATE
--
-- MIB ref		: swCardEventLogSlotXX       .25.79.85.84.80.85.84.95.49.95.76.65.83.69.82.95.66.73.65.83.95.83.84.65.84.69
-- absolute OID	: 1.3.6.1.4.1.7995.2.6.1.1.XX.25.79.85.84.80.85.84.95.49.95.76.65.83.69.82.95.66.73.65.83.95.83.84.65.84.69
-- Vary			: YES
--
-- Value(s)		: 
--				: 
-- Comments		: 
--
---------------------------------------------------------------------------------------------------
-- Header		: OUTPUT_2_LASER_BIAS_STATE
--
-- MIB ref		: swCardEventLogSlotXX       .25.79.85.84.80.85.84.95.50.95.76.65.83.69.82.95.66.73.65.83.95.83.84.65.84.69
-- absolute OID	: 1.3.6.1.4.1.7995.2.6.1.1.XX.25.79.85.84.80.85.84.95.50.95.76.65.83.69.82.95.66.73.65.83.95.83.84.65.84.69
-- Vary			: YES
--
-- Value(s)		: 
--				: 
-- Comments		: 
--
---------------------------------------------------------------------------------------------------
-- Header		: OUTPUT_3_LASER_BIAS_STATE
--
-- MIB ref		: swCardEventLogSlotXX       .25.79.85.84.80.85.84.95.51.95.76.65.83.69.82.95.66.73.65.83.95.83.84.65.84.69
-- absolute OID	: 1.3.6.1.4.1.7995.2.6.1.1.XX.25.79.85.84.80.85.84.95.51.95.76.65.83.69.82.95.66.73.65.83.95.83.84.65.84.69
-- Vary			: YES
--
-- Value(s)		: 
--				: 
-- Comments		: 
--
---------------------------------------------------------------------------------------------------
-- Header		: OUTPUT_4_LASER_BIAS_STATE
--
-- MIB ref		: swCardEventLogSlotXX       .25.79.85.84.80.85.84.95.52.95.76.65.83.69.82.95.66.73.65.83.95.83.84.65.84.69
-- absolute OID	: 1.3.6.1.4.1.7995.2.6.1.1.XX.25.79.85.84.80.85.84.95.52.95.76.65.83.69.82.95.66.73.65.83.95.83.84.65.84.69
-- Vary			: YES
--
-- Value(s)		: 
--				: 
-- Comments		: 
--
---------------------------------------------------------------------------------------------------
-- Header		: OUTPUT_5_LASER_BIAS_STATE
--
-- MIB ref		: swCardEventLogSlotXX       .25.79.85.84.80.85.84.95.53.95.76.65.83.69.82.95.66.73.65.83.95.83.84.65.84.69
-- absolute OID	: 1.3.6.1.4.1.7995.2.6.1.1.XX.25.79.85.84.80.85.84.95.53.95.76.65.83.69.82.95.66.73.65.83.95.83.84.65.84.69
-- Vary			: YES
--
-- Value(s)		: 
--				: 
-- Comments		: 
--
---------------------------------------------------------------------------------------------------
-- Header		: OUTPUT_6_LASER_BIAS_STATE
--
-- MIB ref		: swCardEventLogSlotXX       .25.79.85.84.80.85.84.95.54.95.76.65.83.69.82.95.66.73.65.83.95.83.84.65.84.69
-- absolute OID	: 1.3.6.1.4.1.7995.2.6.1.1.XX.25.79.85.84.80.85.84.95.54.95.76.65.83.69.82.95.66.73.65.83.95.83.84.65.84.69
-- Vary			: YES
--
-- Value(s)		: 
--				: 
-- Comments		: 
--
---------------------------------------------------------------------------------------------------
-- Header		: OUTPUT_7_LASER_BIAS_STATE
--
-- MIB ref		: swCardEventLogSlotXX       .25.79.85.84.80.85.84.95.55.95.76.65.83.69.82.95.66.73.65.83.95.83.84.65.84.69
-- absolute OID	: 1.3.6.1.4.1.7995.2.6.1.1.XX.25.79.85.84.80.85.84.95.55.95.76.65.83.69.82.95.66.73.65.83.95.83.84.65.84.69
-- Vary			: YES
--
-- Value(s)		: 
--				: 
-- Comments		: 
--
---------------------------------------------------------------------------------------------------
-- Header		: OUTPUT_8_LASER_BIAS_STATE
--
-- MIB ref		: swCardEventLogSlotXX       .25.79.85.84.80.85.84.95.56.95.76.65.83.69.82.95.66.73.65.83.95.83.84.65.84.69
-- absolute OID	: 1.3.6.1.4.1.7995.2.6.1.1.XX.25.79.85.84.80.85.84.95.56.95.76.65.83.69.82.95.66.73.65.83.95.83.84.65.84.69
-- Vary			: YES
--
-- Value(s)		: 
--				: 
-- Comments		: 
--
---------------------------------------------------------------------------------------------------
