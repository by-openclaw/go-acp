-- ************************************************************************************
-- Snell&Wilcox Card:IQBADCD
--        Module Id#:107
--       Command Set:8
--          Filename:SNELL-IQBADCD-CMD-MIB.mib
--            Author:Jonathan Riches
--              Date:13/06/2005
--              Time:10:48
-- Last Modification:Logging comments added
--   Version Control:CVS $Id: SNELL-IQBADCD-CMD-MIB.mib 225 2006-12-21 16:32:22Z nikolaoskatsampekis $
-- Copyright (c) 2006 Snell & Wilcox Ltd
-- All rights reserved.
--
-- ************************************************************************************

SNELL-IQBADCD-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQBADCD,
    moduleIQBADCDMIB
        FROM SNELL-WILCOX-PRODUCT-REG;

 moduleIQBADCDCmdMi MODULE-IDENTITY
    LAST-UPDATED "0506131048Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQBADCDMIB 1 }




--********************************************************************************
--*
--*  Snell Wilcox Card:
--*  command set:
--*  list commands/menus:
--*
--******************************************************************************
	iqbadcdCmdTable OBJECT-TYPE
		SYNTAX			SEQUENCE OF IqbadcdCmdEntry
		MAX-ACCESS		not-accessible
		STATUS			current
		DESCRIPTION
				"Note the instance of this table is relected in the command set Version"
		::= { moduleIQBADCD 1 }

	iqbadcdCmdEntry OBJECT-TYPE
		SYNTAX		IqbadcdCmdEntry
		MAX-ACCESS		not-accessible
		STATUS			current
		DESCRIPTION
				"Entry in command table."
		INDEX	{ iqbadcdSlotIndex }
		::= { iqbadcdCmdTable 1 }

	IqbadcdCmdEntry ::=
		SEQUENCE {
			iqbadcdSlotIndex
				Unsigned32,
			iqbadcdChannel1Mute
				INTEGER,
			iqbadcdChannel1LRSwap
				INTEGER,
			iqbadcdChannel1PhaseInvert
				INTEGER,
			iqbadcdChannel1ChannelStatusDefaults
				INTEGER,
			iqbadcdChannel1ChannelStatusUse
				INTEGER,
			iqbadcdChannel1ChannelStatusAudio
				INTEGER,
			iqbadcdChannel1ChannelStatusEmphasis
				INTEGER,
			iqbadcdChannel1ChannelStatusLocking
				INTEGER,
			iqbadcdChannel1ChannelStatusSampFreq
				INTEGER,
			iqbadcdChannel1ChannelStatusMode
				INTEGER,
			iqbadcdChannel1ChannelStatusUser
				INTEGER,
			iqbadcdChannel1ChannelStatusAuxUse
				INTEGER,
			iqbadcdChannel1ChannelStatusSource
				INTEGER,
			iqbadcdChannel1ChannelStatusReference
				INTEGER,
			iqbadcdChannel1ChannelStatusOrigin
				RollCallString,
			iqbadcdChannel1ChannelStatusDestination
				RollCallString,
			iqbadcdChannel2Mute
				INTEGER,
			iqbadcdChannel2LRSwap
				INTEGER,
			iqbadcdChannel2PhaseInvert
				INTEGER,
			iqbadcdChannel2ChannelStatusDefaults
				INTEGER,
			iqbadcdChannel2ChannelStatusUse
				INTEGER,
			iqbadcdChannel2ChannelStatusAudio
				INTEGER,
			iqbadcdChannel2ChannelStatusEmphasis
				INTEGER,
			iqbadcdChannel2ChannelStatusLocking
				INTEGER,
			iqbadcdChannel2ChannelStatusSampFreq
				INTEGER,
			iqbadcdChannel2ChannelStatusMode
				INTEGER,
			iqbadcdChannel2ChannelStatusUser
				INTEGER,
			iqbadcdChannel2ChannelStatusAuxUse
				INTEGER,
			iqbadcdChannel2ChannelStatusSource
				INTEGER,
			iqbadcdChannel2ChannelStatusReference
				INTEGER,
			iqbadcdChannel2ChannelStatusOrigin
				RollCallString,
			iqbadcdChannel2ChannelStatusDestination
				RollCallString,
			iqbadcdDelayManualDelayTime
				INTEGER,
			iqbadcdDelayManualDelay
				INTEGER,
			iqbadcdDelayRollTrack
				INTEGER,
			iqbadcdDelayExternalDelay
				INTEGER,
			iqbadcdDelayJumpToDelay
				INTEGER,
			iqbadcdLocking
				INTEGER,
			iqbadcdSampleRate
				INTEGER,
			iqbadcdMemorySave
				INTEGER,
			iqbadcdMemoryRead
				INTEGER,
			iqbadcdMemoryPreset
				INTEGER,
			iqbadcdMemoryNameMemory1
				RollCallString,
			iqbadcdMemoryNameMemory2
				RollCallString,
			iqbadcdMemoryNameMemory3
				RollCallString,
			iqbadcdMemoryNameMemory4
				RollCallString,
			iqbadcdMemoryNamePresetAllNames
				INTEGER,
			iqbadcdSetupExtDelayPolarity
				INTEGER,
			iqbadcdSetupInputSource
				INTEGER,
			iqbadcdSetupGPI1
				INTEGER,
			iqbadcdSetupLoggingOverflow
				INTEGER,
			iqbadcdSetupLoggingRefLoss
				INTEGER,
			iqbadcdSetupPresetUnit
				INTEGER,
			iqbadcdSetupSoftwareVersion
				RollCallString,
			iqbadcdSetupSerialNo
				RollCallString,
			iqbadcdExtDelay1
				INTEGER,
			iqbadcdExtDelay2
				INTEGER,
			iqbadcdExtDelay3
				INTEGER,
			iqbadcdExtDelay4
				INTEGER,
			iqbadcdExtDelay5
				INTEGER
		}

	iqbadcdSlotIndex OBJECT-TYPE
		SYNTAX		Unsigned32
		MAX-ACCESS		not-accessible
		STATUS			current
		DESCRIPTION
				"The unique Index value for each slot.  Its value
					ranges between 1 and the value of slotNumber."
		::= { iqbadcdCmdEntry 0 }


	iqbadcdChannel1Mute OBJECT-TYPE
		SYNTAX		INTEGER { disable(0), enable(1) }
		MAX-ACCESS		read-write
		STATUS			current
		DESCRIPTION
				"TYPE: - Checkbox
					Mute  cmdID= 6 "
		::= { iqbadcdCmdEntry 6 }


	iqbadcdChannel1LRSwap OBJECT-TYPE
		SYNTAX		INTEGER { disable(0), enable(1) }
		MAX-ACCESS		read-write
		STATUS			current
		DESCRIPTION
				"TYPE: - Checkbox
					L/R_Swap  cmdID= 59 "
		::= { iqbadcdCmdEntry 59 }


	iqbadcdChannel1PhaseInvert OBJECT-TYPE
		SYNTAX		INTEGER { disable(0), enable(1) }
		MAX-ACCESS		read-write
		STATUS			current
		DESCRIPTION
				"TYPE: - Checkbox
					Phase_Invert  cmdID= 61 "
		::= { iqbadcdCmdEntry 61 }


	iqbadcdChannel1ChannelStatusDefaults OBJECT-TYPE
		SYNTAX		INTEGER { noAction(0),val_Defaults(1) }
		MAX-ACCESS		read-write
		STATUS			current
		DESCRIPTION
				"TYPE: - Button
					Defaults  cmdID= 21  value= 1  "
		::= { iqbadcdCmdEntry 21 }


	iqbadcdChannel1ChannelStatusUse OBJECT-TYPE
		SYNTAX		INTEGER {
							val_Consumer(0),
							val_Professional(1)
							}
		MAX-ACCESS		read-write
		STATUS			current
		DESCRIPTION
				"TYPE: - RadiobuttonList
					Use  cmdID= 22 
					Consumer  value= 0  
					Professional  value= 1  "
		::= { iqbadcdCmdEntry 22 }


	iqbadcdChannel1ChannelStatusAudio OBJECT-TYPE
		SYNTAX		INTEGER {
							val_Audio(0),
							val_Non_Audio(1)
							}
		MAX-ACCESS		read-write
		STATUS			current
		DESCRIPTION
				"TYPE: - RadiobuttonList
					Audio  cmdID= 23 
					Audio  value= 0  
					Non_Audio  value= 1  "
		::= { iqbadcdCmdEntry 23 }


	iqbadcdChannel1ChannelStatusEmphasis OBJECT-TYPE
		SYNTAX		INTEGER {
							val_None(1),
							val_50_15us(3),
							val_J17(7),
							val_Not_Indicated(0)
							}
		MAX-ACCESS		read-write
		STATUS			current
		DESCRIPTION
				"TYPE: - RadiobuttonList
					Emphasis  cmdID= 24 
					None  value= 1  
					50/15us  value= 3  
					J17  value= 7  
					Not_Indicated  value= 0  "
		::= { iqbadcdCmdEntry 24 }


	iqbadcdChannel1ChannelStatusLocking OBJECT-TYPE
		SYNTAX		INTEGER {
							val_Locked(0),
							val_Unlocked(1),
							val_Auto(2)
							}
		MAX-ACCESS		read-write
		STATUS			current
		DESCRIPTION
				"TYPE: - RadiobuttonList
					Locking  cmdID= 25 
					Locked  value= 0  
					Unlocked  value= 1  
					Auto  value= 2  "
		::= { iqbadcdCmdEntry 25 }


	iqbadcdChannel1ChannelStatusSampFreq OBJECT-TYPE
		SYNTAX		INTEGER {
							val_48kHz(2),
							val_44_1kHz(1),
							val_32kHz(3),
							val_Not_Indicated(0),
							val_Auto(4)
							}
		MAX-ACCESS		read-write
		STATUS			current
		DESCRIPTION
				"TYPE: - RadiobuttonList
					Samp_Freq  cmdID= 26 
					48kHz  value= 2  
					44.1kHz  value= 1  
					32kHz  value= 3  
					Not_Indicated  value= 0  
					Auto  value= 4  "
		::= { iqbadcdCmdEntry 26 }


	iqbadcdChannel1ChannelStatusMode OBJECT-TYPE
		SYNTAX		INTEGER {
							val_1_Channel(4),
							val_2_Channels(8),
							val_Prim_Sec(12),
							val_Stereo(2),
							val_Reserve1(10),
							val_Reserve2(6),
							val_Vector(15),
							val_Not_Indicated(0)
							}
		MAX-ACCESS		read-write
		STATUS			current
		DESCRIPTION
				"TYPE: - RadiobuttonList
					Mode  cmdID= 27 
					1_Channel  value= 4  
					2_Channels  value= 8  
					Prim/Sec  value= 12  
					Stereo  value= 2  
					Reserve1  value= 10  
					Reserve2  value= 6  
					Vector  value= 15  
					Not_Indicated  value= 0  "
		::= { iqbadcdCmdEntry 27 }


	iqbadcdChannel1ChannelStatusUser OBJECT-TYPE
		SYNTAX		INTEGER {
							val_192_Bits(8),
							val_Reserved(4),
							val_User(12),
							val_Not_Indicated(0)
							}
		MAX-ACCESS		read-write
		STATUS			current
		DESCRIPTION
				"TYPE: - RadiobuttonList
					User  cmdID= 28 
					192_Bits  value= 8  
					Reserved  value= 4  
					User  value= 12  
					Not_Indicated  value= 0  "
		::= { iqbadcdCmdEntry 28 }


	iqbadcdChannel1ChannelStatusAuxUse OBJECT-TYPE
		SYNTAX		INTEGER {
							val_Main_Audio(4),
							val_Talkback(2),
							val_User(6),
							val_Not_Indicated(0)
							}
		MAX-ACCESS		read-write
		STATUS			current
		DESCRIPTION
				"TYPE: - RadiobuttonList
					Aux_Use  cmdID= 29 
					Main_Audio  value= 4  
					Talkback  value= 2  
					User  value= 6  
					Not_Indicated  value= 0  "
		::= { iqbadcdCmdEntry 29 }


	iqbadcdChannel1ChannelStatusSource OBJECT-TYPE
		SYNTAX		INTEGER {
							val_24_Bits(5),
							val_23_Bits(4),
							val_22_Bits(2),
							val_21_Bits(6),
							val_20_Bits(1),
							val_Not_Indicated(0)
							}
		MAX-ACCESS		read-write
		STATUS			current
		DESCRIPTION
				"TYPE: - RadiobuttonList
					Source  cmdID= 30 
					24_Bits  value= 5  
					23_Bits  value= 4  
					22_Bits  value= 2  
					21_Bits  value= 6  
					20_Bits  value= 1  
					Not_Indicated  value= 0  "
		::= { iqbadcdCmdEntry 30 }


	iqbadcdChannel1ChannelStatusReference OBJECT-TYPE
		SYNTAX		INTEGER {
							val_Not_Ref(0),
							val_Grade_1(2),
							val_Grade_2(1)
							}
		MAX-ACCESS		read-write
		STATUS			current
		DESCRIPTION
				"TYPE: - RadiobuttonList
					Reference  cmdID= 31 
					Not_Ref  value= 0  
					Grade_1  value= 2  
					Grade_2  value= 1  "
		::= { iqbadcdCmdEntry 31 }


	iqbadcdChannel1ChannelStatusOrigin OBJECT-TYPE
		SYNTAX		RollCallString
		MAX-ACCESS		read-write
		STATUS			current
		DESCRIPTION
				"TYPE: - Editstring
					Origin  cmdID= 63  "
		::= { iqbadcdCmdEntry 63 }


	iqbadcdChannel1ChannelStatusDestination OBJECT-TYPE
		SYNTAX		RollCallString
		MAX-ACCESS		read-write
		STATUS			current
		DESCRIPTION
				"TYPE: - Editstring
					Destination  cmdID= 64  "
		::= { iqbadcdCmdEntry 64 }


	iqbadcdChannel2Mute OBJECT-TYPE
		SYNTAX		INTEGER { disable(0), enable(1) }
		MAX-ACCESS		read-write
		STATUS			current
		DESCRIPTION
				"TYPE: - Checkbox
					Mute  cmdID= 43 "
		::= { iqbadcdCmdEntry 43 }


	iqbadcdChannel2LRSwap OBJECT-TYPE
		SYNTAX		INTEGER { disable(0), enable(1) }
		MAX-ACCESS		read-write
		STATUS			current
		DESCRIPTION
				"TYPE: - Checkbox
					L/R_Swap  cmdID= 60 "
		::= { iqbadcdCmdEntry 60 }


	iqbadcdChannel2PhaseInvert OBJECT-TYPE
		SYNTAX		INTEGER { disable(0), enable(1) }
		MAX-ACCESS		read-write
		STATUS			current
		DESCRIPTION
				"TYPE: - Checkbox
					Phase_Invert  cmdID= 62 "
		::= { iqbadcdCmdEntry 62 }


	iqbadcdChannel2ChannelStatusDefaults OBJECT-TYPE
		SYNTAX		INTEGER { noAction(0),val_Defaults(1) }
		MAX-ACCESS		read-write
		STATUS			current
		DESCRIPTION
				"TYPE: - Button
					Defaults  cmdID= 32  value= 1  "
		::= { iqbadcdCmdEntry 32 }


	iqbadcdChannel2ChannelStatusUse OBJECT-TYPE
		SYNTAX		INTEGER {
							val_Consumer(0),
							val_Professional(1)
							}
		MAX-ACCESS		read-write
		STATUS			current
		DESCRIPTION
				"TYPE: - RadiobuttonList
					Use  cmdID= 33 
					Consumer  value= 0  
					Professional  value= 1  "
		::= { iqbadcdCmdEntry 33 }


	iqbadcdChannel2ChannelStatusAudio OBJECT-TYPE
		SYNTAX		INTEGER {
							val_Audio(0),
							val_Non_Audio(1)
							}
		MAX-ACCESS		read-write
		STATUS			current
		DESCRIPTION
				"TYPE: - RadiobuttonList
					Audio  cmdID= 34 
					Audio  value= 0  
					Non_Audio  value= 1  "
		::= { iqbadcdCmdEntry 34 }


	iqbadcdChannel2ChannelStatusEmphasis OBJECT-TYPE
		SYNTAX		INTEGER {
							val_None(1),
							val_50_15us(3),
							val_J17(7),
							val_Not_Indicated(0)
							}
		MAX-ACCESS		read-write
		STATUS			current
		DESCRIPTION
				"TYPE: - RadiobuttonList
					Emphasis  cmdID= 35 
					None  value= 1  
					50/15us  value= 3  
					J17  value= 7  
					Not_Indicated  value= 0  "
		::= { iqbadcdCmdEntry 35 }


	iqbadcdChannel2ChannelStatusLocking OBJECT-TYPE
		SYNTAX		INTEGER {
							val_Locked(0),
							val_Unlocked(1),
							val_Auto(2)
							}
		MAX-ACCESS		read-write
		STATUS			current
		DESCRIPTION
				"TYPE: - RadiobuttonList
					Locking  cmdID= 36 
					Locked  value= 0  
					Unlocked  value= 1  
					Auto  value= 2  "
		::= { iqbadcdCmdEntry 36 }


	iqbadcdChannel2ChannelStatusSampFreq OBJECT-TYPE
		SYNTAX		INTEGER {
							val_48kHz(2),
							val_44_1kHz(1),
							val_32kHz(3),
							val_Not_Indicated(0),
							val_Auto(4)
							}
		MAX-ACCESS		read-write
		STATUS			current
		DESCRIPTION
				"TYPE: - RadiobuttonList
					Samp_Freq  cmdID= 37 
					48kHz  value= 2  
					44.1kHz  value= 1  
					32kHz  value= 3  
					Not_Indicated  value= 0  
					Auto  value= 4  "
		::= { iqbadcdCmdEntry 37 }


	iqbadcdChannel2ChannelStatusMode OBJECT-TYPE
		SYNTAX		INTEGER {
							val_1_Channel(4),
							val_2_Channels(8),
							val_Prim_Sec(12),
							val_Stereo(2),
							val_Reserve1(10),
							val_Reserve2(6),
							val_Vector(15),
							val_Not_Indicated(0)
							}
		MAX-ACCESS		read-write
		STATUS			current
		DESCRIPTION
				"TYPE: - RadiobuttonList
					Mode  cmdID= 38 
					1_Channel  value= 4  
					2_Channels  value= 8  
					Prim/Sec  value= 12  
					Stereo  value= 2  
					Reserve1  value= 10  
					Reserve2  value= 6  
					Vector  value= 15  
					Not_Indicated  value= 0  "
		::= { iqbadcdCmdEntry 38 }


	iqbadcdChannel2ChannelStatusUser OBJECT-TYPE
		SYNTAX		INTEGER {
							val_192_Bits(8),
							val_Reserved(4),
							val_User(12),
							val_Not_Indicated(0)
							}
		MAX-ACCESS		read-write
		STATUS			current
		DESCRIPTION
				"TYPE: - RadiobuttonList
					User  cmdID= 39 
					192_Bits  value= 8  
					Reserved  value= 4  
					User  value= 12  
					Not_Indicated  value= 0  "
		::= { iqbadcdCmdEntry 39 }


	iqbadcdChannel2ChannelStatusAuxUse OBJECT-TYPE
		SYNTAX		INTEGER {
							val_Main_Audio(4),
							val_Talkback(2),
							val_User(6),
							val_Not_Indicated(0)
							}
		MAX-ACCESS		read-write
		STATUS			current
		DESCRIPTION
				"TYPE: - RadiobuttonList
					Aux_Use  cmdID= 40 
					Main_Audio  value= 4  
					Talkback  value= 2  
					User  value= 6  
					Not_Indicated  value= 0  "
		::= { iqbadcdCmdEntry 40 }


	iqbadcdChannel2ChannelStatusSource OBJECT-TYPE
		SYNTAX		INTEGER {
							val_24_Bits(5),
							val_23_Bits(4),
							val_22_Bits(2),
							val_21_Bits(6),
							val_20_Bits(1),
							val_Not_Indicated(0)
							}
		MAX-ACCESS		read-write
		STATUS			current
		DESCRIPTION
				"TYPE: - RadiobuttonList
					Source  cmdID= 41 
					24_Bits  value= 5  
					23_Bits  value= 4  
					22_Bits  value= 2  
					21_Bits  value= 6  
					20_Bits  value= 1  
					Not_Indicated  value= 0  "
		::= { iqbadcdCmdEntry 41 }


	iqbadcdChannel2ChannelStatusReference OBJECT-TYPE
		SYNTAX		INTEGER {
							val_Not_Ref(0),
							val_Grade_1(2),
							val_Grade_2(1)
							}
		MAX-ACCESS		read-write
		STATUS			current
		DESCRIPTION
				"TYPE: - RadiobuttonList
					Reference  cmdID= 42 
					Not_Ref  value= 0  
					Grade_1  value= 2  
					Grade_2  value= 1  "
		::= { iqbadcdCmdEntry 42 }


	iqbadcdChannel2ChannelStatusOrigin OBJECT-TYPE
		SYNTAX		RollCallString
		MAX-ACCESS		read-write
		STATUS			current
		DESCRIPTION
				"TYPE: - Editstring
					Origin  cmdID= 65  "
		::= { iqbadcdCmdEntry 65 }


	iqbadcdChannel2ChannelStatusDestination OBJECT-TYPE
		SYNTAX		RollCallString
		MAX-ACCESS		read-write
		STATUS			current
		DESCRIPTION
				"TYPE: - Editstring
					Destination  cmdID= 66  "
		::= { iqbadcdCmdEntry 66 }


	iqbadcdDelayManualDelayTime OBJECT-TYPE
		SYNTAX		INTEGER
		MAX-ACCESS		read-write
		STATUS			current
		DESCRIPTION
				"TYPE: - Number
					Manual_Delay_Time  cmdID= 7  min= -450  max= 450  step= 1  format= %.0f ms  div_scale= 1 
					Min = -450 ms  Max = 450 ms  Step = 1 ms "
		::= { iqbadcdCmdEntry 7 }


	iqbadcdDelayManualDelay OBJECT-TYPE
		SYNTAX		INTEGER { disable(0), enable(1) }
		MAX-ACCESS		read-write
		STATUS			current
		DESCRIPTION
				"TYPE: - Checkbox
					Manual_Delay  cmdID= 48 "
		::= { iqbadcdCmdEntry 48 }


	iqbadcdDelayRollTrack OBJECT-TYPE
		SYNTAX		INTEGER { disable(0), enable(1) }
		MAX-ACCESS		read-write
		STATUS			current
		DESCRIPTION
				"TYPE: - Checkbox
					RollTrack  cmdID= 8 "
		::= { iqbadcdCmdEntry 8 }


	iqbadcdDelayExternalDelay OBJECT-TYPE
		SYNTAX		INTEGER { disable(0), enable(1) }
		MAX-ACCESS		read-write
		STATUS			current
		DESCRIPTION
				"TYPE: - Checkbox
					External_Delay  cmdID= 47 "
		::= { iqbadcdCmdEntry 47 }


	iqbadcdDelayJumpToDelay OBJECT-TYPE
		SYNTAX		INTEGER { noAction(0),val_Jump_To_Delay(1) }
		MAX-ACCESS		read-write
		STATUS			current
		DESCRIPTION
				"TYPE: - Button
					Jump_To_Delay  cmdID= 69  value= 1  "
		::= { iqbadcdCmdEntry 69 }


	iqbadcdLocking OBJECT-TYPE
		SYNTAX		INTEGER {
							val_External_Video(0),
							val_AES_Reference(1),
							val_Internal(2)
							}
		MAX-ACCESS		read-write
		STATUS			current
		DESCRIPTION
				"TYPE: - RadiobuttonList
					Locking  cmdID= 4 
					External_Video  value= 0  
					AES_Reference  value= 1  
					Internal  value= 2  "
		::= { iqbadcdCmdEntry 4 }


	iqbadcdSampleRate OBJECT-TYPE
		SYNTAX		INTEGER {
							val_48KHz(48),
							val_44_1KHz(44),
							val_32KHz(32)
							}
		MAX-ACCESS		read-write
		STATUS			current
		DESCRIPTION
				"TYPE: - RadiobuttonList
					SampleRate  cmdID= 9 
					48KHz  value= 48  
					44.1KHz  value= 44  
					32KHz  value= 32  "
		::= { iqbadcdCmdEntry 9 }


	iqbadcdMemorySave OBJECT-TYPE
		SYNTAX		INTEGER {
							val_Memory_1(1),
							val_Memory_2(2),
							val_Memory_3(3),
							val_Memory_4(4)
							}
		MAX-ACCESS		read-write
		STATUS			current
		DESCRIPTION
				"TYPE: - RadiobuttonList
					Save  cmdID= 51 
					Memory_1  value= 1  
					Memory_2  value= 2  
					Memory_3  value= 3  
					Memory_4  value= 4  "
		::= { iqbadcdCmdEntry 51 }


	iqbadcdMemoryRead OBJECT-TYPE
		SYNTAX		INTEGER {
							val_Memory_1(1),
							val_Memory_2(2),
							val_Memory_3(3),
							val_Memory_4(4)
							}
		MAX-ACCESS		read-write
		STATUS			current
		DESCRIPTION
				"TYPE: - RadiobuttonList
					Read  cmdID= 52 
					Memory_1  value= 1  
					Memory_2  value= 2  
					Memory_3  value= 3  
					Memory_4  value= 4  "
		::= { iqbadcdCmdEntry 52 }


	iqbadcdMemoryPreset OBJECT-TYPE
		SYNTAX		INTEGER {
							val_Memory_1(1),
							val_Memory_2(2),
							val_Memory_3(3),
							val_Memory_4(4),
							val_Preset_All_Memories(5)
							}
		MAX-ACCESS		read-write
		STATUS			current
		DESCRIPTION
				"TYPE: - RadiobuttonList
					Preset  cmdID= 53 
					Memory_1  value= 1  
					Memory_2  value= 2  
					Memory_3  value= 3  
					Memory_4  value= 4  
					Preset_All_Memories  value= 5  "
		::= { iqbadcdCmdEntry 53 }


	iqbadcdMemoryNameMemory1 OBJECT-TYPE
		SYNTAX		RollCallString
		MAX-ACCESS		read-write
		STATUS			current
		DESCRIPTION
				"TYPE: - Editstring
					Memory_1  cmdID= 54  "
		::= { iqbadcdCmdEntry 54 }


	iqbadcdMemoryNameMemory2 OBJECT-TYPE
		SYNTAX		RollCallString
		MAX-ACCESS		read-write
		STATUS			current
		DESCRIPTION
				"TYPE: - Editstring
					Memory_2  cmdID= 55  "
		::= { iqbadcdCmdEntry 55 }


	iqbadcdMemoryNameMemory3 OBJECT-TYPE
		SYNTAX		RollCallString
		MAX-ACCESS		read-write
		STATUS			current
		DESCRIPTION
				"TYPE: - Editstring
					Memory_3  cmdID= 56  "
		::= { iqbadcdCmdEntry 56 }


	iqbadcdMemoryNameMemory4 OBJECT-TYPE
		SYNTAX		RollCallString
		MAX-ACCESS		read-write
		STATUS			current
		DESCRIPTION
				"TYPE: - Editstring
					Memory_4  cmdID= 57  "
		::= { iqbadcdCmdEntry 57 }


	iqbadcdMemoryNamePresetAllNames OBJECT-TYPE
		SYNTAX		INTEGER { noAction(0),val_Preset_All_Names(1) }
		MAX-ACCESS		read-write
		STATUS			current
		DESCRIPTION
				"TYPE: - Button
					Preset_All_Names  cmdID= 58  value= 1  "
		::= { iqbadcdCmdEntry 58 }


	iqbadcdSetupExtDelayPolarity OBJECT-TYPE
		SYNTAX		INTEGER {
							val_Positive(1),
							val_Negative(0)
							}
		MAX-ACCESS		read-write
		STATUS			current
		DESCRIPTION
				"TYPE: - RadiobuttonList
					Ext_Delay_Polarity  cmdID= 20 
					Positive  value= 1  
					Negative  value= 0  "
		::= { iqbadcdCmdEntry 20 }


	iqbadcdSetupInputSource OBJECT-TYPE
		SYNTAX		INTEGER {
							val_Balanced_Ref(1),
							val_Unbalanced_Ref(0)
							}
		MAX-ACCESS		read-write
		STATUS			current
		DESCRIPTION
				"TYPE: - RadiobuttonList
					Input_Source  cmdID= 46 
					Balanced_Ref  value= 1  
					Unbalanced_Ref  value= 0  "
		::= { iqbadcdCmdEntry 46 }


	iqbadcdSetupGPI1 OBJECT-TYPE
		SYNTAX		INTEGER {
							val_Mute_1(1),
							val_Mute_2(2),
							val_Not_used(0)
							}
		MAX-ACCESS		read-write
		STATUS			current
		DESCRIPTION
				"TYPE: - RadiobuttonList
					GPI1  cmdID= 50 
					Mute_1  value= 1  
					Mute_2  value= 2  
					Not_used  value= 0  "
		::= { iqbadcdCmdEntry 50 }


	iqbadcdSetupLoggingOverflow OBJECT-TYPE
		SYNTAX		INTEGER { disable(0), enable(1) }
		MAX-ACCESS		read-write
		STATUS			current
		DESCRIPTION
				"TYPE: - Checkbox
					Overflow  cmdID= 11 "
		::= { iqbadcdCmdEntry 11 }


	iqbadcdSetupLoggingRefLoss OBJECT-TYPE
		SYNTAX		INTEGER { disable(0), enable(1) }
		MAX-ACCESS		read-write
		STATUS			current
		DESCRIPTION
				"TYPE: - Checkbox
					Ref_Loss  cmdID= 12 "
		::= { iqbadcdCmdEntry 12 }


	iqbadcdSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqbadcdCmdEntry 3 }


	iqbadcdSetupSoftwareVersion OBJECT-TYPE
		SYNTAX		RollCallString
		MAX-ACCESS		read-only
		STATUS			current
		DESCRIPTION
				"TYPE: - Display
					Software_Version  cmdID= 2  format=   "
		::= { iqbadcdCmdEntry 2 }


	iqbadcdSetupSerialNo OBJECT-TYPE
		SYNTAX		RollCallString
		MAX-ACCESS		read-only
		STATUS			current
		DESCRIPTION
				"TYPE: - Display
					Serial_No  cmdID= 1  format=   "
		::= { iqbadcdCmdEntry 1 }


	iqbadcdExtDelay1 OBJECT-TYPE
		SYNTAX		INTEGER
		MAX-ACCESS		read-write
		STATUS			current
		DESCRIPTION
				"TYPE: - Number
					Ext_Delay_1  cmdID= 14  min= 0  max= 300  step= 1  format= %1.0f ms  div_scale= 1 
					Min = 0 ms  Max = 300 ms  Step = 1 ms "
		::= { iqbadcdCmdEntry 14 }


	iqbadcdExtDelay2 OBJECT-TYPE
		SYNTAX		INTEGER
		MAX-ACCESS		read-write
		STATUS			current
		DESCRIPTION
				"TYPE: - Number
					Ext_Delay_2  cmdID= 15  min= 0  max= 300  step= 1  format= %1.0f ms  div_scale= 1 
					Min = 0 ms  Max = 300 ms  Step = 1 ms "
		::= { iqbadcdCmdEntry 15 }


	iqbadcdExtDelay3 OBJECT-TYPE
		SYNTAX		INTEGER
		MAX-ACCESS		read-write
		STATUS			current
		DESCRIPTION
				"TYPE: - Number
					Ext_Delay_3  cmdID= 16  min= 0  max= 300  step= 1  format= %1.0f ms  div_scale= 1 
					Min = 0 ms  Max = 300 ms  Step = 1 ms "
		::= { iqbadcdCmdEntry 16 }


	iqbadcdExtDelay4 OBJECT-TYPE
		SYNTAX		INTEGER
		MAX-ACCESS		read-write
		STATUS			current
		DESCRIPTION
				"TYPE: - Number
					Ext_Delay_4  cmdID= 17  min= 0  max= 300  step= 1  format= %1.0f ms  div_scale= 1 
					Min = 0 ms  Max = 300 ms  Step = 1 ms "
		::= { iqbadcdCmdEntry 17 }


	iqbadcdExtDelay5 OBJECT-TYPE
		SYNTAX		INTEGER
		MAX-ACCESS		read-write
		STATUS			current
		DESCRIPTION
				"TYPE: - Number
					Ext_Delay_5  cmdID= 18  min= 0  max= 300  step= 1  format= %1.0f ms  div_scale= 1 
					Min = 0 ms  Max = 300 ms  Step = 1 ms "
		::= { iqbadcdCmdEntry 18 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: This log field shows the unique S&W serial number for this
--				: board instance.
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: This log field shows whether the IQ frame gateway card
--				: can communicate with this module.
--
---------------------------------------------------------------------------------------------------
-- Header		: EXTREF
--
-- MIB ref		: swCardEventLogSlotXX       .6.69.88.84.82.69.70
-- absolute OID	: 1.3.6.1.4.1.7995.2.6.1.1.XX.6.69.88.84.82.69.70
-- Vary			: YES
--
-- Value(s)		: N/A
--				: OK_VIDEO
--				: LOST_VIDEO
--				: OK_AES
--				: LOST_AES
-- Comments		: This log field shows the status of the reference.
--				: OK_VIDEO indicates that the card is locked to the selected Video input.
--				: LOST_VIDEO indicates that the reference video signal has been Lost. 	
--				: OK_AES indicates that the card is locked to the selected AES input.
--				: LOST_AES indicates that the reference AES signal has been Lost. 			
--				: N/A indicates no valid reference signal available.

--
---------------------------------------------------------------------------------------------------
-- Header		: CH-LEFT1
--
-- MIB ref		: swCardEventLogSlotXX       .8.67.72.45.76.69.70.84.49
-- absolute OID	: 1.3.6.1.4.1.7995.2.6.1.1.XX.8.67.72.45.76.69.70.84.49
-- Vary			: YES
--
-- Value(s)		: OK
--				: OVERFLOW
-- Comments		: This log field shows the detected audio state of the Left Channel 1 input.
--				: LOST indicates no input detected at this Channel. 
--				: OVERFLOW indicates that a bit overflow is detected on the Left channel 1.
--
---------------------------------------------------------------------------------------------------
-- Header		: CH-LEFT2
--
-- MIB ref		: swCardEventLogSlotXX       .8.67.72.45.76.69.70.84.50
-- absolute OID	: 1.3.6.1.4.1.7995.2.6.1.1.XX.8.67.72.45.76.69.70.84.50
-- Vary			: YES
--
-- Value(s)		: OK
--				: OVERFLOW
-- Comments		: This log field shows the detected audio state of the Left Channel 2 input.
--				: LOST indicates no input detected at this Channel. 
--				: OVERFLOW indicates that a bit overflow is detected on the Left channel 2.
--
---------------------------------------------------------------------------------------------------
-- Header		: CH-RIGHT1
--
-- MIB ref		: swCardEventLogSlotXX       .9.67.72.45.82.73.71.72.84.49
-- absolute OID	: 1.3.6.1.4.1.7995.2.6.1.1.XX.9.67.72.45.82.73.71.72.84.49
-- Vary			: YES
--
-- Value(s)		: OK
--				: OVERFLOW
-- Comments		: This log field shows the detected audio state of the Right Channel 1 input.
--				: LOST indicates no input detected at this Channel. 
--				: OVERFLOW indicates that a bit overflow is detected on the Right channel 1.
--
---------------------------------------------------------------------------------------------------
-- Header		: CH-RIGHT2
--
-- MIB ref		: swCardEventLogSlotXX       .9.67.72.45.82.73.71.72.84.50
-- absolute OID	: 1.3.6.1.4.1.7995.2.6.1.1.XX.9.67.72.45.82.73.71.72.84.50
-- Vary			: YES
--
-- Value(s)		: OK
--				: OVERFLOW
-- Comments		: This log field shows the detected audio state of the Right Channel 2 input.
--				: LOST indicates no input detected at this Channel. 
--				: OVERFLOW indicates that a bit overflow is detected on the Right channel 2.
--
---------------------------------------------------------------------------------------------------
