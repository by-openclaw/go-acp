-- ************************************************************************************
-- Snell&Wilcox Card:IQDMX01
--        Module Id#:363
--       Command Set:6
--          Filename:SNELL-IQDMX01-CMD-MIB.mib
--            Author:Jonathan Riches
--              Date:10/01/2008
--              Time:09:31
--
-- Copyright (c) 2005 Snell & Wilcox Ltd
-- All rights reserved.
--
-- ************************************************************************************

SNELL-IQDMX01-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDMX01,
    moduleIQDMX01MIB
        FROM SNELL-WILCOX-PRODUCT-REG;

 moduleIQDMX01CmdMi MODULE-IDENTITY
    LAST-UPDATED "0801100931Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDMX01MIB 1 }




--********************************************************************************
--*
--*  Snell Wilcox Card:
--*  command set:
--*  list commands/menus:
--*
--******************************************************************************
	iqdmx01CmdTable OBJECT-TYPE
		SYNTAX			SEQUENCE OF Iqdmx01CmdEntry
		MAX-ACCESS		not-accessible
		STATUS			current
		DESCRIPTION
				"Note the instance of this table is relected in the command set Version"
		::= { moduleIQDMX01 1 }

	iqdmx01CmdEntry OBJECT-TYPE
		SYNTAX		Iqdmx01CmdEntry
		MAX-ACCESS		not-accessible
		STATUS			current
		DESCRIPTION
				"Entry in command table."
		INDEX	{ iqdmx01SlotIndex }
		::= { iqdmx01CmdTable 1 }

	Iqdmx01CmdEntry ::=
		SEQUENCE {
			iqdmx01SlotIndex
				Unsigned32,
			iqdmx01VideoInput
				INTEGER,
			iqdmx01VideoInput525
				INTEGER,
			iqdmx01VideoInput625
				INTEGER,
			iqdmx01VideoProcAmp1In1ProcAmpEnable
				INTEGER,
			iqdmx01VideoProcAmp1LumaGain
				INTEGER,
			iqdmx01VideoProcAmp1ChromaGain
				INTEGER,
			iqdmx01VideoProcAmp1BlackLevel
				INTEGER,
			iqdmx01VideoProcAmp1PicturePosition
				INTEGER,
			iqdmx01VideoProcAmp1YCTiming
				INTEGER,
			iqdmx01VideoProcAmp2In2ProcAmpEnable
				INTEGER,
			iqdmx01VideoProcAmp2LumaGain
				INTEGER,
			iqdmx01VideoProcAmp2ChromaGain
				INTEGER,
			iqdmx01VideoProcAmp2BlackLevel
				INTEGER,
			iqdmx01VideoProcAmp2PicturePosition
				INTEGER,
			iqdmx01VideoProcAmp2YCTiming
				INTEGER,
			iqdmx01AudioDeembed
				INTEGER,
			iqdmx01AudioAESOutputAES1Source
				INTEGER,
			iqdmx01AudioAESOutputAES2Source
				INTEGER,
			iqdmx01AudioProcAmpStereo1
				INTEGER,
			iqdmx01ProcAmpDeembed1LGainDeembed1L
				INTEGER,
			iqdmx01ProcAmpDeembed1LInvert
				INTEGER,
			iqdmx01ProcAmpDeembed1LMute
				INTEGER,
			iqdmx01ProcAmpDeembed1RGainDeembed1R
				INTEGER,
			iqdmx01ProcAmpDeembed1RInvert
				INTEGER,
			iqdmx01ProcAmpDeembed1RMute
				INTEGER,
			iqdmx01AudioProcAmpStereo2
				INTEGER,
			iqdmx01ProcAmpDeembed2LGainDeembed2L
				INTEGER,
			iqdmx01ProcAmpDeembed2LInvert
				INTEGER,
			iqdmx01ProcAmpDeembed2LMute
				INTEGER,
			iqdmx01ProcAmpDeembed2RGainDeembed2R
				INTEGER,
			iqdmx01ProcAmpDeembed2RInvert
				INTEGER,
			iqdmx01ProcAmpDeembed2RMute
				INTEGER,
			iqdmx01AudioProcAmpStereo3
				INTEGER,
			iqdmx01ProcAmpDeembed3LGainDeembed3L
				INTEGER,
			iqdmx01ProcAmpDeembed3LInvert
				INTEGER,
			iqdmx01ProcAmpDeembed3LMute
				INTEGER,
			iqdmx01ProcAmpDeembed3RGainDeembed3R
				INTEGER,
			iqdmx01ProcAmpDeembed3RInvert
				INTEGER,
			iqdmx01ProcAmpDeembed3RMute
				INTEGER,
			iqdmx01AudioProcAmpStereo4
				INTEGER,
			iqdmx01ProcAmpDeembed4LGainDeembed4L
				INTEGER,
			iqdmx01ProcAmpDeembed4LInvert
				INTEGER,
			iqdmx01ProcAmpDeembed4LMute
				INTEGER,
			iqdmx01ProcAmpDeembed4RGainDeembed4R
				INTEGER,
			iqdmx01ProcAmpDeembed4RInvert
				INTEGER,
			iqdmx01ProcAmpDeembed4RMute
				INTEGER,
			iqdmx01AudioProcAmpStereo5
				INTEGER,
			iqdmx01ProcAmpDeembed5LGainDeembed5L
				INTEGER,
			iqdmx01ProcAmpDeembed5LInvert
				INTEGER,
			iqdmx01ProcAmpDeembed5LMute
				INTEGER,
			iqdmx01ProcAmpDeembed5RGainDeembed5R
				INTEGER,
			iqdmx01ProcAmpDeembed5RInvert
				INTEGER,
			iqdmx01ProcAmpDeembed5RMute
				INTEGER,
			iqdmx01AudioProcAmpStereo6
				INTEGER,
			iqdmx01ProcAmpDeembed6LGainDeembed6L
				INTEGER,
			iqdmx01ProcAmpDeembed6LInvert
				INTEGER,
			iqdmx01ProcAmpDeembed6LMute
				INTEGER,
			iqdmx01ProcAmpDeembed6RGainDeembed6R
				INTEGER,
			iqdmx01ProcAmpDeembed6RInvert
				INTEGER,
			iqdmx01ProcAmpDeembed6RMute
				INTEGER,
			iqdmx01AudioProcAmpStereo7
				INTEGER,
			iqdmx01ProcAmpDeembed7LGainDeembed7L
				INTEGER,
			iqdmx01ProcAmpDeembed7LInvert
				INTEGER,
			iqdmx01ProcAmpDeembed7LMute
				INTEGER,
			iqdmx01ProcAmpDeembed7RGainDeembed7R
				INTEGER,
			iqdmx01ProcAmpDeembed7RInvert
				INTEGER,
			iqdmx01ProcAmpDeembed7RMute
				INTEGER,
			iqdmx01AudioProcAmpStereo8
				INTEGER,
			iqdmx01ProcAmpDeembed8LGainDeembed8L
				INTEGER,
			iqdmx01ProcAmpDeembed8LInvert
				INTEGER,
			iqdmx01ProcAmpDeembed8LMute
				INTEGER,
			iqdmx01ProcAmpDeembed8RGainDeembed8R
				INTEGER,
			iqdmx01ProcAmpDeembed8RInvert
				INTEGER,
			iqdmx01ProcAmpDeembed8RMute
				INTEGER,
			iqdmx01EmbedEmbedder1Embed1Source
				INTEGER,
			iqdmx01EmbedEmbedder1PairSelection
				INTEGER,
			iqdmx01EmbedEmbedder1Disable
				INTEGER,
			iqdmx01EmbedEmbedder2Embed2Source
				INTEGER,
			iqdmx01EmbedEmbedder2PairSelection
				INTEGER,
			iqdmx01EmbedEmbedder2Disable
				INTEGER,
			iqdmx01EmbedEmbedder3Embed3Source
				INTEGER,
			iqdmx01EmbedEmbedder3PairSelection
				INTEGER,
			iqdmx01EmbedEmbedder3Disable
				INTEGER,
			iqdmx01EmbedEmbedder4Embed4Source
				INTEGER,
			iqdmx01EmbedEmbedder4PairSelection
				INTEGER,
			iqdmx01EmbedEmbedder4Disable
				INTEGER,
			iqdmx01Mixer1Mix1Source1
				INTEGER,
			iqdmx01MixMixer1Gain1
				INTEGER,
			iqdmx01Mixer1Mix1Source2
				INTEGER,
			iqdmx01MixMixer1Gain2
				INTEGER,
			iqdmx01Mixer1Mix1Source3
				INTEGER,
			iqdmx01MixMixer1Gain3
				INTEGER,
			iqdmx01Mixer1Mix1Source4
				INTEGER,
			iqdmx01MixMixer1Gain4
				INTEGER,
			iqdmx01Mixer2Mix2Source1
				INTEGER,
			iqdmx01MixMixer2Gain1
				INTEGER,
			iqdmx01Mixer2Mix2Source2
				INTEGER,
			iqdmx01MixMixer2Gain2
				INTEGER,
			iqdmx01Mixer2Mix2Source3
				INTEGER,
			iqdmx01MixMixer2Gain3
				INTEGER,
			iqdmx01Mixer2Mix2Source4
				INTEGER,
			iqdmx01MixMixer2Gain4
				INTEGER,
			iqdmx01Mixer3Mix3Source1
				INTEGER,
			iqdmx01MixMixer3Gain1
				INTEGER,
			iqdmx01Mixer3Mix3Source2
				INTEGER,
			iqdmx01MixMixer3Gain2
				INTEGER,
			iqdmx01Mixer3Mix3Source3
				INTEGER,
			iqdmx01MixMixer3Gain3
				INTEGER,
			iqdmx01Mixer3Mix3Source4
				INTEGER,
			iqdmx01MixMixer3Gain4
				INTEGER,
			iqdmx01Mixer4Mix4Source1
				INTEGER,
			iqdmx01MixMixer4Gain1
				INTEGER,
			iqdmx01Mixer4Mix4Source2
				INTEGER,
			iqdmx01MixMixer4Gain2
				INTEGER,
			iqdmx01Mixer4Mix4Source3
				INTEGER,
			iqdmx01MixMixer4Gain3
				INTEGER,
			iqdmx01Mixer4Mix4Source4
				INTEGER,
			iqdmx01MixMixer4Gain4
				INTEGER,
			iqdmx01BusSourceBusALSource
				INTEGER,
			iqdmx01BusSourceBusARSource
				INTEGER,
			iqdmx01BusSourceBusBLSource
				INTEGER,
			iqdmx01BusSourceBusBRSource
				INTEGER,
			iqdmx01BusSourceBusCLSource
				INTEGER,
			iqdmx01BusSourceBusCRSource
				INTEGER,
			iqdmx01BusSourceBusDLSource
				INTEGER,
			iqdmx01BusSourceBusDRSource
				INTEGER,
			iqdmx01BusesBusProcAmpStereoA
				INTEGER,
			iqdmx01BusProcAmpBusALGainBusAL
				INTEGER,
			iqdmx01BusProcAmpBusALInvert
				INTEGER,
			iqdmx01BusProcAmpBusALMute
				INTEGER,
			iqdmx01BusProcAmpBusARGainBusAR
				INTEGER,
			iqdmx01BusProcAmpBusARInvert
				INTEGER,
			iqdmx01BusProcAmpBusARMute
				INTEGER,
			iqdmx01BusesBusProcAmpStereoB
				INTEGER,
			iqdmx01BusProcAmpBusBLGainBusBL
				INTEGER,
			iqdmx01BusProcAmpBusBLInvert
				INTEGER,
			iqdmx01BusProcAmpBusBLMute
				INTEGER,
			iqdmx01BusProcAmpBusBRGainBusBR
				INTEGER,
			iqdmx01BusProcAmpBusBRInvert
				INTEGER,
			iqdmx01BusProcAmpBusBRMute
				INTEGER,
			iqdmx01BusesBusProcAmpStereoC
				INTEGER,
			iqdmx01BusProcAmpBusCLGainBusCL
				INTEGER,
			iqdmx01BusProcAmpBusCLInvert
				INTEGER,
			iqdmx01BusProcAmpBusCLMute
				INTEGER,
			iqdmx01BusProcAmpBusCRGainBusCR
				INTEGER,
			iqdmx01BusProcAmpBusCRInvert
				INTEGER,
			iqdmx01BusProcAmpBusCRMute
				INTEGER,
			iqdmx01BusesBusProcAmpStereoD
				INTEGER,
			iqdmx01BusProcAmpBusDLGainBusDL
				INTEGER,
			iqdmx01BusProcAmpBusDLInvert
				INTEGER,
			iqdmx01BusProcAmpBusDLMute
				INTEGER,
			iqdmx01BusProcAmpBusDRGainBusDR
				INTEGER,
			iqdmx01BusProcAmpBusDRInvert
				INTEGER,
			iqdmx01BusProcAmpBusDRMute
				INTEGER,
			iqdmx01DelayDelaySelectInternal
				INTEGER,
			iqdmx01DelayDelaySelectManual
				INTEGER,
			iqdmx01DelayDelaySelectRolltrack14
				INTEGER,
			iqdmx01DelayDelaySelectRolltrack15
				INTEGER,
			iqdmx01DelayDelaySelectRolltrack16
				INTEGER,
			iqdmx01DelayDelaySelectRolltrack17
				INTEGER,
			iqdmx01DelayDelaySelectGPIDelaySelect
				INTEGER,
			iqdmx01DelayDelayStatusManual
				INTEGER,
			iqdmx01DelayDelayStatusInternal
				RollCallString,
			iqdmx01DelayDelayStatusRolltrack14
				RollCallString,
			iqdmx01DelayDelayStatusRolltrack15
				RollCallString,
			iqdmx01DelayDelayStatusRolltrack16
				RollCallString,
			iqdmx01DelayDelayStatusRolltrack17
				RollCallString,
			iqdmx01DelayDelayStatusGPIDelayDisplay
				RollCallString,
			iqdmx01DelayDelayStatusTotalDelayDisplay
				RollCallString,
			iqdmx01AudioMonitorSilenceLevel
				INTEGER,
			iqdmx01AudioMonitorLowLevel
				INTEGER,
			iqdmx01AudioMonitorHighLevel
				INTEGER,
			iqdmx01AudioMonitorOverloadLevel
				INTEGER,
			iqdmx01AudioMonitorWarningTimer
				INTEGER,
			iqdmx01Freeze
				INTEGER,
			iqdmx01VideoDelay
				INTEGER,
			iqdmx01VideoDelayDelayPhase625HPhase
				INTEGER,
			iqdmx01VideoDelayDelayPhase625VPhase
				INTEGER,
			iqdmx01VideoDelayDelayPhase525HPhase
				INTEGER,
			iqdmx01VideoDelayDelayPhase525VPhase
				INTEGER,
			iqdmx01UserMemMemory1Save1
				INTEGER,
			iqdmx01UserMemMemory1Recall1
				INTEGER,
			iqdmx01UserMemMemory1Clear1
				INTEGER,
			iqdmx01UserMemMemory1Name1
				RollCallString,
			iqdmx01UserMemMemory2Save2
				INTEGER,
			iqdmx01UserMemMemory2Recall2
				INTEGER,
			iqdmx01UserMemMemory2Clear2
				INTEGER,
			iqdmx01UserMemMemory2Name2
				RollCallString,
			iqdmx01UserMemMemory3Save3
				INTEGER,
			iqdmx01UserMemMemory3Recall3
				INTEGER,
			iqdmx01UserMemMemory3Clear3
				INTEGER,
			iqdmx01UserMemMemory3Name3
				RollCallString,
			iqdmx01UserMemMemory4Save4
				INTEGER,
			iqdmx01UserMemMemory4Recall4
				INTEGER,
			iqdmx01UserMemMemory4Clear4
				INTEGER,
			iqdmx01UserMemMemory4Name4
				RollCallString,
			iqdmx01UserMemMemory5Save5
				INTEGER,
			iqdmx01UserMemMemory5Recall5
				INTEGER,
			iqdmx01UserMemMemory5Clear5
				INTEGER,
			iqdmx01UserMemMemory5Name5
				RollCallString,
			iqdmx01UserMemMemory6Save6
				INTEGER,
			iqdmx01UserMemMemory6Recall6
				INTEGER,
			iqdmx01UserMemMemory6Clear6
				INTEGER,
			iqdmx01UserMemMemory6Name6
				RollCallString,
			iqdmx01UserMemMemory7Save7
				INTEGER,
			iqdmx01UserMemMemory7Recall7
				INTEGER,
			iqdmx01UserMemMemory7Clear7
				INTEGER,
			iqdmx01UserMemMemory7Name7
				RollCallString,
			iqdmx01UserMemMemory8Save8
				INTEGER,
			iqdmx01UserMemMemory8Recall8
				INTEGER,
			iqdmx01UserMemMemory8Clear8
				INTEGER,
			iqdmx01UserMemMemory8Name8
				RollCallString,
			iqdmx01SetupPatternAnimatedPattern
				INTEGER,
			iqdmx01SetupPatternEnablePattern
				INTEGER,
			iqdmx01SetupPattern
				INTEGER,
			iqdmx01SetupCaptionEditCaption
				RollCallString,
			iqdmx01SetupCaption
				INTEGER,
			iqdmx01BlankingVIPass525BlankAll
				INTEGER,
			iqdmx01BlankingVIPass525PassAll
				INTEGER,
			iqdmx01BlankingVIPass525Line11
				INTEGER,
			iqdmx01BlankingVIPass525Line274
				INTEGER,
			iqdmx01BlankingVIPass525Line12
				INTEGER,
			iqdmx01BlankingVIPass525Line275
				INTEGER,
			iqdmx01BlankingVIPass525Line13
				INTEGER,
			iqdmx01BlankingVIPass525Line276
				INTEGER,
			iqdmx01BlankingVIPass525Line14
				INTEGER,
			iqdmx01BlankingVIPass525Line277
				INTEGER,
			iqdmx01BlankingVIPass525Line15
				INTEGER,
			iqdmx01BlankingVIPass525Line278
				INTEGER,
			iqdmx01BlankingVIPass525Line16
				INTEGER,
			iqdmx01BlankingVIPass525Line279
				INTEGER,
			iqdmx01BlankingVIPass525Line17
				INTEGER,
			iqdmx01BlankingVIPass525Line280
				INTEGER,
			iqdmx01BlankingVIPass525Line18
				INTEGER,
			iqdmx01BlankingVIPass525Line281
				INTEGER,
			iqdmx01BlankingVIPass525Line19
				INTEGER,
			iqdmx01BlankingVIPass525Line282
				INTEGER,
			iqdmx01BlankingVIPass525Line20
				INTEGER,
			iqdmx01BlankingVIPass525Line283
				INTEGER,
			iqdmx01BlankingVIPass525Line21
				INTEGER,
			iqdmx01BlankingVIPass625BlankAll
				INTEGER,
			iqdmx01BlankingVIPass625PassAll
				INTEGER,
			iqdmx01BlankingVIPass625Line7
				INTEGER,
			iqdmx01BlankingVIPass625Line320
				INTEGER,
			iqdmx01BlankingVIPass625Line8
				INTEGER,
			iqdmx01BlankingVIPass625Line321
				INTEGER,
			iqdmx01BlankingVIPass625Line9
				INTEGER,
			iqdmx01BlankingVIPass625Line322
				INTEGER,
			iqdmx01BlankingVIPass625Line10
				INTEGER,
			iqdmx01BlankingVIPass625Line323
				INTEGER,
			iqdmx01BlankingVIPass625Line11
				INTEGER,
			iqdmx01BlankingVIPass625Line324
				INTEGER,
			iqdmx01BlankingVIPass625Line12
				INTEGER,
			iqdmx01BlankingVIPass625Line325
				INTEGER,
			iqdmx01BlankingVIPass625Line13
				INTEGER,
			iqdmx01BlankingVIPass625Line326
				INTEGER,
			iqdmx01BlankingVIPass625Line14
				INTEGER,
			iqdmx01BlankingVIPass625Line327
				INTEGER,
			iqdmx01BlankingVIPass625Line15
				INTEGER,
			iqdmx01BlankingVIPass625Line328
				INTEGER,
			iqdmx01BlankingVIPass625Line16
				INTEGER,
			iqdmx01BlankingVIPass625Line329
				INTEGER,
			iqdmx01BlankingVIPass625Line17
				INTEGER,
			iqdmx01BlankingVIPass625Line330
				INTEGER,
			iqdmx01BlankingVIPass625Line18
				INTEGER,
			iqdmx01BlankingVIPass625Line331
				INTEGER,
			iqdmx01BlankingVIPass625Line19
				INTEGER,
			iqdmx01BlankingVIPass625Line332
				INTEGER,
			iqdmx01BlankingVIPass625Line20
				INTEGER,
			iqdmx01BlankingVIPass625Line333
				INTEGER,
			iqdmx01BlankingVIPass625Line21
				INTEGER,
			iqdmx01BlankingVIPass625Line334
				INTEGER,
			iqdmx01BlankingVIPass625Line22
				INTEGER,
			iqdmx01BlankingVIPass625Line335
				INTEGER,
			iqdmx01BlankingVIPass625Line23
				INTEGER,
			iqdmx01SetupBlankingHancBlank
				INTEGER,
			iqdmx01SetupBlankingVFlagOBD
				INTEGER,
			iqdmx01SetupAudioToneIdentEnable
				INTEGER,
			iqdmx01SetupAudioToneFrequency
				INTEGER,
			iqdmx01SetupAudioToneFrequencyR
				INTEGER,
			iqdmx01SetupAudioToneHeadRoom
				INTEGER,
			iqdmx01SetupSlewRate
				INTEGER,
			iqdmx01SetupChannelStatus
				RollCallString,
			iqdmx01GPIIOGPIInputDisableInputs
				INTEGER,
			iqdmx01GPIIOGPIInputInputTimerEnable
				INTEGER,
			iqdmx01GPIIOGPIInputTimerActiveHigh
				INTEGER,
			iqdmx01GPIIOGPIInputInputSelection
				INTEGER,
			iqdmx01GPIIOGPIInputGPIInStatus
				RollCallString,
			iqdmx01GPIIOGPIOutputOutActiveHigh
				INTEGER,
			iqdmx01GPIIOGPIOutputOutputSelection
				INTEGER,
			iqdmx01GPIIOGPIOutputGPIOutStatus
				RollCallString,
			iqdmx01GPIIOGPIInputOutputGPIO1
				INTEGER,
			iqdmx01SetupGPIIOInputSelection
				INTEGER,
			iqdmx01SetupGPIIOOutputSelection
				INTEGER,
			iqdmx01SetupRollTrackRollTrackIndex
				INTEGER,
			iqdmx01SetupRollTrackRollTrackSource
				INTEGER,
			iqdmx01SetupRollTrackRollTrackDisable
				INTEGER,
			iqdmx01SetupRollTrackRollTrackAddress
				RollCallString,
			iqdmx01SetupRollTrackRollTrackCommand
				RollCallString,
			iqdmx01SetupRollTrackRollTrackSending
				RollCallString,
			iqdmx01SetupRollTrackRollTrackStatus
				RollCallString,
			iqdmx01SetupRollTrackRollTrack_Index
				INTEGER,
			iqdmx01SetupRollTrackRollTrack_Source
				INTEGER,
			iqdmx01SetupRollTrackRollTrack_Address
				RollCallString,
			iqdmx01SetupRollTrackRollTrack_Command
				RollCallString,
			iqdmx01SetupLoggingInput
				INTEGER,
			iqdmx01SetupLoggingStd
				INTEGER,
			iqdmx01SetupLoggingInput1
				INTEGER,
			iqdmx01SetupLoggingStd1
				INTEGER,
			iqdmx01SetupLoggingInput2
				INTEGER,
			iqdmx01SetupLoggingStd2
				INTEGER,
			iqdmx01SetupLoggingEDH
				INTEGER,
			iqdmx01SetupLoggingEDHErrors
				INTEGER,
			iqdmx01SetupLoggingRollTrack
				INTEGER,
			iqdmx01SetupLoggingDeembed1
				INTEGER,
			iqdmx01SetupLoggingDeembed2
				INTEGER,
			iqdmx01SetupLoggingDeembed3
				INTEGER,
			iqdmx01SetupLoggingDeembed4
				INTEGER,
			iqdmx01SetupLoggingDeembed5
				INTEGER,
			iqdmx01SetupLoggingDeembed6
				INTEGER,
			iqdmx01SetupLoggingDeembed7
				INTEGER,
			iqdmx01SetupLoggingDeembed8
				INTEGER,
			iqdmx01SetupLoggingnPCM1
				INTEGER,
			iqdmx01SetupLoggingnPCM2
				INTEGER,
			iqdmx01SetupLoggingnPCM3
				INTEGER,
			iqdmx01SetupLoggingnPCM4
				INTEGER,
			iqdmx01SetupLoggingnPCM5
				INTEGER,
			iqdmx01SetupLoggingnPCM6
				INTEGER,
			iqdmx01SetupLoggingnPCM7
				INTEGER,
			iqdmx01SetupLoggingnPCM8
				INTEGER,
			iqdmx01SetupLoggingBusAL
				INTEGER,
			iqdmx01SetupLoggingBusAR
				INTEGER,
			iqdmx01SetupLoggingBusBL
				INTEGER,
			iqdmx01SetupLoggingBusBR
				INTEGER,
			iqdmx01SetupLoggingBusCL
				INTEGER,
			iqdmx01SetupLoggingBusCR
				INTEGER,
			iqdmx01SetupLoggingBusDL
				INTEGER,
			iqdmx01SetupLoggingBusDR
				INTEGER,
			iqdmx01SetupLoggingFault
				INTEGER,
			iqdmx01SetupLoggingStatusINPUT
				RollCallString,
			iqdmx01SetupLoggingStatusSTD
				RollCallString,
			iqdmx01SetupLoggingStatusINPUT1
				RollCallString,
			iqdmx01SetupLoggingStatusSTD1
				RollCallString,
			iqdmx01SetupLoggingStatusINPUT2
				RollCallString,
			iqdmx01SetupLoggingStatusSTD2
				RollCallString,
			iqdmx01SetupLoggingStatusEDH
				RollCallString,
			iqdmx01SetupLoggingStatusERRSEC
				RollCallString,
			iqdmx01SetupLoggingStatusROLLTRACK
				RollCallString,
			iqdmx01SetupLoggingStatusDEEMBED1
				RollCallString,
			iqdmx01SetupLoggingStatusDEEMBED2
				RollCallString,
			iqdmx01SetupLoggingStatusDEEMBED3
				RollCallString,
			iqdmx01SetupLoggingStatusDEEMBED4
				RollCallString,
			iqdmx01SetupLoggingStatusDEEMBED5
				RollCallString,
			iqdmx01SetupLoggingStatusDEEMBED6
				RollCallString,
			iqdmx01SetupLoggingStatusDEEMBED7
				RollCallString,
			iqdmx01SetupLoggingStatusDEEMBED8
				RollCallString,
			iqdmx01SetupLoggingStatusNPCM1
				RollCallString,
			iqdmx01SetupLoggingStatusNPCM2
				RollCallString,
			iqdmx01SetupLoggingStatusNPCM3
				RollCallString,
			iqdmx01SetupLoggingStatusNPCM4
				RollCallString,
			iqdmx01SetupLoggingStatusNPCM5
				RollCallString,
			iqdmx01SetupLoggingStatusNPCM6
				RollCallString,
			iqdmx01SetupLoggingStatusNPCM7
				RollCallString,
			iqdmx01SetupLoggingStatusNPCM8
				RollCallString,
			iqdmx01SetupLoggingStatusBUSAL
				RollCallString,
			iqdmx01SetupLoggingStatusBUSAR
				RollCallString,
			iqdmx01SetupLoggingStatusBUSBL
				RollCallString,
			iqdmx01SetupLoggingStatusBUSBR
				RollCallString,
			iqdmx01SetupLoggingStatusBUSCL
				RollCallString,
			iqdmx01SetupLoggingStatusBUSCR
				RollCallString,
			iqdmx01SetupLoggingStatusBUSDL
				RollCallString,
			iqdmx01SetupLoggingStatusBUSDR
				RollCallString,
			iqdmx01SetupLoggingStatusFAULT
				RollCallString,
			iqdmx01SetupInformationWindow
				INTEGER,
			iqdmx01SetupInformationWindowResetErrors
				INTEGER,
			iqdmx01SetupDefaultOutput
				INTEGER,
			iqdmx01SetupDefaultPattern
				INTEGER,
			iqdmx01SetupUnitSoftwareVersion
				RollCallString,
			iqdmx01SetupUnitSerialNo
				RollCallString,
			iqdmx01SetupUnitPresetUnit
				INTEGER,
			iqdmx01SetupUnitRestart
				INTEGER,
			iqdmx01SetupUnitBuildNo
				RollCallString
		}

	iqdmx01SlotIndex OBJECT-TYPE
		SYNTAX		Unsigned32
		MAX-ACCESS		not-accessible
		STATUS			current
		DESCRIPTION
				"The unique Index value for each slot.  Its value
					ranges between 1 and the value of slotNumber."
		::= { iqdmx01CmdEntry 0 }


	iqdmx01VideoInput OBJECT-TYPE
		SYNTAX		INTEGER {
							val_Input_1_SDI(0),
							val_Input_2_SDI(1)
							}
		MAX-ACCESS		read-write
		STATUS			current
		DESCRIPTION
				"TYPE: - Button
				 PAGE: - Video- Input
					Input 1 SDI  cmdID= 2251  value= 0
					Input 2 SDI  cmdID= 2251  value= 1  "
		::= { iqdmx01CmdEntry 2251 }


	iqdmx01VideoInput525 OBJECT-TYPE
		SYNTAX		INTEGER { disable(0), enable(1) }
		MAX-ACCESS		read-write
		STATUS			current
		DESCRIPTION
				"TYPE: - Checkbox
				 PAGE: - Video- Input
					525  cmdID= 1405 "
		::= { iqdmx01CmdEntry 1405 }


	iqdmx01VideoInput625 OBJECT-TYPE
		SYNTAX		INTEGER { disable(0), enable(1) }
		MAX-ACCESS		read-write
		STATUS			current
		DESCRIPTION
				"TYPE: - Checkbox
				 PAGE: - Video- Input
					625  cmdID= 1406 "
		::= { iqdmx01CmdEntry 1406 }


	iqdmx01VideoProcAmp1In1ProcAmpEnable OBJECT-TYPE
		SYNTAX		INTEGER { disable(0), enable(1) }
		MAX-ACCESS		read-write
		STATUS			current
		DESCRIPTION
				"TYPE: - Checkbox
				 PAGE: - Video- ProcAmp 1
					In1 ProcAmp Enable  cmdID= 2864 "
		::= { iqdmx01CmdEntry 2864 }


	iqdmx01VideoProcAmp1LumaGain OBJECT-TYPE
		SYNTAX		INTEGER
		MAX-ACCESS		read-write
		STATUS			current
		DESCRIPTION
				"TYPE: - Number
				 PAGE: - Video- ProcAmp 1
					Luma Gain  cmdID= 2707  min= -60  max= 60  step= 1  format= %1.1f dB  div_scale= 10
					Min = -6.0 dB  Max = 6.0 dB  Step = 0.1 dB "
		::= { iqdmx01CmdEntry 2707 }


	iqdmx01VideoProcAmp1ChromaGain OBJECT-TYPE
		SYNTAX		INTEGER
		MAX-ACCESS		read-write
		STATUS			current
		DESCRIPTION
				"TYPE: - Number
				 PAGE: - Video- ProcAmp 1
					Chroma Gain  cmdID= 2706  min= -60  max= 60  step= 1  format= %1.1f dB  div_scale= 10
					Min = -6.0 dB  Max = 6.0 dB  Step = 0.1 dB "
		::= { iqdmx01CmdEntry 2706 }


	iqdmx01VideoProcAmp1BlackLevel OBJECT-TYPE
		SYNTAX		INTEGER
		MAX-ACCESS		read-write
		STATUS			current
		DESCRIPTION
				"TYPE: - Number
				 PAGE: - Video- ProcAmp 1
					Black Level  cmdID= 2708  min= -1000  max= 1000  step= 8  format= %1.1f mV  div_scale= 10
					Min = -100.0 mV  Max = 100.0 mV  Step = 0.8 mV "
		::= { iqdmx01CmdEntry 2708 }


	iqdmx01VideoProcAmp1PicturePosition OBJECT-TYPE
		SYNTAX		INTEGER
		MAX-ACCESS		read-write
		STATUS			current
		DESCRIPTION
				"TYPE: - Number
				 PAGE: - Video- ProcAmp 1
					Picture Position  cmdID= 2709  min= -592  max= 592  step= 148  format= %3.0f ns  div_scale= 1
					Min = -592 ns  Max = 592 ns  Step = 148 ns "
		::= { iqdmx01CmdEntry 2709 }


	iqdmx01VideoProcAmp1YCTiming OBJECT-TYPE
		SYNTAX		INTEGER
		MAX-ACCESS		read-write
		STATUS			current
		DESCRIPTION
				"TYPE: - Number
				 PAGE: - Video- ProcAmp 1
					Y/C Timing  cmdID= 2924  min= -592  max= 592  step= 148  format= %3.0fns  div_scale= 1
					Min = -592ns  Max = 592ns  Step = 148ns "
		::= { iqdmx01CmdEntry 2924 }


	iqdmx01VideoProcAmp2In2ProcAmpEnable OBJECT-TYPE
		SYNTAX		INTEGER { disable(0), enable(1) }
		MAX-ACCESS		read-write
		STATUS			current
		DESCRIPTION
				"TYPE: - Checkbox
				 PAGE: - Video- ProcAmp 2
					In2 ProcAmp Enable  cmdID= 2865 "
		::= { iqdmx01CmdEntry 2865 }


	iqdmx01VideoProcAmp2LumaGain OBJECT-TYPE
		SYNTAX		INTEGER
		MAX-ACCESS		read-write
		STATUS			current
		DESCRIPTION
				"TYPE: - Number
				 PAGE: - Video- ProcAmp 2
					Luma Gain  cmdID= 2711  min= -60  max= 60  step= 1  format= %1.1f dB  div_scale= 10
					Min = -6.0 dB  Max = 6.0 dB  Step = 0.1 dB "
		::= { iqdmx01CmdEntry 2711 }


	iqdmx01VideoProcAmp2ChromaGain OBJECT-TYPE
		SYNTAX		INTEGER
		MAX-ACCESS		read-write
		STATUS			current
		DESCRIPTION
				"TYPE: - Number
				 PAGE: - Video- ProcAmp 2
					Chroma Gain  cmdID= 2710  min= -60  max= 60  step= 1  format= %1.1f dB  div_scale= 10
					Min = -6.0 dB  Max = 6.0 dB  Step = 0.1 dB "
		::= { iqdmx01CmdEntry 2710 }


	iqdmx01VideoProcAmp2BlackLevel OBJECT-TYPE
		SYNTAX		INTEGER
		MAX-ACCESS		read-write
		STATUS			current
		DESCRIPTION
				"TYPE: - Number
				 PAGE: - Video- ProcAmp 2
					Black Level  cmdID= 2712  min= -1000  max= 1000  step= 8  format= %1.1f mV  div_scale= 10
					Min = -100.0 mV  Max = 100.0 mV  Step = 0.8 mV "
		::= { iqdmx01CmdEntry 2712 }


	iqdmx01VideoProcAmp2PicturePosition OBJECT-TYPE
		SYNTAX		INTEGER
		MAX-ACCESS		read-write
		STATUS			current
		DESCRIPTION
				"TYPE: - Number
				 PAGE: - Video- ProcAmp 2
					Picture Position  cmdID= 2713  min= -592  max= 592  step= 148  format= %3.0f ns  div_scale= 1
					Min = -592 ns  Max = 592 ns  Step = 148 ns "
		::= { iqdmx01CmdEntry 2713 }


	iqdmx01VideoProcAmp2YCTiming OBJECT-TYPE
		SYNTAX		INTEGER
		MAX-ACCESS		read-write
		STATUS			current
		DESCRIPTION
				"TYPE: - Number
				 PAGE: - Video- ProcAmp 2
					Y/C Timing  cmdID= 2925  min= -592  max= 592  step= 148  format= %3.0fns  div_scale= 1
					Min = -592ns  Max = 592ns  Step = 148ns "
		::= { iqdmx01CmdEntry 2925 }


	iqdmx01AudioDeembed OBJECT-TYPE
		SYNTAX		INTEGER {
							val_Input_1_SDI(0),
							val_Input_2_SDI(1),
							val_Follow_Video(2)
							}
		MAX-ACCESS		read-write
		STATUS			current
		DESCRIPTION
				"TYPE: - Button
				 PAGE: - Audio- De-embed
					Input 1 SDI  cmdID= 2923  value= 0
					Input 2 SDI  cmdID= 2923  value= 1
					Follow Video  cmdID= 2923  value= 2  "
		::= { iqdmx01CmdEntry 2923 }


	iqdmx01AudioAESOutputAES1Source OBJECT-TYPE
		SYNTAX		INTEGER {
							val_BUS_A(0),
							val_BUS_B(1),
							val_BUS_C(2),
							val_BUS_D(3),
							val_DeEmbed_1(4),
							val_DeEmbed_2(5),
							val_DeEmbed_3(6),
							val_DeEmbed_4(7),
							val_DeEmbed_5(8),
							val_DeEmbed_6(9),
							val_DeEmbed_7(10),
							val_DeEmbed_8(11),
							val_Test_tone(12),
							val_Silence(13)
							}
		MAX-ACCESS		read-write
		STATUS			current
		DESCRIPTION
				"TYPE: - RadiobuttonList
				 PAGE: - Audio- AES Output
					AES 1 Source  cmdID= 2951
					BUS A  value= 0
					BUS B  value= 1
					BUS C  value= 2
					BUS D  value= 3
					DeEmbed 1  value= 4
					DeEmbed 2  value= 5
					DeEmbed 3  value= 6
					DeEmbed 4  value= 7
					DeEmbed 5  value= 8
					DeEmbed 6  value= 9
					DeEmbed 7  value= 10
					DeEmbed 8  value= 11
					Test tone  value= 12
					Silence  value= 13  "
		::= { iqdmx01CmdEntry 2951 }


	iqdmx01AudioAESOutputAES2Source OBJECT-TYPE
		SYNTAX		INTEGER {
							val_BUS_A(0),
							val_BUS_B(1),
							val_BUS_C(2),
							val_BUS_D(3),
							val_DeEmbed_1(4),
							val_DeEmbed_2(5),
							val_DeEmbed_3(6),
							val_DeEmbed_4(7),
							val_DeEmbed_5(8),
							val_DeEmbed_6(9),
							val_DeEmbed_7(10),
							val_DeEmbed_8(11),
							val_Test_tone(12),
							val_Silence(13)
							}
		MAX-ACCESS		read-write
		STATUS			current
		DESCRIPTION
				"TYPE: - RadiobuttonList
				 PAGE: - Audio- AES Output
					AES 2 Source  cmdID= 2952
					BUS A  value= 0
					BUS B  value= 1
					BUS C  value= 2
					BUS D  value= 3
					DeEmbed 1  value= 4
					DeEmbed 2  value= 5
					DeEmbed 3  value= 6
					DeEmbed 4  value= 7
					DeEmbed 5  value= 8
					DeEmbed 6  value= 9
					DeEmbed 7  value= 10
					DeEmbed 8  value= 11
					Test tone  value= 12
					Silence  value= 13  "
		::= { iqdmx01CmdEntry 2952 }


	iqdmx01AudioProcAmpStereo1 OBJECT-TYPE
		SYNTAX		INTEGER { disable(0), enable(1) }
		MAX-ACCESS		read-write
		STATUS			current
		DESCRIPTION
				"TYPE: - Checkbox
				 PAGE: - Audio- ProcAmp
					Stereo 1  cmdID= 3324 "
		::= { iqdmx01CmdEntry 3324 }


	iqdmx01ProcAmpDeembed1LGainDeembed1L OBJECT-TYPE
		SYNTAX		INTEGER
		MAX-ACCESS		read-write
		STATUS			current
		DESCRIPTION
				"TYPE: - Number
				 PAGE: - Audio- ProcAmp
					Gain De-embed 1L  cmdID= 3088  min= -180  max= 180  step= 1  format= %0.1fdB  div_scale= 10
					Min = -18.0dB  Max = 18.0dB  Step = 0.1dB "
		::= { iqdmx01CmdEntry 3088 }


	iqdmx01ProcAmpDeembed1LInvert OBJECT-TYPE
		SYNTAX		INTEGER { disable(0), enable(1) }
		MAX-ACCESS		read-write
		STATUS			current
		DESCRIPTION
				"TYPE: - Checkbox
				 PAGE: - Audio- ProcAmp
					Invert  cmdID= 3168 "
		::= { iqdmx01CmdEntry 3168 }


	iqdmx01ProcAmpDeembed1LMute OBJECT-TYPE
		SYNTAX		INTEGER { disable(0), enable(1) }
		MAX-ACCESS		read-write
		STATUS			current
		DESCRIPTION
				"TYPE: - Checkbox
				 PAGE: - Audio- ProcAmp
					Mute  cmdID= 3248 "
		::= { iqdmx01CmdEntry 3248 }


	iqdmx01ProcAmpDeembed1RGainDeembed1R OBJECT-TYPE
		SYNTAX		INTEGER
		MAX-ACCESS		read-write
		STATUS			current
		DESCRIPTION
				"TYPE: - Number
				 PAGE: - Audio- ProcAmp
					Gain De-embed 1R  cmdID= 3089  min= -180  max= 180  step= 1  format= %0.1fdB  div_scale= 10
					Min = -18.0dB  Max = 18.0dB  Step = 0.1dB "
		::= { iqdmx01CmdEntry 3089 }


	iqdmx01ProcAmpDeembed1RInvert OBJECT-TYPE
		SYNTAX		INTEGER { disable(0), enable(1) }
		MAX-ACCESS		read-write
		STATUS			current
		DESCRIPTION
				"TYPE: - Checkbox
				 PAGE: - Audio- ProcAmp
					Invert  cmdID= 3169 "
		::= { iqdmx01CmdEntry 3169 }


	iqdmx01ProcAmpDeembed1RMute OBJECT-TYPE
		SYNTAX		INTEGER { disable(0), enable(1) }
		MAX-ACCESS		read-write
		STATUS			current
		DESCRIPTION
				"TYPE: - Checkbox
				 PAGE: - Audio- ProcAmp
					Mute  cmdID= 3249 "
		::= { iqdmx01CmdEntry 3249 }


	iqdmx01AudioProcAmpStereo2 OBJECT-TYPE
		SYNTAX		INTEGER { disable(0), enable(1) }
		MAX-ACCESS		read-write
		STATUS			current
		DESCRIPTION
				"TYPE: - Checkbox
				 PAGE: - Audio- ProcAmp
					Stereo 2  cmdID= 3325 "
		::= { iqdmx01CmdEntry 3325 }


	iqdmx01ProcAmpDeembed2LGainDeembed2L OBJECT-TYPE
		SYNTAX		INTEGER
		MAX-ACCESS		read-write
		STATUS			current
		DESCRIPTION
				"TYPE: - Number
				 PAGE: - Audio- ProcAmp
					Gain De-embed 2L  cmdID= 3090  min= -180  max= 180  step= 1  format= %0.1fdB  div_scale= 10
					Min = -18.0dB  Max = 18.0dB  Step = 0.1dB "
		::= { iqdmx01CmdEntry 3090 }


	iqdmx01ProcAmpDeembed2LInvert OBJECT-TYPE
		SYNTAX		INTEGER { disable(0), enable(1) }
		MAX-ACCESS		read-write
		STATUS			current
		DESCRIPTION
				"TYPE: - Checkbox
				 PAGE: - Audio- ProcAmp
					Invert  cmdID= 3170 "
		::= { iqdmx01CmdEntry 3170 }


	iqdmx01ProcAmpDeembed2LMute OBJECT-TYPE
		SYNTAX		INTEGER { disable(0), enable(1) }
		MAX-ACCESS		read-write
		STATUS			current
		DESCRIPTION
				"TYPE: - Checkbox
				 PAGE: - Audio- ProcAmp
					Mute  cmdID= 3250 "
		::= { iqdmx01CmdEntry 3250 }


	iqdmx01ProcAmpDeembed2RGainDeembed2R OBJECT-TYPE
		SYNTAX		INTEGER
		MAX-ACCESS		read-write
		STATUS			current
		DESCRIPTION
				"TYPE: - Number
				 PAGE: - Audio- ProcAmp
					Gain De-embed 2R  cmdID= 3091  min= -180  max= 180  step= 1  format= %0.1fdB  div_scale= 10
					Min = -18.0dB  Max = 18.0dB  Step = 0.1dB "
		::= { iqdmx01CmdEntry 3091 }


	iqdmx01ProcAmpDeembed2RInvert OBJECT-TYPE
		SYNTAX		INTEGER { disable(0), enable(1) }
		MAX-ACCESS		read-write
		STATUS			current
		DESCRIPTION
				"TYPE: - Checkbox
				 PAGE: - Audio- ProcAmp
					Invert  cmdID= 3171 "
		::= { iqdmx01CmdEntry 3171 }


	iqdmx01ProcAmpDeembed2RMute OBJECT-TYPE
		SYNTAX		INTEGER { disable(0), enable(1) }
		MAX-ACCESS		read-write
		STATUS			current
		DESCRIPTION
				"TYPE: - Checkbox
				 PAGE: - Audio- ProcAmp
					Mute  cmdID= 3251 "
		::= { iqdmx01CmdEntry 3251 }


	iqdmx01AudioProcAmpStereo3 OBJECT-TYPE
		SYNTAX		INTEGER { disable(0), enable(1) }
		MAX-ACCESS		read-write
		STATUS			current
		DESCRIPTION
				"TYPE: - Checkbox
				 PAGE: - Audio- ProcAmp
					Stereo 3  cmdID= 3326 "
		::= { iqdmx01CmdEntry 3326 }


	iqdmx01ProcAmpDeembed3LGainDeembed3L OBJECT-TYPE
		SYNTAX		INTEGER
		MAX-ACCESS		read-write
		STATUS			current
		DESCRIPTION
				"TYPE: - Number
				 PAGE: - Audio- ProcAmp
					Gain De-embed 3L  cmdID= 3092  min= -180  max= 180  step= 1  format= %0.1fdB  div_scale= 10
					Min = -18.0dB  Max = 18.0dB  Step = 0.1dB "
		::= { iqdmx01CmdEntry 3092 }


	iqdmx01ProcAmpDeembed3LInvert OBJECT-TYPE
		SYNTAX		INTEGER { disable(0), enable(1) }
		MAX-ACCESS		read-write
		STATUS			current
		DESCRIPTION
				"TYPE: - Checkbox
				 PAGE: - Audio- ProcAmp
					Invert  cmdID= 3172 "
		::= { iqdmx01CmdEntry 3172 }


	iqdmx01ProcAmpDeembed3LMute OBJECT-TYPE
		SYNTAX		INTEGER { disable(0), enable(1) }
		MAX-ACCESS		read-write
		STATUS			current
		DESCRIPTION
				"TYPE: - Checkbox
				 PAGE: - Audio- ProcAmp
					Mute  cmdID= 3252 "
		::= { iqdmx01CmdEntry 3252 }


	iqdmx01ProcAmpDeembed3RGainDeembed3R OBJECT-TYPE
		SYNTAX		INTEGER
		MAX-ACCESS		read-write
		STATUS			current
		DESCRIPTION
				"TYPE: - Number
				 PAGE: - Audio- ProcAmp
					Gain De-embed 3R  cmdID= 3093  min= -180  max= 180  step= 1  format= %0.1fdB  div_scale= 10
					Min = -18.0dB  Max = 18.0dB  Step = 0.1dB "
		::= { iqdmx01CmdEntry 3093 }


	iqdmx01ProcAmpDeembed3RInvert OBJECT-TYPE
		SYNTAX		INTEGER { disable(0), enable(1) }
		MAX-ACCESS		read-write
		STATUS			current
		DESCRIPTION
				"TYPE: - Checkbox
				 PAGE: - Audio- ProcAmp
					Invert  cmdID= 3173 "
		::= { iqdmx01CmdEntry 3173 }


	iqdmx01ProcAmpDeembed3RMute OBJECT-TYPE
		SYNTAX		INTEGER { disable(0), enable(1) }
		MAX-ACCESS		read-write
		STATUS			current
		DESCRIPTION
				"TYPE: - Checkbox
				 PAGE: - Audio- ProcAmp
					Mute  cmdID= 3253 "
		::= { iqdmx01CmdEntry 3253 }


	iqdmx01AudioProcAmpStereo4 OBJECT-TYPE
		SYNTAX		INTEGER { disable(0), enable(1) }
		MAX-ACCESS		read-write
		STATUS			current
		DESCRIPTION
				"TYPE: - Checkbox
				 PAGE: - Audio- ProcAmp
					Stereo 4  cmdID= 3327 "
		::= { iqdmx01CmdEntry 3327 }


	iqdmx01ProcAmpDeembed4LGainDeembed4L OBJECT-TYPE
		SYNTAX		INTEGER
		MAX-ACCESS		read-write
		STATUS			current
		DESCRIPTION
				"TYPE: - Number
				 PAGE: - Audio- ProcAmp
					Gain De-embed 4L  cmdID= 3094  min= -180  max= 180  step= 1  format= %0.1fdB  div_scale= 10
					Min = -18.0dB  Max = 18.0dB  Step = 0.1dB "
		::= { iqdmx01CmdEntry 3094 }


	iqdmx01ProcAmpDeembed4LInvert OBJECT-TYPE
		SYNTAX		INTEGER { disable(0), enable(1) }
		MAX-ACCESS		read-write
		STATUS			current
		DESCRIPTION
				"TYPE: - Checkbox
				 PAGE: - Audio- ProcAmp
					Invert  cmdID= 3174 "
		::= { iqdmx01CmdEntry 3174 }


	iqdmx01ProcAmpDeembed4LMute OBJECT-TYPE
		SYNTAX		INTEGER { disable(0), enable(1) }
		MAX-ACCESS		read-write
		STATUS			current
		DESCRIPTION
				"TYPE: - Checkbox
				 PAGE: - Audio- ProcAmp
					Mute  cmdID= 3254 "
		::= { iqdmx01CmdEntry 3254 }


	iqdmx01ProcAmpDeembed4RGainDeembed4R OBJECT-TYPE
		SYNTAX		INTEGER
		MAX-ACCESS		read-write
		STATUS			current
		DESCRIPTION
				"TYPE: - Number
				 PAGE: - Audio- ProcAmp
					Gain De-embed 4R  cmdID= 3095  min= -180  max= 180  step= 1  format= %0.1fdB  div_scale= 10
					Min = -18.0dB  Max = 18.0dB  Step = 0.1dB "
		::= { iqdmx01CmdEntry 3095 }


	iqdmx01ProcAmpDeembed4RInvert OBJECT-TYPE
		SYNTAX		INTEGER { disable(0), enable(1) }
		MAX-ACCESS		read-write
		STATUS			current
		DESCRIPTION
				"TYPE: - Checkbox
				 PAGE: - Audio- ProcAmp
					Invert  cmdID= 3175 "
		::= { iqdmx01CmdEntry 3175 }


	iqdmx01ProcAmpDeembed4RMute OBJECT-TYPE
		SYNTAX		INTEGER { disable(0), enable(1) }
		MAX-ACCESS		read-write
		STATUS			current
		DESCRIPTION
				"TYPE: - Checkbox
				 PAGE: - Audio- ProcAmp
					Mute  cmdID= 3255 "
		::= { iqdmx01CmdEntry 3255 }


	iqdmx01AudioProcAmpStereo5 OBJECT-TYPE
		SYNTAX		INTEGER { disable(0), enable(1) }
		MAX-ACCESS		read-write
		STATUS			current
		DESCRIPTION
				"TYPE: - Checkbox
				 PAGE: - Audio- ProcAmp
					Stereo 5  cmdID= 3328 "
		::= { iqdmx01CmdEntry 3328 }


	iqdmx01ProcAmpDeembed5LGainDeembed5L OBJECT-TYPE
		SYNTAX		INTEGER
		MAX-ACCESS		read-write
		STATUS			current
		DESCRIPTION
				"TYPE: - Number
				 PAGE: - Audio- ProcAmp
					Gain De-embed 5L  cmdID= 3096  min= -180  max= 180  step= 1  format= %0.1fdB  div_scale= 10
					Min = -18.0dB  Max = 18.0dB  Step = 0.1dB "
		::= { iqdmx01CmdEntry 3096 }


	iqdmx01ProcAmpDeembed5LInvert OBJECT-TYPE
		SYNTAX		INTEGER { disable(0), enable(1) }
		MAX-ACCESS		read-write
		STATUS			current
		DESCRIPTION
				"TYPE: - Checkbox
				 PAGE: - Audio- ProcAmp
					Invert  cmdID= 3176 "
		::= { iqdmx01CmdEntry 3176 }


	iqdmx01ProcAmpDeembed5LMute OBJECT-TYPE
		SYNTAX		INTEGER { disable(0), enable(1) }
		MAX-ACCESS		read-write
		STATUS			current
		DESCRIPTION
				"TYPE: - Checkbox
				 PAGE: - Audio- ProcAmp
					Mute  cmdID= 3256 "
		::= { iqdmx01CmdEntry 3256 }


	iqdmx01ProcAmpDeembed5RGainDeembed5R OBJECT-TYPE
		SYNTAX		INTEGER
		MAX-ACCESS		read-write
		STATUS			current
		DESCRIPTION
				"TYPE: - Number
				 PAGE: - Audio- ProcAmp
					Gain De-embed 5R  cmdID= 3097  min= -180  max= 180  step= 1  format= %0.1fdB  div_scale= 10
					Min = -18.0dB  Max = 18.0dB  Step = 0.1dB "
		::= { iqdmx01CmdEntry 3097 }


	iqdmx01ProcAmpDeembed5RInvert OBJECT-TYPE
		SYNTAX		INTEGER { disable(0), enable(1) }
		MAX-ACCESS		read-write
		STATUS			current
		DESCRIPTION
				"TYPE: - Checkbox
				 PAGE: - Audio- ProcAmp
					Invert  cmdID= 3177 "
		::= { iqdmx01CmdEntry 3177 }


	iqdmx01ProcAmpDeembed5RMute OBJECT-TYPE
		SYNTAX		INTEGER { disable(0), enable(1) }
		MAX-ACCESS		read-write
		STATUS			current
		DESCRIPTION
				"TYPE: - Checkbox
				 PAGE: - Audio- ProcAmp
					Mute  cmdID= 3257 "
		::= { iqdmx01CmdEntry 3257 }


	iqdmx01AudioProcAmpStereo6 OBJECT-TYPE
		SYNTAX		INTEGER { disable(0), enable(1) }
		MAX-ACCESS		read-write
		STATUS			current
		DESCRIPTION
				"TYPE: - Checkbox
				 PAGE: - Audio- ProcAmp
					Stereo 6  cmdID= 3329 "
		::= { iqdmx01CmdEntry 3329 }


	iqdmx01ProcAmpDeembed6LGainDeembed6L OBJECT-TYPE
		SYNTAX		INTEGER
		MAX-ACCESS		read-write
		STATUS			current
		DESCRIPTION
				"TYPE: - Number
				 PAGE: - Audio- ProcAmp
					Gain De-embed 6L  cmdID= 3098  min= -180  max= 180  step= 1  format= %0.1fdB  div_scale= 10
					Min = -18.0dB  Max = 18.0dB  Step = 0.1dB "
		::= { iqdmx01CmdEntry 3098 }


	iqdmx01ProcAmpDeembed6LInvert OBJECT-TYPE
		SYNTAX		INTEGER { disable(0), enable(1) }
		MAX-ACCESS		read-write
		STATUS			current
		DESCRIPTION
				"TYPE: - Checkbox
				 PAGE: - Audio- ProcAmp
					Invert  cmdID= 3178 "
		::= { iqdmx01CmdEntry 3178 }


	iqdmx01ProcAmpDeembed6LMute OBJECT-TYPE
		SYNTAX		INTEGER { disable(0), enable(1) }
		MAX-ACCESS		read-write
		STATUS			current
		DESCRIPTION
				"TYPE: - Checkbox
				 PAGE: - Audio- ProcAmp
					Mute  cmdID= 3258 "
		::= { iqdmx01CmdEntry 3258 }


	iqdmx01ProcAmpDeembed6RGainDeembed6R OBJECT-TYPE
		SYNTAX		INTEGER
		MAX-ACCESS		read-write
		STATUS			current
		DESCRIPTION
				"TYPE: - Number
				 PAGE: - Audio- ProcAmp
					Gain De-embed 6R  cmdID= 3099  min= -180  max= 180  step= 1  format= %0.1fdB  div_scale= 10
					Min = -18.0dB  Max = 18.0dB  Step = 0.1dB "
		::= { iqdmx01CmdEntry 3099 }


	iqdmx01ProcAmpDeembed6RInvert OBJECT-TYPE
		SYNTAX		INTEGER { disable(0), enable(1) }
		MAX-ACCESS		read-write
		STATUS			current
		DESCRIPTION
				"TYPE: - Checkbox
				 PAGE: - Audio- ProcAmp
					Invert  cmdID= 3179 "
		::= { iqdmx01CmdEntry 3179 }


	iqdmx01ProcAmpDeembed6RMute OBJECT-TYPE
		SYNTAX		INTEGER { disable(0), enable(1) }
		MAX-ACCESS		read-write
		STATUS			current
		DESCRIPTION
				"TYPE: - Checkbox
				 PAGE: - Audio- ProcAmp
					Mute  cmdID= 3259 "
		::= { iqdmx01CmdEntry 3259 }


	iqdmx01AudioProcAmpStereo7 OBJECT-TYPE
		SYNTAX		INTEGER { disable(0), enable(1) }
		MAX-ACCESS		read-write
		STATUS			current
		DESCRIPTION
				"TYPE: - Checkbox
				 PAGE: - Audio- ProcAmp
					Stereo 7  cmdID= 3330 "
		::= { iqdmx01CmdEntry 3330 }


	iqdmx01ProcAmpDeembed7LGainDeembed7L OBJECT-TYPE
		SYNTAX		INTEGER
		MAX-ACCESS		read-write
		STATUS			current
		DESCRIPTION
				"TYPE: - Number
				 PAGE: - Audio- ProcAmp
					Gain De-embed 7L  cmdID= 3100  min= -180  max= 180  step= 1  format= %0.1fdB  div_scale= 10
					Min = -18.0dB  Max = 18.0dB  Step = 0.1dB "
		::= { iqdmx01CmdEntry 3100 }


	iqdmx01ProcAmpDeembed7LInvert OBJECT-TYPE
		SYNTAX		INTEGER { disable(0), enable(1) }
		MAX-ACCESS		read-write
		STATUS			current
		DESCRIPTION
				"TYPE: - Checkbox
				 PAGE: - Audio- ProcAmp
					Invert  cmdID= 3180 "
		::= { iqdmx01CmdEntry 3180 }


	iqdmx01ProcAmpDeembed7LMute OBJECT-TYPE
		SYNTAX		INTEGER { disable(0), enable(1) }
		MAX-ACCESS		read-write
		STATUS			current
		DESCRIPTION
				"TYPE: - Checkbox
				 PAGE: - Audio- ProcAmp
					Mute  cmdID= 3260 "
		::= { iqdmx01CmdEntry 3260 }


	iqdmx01ProcAmpDeembed7RGainDeembed7R OBJECT-TYPE
		SYNTAX		INTEGER
		MAX-ACCESS		read-write
		STATUS			current
		DESCRIPTION
				"TYPE: - Number
				 PAGE: - Audio- ProcAmp
					Gain De-embed 7R  cmdID= 3101  min= -180  max= 180  step= 1  format= %0.1fdB  div_scale= 10
					Min = -18.0dB  Max = 18.0dB  Step = 0.1dB "
		::= { iqdmx01CmdEntry 3101 }


	iqdmx01ProcAmpDeembed7RInvert OBJECT-TYPE
		SYNTAX		INTEGER { disable(0), enable(1) }
		MAX-ACCESS		read-write
		STATUS			current
		DESCRIPTION
				"TYPE: - Checkbox
				 PAGE: - Audio- ProcAmp
					Invert  cmdID= 3181 "
		::= { iqdmx01CmdEntry 3181 }


	iqdmx01ProcAmpDeembed7RMute OBJECT-TYPE
		SYNTAX		INTEGER { disable(0), enable(1) }
		MAX-ACCESS		read-write
		STATUS			current
		DESCRIPTION
				"TYPE: - Checkbox
				 PAGE: - Audio- ProcAmp
					Mute  cmdID= 3261 "
		::= { iqdmx01CmdEntry 3261 }


	iqdmx01AudioProcAmpStereo8 OBJECT-TYPE
		SYNTAX		INTEGER { disable(0), enable(1) }
		MAX-ACCESS		read-write
		STATUS			current
		DESCRIPTION
				"TYPE: - Checkbox
				 PAGE: - Audio- ProcAmp
					Stereo 8  cmdID= 3331 "
		::= { iqdmx01CmdEntry 3331 }


	iqdmx01ProcAmpDeembed8LGainDeembed8L OBJECT-TYPE
		SYNTAX		INTEGER
		MAX-ACCESS		read-write
		STATUS			current
		DESCRIPTION
				"TYPE: - Number
				 PAGE: - Audio- ProcAmp
					Gain De-embed 8L  cmdID= 3102  min= -180  max= 180  step= 1  format= %0.1fdB  div_scale= 10
					Min = -18.0dB  Max = 18.0dB  Step = 0.1dB "
		::= { iqdmx01CmdEntry 3102 }


	iqdmx01ProcAmpDeembed8LInvert OBJECT-TYPE
		SYNTAX		INTEGER { disable(0), enable(1) }
		MAX-ACCESS		read-write
		STATUS			current
		DESCRIPTION
				"TYPE: - Checkbox
				 PAGE: - Audio- ProcAmp
					Invert  cmdID= 3182 "
		::= { iqdmx01CmdEntry 3182 }


	iqdmx01ProcAmpDeembed8LMute OBJECT-TYPE
		SYNTAX		INTEGER { disable(0), enable(1) }
		MAX-ACCESS		read-write
		STATUS			current
		DESCRIPTION
				"TYPE: - Checkbox
				 PAGE: - Audio- ProcAmp
					Mute  cmdID= 3262 "
		::= { iqdmx01CmdEntry 3262 }


	iqdmx01ProcAmpDeembed8RGainDeembed8R OBJECT-TYPE
		SYNTAX		INTEGER
		MAX-ACCESS		read-write
		STATUS			current
		DESCRIPTION
				"TYPE: - Number
				 PAGE: - Audio- ProcAmp
					Gain De-embed 8R  cmdID= 3103  min= -180  max= 180  step= 1  format= %0.1fdB  div_scale= 10
					Min = -18.0dB  Max = 18.0dB  Step = 0.1dB "
		::= { iqdmx01CmdEntry 3103 }


	iqdmx01ProcAmpDeembed8RInvert OBJECT-TYPE
		SYNTAX		INTEGER { disable(0), enable(1) }
		MAX-ACCESS		read-write
		STATUS			current
		DESCRIPTION
				"TYPE: - Checkbox
				 PAGE: - Audio- ProcAmp
					Invert  cmdID= 3183 "
		::= { iqdmx01CmdEntry 3183 }


	iqdmx01ProcAmpDeembed8RMute OBJECT-TYPE
		SYNTAX		INTEGER { disable(0), enable(1) }
		MAX-ACCESS		read-write
		STATUS			current
		DESCRIPTION
				"TYPE: - Checkbox
				 PAGE: - Audio- ProcAmp
					Mute  cmdID= 3263 "
		::= { iqdmx01CmdEntry 3263 }


	iqdmx01EmbedEmbedder1Embed1Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 1
					Embed 1 Source  cmdID= 2941
					BUS A  value= 0
					BUS B  value= 1
					BUS C  value= 2
					BUS D  value= 3
					Test tone  value= 4
					Silence  value= 5  "
		::= { iqdmx01CmdEntry 2941 }


	iqdmx01EmbedEmbedder1PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 1
					Pair Selection  cmdID= 2531
					Select Pair 1  value= 0
					Select Pair 2  value= 1
					Select Pair 3  value= 2
					Select Pair 4  value= 3
					Select Pair 5  value= 4
					Select Pair 6  value= 5
					Select Pair 7  value= 6
					Select Pair 8  value= 7  "
		::= { iqdmx01CmdEntry 2531 }


	iqdmx01EmbedEmbedder1Disable OBJECT-TYPE
		SYNTAX		INTEGER { disable(0), enable(1) }
		MAX-ACCESS		read-write
		STATUS			current
		DESCRIPTION
				"TYPE: - Checkbox
				 PAGE: - Audio- Embed- Embedder 1
					Disable  cmdID= 2541 "
		::= { iqdmx01CmdEntry 2541 }


	iqdmx01EmbedEmbedder2Embed2Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 2
					Embed 2 Source  cmdID= 2942
					BUS A  value= 0
					BUS B  value= 1
					BUS C  value= 2
					BUS D  value= 3
					Test tone  value= 4
					Silence  value= 5  "
		::= { iqdmx01CmdEntry 2942 }


	iqdmx01EmbedEmbedder2PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 2
					Pair Selection  cmdID= 2532
					Select Pair 1  value= 0
					Select Pair 2  value= 1
					Select Pair 3  value= 2
					Select Pair 4  value= 3
					Select Pair 5  value= 4
					Select Pair 6  value= 5
					Select Pair 7  value= 6
					Select Pair 8  value= 7  "
		::= { iqdmx01CmdEntry 2532 }


	iqdmx01EmbedEmbedder2Disable OBJECT-TYPE
		SYNTAX		INTEGER { disable(0), enable(1) }
		MAX-ACCESS		read-write
		STATUS			current
		DESCRIPTION
				"TYPE: - Checkbox
				 PAGE: - Audio- Embed- Embedder 2
					Disable  cmdID= 2542 "
		::= { iqdmx01CmdEntry 2542 }


	iqdmx01EmbedEmbedder3Embed3Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 3
					Embed 3 Source  cmdID= 2943
					BUS A  value= 0
					BUS B  value= 1
					BUS C  value= 2
					BUS D  value= 3
					Test tone  value= 4
					Silence  value= 5  "
		::= { iqdmx01CmdEntry 2943 }


	iqdmx01EmbedEmbedder3PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 3
					Pair Selection  cmdID= 2533
					Select Pair 1  value= 0
					Select Pair 2  value= 1
					Select Pair 3  value= 2
					Select Pair 4  value= 3
					Select Pair 5  value= 4
					Select Pair 6  value= 5
					Select Pair 7  value= 6
					Select Pair 8  value= 7  "
		::= { iqdmx01CmdEntry 2533 }


	iqdmx01EmbedEmbedder3Disable OBJECT-TYPE
		SYNTAX		INTEGER { disable(0), enable(1) }
		MAX-ACCESS		read-write
		STATUS			current
		DESCRIPTION
				"TYPE: - Checkbox
				 PAGE: - Audio- Embed- Embedder 3
					Disable  cmdID= 2543 "
		::= { iqdmx01CmdEntry 2543 }


	iqdmx01EmbedEmbedder4Embed4Source OBJECT-TYPE
		SYNTAX		INTEGER {
							val_BUS_A(0),
							val_BUS_B(1),
							val_BUS_C(2),
							val_BUS_D(3),
							val_Test_tone(4),
							val_Silence(5)
							}
		MAX-ACCESS		read-write
		STATUS			current
		DESCRIPTION
				"TYPE: - RadiobuttonList
				 PAGE: - Audio- Embed- Embedder 4
					Embed 4 Source  cmdID= 2944
					BUS A  value= 0
					BUS B  value= 1
					BUS C  value= 2
					BUS D  value= 3
					Test tone  value= 4
					Silence  value= 5  "
		::= { iqdmx01CmdEntry 2944 }


	iqdmx01EmbedEmbedder4PairSelection OBJECT-TYPE
		SYNTAX		INTEGER {
							val_Select_Pair_1(0),
							val_Select_Pair_2(1),
							val_Select_Pair_3(2),
							val_Select_Pair_4(3),
							val_Select_Pair_5(4),
							val_Select_Pair_6(5),
							val_Select_Pair_7(6),
							val_Select_Pair_8(7)
							}
		MAX-ACCESS		read-write
		STATUS			current
		DESCRIPTION
				"TYPE: - RadiobuttonList
				 PAGE: - Audio- Embed- Embedder 4
					Pair Selection  cmdID= 2534
					Select Pair 1  value= 0
					Select Pair 2  value= 1
					Select Pair 3  value= 2
					Select Pair 4  value= 3
					Select Pair 5  value= 4
					Select Pair 6  value= 5
					Select Pair 7  value= 6
					Select Pair 8  value= 7  "
		::= { iqdmx01CmdEntry 2534 }


	iqdmx01EmbedEmbedder4Disable OBJECT-TYPE
		SYNTAX		INTEGER { disable(0), enable(1) }
		MAX-ACCESS		read-write
		STATUS			current
		DESCRIPTION
				"TYPE: - Checkbox
				 PAGE: - Audio- Embed- Embedder 4
					Disable  cmdID= 2544 "
		::= { iqdmx01CmdEntry 2544 }


	iqdmx01Mixer1Mix1Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source1
					Mix1 Source1  cmdID= 3440
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3440 }


	iqdmx01MixMixer1Gain1 OBJECT-TYPE
		SYNTAX		INTEGER
		MAX-ACCESS		read-write
		STATUS			current
		DESCRIPTION
				"TYPE: - Number
				 PAGE: - Audio- Mix- Mixer 1
					Gain1  cmdID= 3360  min= -71  max= 0  step= 1  format= %0.0fdB  div_scale= 1
					Min = -71dB  Max = 0dB  Step = 1dB "
		::= { iqdmx01CmdEntry 3360 }


	iqdmx01Mixer1Mix1Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source2
					Mix1 Source2  cmdID= 3441
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3441 }


	iqdmx01MixMixer1Gain2 OBJECT-TYPE
		SYNTAX		INTEGER
		MAX-ACCESS		read-write
		STATUS			current
		DESCRIPTION
				"TYPE: - Number
				 PAGE: - Audio- Mix- Mixer 1
					Gain2  cmdID= 3361  min= -71  max= 0  step= 1  format= %0.0fdB  div_scale= 1
					Min = -71dB  Max = 0dB  Step = 1dB "
		::= { iqdmx01CmdEntry 3361 }


	iqdmx01Mixer1Mix1Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source3
					Mix1 Source3  cmdID= 3442
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3442 }


	iqdmx01MixMixer1Gain3 OBJECT-TYPE
		SYNTAX		INTEGER
		MAX-ACCESS		read-write
		STATUS			current
		DESCRIPTION
				"TYPE: - Number
				 PAGE: - Audio- Mix- Mixer 1
					Gain3  cmdID= 3362  min= -71  max= 0  step= 1  format= %0.0fdB  div_scale= 1
					Min = -71dB  Max = 0dB  Step = 1dB "
		::= { iqdmx01CmdEntry 3362 }


	iqdmx01Mixer1Mix1Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 1- Mix1 Source4
					Mix1 Source4  cmdID= 3443
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3443 }


	iqdmx01MixMixer1Gain4 OBJECT-TYPE
		SYNTAX		INTEGER
		MAX-ACCESS		read-write
		STATUS			current
		DESCRIPTION
				"TYPE: - Number
				 PAGE: - Audio- Mix- Mixer 1
					Gain4  cmdID= 3363  min= -71  max= 0  step= 1  format= %0.0fdB  div_scale= 1
					Min = -71dB  Max = 0dB  Step = 1dB "
		::= { iqdmx01CmdEntry 3363 }


	iqdmx01Mixer2Mix2Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source1
					Mix2 Source1  cmdID= 3444
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3444 }


	iqdmx01MixMixer2Gain1 OBJECT-TYPE
		SYNTAX		INTEGER
		MAX-ACCESS		read-write
		STATUS			current
		DESCRIPTION
				"TYPE: - Number
				 PAGE: - Audio- Mix- Mixer 2
					Gain1  cmdID= 3364  min= -71  max= 0  step= 1  format= %0.0fdB  div_scale= 1
					Min = -71dB  Max = 0dB  Step = 1dB "
		::= { iqdmx01CmdEntry 3364 }


	iqdmx01Mixer2Mix2Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source2
					Mix2 Source2  cmdID= 3445
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3445 }


	iqdmx01MixMixer2Gain2 OBJECT-TYPE
		SYNTAX		INTEGER
		MAX-ACCESS		read-write
		STATUS			current
		DESCRIPTION
				"TYPE: - Number
				 PAGE: - Audio- Mix- Mixer 2
					Gain2  cmdID= 3365  min= -71  max= 0  step= 1  format= %0.0fdB  div_scale= 1
					Min = -71dB  Max = 0dB  Step = 1dB "
		::= { iqdmx01CmdEntry 3365 }


	iqdmx01Mixer2Mix2Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source3
					Mix2 Source3  cmdID= 3446
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3446 }


	iqdmx01MixMixer2Gain3 OBJECT-TYPE
		SYNTAX		INTEGER
		MAX-ACCESS		read-write
		STATUS			current
		DESCRIPTION
				"TYPE: - Number
				 PAGE: - Audio- Mix- Mixer 2
					Gain3  cmdID= 3366  min= -71  max= 0  step= 1  format= %0.0fdB  div_scale= 1
					Min = -71dB  Max = 0dB  Step = 1dB "
		::= { iqdmx01CmdEntry 3366 }


	iqdmx01Mixer2Mix2Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 2- Mix2 Source4
					Mix2 Source4  cmdID= 3447
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3447 }


	iqdmx01MixMixer2Gain4 OBJECT-TYPE
		SYNTAX		INTEGER
		MAX-ACCESS		read-write
		STATUS			current
		DESCRIPTION
				"TYPE: - Number
				 PAGE: - Audio- Mix- Mixer 2
					Gain4  cmdID= 3367  min= -71  max= 0  step= 1  format= %0.0fdB  div_scale= 1
					Min = -71dB  Max = 0dB  Step = 1dB "
		::= { iqdmx01CmdEntry 3367 }


	iqdmx01Mixer3Mix3Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source1
					Mix3 Source1  cmdID= 3448
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3448 }


	iqdmx01MixMixer3Gain1 OBJECT-TYPE
		SYNTAX		INTEGER
		MAX-ACCESS		read-write
		STATUS			current
		DESCRIPTION
				"TYPE: - Number
				 PAGE: - Audio- Mix- Mixer 3
					Gain1  cmdID= 3368  min= -71  max= 0  step= 1  format= %0.0fdB  div_scale= 1
					Min = -71dB  Max = 0dB  Step = 1dB "
		::= { iqdmx01CmdEntry 3368 }


	iqdmx01Mixer3Mix3Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source2
					Mix3 Source2  cmdID= 3449
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3449 }


	iqdmx01MixMixer3Gain2 OBJECT-TYPE
		SYNTAX		INTEGER
		MAX-ACCESS		read-write
		STATUS			current
		DESCRIPTION
				"TYPE: - Number
				 PAGE: - Audio- Mix- Mixer 3
					Gain2  cmdID= 3369  min= -71  max= 0  step= 1  format= %0.0fdB  div_scale= 1
					Min = -71dB  Max = 0dB  Step = 1dB "
		::= { iqdmx01CmdEntry 3369 }


	iqdmx01Mixer3Mix3Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source3
					Mix3 Source3  cmdID= 3450
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3450 }


	iqdmx01MixMixer3Gain3 OBJECT-TYPE
		SYNTAX		INTEGER
		MAX-ACCESS		read-write
		STATUS			current
		DESCRIPTION
				"TYPE: - Number
				 PAGE: - Audio- Mix- Mixer 3
					Gain3  cmdID= 3370  min= -71  max= 0  step= 1  format= %0.0fdB  div_scale= 1
					Min = -71dB  Max = 0dB  Step = 1dB "
		::= { iqdmx01CmdEntry 3370 }


	iqdmx01Mixer3Mix3Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 3- Mix3 Source4
					Mix3 Source4  cmdID= 3451
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3451 }


	iqdmx01MixMixer3Gain4 OBJECT-TYPE
		SYNTAX		INTEGER
		MAX-ACCESS		read-write
		STATUS			current
		DESCRIPTION
				"TYPE: - Number
				 PAGE: - Audio- Mix- Mixer 3
					Gain4  cmdID= 3371  min= -71  max= 0  step= 1  format= %0.0fdB  div_scale= 1
					Min = -71dB  Max = 0dB  Step = 1dB "
		::= { iqdmx01CmdEntry 3371 }


	iqdmx01Mixer4Mix4Source1 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source1
					Mix4 Source1  cmdID= 3452
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3452 }


	iqdmx01MixMixer4Gain1 OBJECT-TYPE
		SYNTAX		INTEGER
		MAX-ACCESS		read-write
		STATUS			current
		DESCRIPTION
				"TYPE: - Number
				 PAGE: - Audio- Mix- Mixer 4
					Gain1  cmdID= 3372  min= -71  max= 0  step= 1  format= %0.0fdB  div_scale= 1
					Min = -71dB  Max = 0dB  Step = 1dB "
		::= { iqdmx01CmdEntry 3372 }


	iqdmx01Mixer4Mix4Source2 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source2
					Mix4 Source2  cmdID= 3453
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3453 }


	iqdmx01MixMixer4Gain2 OBJECT-TYPE
		SYNTAX		INTEGER
		MAX-ACCESS		read-write
		STATUS			current
		DESCRIPTION
				"TYPE: - Number
				 PAGE: - Audio- Mix- Mixer 4
					Gain2  cmdID= 3373  min= -71  max= 0  step= 1  format= %0.0fdB  div_scale= 1
					Min = -71dB  Max = 0dB  Step = 1dB "
		::= { iqdmx01CmdEntry 3373 }


	iqdmx01Mixer4Mix4Source3 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source3
					Mix4 Source3  cmdID= 3454
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3454 }


	iqdmx01MixMixer4Gain3 OBJECT-TYPE
		SYNTAX		INTEGER
		MAX-ACCESS		read-write
		STATUS			current
		DESCRIPTION
				"TYPE: - Number
				 PAGE: - Audio- Mix- Mixer 4
					Gain3  cmdID= 3374  min= -71  max= 0  step= 1  format= %0.0fdB  div_scale= 1
					Min = -71dB  Max = 0dB  Step = 1dB "
		::= { iqdmx01CmdEntry 3374 }


	iqdmx01Mixer4Mix4Source4 OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15)
							}
		MAX-ACCESS		read-write
		STATUS			current
		DESCRIPTION
				"TYPE: - RadiobuttonList
				 PAGE: - Audio- Mix- Mixer 4- Mix4 Source4
					Mix4 Source4  cmdID= 3455
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15  "
		::= { iqdmx01CmdEntry 3455 }


	iqdmx01MixMixer4Gain4 OBJECT-TYPE
		SYNTAX		INTEGER
		MAX-ACCESS		read-write
		STATUS			current
		DESCRIPTION
				"TYPE: - Number
				 PAGE: - Audio- Mix- Mixer 4
					Gain4  cmdID= 3375  min= -71  max= 0  step= 1  format= %0.0fdB  div_scale= 1
					Min = -71dB  Max = 0dB  Step = 1dB "
		::= { iqdmx01CmdEntry 3375 }


	iqdmx01BusSourceBusALSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusAL Source
					BusAL Source  cmdID= 3520
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3520 }


	iqdmx01BusSourceBusARSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusAR Source
					BusAR Source  cmdID= 3521
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3521 }


	iqdmx01BusSourceBusBLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusBL Source
					BusBL Source  cmdID= 3522
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3522 }


	iqdmx01BusSourceBusBRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusBR Source
					BusBR Source  cmdID= 3523
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3523 }


	iqdmx01BusSourceBusCLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusCL Source
					BusCL Source  cmdID= 3524
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3524 }


	iqdmx01BusSourceBusCRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusCR Source
					BusCR Source  cmdID= 3525
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3525 }


	iqdmx01BusSourceBusDLSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusDL Source
					BusDL Source  cmdID= 3526
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3526 }


	iqdmx01BusSourceBusDRSource OBJECT-TYPE
		SYNTAX		INTEGER {
							val_DeEmbed_1L(0),
							val_DeEmbed_1R(1),
							val_DeEmbed_2L(2),
							val_DeEmbed_2R(3),
							val_DeEmbed_3L(4),
							val_DeEmbed_3R(5),
							val_DeEmbed_4L(6),
							val_DeEmbed_4R(7),
							val_DeEmbed_5L(8),
							val_DeEmbed_5R(9),
							val_DeEmbed_6L(10),
							val_DeEmbed_6R(11),
							val_DeEmbed_7L(12),
							val_DeEmbed_7R(13),
							val_DeEmbed_8L(14),
							val_DeEmbed_8R(15),
							val_MIX_1(16),
							val_MIX_2(17),
							val_MIX_3(18),
							val_MIX_4(19)
							}
		MAX-ACCESS		read-write
		STATUS			current
		DESCRIPTION
				"TYPE: - RadiobuttonList
				 PAGE: - Audio- Buses- Bus Source- BusDR Source
					BusDR Source  cmdID= 3527
					DeEmbed 1L  value= 0
					DeEmbed 1R  value= 1
					DeEmbed 2L  value= 2
					DeEmbed 2R  value= 3
					DeEmbed 3L  value= 4
					DeEmbed 3R  value= 5
					DeEmbed 4L  value= 6
					DeEmbed 4R  value= 7
					DeEmbed 5L  value= 8
					DeEmbed 5R  value= 9
					DeEmbed 6L  value= 10
					DeEmbed 6R  value= 11
					DeEmbed 7L  value= 12
					DeEmbed 7R  value= 13
					DeEmbed 8L  value= 14
					DeEmbed 8R  value= 15
					MIX 1  value= 16
					MIX 2  value= 17
					MIX 3  value= 18
					MIX 4  value= 19  "
		::= { iqdmx01CmdEntry 3527 }


	iqdmx01BusesBusProcAmpStereoA OBJECT-TYPE
		SYNTAX		INTEGER { disable(0), enable(1) }
		MAX-ACCESS		read-write
		STATUS			current
		DESCRIPTION
				"TYPE: - Checkbox
				 PAGE: - Audio- Buses
					Stereo A  cmdID= 3320 "
		::= { iqdmx01CmdEntry 3320 }


	iqdmx01BusProcAmpBusALGainBusAL OBJECT-TYPE
		SYNTAX		INTEGER
		MAX-ACCESS		read-write
		STATUS			current
		DESCRIPTION
				"TYPE: - Number
				 PAGE: - Audio- Buses
					Gain Bus AL  cmdID= 3080  min= -180  max= 180  step= 1  format= %0.1fdB  div_scale= 10
					Min = -18.0dB  Max = 18.0dB  Step = 0.1dB "
		::= { iqdmx01CmdEntry 3080 }


	iqdmx01BusProcAmpBusALInvert OBJECT-TYPE
		SYNTAX		INTEGER { disable(0), enable(1) }
		MAX-ACCESS		read-write
		STATUS			current
		DESCRIPTION
				"TYPE: - Checkbox
				 PAGE: - Audio- Buses
					Invert  cmdID= 3160 "
		::= { iqdmx01CmdEntry 3160 }


	iqdmx01BusProcAmpBusALMute OBJECT-TYPE
		SYNTAX		INTEGER { disable(0), enable(1) }
		MAX-ACCESS		read-write
		STATUS			current
		DESCRIPTION
				"TYPE: - Checkbox
				 PAGE: - Audio- Buses
					Mute  cmdID= 3240 "
		::= { iqdmx01CmdEntry 3240 }


	iqdmx01BusProcAmpBusARGainBusAR OBJECT-TYPE
		SYNTAX		INTEGER
		MAX-ACCESS		read-write
		STATUS			current
		DESCRIPTION
				"TYPE: - Number
				 PAGE: - Audio- Buses
					Gain Bus AR  cmdID= 3081  min= -180  max= 180  step= 1  format= %0.1fdB  div_scale= 10
					Min = -18.0dB  Max = 18.0dB  Step = 0.1dB "
		::= { iqdmx01CmdEntry 3081 }


	iqdmx01BusProcAmpBusARInvert OBJECT-TYPE
		SYNTAX		INTEGER { disable(0), enable(1) }
		MAX-ACCESS		read-write
		STATUS			current
		DESCRIPTION
				"TYPE: - Checkbox
				 PAGE: - Audio- Buses
					Invert  cmdID= 3161 "
		::= { iqdmx01CmdEntry 3161 }


	iqdmx01BusProcAmpBusARMute OBJECT-TYPE
		SYNTAX		INTEGER { disable(0), enable(1) }
		MAX-ACCESS		read-write
		STATUS			current
		DESCRIPTION
				"TYPE: - Checkbox
				 PAGE: - Audio- Buses
					Mute  cmdID= 3241 "
		::= { iqdmx01CmdEntry 3241 }


	iqdmx01BusesBusProcAmpStereoB OBJECT-TYPE
		SYNTAX		INTEGER { disable(0), enable(1) }
		MAX-ACCESS		read-write
		STATUS			current
		DESCRIPTION
				"TYPE: - Checkbox
				 PAGE: - Audio- Buses
					Stereo B  cmdID= 3321 "
		::= { iqdmx01CmdEntry 3321 }


	iqdmx01BusProcAmpBusBLGainBusBL OBJECT-TYPE
		SYNTAX		INTEGER
		MAX-ACCESS		read-write
		STATUS			current
		DESCRIPTION
				"TYPE: - Number
				 PAGE: - Audio- Buses
					Gain Bus BL  cmdID= 3082  min= -180  max= 180  step= 1  format= %0.1fdB  div_scale= 10
					Min = -18.0dB  Max = 18.0dB  Step = 0.1dB "
		::= { iqdmx01CmdEntry 3082 }


	iqdmx01BusProcAmpBusBLInvert OBJECT-TYPE
		SYNTAX		INTEGER { disable(0), enable(1) }
		MAX-ACCESS		read-write
		STATUS			current
		DESCRIPTION
				"TYPE: - Checkbox
				 PAGE: - Audio- Buses
					Invert  cmdID= 3162 "
		::= { iqdmx01CmdEntry 3162 }


	iqdmx01BusProcAmpBusBLMute OBJECT-TYPE
		SYNTAX		INTEGER { disable(0), enable(1) }
		MAX-ACCESS		read-write
		STATUS			current
		DESCRIPTION
				"TYPE: - Checkbox
				 PAGE: - Audio- Buses
					Mute  cmdID= 3242 "
		::= { iqdmx01CmdEntry 3242 }


	iqdmx01BusProcAmpBusBRGainBusBR OBJECT-TYPE
		SYNTAX		INTEGER
		MAX-ACCESS		read-write
		STATUS			current
		DESCRIPTION
				"TYPE: - Number
				 PAGE: - Audio- Buses
					Gain Bus BR  cmdID= 3083  min= -180  max= 180  step= 1  format= %0.1fdB  div_scale= 10
					Min = -18.0dB  Max = 18.0dB  Step = 0.1dB "
		::= { iqdmx01CmdEntry 3083 }


	iqdmx01BusProcAmpBusBRInvert OBJECT-TYPE
		SYNTAX		INTEGER { disable(0), enable(1) }
		MAX-ACCESS		read-write
		STATUS			current
		DESCRIPTION
				"TYPE: - Checkbox
				 PAGE: - Audio- Buses
					Invert  cmdID= 3163 "
		::= { iqdmx01CmdEntry 3163 }


	iqdmx01BusProcAmpBusBRMute OBJECT-TYPE
		SYNTAX		INTEGER { disable(0), enable(1) }
		MAX-ACCESS		read-write
		STATUS			current
		DESCRIPTION
				"TYPE: - Checkbox
				 PAGE: - Audio- Buses
					Mute  cmdID= 3243 "
		::= { iqdmx01CmdEntry 3243 }


	iqdmx01BusesBusProcAmpStereoC OBJECT-TYPE
		SYNTAX		INTEGER { disable(0), enable(1) }
		MAX-ACCESS		read-write
		STATUS			current
		DESCRIPTION
				"TYPE: - Checkbox
				 PAGE: - Audio- Buses
					Stereo C  cmdID= 3322 "
		::= { iqdmx01CmdEntry 3322 }


	iqdmx01BusProcAmpBusCLGainBusCL OBJECT-TYPE
		SYNTAX		INTEGER
		MAX-ACCESS		read-write
		STATUS			current
		DESCRIPTION
				"TYPE: - Number
				 PAGE: - Audio- Buses
					Gain Bus CL  cmdID= 3084  min= -180  max= 180  step= 1  format= %0.1fdB  div_scale= 10
					Min = -18.0dB  Max = 18.0dB  Step = 0.1dB "
		::= { iqdmx01CmdEntry 3084 }


	iqdmx01BusProcAmpBusCLInvert OBJECT-TYPE
		SYNTAX		INTEGER { disable(0), enable(1) }
		MAX-ACCESS		read-write
		STATUS			current
		DESCRIPTION
				"TYPE: - Checkbox
				 PAGE: - Audio- Buses
					Invert  cmdID= 3164 "
		::= { iqdmx01CmdEntry 3164 }


	iqdmx01BusProcAmpBusCLMute OBJECT-TYPE
		SYNTAX		INTEGER { disable(0), enable(1) }
		MAX-ACCESS		read-write
		STATUS			current
		DESCRIPTION
				"TYPE: - Checkbox
				 PAGE: - Audio- Buses
					Mute  cmdID= 3244 "
		::= { iqdmx01CmdEntry 3244 }


	iqdmx01BusProcAmpBusCRGainBusCR OBJECT-TYPE
		SYNTAX		INTEGER
		MAX-ACCESS		read-write
		STATUS			current
		DESCRIPTION
				"TYPE: - Number
				 PAGE: - Audio- Buses
					Gain Bus CR  cmdID= 3085  min= -180  max= 180  step= 1  format= %0.1fdB  div_scale= 10
					Min = -18.0dB  Max = 18.0dB  Step = 0.1dB "
		::= { iqdmx01CmdEntry 3085 }


	iqdmx01BusProcAmpBusCRInvert OBJECT-TYPE
		SYNTAX		INTEGER { disable(0), enable(1) }
		MAX-ACCESS		read-write
		STATUS			current
		DESCRIPTION
				"TYPE: - Checkbox
				 PAGE: - Audio- Buses
					Invert  cmdID= 3165 "
		::= { iqdmx01CmdEntry 3165 }


	iqdmx01BusProcAmpBusCRMute OBJECT-TYPE
		SYNTAX		INTEGER { disable(0), enable(1) }
		MAX-ACCESS		read-write
		STATUS			current
		DESCRIPTION
				"TYPE: - Checkbox
				 PAGE: - Audio- Buses
					Mute  cmdID= 3245 "
		::= { iqdmx01CmdEntry 3245 }


	iqdmx01BusesBusProcAmpStereoD OBJECT-TYPE
		SYNTAX		INTEGER { disable(0), enable(1) }
		MAX-ACCESS		read-write
		STATUS			current
		DESCRIPTION
				"TYPE: - Checkbox
				 PAGE: - Audio- Buses
					Stereo D  cmdID= 3323 "
		::= { iqdmx01CmdEntry 3323 }


	iqdmx01BusProcAmpBusDLGainBusDL OBJECT-TYPE
		SYNTAX		INTEGER
		MAX-ACCESS		read-write
		STATUS			current
		DESCRIPTION
				"TYPE: - Number
				 PAGE: - Audio- Buses
					Gain Bus DL  cmdID= 3086  min= -180  max= 180  step= 1  format= %0.1fdB  div_scale= 10
					Min = -18.0dB  Max = 18.0dB  Step = 0.1dB "
		::= { iqdmx01CmdEntry 3086 }


	iqdmx01BusProcAmpBusDLInvert OBJECT-TYPE
		SYNTAX		INTEGER { disable(0), enable(1) }
		MAX-ACCESS		read-write
		STATUS			current
		DESCRIPTION
				"TYPE: - Checkbox
				 PAGE: - Audio- Buses
					Invert  cmdID= 3166 "
		::= { iqdmx01CmdEntry 3166 }


	iqdmx01BusProcAmpBusDLMute OBJECT-TYPE
		SYNTAX		INTEGER { disable(0), enable(1) }
		MAX-ACCESS		read-write
		STATUS			current
		DESCRIPTION
				"TYPE: - Checkbox
				 PAGE: - Audio- Buses
					Mute  cmdID= 3246 "
		::= { iqdmx01CmdEntry 3246 }


	iqdmx01BusProcAmpBusDRGainBusDR OBJECT-TYPE
		SYNTAX		INTEGER
		MAX-ACCESS		read-write
		STATUS			current
		DESCRIPTION
				"TYPE: - Number
				 PAGE: - Audio- Buses
					Gain Bus DR  cmdID= 3087  min= -180  max= 180  step= 1  format= %0.1fdB  div_scale= 10
					Min = -18.0dB  Max = 18.0dB  Step = 0.1dB "
		::= { iqdmx01CmdEntry 3087 }


	iqdmx01BusProcAmpBusDRInvert OBJECT-TYPE
		SYNTAX		INTEGER { disable(0), enable(1) }
		MAX-ACCESS		read-write
		STATUS			current
		DESCRIPTION
				"TYPE: - Checkbox
				 PAGE: - Audio- Buses
					Invert  cmdID= 3167 "
		::= { iqdmx01CmdEntry 3167 }


	iqdmx01BusProcAmpBusDRMute OBJECT-TYPE
		SYNTAX		INTEGER { disable(0), enable(1) }
		MAX-ACCESS		read-write
		STATUS			current
		DESCRIPTION
				"TYPE: - Checkbox
				 PAGE: - Audio- Buses
					Mute  cmdID= 3247 "
		::= { iqdmx01CmdEntry 3247 }


	iqdmx01DelayDelaySelectInternal OBJECT-TYPE
		SYNTAX		INTEGER { disable(0), enable(1) }
		MAX-ACCESS		read-write
		STATUS			current
		DESCRIPTION
				"TYPE: - Checkbox
				 PAGE: - Audio- Delay
					Internal  cmdID= 2567 "
		::= { iqdmx01CmdEntry 2567 }


	iqdmx01DelayDelaySelectManual OBJECT-TYPE
		SYNTAX		INTEGER { disable(0), enable(1) }
		MAX-ACCESS		read-write
		STATUS			current
		DESCRIPTION
				"TYPE: - Checkbox
				 PAGE: - Audio- Delay
					Manual  cmdID= 2568 "
		::= { iqdmx01CmdEntry 2568 }


	iqdmx01DelayDelaySelectRolltrack14 OBJECT-TYPE
		SYNTAX		INTEGER { disable(0), enable(1) }
		MAX-ACCESS		read-write
		STATUS			current
		DESCRIPTION
				"TYPE: - Checkbox
				 PAGE: - Audio- Delay
					Rolltrack 14  cmdID= 2569 "
		::= { iqdmx01CmdEntry 2569 }


	iqdmx01DelayDelaySelectRolltrack15 OBJECT-TYPE
		SYNTAX		INTEGER { disable(0), enable(1) }
		MAX-ACCESS		read-write
		STATUS			current
		DESCRIPTION
				"TYPE: - Checkbox
				 PAGE: - Audio- Delay
					Rolltrack 15  cmdID= 2570 "
		::= { iqdmx01CmdEntry 2570 }


	iqdmx01DelayDelaySelectRolltrack16 OBJECT-TYPE
		SYNTAX		INTEGER { disable(0), enable(1) }
		MAX-ACCESS		read-write
		STATUS			current
		DESCRIPTION
				"TYPE: - Checkbox
				 PAGE: - Audio- Delay
					Rolltrack 16  cmdID= 2571 "
		::= { iqdmx01CmdEntry 2571 }


	iqdmx01DelayDelaySelectRolltrack17 OBJECT-TYPE
		SYNTAX		INTEGER { disable(0), enable(1) }
		MAX-ACCESS		read-write
		STATUS			current
		DESCRIPTION
				"TYPE: - Checkbox
				 PAGE: - Audio- Delay
					Rolltrack 17  cmdID= 2572 "
		::= { iqdmx01CmdEntry 2572 }


	iqdmx01DelayDelaySelectGPIDelaySelect OBJECT-TYPE
		SYNTAX		INTEGER { disable(0), enable(1) }
		MAX-ACCESS		read-write
		STATUS			current
		DESCRIPTION
				"TYPE: - Checkbox
				 PAGE: - Audio- Delay
					GPI Delay Select  cmdID= 3051 "
		::= { iqdmx01CmdEntry 3051 }


	iqdmx01DelayDelayStatusManual OBJECT-TYPE
		SYNTAX		INTEGER
		MAX-ACCESS		read-write
		STATUS			current
		DESCRIPTION
				"TYPE: - Number
				 PAGE: - Audio- Delay
					Manual Delay  cmdID= 2573  min= -40  max= 1500  step= 1  format= %3.0f ms  div_scale= 1
					Manual  cmdID= 2573  format=
					Min = -40 ms  Max = 1500 ms  Step =   1 ms "
		::= { iqdmx01CmdEntry 2573 }


	iqdmx01DelayDelayStatusInternal OBJECT-TYPE
		SYNTAX		RollCallString
		MAX-ACCESS		read-only
		STATUS			current
		DESCRIPTION
				"TYPE: - Display
				 PAGE: - Audio- Delay
					Internal  cmdID= 2574  format=   "
		::= { iqdmx01CmdEntry 2574 }


	iqdmx01DelayDelayStatusRolltrack14 OBJECT-TYPE
		SYNTAX		RollCallString
		MAX-ACCESS		read-only
		STATUS			current
		DESCRIPTION
				"TYPE: - Display
				 PAGE: - Audio- Delay
					Rolltrack 14  cmdID= 14  format=   "
		::= { iqdmx01CmdEntry 14 }


	iqdmx01DelayDelayStatusRolltrack15 OBJECT-TYPE
		SYNTAX		RollCallString
		MAX-ACCESS		read-only
		STATUS			current
		DESCRIPTION
				"TYPE: - Display
				 PAGE: - Audio- Delay
					Rolltrack 15  cmdID= 15  format=   "
		::= { iqdmx01CmdEntry 15 }


	iqdmx01DelayDelayStatusRolltrack16 OBJECT-TYPE
		SYNTAX		RollCallString
		MAX-ACCESS		read-only
		STATUS			current
		DESCRIPTION
				"TYPE: - Display
				 PAGE: - Audio- Delay
					Rolltrack 16  cmdID= 16  format=   "
		::= { iqdmx01CmdEntry 16 }


	iqdmx01DelayDelayStatusRolltrack17 OBJECT-TYPE
		SYNTAX		RollCallString
		MAX-ACCESS		read-only
		STATUS			current
		DESCRIPTION
				"TYPE: - Display
				 PAGE: - Audio- Delay
					Rolltrack 17  cmdID= 17  format=   "
		::= { iqdmx01CmdEntry 17 }


	iqdmx01DelayDelayStatusGPIDelayDisplay OBJECT-TYPE
		SYNTAX		RollCallString
		MAX-ACCESS		read-only
		STATUS			current
		DESCRIPTION
				"TYPE: - Display
				 PAGE: - Audio- Delay
					GPI Delay Display  cmdID= 3052  format=   "
		::= { iqdmx01CmdEntry 3052 }


	iqdmx01DelayDelayStatusTotalDelayDisplay OBJECT-TYPE
		SYNTAX		RollCallString
		MAX-ACCESS		read-only
		STATUS			current
		DESCRIPTION
				"TYPE: - Display
				 PAGE: - Audio- Delay
					Total Delay Display  cmdID= 2979  format=   "
		::= { iqdmx01CmdEntry 2979 }


	iqdmx01AudioMonitorSilenceLevel OBJECT-TYPE
		SYNTAX		INTEGER
		MAX-ACCESS		read-write
		STATUS			current
		DESCRIPTION
				"TYPE: - Number
				 PAGE: - Audio- Monitor
					Silence Level  cmdID= 3056  min= -80  max= 0  step= 1  format= %1.1f dB  div_scale= 1
					Min = -80.0 dB  Max = 0.0 dB  Step = 1.0 dB "
		::= { iqdmx01CmdEntry 3056 }


	iqdmx01AudioMonitorLowLevel OBJECT-TYPE
		SYNTAX		INTEGER
		MAX-ACCESS		read-write
		STATUS			current
		DESCRIPTION
				"TYPE: - Number
				 PAGE: - Audio- Monitor
					Low Level  cmdID= 2517  min= -80  max= 0  step= 1  format= %1.1f dB  div_scale= 1
					Min = -80.0 dB  Max = 0.0 dB  Step = 1.0 dB "
		::= { iqdmx01CmdEntry 2517 }


	iqdmx01AudioMonitorHighLevel OBJECT-TYPE
		SYNTAX		INTEGER
		MAX-ACCESS		read-write
		STATUS			current
		DESCRIPTION
				"TYPE: - Number
				 PAGE: - Audio- Monitor
					High Level  cmdID= 3057  min= -80  max= 0  step= 1  format= %1.1f dB  div_scale= 1
					Min = -80.0 dB  Max = 0.0 dB  Step = 1.0 dB "
		::= { iqdmx01CmdEntry 3057 }


	iqdmx01AudioMonitorOverloadLevel OBJECT-TYPE
		SYNTAX		INTEGER
		MAX-ACCESS		read-write
		STATUS			current
		DESCRIPTION
				"TYPE: - Number
				 PAGE: - Audio- Monitor
					Overload Level  cmdID= 3058  min= -80  max= 0  step= 1  format= %1.1f dB  div_scale= 1
					Min = -80.0 dB  Max = 0.0 dB  Step = 1.0 dB "
		::= { iqdmx01CmdEntry 3058 }


	iqdmx01AudioMonitorWarningTimer OBJECT-TYPE
		SYNTAX		INTEGER
		MAX-ACCESS		read-write
		STATUS			current
		DESCRIPTION
				"TYPE: - Number
				 PAGE: - Audio- Monitor
					Warning Timer  cmdID= 2518  min= 1  max= 20  step= 1  format= %1.0f sec  div_scale= 1
					Min = 1 sec  Max = 20 sec  Step = 1 sec "
		::= { iqdmx01CmdEntry 2518 }


	iqdmx01Freeze OBJECT-TYPE
		SYNTAX		INTEGER { disable(0), enable(1) }
		MAX-ACCESS		read-write
		STATUS			current
		DESCRIPTION
				"TYPE: - Checkbox
					Freeze  cmdID= 1208 "
		::= { iqdmx01CmdEntry 1208 }


	iqdmx01VideoDelay OBJECT-TYPE
		SYNTAX		INTEGER {
							val_0_Frame_Delay(0),
							val_1_Frame_Delay(1),
							val_2_Frame_Delay(2)
							}
		MAX-ACCESS		read-write
		STATUS			current
		DESCRIPTION
				"TYPE: - Button
				 PAGE: - Video Delay
					0 Frame Delay  cmdID= 2973  value= 0
					1 Frame Delay  cmdID= 2973  value= 1
					2 Frame Delay  cmdID= 2973  value= 2  "
		::= { iqdmx01CmdEntry 2973 }


	iqdmx01VideoDelayDelayPhase625HPhase OBJECT-TYPE
		SYNTAX		INTEGER
		MAX-ACCESS		read-write
		STATUS			current
		DESCRIPTION
				"TYPE: - Number
				 PAGE: - Video Delay
					625 H Phase  cmdID= 2974  min= 0  max= 63962899  step= -28499  format=  %.0fns  div_scale= 1000
					Min =  0ns  Max =  63963ns  Step =  -28ns "
		::= { iqdmx01CmdEntry 2974 }


	iqdmx01VideoDelayDelayPhase625VPhase OBJECT-TYPE
		SYNTAX		INTEGER
		MAX-ACCESS		read-write
		STATUS			current
		DESCRIPTION
				"TYPE: - Number
				 PAGE: - Video Delay
					625 V Phase  cmdID= 2975  min= 0  max= 624  step= 1  format=  %.0flines  div_scale= 1
					Min =  0lines  Max =  624lines  Step =  1lines "
		::= { iqdmx01CmdEntry 2975 }


	iqdmx01VideoDelayDelayPhase525HPhase OBJECT-TYPE
		SYNTAX		INTEGER
		MAX-ACCESS		read-write
		STATUS			current
		DESCRIPTION
				"TYPE: - Number
				 PAGE: - Video Delay
					525 H Phase  cmdID= 2976  min= 0  max= 63518455  step= -28499  format=  %.0fns  div_scale= 1000
					Min =  0ns  Max =  63518ns  Step =  -28ns "
		::= { iqdmx01CmdEntry 2976 }


	iqdmx01VideoDelayDelayPhase525VPhase OBJECT-TYPE
		SYNTAX		INTEGER
		MAX-ACCESS		read-write
		STATUS			current
		DESCRIPTION
				"TYPE: - Number
				 PAGE: - Video Delay
					525 V Phase  cmdID= 2977  min= 0  max= 524  step= 1  format=  %.0flines  div_scale= 1
					Min =  0lines  Max =  524lines  Step =  1lines "
		::= { iqdmx01CmdEntry 2977 }


	iqdmx01UserMemMemory1Save1 OBJECT-TYPE
		SYNTAX		INTEGER { noAction(0),val_Save_1(1) }
		MAX-ACCESS		read-write
		STATUS			current
		DESCRIPTION
				"TYPE: - Button
				 PAGE: - User Mem
					Save 1  cmdID= 1600  value= 1  "
		::= { iqdmx01CmdEntry 1600 }


	iqdmx01UserMemMemory1Recall1 OBJECT-TYPE
		SYNTAX		INTEGER { noAction(0),val_Recall_1(1) }
		MAX-ACCESS		read-write
		STATUS			current
		DESCRIPTION
				"TYPE: - Button
				 PAGE: - User Mem
					Recall 1  cmdID= 1601  value= 1  "
		::= { iqdmx01CmdEntry 1601 }


	iqdmx01UserMemMemory1Clear1 OBJECT-TYPE
		SYNTAX		INTEGER { noAction(0),val_Clear_1(1) }
		MAX-ACCESS		read-write
		STATUS			current
		DESCRIPTION
				"TYPE: - Button
				 PAGE: - User Mem
					Clear 1  cmdID= 1602  value= 1  "
		::= { iqdmx01CmdEntry 1602 }


	iqdmx01UserMemMemory1Name1 OBJECT-TYPE
		SYNTAX		RollCallString
		MAX-ACCESS		read-write
		STATUS			current
		DESCRIPTION
				"TYPE: - Editstring
				 PAGE: - User Mem
					Name 1  cmdID= 1603  "
		::= { iqdmx01CmdEntry 1603 }


	iqdmx01UserMemMemory2Save2 OBJECT-TYPE
		SYNTAX		INTEGER { noAction(0),val_Save_2(1) }
		MAX-ACCESS		read-write
		STATUS			current
		DESCRIPTION
				"TYPE: - Button
				 PAGE: - User Mem
					Save 2  cmdID= 1604  value= 1  "
		::= { iqdmx01CmdEntry 1604 }


	iqdmx01UserMemMemory2Recall2 OBJECT-TYPE
		SYNTAX		INTEGER { noAction(0),val_Recall_2(1) }
		MAX-ACCESS		read-write
		STATUS			current
		DESCRIPTION
				"TYPE: - Button
				 PAGE: - User Mem
					Recall 2  cmdID= 1605  value= 1  "
		::= { iqdmx01CmdEntry 1605 }


	iqdmx01UserMemMemory2Clear2 OBJECT-TYPE
		SYNTAX		INTEGER { noAction(0),val_Clear_2(1) }
		MAX-ACCESS		read-write
		STATUS			current
		DESCRIPTION
				"TYPE: - Button
				 PAGE: - User Mem
					Clear 2  cmdID= 1606  value= 1  "
		::= { iqdmx01CmdEntry 1606 }


	iqdmx01UserMemMemory2Name2 OBJECT-TYPE
		SYNTAX		RollCallString
		MAX-ACCESS		read-write
		STATUS			current
		DESCRIPTION
				"TYPE: - Editstring
				 PAGE: - User Mem
					Name 2  cmdID= 1607  "
		::= { iqdmx01CmdEntry 1607 }


	iqdmx01UserMemMemory3Save3 OBJECT-TYPE
		SYNTAX		INTEGER { noAction(0),val_Save_3(1) }
		MAX-ACCESS		read-write
		STATUS			current
		DESCRIPTION
				"TYPE: - Button
				 PAGE: - User Mem
					Save 3  cmdID= 1608  value= 1  "
		::= { iqdmx01CmdEntry 1608 }


	iqdmx01UserMemMemory3Recall3 OBJECT-TYPE
		SYNTAX		INTEGER { noAction(0),val_Recall_3(1) }
		MAX-ACCESS		read-write
		STATUS			current
		DESCRIPTION
				"TYPE: - Button
				 PAGE: - User Mem
					Recall 3  cmdID= 1609  value= 1  "
		::= { iqdmx01CmdEntry 1609 }


	iqdmx01UserMemMemory3Clear3 OBJECT-TYPE
		SYNTAX		INTEGER { noAction(0),val_Clear_3(1) }
		MAX-ACCESS		read-write
		STATUS			current
		DESCRIPTION
				"TYPE: - Button
				 PAGE: - User Mem
					Clear 3  cmdID= 1610  value= 1  "
		::= { iqdmx01CmdEntry 1610 }


	iqdmx01UserMemMemory3Name3 OBJECT-TYPE
		SYNTAX		RollCallString
		MAX-ACCESS		read-write
		STATUS			current
		DESCRIPTION
				"TYPE: - Editstring
				 PAGE: - User Mem
					Name 3  cmdID= 1611  "
		::= { iqdmx01CmdEntry 1611 }


	iqdmx01UserMemMemory4Save4 OBJECT-TYPE
		SYNTAX		INTEGER { noAction(0),val_Save_4(1) }
		MAX-ACCESS		read-write
		STATUS			current
		DESCRIPTION
				"TYPE: - Button
				 PAGE: - User Mem
					Save 4  cmdID= 1612  value= 1  "
		::= { iqdmx01CmdEntry 1612 }


	iqdmx01UserMemMemory4Recall4 OBJECT-TYPE
		SYNTAX		INTEGER { noAction(0),val_Recall_4(1) }
		MAX-ACCESS		read-write
		STATUS			current
		DESCRIPTION
				"TYPE: - Button
				 PAGE: - User Mem
					Recall 4  cmdID= 1613  value= 1  "
		::= { iqdmx01CmdEntry 1613 }


	iqdmx01UserMemMemory4Clear4 OBJECT-TYPE
		SYNTAX		INTEGER { noAction(0),val_Clear_4(1) }
		MAX-ACCESS		read-write
		STATUS			current
		DESCRIPTION
				"TYPE: - Button
				 PAGE: - User Mem
					Clear 4  cmdID= 1614  value= 1  "
		::= { iqdmx01CmdEntry 1614 }


	iqdmx01UserMemMemory4Name4 OBJECT-TYPE
		SYNTAX		RollCallString
		MAX-ACCESS		read-write
		STATUS			current
		DESCRIPTION
				"TYPE: - Editstring
				 PAGE: - User Mem
					Name 4  cmdID= 1615  "
		::= { iqdmx01CmdEntry 1615 }


	iqdmx01UserMemMemory5Save5 OBJECT-TYPE
		SYNTAX		INTEGER { noAction(0),val_Save_5(1) }
		MAX-ACCESS		read-write
		STATUS			current
		DESCRIPTION
				"TYPE: - Button
				 PAGE: - User Mem
					Save 5  cmdID= 1616  value= 1  "
		::= { iqdmx01CmdEntry 1616 }


	iqdmx01UserMemMemory5Recall5 OBJECT-TYPE
		SYNTAX		INTEGER { noAction(0),val_Recall_5(1) }
		MAX-ACCESS		read-write
		STATUS			current
		DESCRIPTION
				"TYPE: - Button
				 PAGE: - User Mem
					Recall 5  cmdID= 1617  value= 1  "
		::= { iqdmx01CmdEntry 1617 }


	iqdmx01UserMemMemory5Clear5 OBJECT-TYPE
		SYNTAX		INTEGER { noAction(0),val_Clear_5(1) }
		MAX-ACCESS		read-write
		STATUS			current
		DESCRIPTION
				"TYPE: - Button
				 PAGE: - User Mem
					Clear 5  cmdID= 1618  value= 1  "
		::= { iqdmx01CmdEntry 1618 }


	iqdmx01UserMemMemory5Name5 OBJECT-TYPE
		SYNTAX		RollCallString
		MAX-ACCESS		read-write
		STATUS			current
		DESCRIPTION
				"TYPE: - Editstring
				 PAGE: - User Mem
					Name 5  cmdID= 1619  "
		::= { iqdmx01CmdEntry 1619 }


	iqdmx01UserMemMemory6Save6 OBJECT-TYPE
		SYNTAX		INTEGER { noAction(0),val_Save_6(1) }
		MAX-ACCESS		read-write
		STATUS			current
		DESCRIPTION
				"TYPE: - Button
				 PAGE: - User Mem
					Save 6  cmdID= 1620  value= 1  "
		::= { iqdmx01CmdEntry 1620 }


	iqdmx01UserMemMemory6Recall6 OBJECT-TYPE
		SYNTAX		INTEGER { noAction(0),val_Recall_6(1) }
		MAX-ACCESS		read-write
		STATUS			current
		DESCRIPTION
				"TYPE: - Button
				 PAGE: - User Mem
					Recall 6  cmdID= 1621  value= 1  "
		::= { iqdmx01CmdEntry 1621 }


	iqdmx01UserMemMemory6Clear6 OBJECT-TYPE
		SYNTAX		INTEGER { noAction(0),val_Clear_6(1) }
		MAX-ACCESS		read-write
		STATUS			current
		DESCRIPTION
				"TYPE: - Button
				 PAGE: - User Mem
					Clear 6  cmdID= 1622  value= 1  "
		::= { iqdmx01CmdEntry 1622 }


	iqdmx01UserMemMemory6Name6 OBJECT-TYPE
		SYNTAX		RollCallString
		MAX-ACCESS		read-write
		STATUS			current
		DESCRIPTION
				"TYPE: - Editstring
				 PAGE: - User Mem
					Name 6  cmdID= 1623  "
		::= { iqdmx01CmdEntry 1623 }


	iqdmx01UserMemMemory7Save7 OBJECT-TYPE
		SYNTAX		INTEGER { noAction(0),val_Save_7(1) }
		MAX-ACCESS		read-write
		STATUS			current
		DESCRIPTION
				"TYPE: - Button
				 PAGE: - User Mem
					Save 7  cmdID= 1624  value= 1  "
		::= { iqdmx01CmdEntry 1624 }


	iqdmx01UserMemMemory7Recall7 OBJECT-TYPE
		SYNTAX		INTEGER { noAction(0),val_Recall_7(1) }
		MAX-ACCESS		read-write
		STATUS			current
		DESCRIPTION
				"TYPE: - Button
				 PAGE: - User Mem
					Recall 7  cmdID= 1625  value= 1  "
		::= { iqdmx01CmdEntry 1625 }


	iqdmx01UserMemMemory7Clear7 OBJECT-TYPE
		SYNTAX		INTEGER { noAction(0),val_Clear_7(1) }
		MAX-ACCESS		read-write
		STATUS			current
		DESCRIPTION
				"TYPE: - Button
				 PAGE: - User Mem
					Clear 7  cmdID= 1626  value= 1  "
		::= { iqdmx01CmdEntry 1626 }


	iqdmx01UserMemMemory7Name7 OBJECT-TYPE
		SYNTAX		RollCallString
		MAX-ACCESS		read-write
		STATUS			current
		DESCRIPTION
				"TYPE: - Editstring
				 PAGE: - User Mem
					Name 7  cmdID= 1627  "
		::= { iqdmx01CmdEntry 1627 }


	iqdmx01UserMemMemory8Save8 OBJECT-TYPE
		SYNTAX		INTEGER { noAction(0),val_Save_8(1) }
		MAX-ACCESS		read-write
		STATUS			current
		DESCRIPTION
				"TYPE: - Button
				 PAGE: - User Mem
					Save 8  cmdID= 1628  value= 1  "
		::= { iqdmx01CmdEntry 1628 }


	iqdmx01UserMemMemory8Recall8 OBJECT-TYPE
		SYNTAX		INTEGER { noAction(0),val_Recall_8(1) }
		MAX-ACCESS		read-write
		STATUS			current
		DESCRIPTION
				"TYPE: - Button
				 PAGE: - User Mem
					Recall 8  cmdID= 1629  value= 1  "
		::= { iqdmx01CmdEntry 1629 }


	iqdmx01UserMemMemory8Clear8 OBJECT-TYPE
		SYNTAX		INTEGER { noAction(0),val_Clear_8(1) }
		MAX-ACCESS		read-write
		STATUS			current
		DESCRIPTION
				"TYPE: - Button
				 PAGE: - User Mem
					Clear 8  cmdID= 1630  value= 1  "
		::= { iqdmx01CmdEntry 1630 }


	iqdmx01UserMemMemory8Name8 OBJECT-TYPE
		SYNTAX		RollCallString
		MAX-ACCESS		read-write
		STATUS			current
		DESCRIPTION
				"TYPE: - Editstring
				 PAGE: - User Mem
					Name 8  cmdID= 1631  "
		::= { iqdmx01CmdEntry 1631 }


	iqdmx01SetupPatternAnimatedPattern OBJECT-TYPE
		SYNTAX		INTEGER { disable(0), enable(1) }
		MAX-ACCESS		read-write
		STATUS			current
		DESCRIPTION
				"TYPE: - Checkbox
				 PAGE: - Setup- Pattern
					Animated Pattern  cmdID= 2940 "
		::= { iqdmx01CmdEntry 2940 }


	iqdmx01SetupPatternEnablePattern OBJECT-TYPE
		SYNTAX		INTEGER { disable(0), enable(1) }
		MAX-ACCESS		read-write
		STATUS			current
		DESCRIPTION
				"TYPE: - Checkbox
				 PAGE: - Setup- Pattern
					Enable Pattern  cmdID= 1035 "
		::= { iqdmx01CmdEntry 1035 }


	iqdmx01SetupPattern OBJECT-TYPE
		SYNTAX		INTEGER {
							val_Black(0),
							val_EBU_Colour_Bars(1),
							val_100_Colour_Bars(2),
							val_Ramp(3),
							val_Multiburst(4),
							val_Pulse_Bar(5)
							}
		MAX-ACCESS		read-write
		STATUS			current
		DESCRIPTION
				"TYPE: - Button
				 PAGE: - Setup- Pattern
					Black  cmdID= 1036  value= 0
					EBU Colour Bars  cmdID= 1036  value= 1
					100% Colour Bars  cmdID= 1036  value= 2
					Ramp  cmdID= 1036  value= 3
					Multiburst  cmdID= 1036  value= 4
					Pulse & Bar  cmdID= 1036  value= 5  "
		::= { iqdmx01CmdEntry 1036 }


	iqdmx01SetupCaptionEditCaption OBJECT-TYPE
		SYNTAX		RollCallString
		MAX-ACCESS		read-write
		STATUS			current
		DESCRIPTION
				"TYPE: - Editstring
				 PAGE: - Setup- Caption
					Edit Caption  cmdID= 1041  "
		::= { iqdmx01CmdEntry 1041 }


	iqdmx01SetupCaption OBJECT-TYPE
		SYNTAX		INTEGER {
							val_Caption_Off(0),
							val_Caption_On(1)
							}
		MAX-ACCESS		read-write
		STATUS			current
		DESCRIPTION
				"TYPE: - Button
				 PAGE: - Setup- Caption
					Caption Off  cmdID= 1037  value= 0
					Caption On  cmdID= 1037  value= 1  "
		::= { iqdmx01CmdEntry 1037 }


	iqdmx01BlankingVIPass525BlankAll OBJECT-TYPE
		SYNTAX		INTEGER { noAction(0),val_Blank_All(1) }
		MAX-ACCESS		read-write
		STATUS			current
		DESCRIPTION
				"TYPE: - Button
				 PAGE: - Setup- Blanking
					Blank All  cmdID= 1298  value= 1  "
		::= { iqdmx01CmdEntry 1298 }


	iqdmx01BlankingVIPass525PassAll OBJECT-TYPE
		SYNTAX		INTEGER { noAction(0),val_Pass_All(1) }
		MAX-ACCESS		read-write
		STATUS			current
		DESCRIPTION
				"TYPE: - Button
				 PAGE: - Setup- Blanking
					Pass All  cmdID= 1297  value= 1  "
		::= { iqdmx01CmdEntry 1297 }


	iqdmx01BlankingVIPass525Line11 OBJECT-TYPE
		SYNTAX		INTEGER { disable(0), enable(1) }
		MAX-ACCESS		read-write
		STATUS			current
		DESCRIPTION
				"TYPE: - Checkbox
				 PAGE: - Setup- Blanking
					Line 11  cmdID= 1211 "
		::= { iqdmx01CmdEntry 1211 }


	iqdmx01BlankingVIPass525Line274 OBJECT-TYPE
		SYNTAX		INTEGER { disable(0), enable(1) }
		MAX-ACCESS		read-write
		STATUS			current
		DESCRIPTION
				"TYPE: - Checkbox
				 PAGE: - Setup- Blanking
					Line 274  cmdID= 1231 "
		::= { iqdmx01CmdEntry 1231 }


	iqdmx01BlankingVIPass525Line12 OBJECT-TYPE
		SYNTAX		INTEGER { disable(0), enable(1) }
		MAX-ACCESS		read-write
		STATUS			current
		DESCRIPTION
				"TYPE: - Checkbox
				 PAGE: - Setup- Blanking
					Line 12  cmdID= 1212 "
		::= { iqdmx01CmdEntry 1212 }


	iqdmx01BlankingVIPass525Line275 OBJECT-TYPE
		SYNTAX		INTEGER { disable(0), enable(1) }
		MAX-ACCESS		read-write
		STATUS			current
		DESCRIPTION
				"TYPE: - Checkbox
				 PAGE: - Setup- Blanking
					Line 275  cmdID= 1232 "
		::= { iqdmx01CmdEntry 1232 }


	iqdmx01BlankingVIPass525Line13 OBJECT-TYPE
		SYNTAX		INTEGER { disable(0), enable(1) }
		MAX-ACCESS		read-write
		STATUS			current
		DESCRIPTION
				"TYPE: - Checkbox
				 PAGE: - Setup- Blanking
					Line 13  cmdID= 1213 "
		::= { iqdmx01CmdEntry 1213 }


	iqdmx01BlankingVIPass525Line276 OBJECT-TYPE
		SYNTAX		INTEGER { disable(0), enable(1) }
		MAX-ACCESS		read-write
		STATUS			current
		DESCRIPTION
				"TYPE: - Checkbox
				 PAGE: - Setup- Blanking
					Line 276  cmdID= 1233 "
		::= { iqdmx01CmdEntry 1233 }


	iqdmx01BlankingVIPass525Line14 OBJECT-TYPE
		SYNTAX		INTEGER { disable(0), enable(1) }
		MAX-ACCESS		read-write
		STATUS			current
		DESCRIPTION
				"TYPE: - Checkbox
				 PAGE: - Setup- Blanking
					Line 14  cmdID= 1214 "
		::= { iqdmx01CmdEntry 1214 }


	iqdmx01BlankingVIPass525Line277 OBJECT-TYPE
		SYNTAX		INTEGER { disable(0), enable(1) }
		MAX-ACCESS		read-write
		STATUS			current
		DESCRIPTION
				"TYPE: - Checkbox
				 PAGE: - Setup- Blanking
					Line 277  cmdID= 1234 "
		::= { iqdmx01CmdEntry 1234 }


	iqdmx01BlankingVIPass525Line15 OBJECT-TYPE
		SYNTAX		INTEGER { disable(0), enable(1) }
		MAX-ACCESS		read-write
		STATUS			current
		DESCRIPTION
				"TYPE: - Checkbox
				 PAGE: - Setup- Blanking
					Line 15  cmdID= 1215 "
		::= { iqdmx01CmdEntry 1215 }


	iqdmx01BlankingVIPass525Line278 OBJECT-TYPE
		SYNTAX		INTEGER { disable(0), enable(1) }
		MAX-ACCESS		read-write
		STATUS			current
		DESCRIPTION
				"TYPE: - Checkbox
				 PAGE: - Setup- Blanking
					Line 278  cmdID= 1235 "
		::= { iqdmx01CmdEntry 1235 }


	iqdmx01BlankingVIPass525Line16 OBJECT-TYPE
		SYNTAX		INTEGER { disable(0), enable(1) }
		MAX-ACCESS		read-write
		STATUS			current
		DESCRIPTION
				"TYPE: - Checkbox
				 PAGE: - Setup- Blanking
					Line 16  cmdID= 1216 "
		::= { iqdmx01CmdEntry 1216 }


	iqdmx01BlankingVIPass525Line279 OBJECT-TYPE
		SYNTAX		INTEGER { disable(0), enable(1) }
		MAX-ACCESS		read-write
		STATUS			current
		DESCRIPTION
				"TYPE: - Checkbox
				 PAGE: - Setup- Blanking
					Line 279  cmdID= 1236 "
		::= { iqdmx01CmdEntry 1236 }


	iqdmx01BlankingVIPass525Line17 OBJECT-TYPE
		SYNTAX		INTEGER { disable(0), enable(1) }
		MAX-ACCESS		read-write
		STATUS			current
		DESCRIPTION
				"TYPE: - Checkbox
				 PAGE: - Setup- Blanking
					Line 17  cmdID= 1217 "
		::= { iqdmx01CmdEntry 1217 }


	iqdmx01BlankingVIPass525Line280 OBJECT-TYPE
		SYNTAX		INTEGER { disable(0), enable(1) }
		MAX-ACCESS		read-write
		STATUS			current
		DESCRIPTION
				"TYPE: - Checkbox
				 PAGE: - Setup- Blanking
					Line 280  cmdID= 1237 "
		::= { iqdmx01CmdEntry 1237 }


	iqdmx01BlankingVIPass525Line18 OBJECT-TYPE
		SYNTAX		INTEGER { disable(0), enable(1) }
		MAX-ACCESS		read-write
		STATUS			current
		DESCRIPTION
				"TYPE: - Checkbox
				 PAGE: - Setup- Blanking
					Line 18  cmdID= 1218 "
		::= { iqdmx01CmdEntry 1218 }


	iqdmx01BlankingVIPass525Line281 OBJECT-TYPE
		SYNTAX		INTEGER { disable(0), enable(1) }
		MAX-ACCESS		read-write
		STATUS			current
		DESCRIPTION
				"TYPE: - Checkbox
				 PAGE: - Setup- Blanking
					Line 281  cmdID= 1238 "
		::= { iqdmx01CmdEntry 1238 }


	iqdmx01BlankingVIPass525Line19 OBJECT-TYPE
		SYNTAX		INTEGER { disable(0), enable(1) }
		MAX-ACCESS		read-write
		STATUS			current
		DESCRIPTION
				"TYPE: - Checkbox
				 PAGE: - Setup- Blanking
					Line 19  cmdID= 1219 "
		::= { iqdmx01CmdEntry 1219 }


	iqdmx01BlankingVIPass525Line282 OBJECT-TYPE
		SYNTAX		INTEGER { disable(0), enable(1) }
		MAX-ACCESS		read-write
		STATUS			current
		DESCRIPTION
				"TYPE: - Checkbox
				 PAGE: - Setup- Blanking
					Line 282  cmdID= 1239 "
		::= { iqdmx01CmdEntry 1239 }


	iqdmx01BlankingVIPass525Line20 OBJECT-TYPE
		SYNTAX		INTEGER { disable(0), enable(1) }
		MAX-ACCESS		read-write
		STATUS			current
		DESCRIPTION
				"TYPE: - Checkbox
				 PAGE: - Setup- Blanking
					Line 20  cmdID= 1220 "
		::= { iqdmx01CmdEntry 1220 }


	iqdmx01BlankingVIPass525Line283 OBJECT-TYPE
		SYNTAX		INTEGER { disable(0), enable(1) }
		MAX-ACCESS		read-write
		STATUS			current
		DESCRIPTION
				"TYPE: - Checkbox
				 PAGE: - Setup- Blanking
					Line 283  cmdID= 1240 "
		::= { iqdmx01CmdEntry 1240 }


	iqdmx01BlankingVIPass525Line21 OBJECT-TYPE
		SYNTAX		INTEGER { disable(0), enable(1) }
		MAX-ACCESS		read-write
		STATUS			current
		DESCRIPTION
				"TYPE: - Checkbox
				 PAGE: - Setup- Blanking
					Line 21  cmdID= 1221 "
		::= { iqdmx01CmdEntry 1221 }


	iqdmx01BlankingVIPass625BlankAll OBJECT-TYPE
		SYNTAX		INTEGER { noAction(0),val_Blank_All(1) }
		MAX-ACCESS		read-write
		STATUS			current
		DESCRIPTION
				"TYPE: - Button
				 PAGE: - Setup- Blanking
					Blank All  cmdID= 1296  value= 1  "
		::= { iqdmx01CmdEntry 1296 }


	iqdmx01BlankingVIPass625PassAll OBJECT-TYPE
		SYNTAX		INTEGER { noAction(0),val_Pass_All(1) }
		MAX-ACCESS		read-write
		STATUS			current
		DESCRIPTION
				"TYPE: - Button
				 PAGE: - Setup- Blanking
					Pass All  cmdID= 1295  value= 1  "
		::= { iqdmx01CmdEntry 1295 }


	iqdmx01BlankingVIPass625Line7 OBJECT-TYPE
		SYNTAX		INTEGER { disable(0), enable(1) }
		MAX-ACCESS		read-write
		STATUS			current
		DESCRIPTION
				"TYPE: - Checkbox
				 PAGE: - Setup- Blanking
					Line 7  cmdID= 1251 "
		::= { iqdmx01CmdEntry 1251 }


	iqdmx01BlankingVIPass625Line320 OBJECT-TYPE
		SYNTAX		INTEGER { disable(0), enable(1) }
		MAX-ACCESS		read-write
		STATUS			current
		DESCRIPTION
				"TYPE: - Checkbox
				 PAGE: - Setup- Blanking
					Line 320  cmdID= 1272 "
		::= { iqdmx01CmdEntry 1272 }


	iqdmx01BlankingVIPass625Line8 OBJECT-TYPE
		SYNTAX		INTEGER { disable(0), enable(1) }
		MAX-ACCESS		read-write
		STATUS			current
		DESCRIPTION
				"TYPE: - Checkbox
				 PAGE: - Setup- Blanking
					Line 8  cmdID= 1252 "
		::= { iqdmx01CmdEntry 1252 }


	iqdmx01BlankingVIPass625Line321 OBJECT-TYPE
		SYNTAX		INTEGER { disable(0), enable(1) }
		MAX-ACCESS		read-write
		STATUS			current
		DESCRIPTION
				"TYPE: - Checkbox
				 PAGE: - Setup- Blanking
					Line 321  cmdID= 1273 "
		::= { iqdmx01CmdEntry 1273 }


	iqdmx01BlankingVIPass625Line9 OBJECT-TYPE
		SYNTAX		INTEGER { disable(0), enable(1) }
		MAX-ACCESS		read-write
		STATUS			current
		DESCRIPTION
				"TYPE: - Checkbox
				 PAGE: - Setup- Blanking
					Line 9  cmdID= 1253 "
		::= { iqdmx01CmdEntry 1253 }


	iqdmx01BlankingVIPass625Line322 OBJECT-TYPE
		SYNTAX		INTEGER { disable(0), enable(1) }
		MAX-ACCESS		read-write
		STATUS			current
		DESCRIPTION
				"TYPE: - Checkbox
				 PAGE: - Setup- Blanking
					Line 322  cmdID= 1274 "
		::= { iqdmx01CmdEntry 1274 }


	iqdmx01BlankingVIPass625Line10 OBJECT-TYPE
		SYNTAX		INTEGER { disable(0), enable(1) }
		MAX-ACCESS		read-write
		STATUS			current
		DESCRIPTION
				"TYPE: - Checkbox
				 PAGE: - Setup- Blanking
					Line 10  cmdID= 1254 "
		::= { iqdmx01CmdEntry 1254 }


	iqdmx01BlankingVIPass625Line323 OBJECT-TYPE
		SYNTAX		INTEGER { disable(0), enable(1) }
		MAX-ACCESS		read-write
		STATUS			current
		DESCRIPTION
				"TYPE: - Checkbox
				 PAGE: - Setup- Blanking
					Line 323  cmdID= 1275 "
		::= { iqdmx01CmdEntry 1275 }


	iqdmx01BlankingVIPass625Line11 OBJECT-TYPE
		SYNTAX		INTEGER { disable(0), enable(1) }
		MAX-ACCESS		read-write
		STATUS			current
		DESCRIPTION
				"TYPE: - Checkbox
				 PAGE: - Setup- Blanking
					Line 11  cmdID= 1255 "
		::= { iqdmx01CmdEntry 1255 }


	iqdmx01BlankingVIPass625Line324 OBJECT-TYPE
		SYNTAX		INTEGER { disable(0), enable(1) }
		MAX-ACCESS		read-write
		STATUS			current
		DESCRIPTION
				"TYPE: - Checkbox
				 PAGE: - Setup- Blanking
					Line 324  cmdID= 1276 "
		::= { iqdmx01CmdEntry 1276 }


	iqdmx01BlankingVIPass625Line12 OBJECT-TYPE
		SYNTAX		INTEGER { disable(0), enable(1) }
		MAX-ACCESS		read-write
		STATUS			current
		DESCRIPTION
				"TYPE: - Checkbox
				 PAGE: - Setup- Blanking
					Line 12  cmdID= 1256 "
		::= { iqdmx01CmdEntry 1256 }


	iqdmx01BlankingVIPass625Line325 OBJECT-TYPE
		SYNTAX		INTEGER { disable(0), enable(1) }
		MAX-ACCESS		read-write
		STATUS			current
		DESCRIPTION
				"TYPE: - Checkbox
				 PAGE: - Setup- Blanking
					Line 325  cmdID= 1277 "
		::= { iqdmx01CmdEntry 1277 }


	iqdmx01BlankingVIPass625Line13 OBJECT-TYPE
		SYNTAX		INTEGER { disable(0), enable(1) }
		MAX-ACCESS		read-write
		STATUS			current
		DESCRIPTION
				"TYPE: - Checkbox
				 PAGE: - Setup- Blanking
					Line 13  cmdID= 1257 "
		::= { iqdmx01CmdEntry 1257 }


	iqdmx01BlankingVIPass625Line326 OBJECT-TYPE
		SYNTAX		INTEGER { disable(0), enable(1) }
		MAX-ACCESS		read-write
		STATUS			current
		DESCRIPTION
				"TYPE: - Checkbox
				 PAGE: - Setup- Blanking
					Line 326  cmdID= 1278 "
		::= { iqdmx01CmdEntry 1278 }


	iqdmx01BlankingVIPass625Line14 OBJECT-TYPE
		SYNTAX		INTEGER { disable(0), enable(1) }
		MAX-ACCESS		read-write
		STATUS			current
		DESCRIPTION
				"TYPE: - Checkbox
				 PAGE: - Setup- Blanking
					Line 14  cmdID= 1258 "
		::= { iqdmx01CmdEntry 1258 }


	iqdmx01BlankingVIPass625Line327 OBJECT-TYPE
		SYNTAX		INTEGER { disable(0), enable(1) }
		MAX-ACCESS		read-write
		STATUS			current
		DESCRIPTION
				"TYPE: - Checkbox
				 PAGE: - Setup- Blanking
					Line 327  cmdID= 1279 "
		::= { iqdmx01CmdEntry 1279 }


	iqdmx01BlankingVIPass625Line15 OBJECT-TYPE
		SYNTAX		INTEGER { disable(0), enable(1) }
		MAX-ACCESS		read-write
		STATUS			current
		DESCRIPTION
				"TYPE: - Checkbox
				 PAGE: - Setup- Blanking
					Line 15  cmdID= 1259 "
		::= { iqdmx01CmdEntry 1259 }


	iqdmx01BlankingVIPass625Line328 OBJECT-TYPE
		SYNTAX		INTEGER { disable(0), enable(1) }
		MAX-ACCESS		read-write
		STATUS			current
		DESCRIPTION
				"TYPE: - Checkbox
				 PAGE: - Setup- Blanking
					Line 328  cmdID= 1280 "
		::= { iqdmx01CmdEntry 1280 }


	iqdmx01BlankingVIPass625Line16 OBJECT-TYPE
		SYNTAX		INTEGER { disable(0), enable(1) }
		MAX-ACCESS		read-write
		STATUS			current
		DESCRIPTION
				"TYPE: - Checkbox
				 PAGE: - Setup- Blanking
					Line 16  cmdID= 1260 "
		::= { iqdmx01CmdEntry 1260 }


	iqdmx01BlankingVIPass625Line329 OBJECT-TYPE
		SYNTAX		INTEGER { disable(0), enable(1) }
		MAX-ACCESS		read-write
		STATUS			current
		DESCRIPTION
				"TYPE: - Checkbox
				 PAGE: - Setup- Blanking
					Line 329  cmdID= 1281 "
		::= { iqdmx01CmdEntry 1281 }


	iqdmx01BlankingVIPass625Line17 OBJECT-TYPE
		SYNTAX		INTEGER { disable(0), enable(1) }
		MAX-ACCESS		read-write
		STATUS			current
		DESCRIPTION
				"TYPE: - Checkbox
				 PAGE: - Setup- Blanking
					Line 17  cmdID= 1261 "
		::= { iqdmx01CmdEntry 1261 }


	iqdmx01BlankingVIPass625Line330 OBJECT-TYPE
		SYNTAX		INTEGER { disable(0), enable(1) }
		MAX-ACCESS		read-write
		STATUS			current
		DESCRIPTION
				"TYPE: - Checkbox
				 PAGE: - Setup- Blanking
					Line 330  cmdID= 1282 "
		::= { iqdmx01CmdEntry 1282 }


	iqdmx01BlankingVIPass625Line18 OBJECT-TYPE
		SYNTAX		INTEGER { disable(0), enable(1) }
		MAX-ACCESS		read-write
		STATUS			current
		DESCRIPTION
				"TYPE: - Checkbox
				 PAGE: - Setup- Blanking
					Line 18  cmdID= 1262 "
		::= { iqdmx01CmdEntry 1262 }


	iqdmx01BlankingVIPass625Line331 OBJECT-TYPE
		SYNTAX		INTEGER { disable(0), enable(1) }
		MAX-ACCESS		read-write
		STATUS			current
		DESCRIPTION
				"TYPE: - Checkbox
				 PAGE: - Setup- Blanking
					Line 331  cmdID= 1283 "
		::= { iqdmx01CmdEntry 1283 }


	iqdmx01BlankingVIPass625Line19 OBJECT-TYPE
		SYNTAX		INTEGER { disable(0), enable(1) }
		MAX-ACCESS		read-write
		STATUS			current
		DESCRIPTION
				"TYPE: - Checkbox
				 PAGE: - Setup- Blanking
					Line 19  cmdID= 1263 "
		::= { iqdmx01CmdEntry 1263 }


	iqdmx01BlankingVIPass625Line332 OBJECT-TYPE
		SYNTAX		INTEGER { disable(0), enable(1) }
		MAX-ACCESS		read-write
		STATUS			current
		DESCRIPTION
				"TYPE: - Checkbox
				 PAGE: - Setup- Blanking
					Line 332  cmdID= 1284 "
		::= { iqdmx01CmdEntry 1284 }


	iqdmx01BlankingVIPass625Line20 OBJECT-TYPE
		SYNTAX		INTEGER { disable(0), enable(1) }
		MAX-ACCESS		read-write
		STATUS			current
		DESCRIPTION
				"TYPE: - Checkbox
				 PAGE: - Setup- Blanking
					Line 20  cmdID= 1264 "
		::= { iqdmx01CmdEntry 1264 }


	iqdmx01BlankingVIPass625Line333 OBJECT-TYPE
		SYNTAX		INTEGER { disable(0), enable(1) }
		MAX-ACCESS		read-write
		STATUS			current
		DESCRIPTION
				"TYPE: - Checkbox
				 PAGE: - Setup- Blanking
					Line 333  cmdID= 1285 "
		::= { iqdmx01CmdEntry 1285 }


	iqdmx01BlankingVIPass625Line21 OBJECT-TYPE
		SYNTAX		INTEGER { disable(0), enable(1) }
		MAX-ACCESS		read-write
		STATUS			current
		DESCRIPTION
				"TYPE: - Checkbox
				 PAGE: - Setup- Blanking
					Line 21  cmdID= 1265 "
		::= { iqdmx01CmdEntry 1265 }


	iqdmx01BlankingVIPass625Line334 OBJECT-TYPE
		SYNTAX		INTEGER { disable(0), enable(1) }
		MAX-ACCESS		read-write
		STATUS			current
		DESCRIPTION
				"TYPE: - Checkbox
				 PAGE: - Setup- Blanking
					Line 334  cmdID= 1286 "
		::= { iqdmx01CmdEntry 1286 }


	iqdmx01BlankingVIPass625Line22 OBJECT-TYPE
		SYNTAX		INTEGER { disable(0), enable(1) }
		MAX-ACCESS		read-write
		STATUS			current
		DESCRIPTION
				"TYPE: - Checkbox
				 PAGE: - Setup- Blanking
					Line 22  cmdID= 1266 "
		::= { iqdmx01CmdEntry 1266 }


	iqdmx01BlankingVIPass625Line335 OBJECT-TYPE
		SYNTAX		INTEGER { disable(0), enable(1) }
		MAX-ACCESS		read-write
		STATUS			current
		DESCRIPTION
				"TYPE: - Checkbox
				 PAGE: - Setup- Blanking
					Line 335  cmdID= 1287 "
		::= { iqdmx01CmdEntry 1287 }


	iqdmx01BlankingVIPass625Line23 OBJECT-TYPE
		SYNTAX		INTEGER { disable(0), enable(1) }
		MAX-ACCESS		read-write
		STATUS			current
		DESCRIPTION
				"TYPE: - Checkbox
				 PAGE: - Setup- Blanking
					Line 23  cmdID= 1267 "
		::= { iqdmx01CmdEntry 1267 }


	iqdmx01SetupBlankingHancBlank OBJECT-TYPE
		SYNTAX		INTEGER { disable(0), enable(1) }
		MAX-ACCESS		read-write
		STATUS			current
		DESCRIPTION
				"TYPE: - Checkbox
				 PAGE: - Setup- Blanking
					Hanc Blank  cmdID= 2971 "
		::= { iqdmx01CmdEntry 2971 }


	iqdmx01SetupBlankingVFlagOBD OBJECT-TYPE
		SYNTAX		INTEGER { disable(0), enable(1) }
		MAX-ACCESS		read-write
		STATUS			current
		DESCRIPTION
				"TYPE: - Checkbox
				 PAGE: - Setup- Blanking
					V Flag (OBD)  cmdID= 3590 "
		::= { iqdmx01CmdEntry 3590 }


	iqdmx01SetupAudioToneIdentEnable OBJECT-TYPE
		SYNTAX		INTEGER { disable(0), enable(1) }
		MAX-ACCESS		read-write
		STATUS			current
		DESCRIPTION
				"TYPE: - Checkbox
				 PAGE: - Setup- Audio Tone
					Ident Enable  cmdID= 2489 "
		::= { iqdmx01CmdEntry 2489 }


	iqdmx01SetupAudioToneFrequency OBJECT-TYPE
		SYNTAX		INTEGER
		MAX-ACCESS		read-write
		STATUS			current
		DESCRIPTION
				"TYPE: - Number
				 PAGE: - Setup- Audio Tone
					Frequency  cmdID= 2487  min= 100  max= 15000  step= 100  format= %.1f Hz  div_scale= 1
					Min = 100.0 Hz  Max = 15000.0 Hz  Step = 100.0 Hz "
		::= { iqdmx01CmdEntry 2487 }


	iqdmx01SetupAudioToneFrequencyR OBJECT-TYPE
		SYNTAX		INTEGER
		MAX-ACCESS		read-write
		STATUS			current
		DESCRIPTION
				"TYPE: - Number
				 PAGE: - Setup- Audio Tone
					Frequency R  cmdID= 2488  min= 100  max= 15000  step= 100  format= %.1f Hz  div_scale= 1
					Min = 100.0 Hz  Max = 15000.0 Hz  Step = 100.0 Hz "
		::= { iqdmx01CmdEntry 2488 }


	iqdmx01SetupAudioToneHeadRoom OBJECT-TYPE
		SYNTAX		INTEGER
		MAX-ACCESS		read-write
		STATUS			current
		DESCRIPTION
				"TYPE: - Number
				 PAGE: - Setup- Audio Tone
					HeadRoom  cmdID= 3055  min= 4  max= 24  step= 1  format= %.1f dB  div_scale= 1
					Min = 4.0 dB  Max = 24.0 dB  Step = 1.0 dB "
		::= { iqdmx01CmdEntry 3055 }


	iqdmx01SetupSlewRate OBJECT-TYPE
		SYNTAX		INTEGER {
							val_Instant(0),
							val_Fast(1),
							val_Medium(2),
							val_Slow(3),
							val_Slowest(4)
							}
		MAX-ACCESS		read-write
		STATUS			current
		DESCRIPTION
				"TYPE: - RadiobuttonList
				 PAGE: - Setup
					Slew Rate  cmdID= 2972
					Instant  value= 0
					Fast  value= 1
					Medium  value= 2
					Slow  value= 3
					Slowest  value= 4  "
		::= { iqdmx01CmdEntry 2972 }


	iqdmx01SetupChannelStatus OBJECT-TYPE
		SYNTAX		RollCallString
		MAX-ACCESS		read-write
		STATUS			current
		DESCRIPTION
				"TYPE: - Editstring
				 PAGE: - Setup
					Channel Status  cmdID= 3060  "
		::= { iqdmx01CmdEntry 3060 }


	iqdmx01GPIIOGPIInputDisableInputs OBJECT-TYPE
		SYNTAX		INTEGER { disable(0), enable(1) }
		MAX-ACCESS		read-write
		STATUS			current
		DESCRIPTION
				"TYPE: - Checkbox
				 PAGE: - Setup- GPI I/O
					Disable Inputs  cmdID= 2605 "
		::= { iqdmx01CmdEntry 2605 }


	iqdmx01GPIIOGPIInputInputTimerEnable OBJECT-TYPE
		SYNTAX		INTEGER { disable(0), enable(1) }
		MAX-ACCESS		read-write
		STATUS			current
		DESCRIPTION
				"TYPE: - Checkbox
				 PAGE: - Setup- GPI I/O
					InputTimer Enable  cmdID= 3053 "
		::= { iqdmx01CmdEntry 3053 }


	iqdmx01GPIIOGPIInputTimerActiveHigh OBJECT-TYPE
		SYNTAX		INTEGER { disable(0), enable(1) }
		MAX-ACCESS		read-write
		STATUS			current
		DESCRIPTION
				"TYPE: - Checkbox
				 PAGE: - Setup- GPI I/O
					TimerActive High  cmdID= 3054 "
		::= { iqdmx01CmdEntry 3054 }


	iqdmx01GPIIOGPIInputInputSelection OBJECT-TYPE
		SYNTAX		INTEGER
		MAX-ACCESS		read-write
		STATUS			current
		DESCRIPTION
				"TYPE: - Number
				 PAGE: - Setup- GPI I/O
					Input Selection  cmdID= 2011  min= -1  max= 12  step= 1  format= %.0f  div_scale= 1
					Min = -1  Max = 12  Step = 1 "
		::= { iqdmx01CmdEntry 2011 }


	iqdmx01GPIIOGPIInputGPIInStatus OBJECT-TYPE
		SYNTAX		RollCallString
		MAX-ACCESS		read-only
		STATUS			current
		DESCRIPTION
				"TYPE: - Display
				 PAGE: - Setup- GPI I/O
					GPI In Status  cmdID= 2048  format=   "
		::= { iqdmx01CmdEntry 2048 }


	iqdmx01GPIIOGPIOutputOutActiveHigh OBJECT-TYPE
		SYNTAX		INTEGER { disable(0), enable(1) }
		MAX-ACCESS		read-write
		STATUS			current
		DESCRIPTION
				"TYPE: - Checkbox
				 PAGE: - Setup- GPI I/O
					Out Active High  cmdID= 3540 "
		::= { iqdmx01CmdEntry 3540 }


	iqdmx01GPIIOGPIOutputOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2013
					Input Present  value= 0
					Standard 625  value= 1
					Video Delay  value= 2
					Unused  value= 3  "
		::= { iqdmx01CmdEntry 2013 }


	iqdmx01GPIIOGPIOutputGPIOutStatus OBJECT-TYPE
		SYNTAX		RollCallString
		MAX-ACCESS		read-only
		STATUS			current
		DESCRIPTION
				"TYPE: - Display
				 PAGE: - Setup- GPI I/O
					GPI Out Status  cmdID= 2049  format=   "
		::= { iqdmx01CmdEntry 2049 }


	iqdmx01GPIIOGPIInputOutputGPIO1 OBJECT-TYPE
		SYNTAX		INTEGER { disable(0), enable(1) }
		MAX-ACCESS		read-write
		STATUS			current
		DESCRIPTION
				"TYPE: - Checkbox
				 PAGE: - Setup- GPI I/O
					GPI/O 1  cmdID= 2014 "
		::= { iqdmx01CmdEntry 2014 }


	iqdmx01SetupGPIIOInputSelection OBJECT-TYPE
		SYNTAX		INTEGER
		MAX-ACCESS		read-write
		STATUS			current
		DESCRIPTION
				"TYPE: - Number
				 PAGE: - Setup- GPI I/O
					Input Selection  cmdID= 2875  min= -1  max= 12  step= 1  format= %.0f  div_scale= 1
					Min = -1  Max = 12  Step = 1 "
		::= { iqdmx01CmdEntry 2875 }


	iqdmx01SetupGPIIOOutputSelection OBJECT-TYPE
		SYNTAX		INTEGER {
							val_Input_Present(0),
							val_Standard_625(1),
							val_Video_Delay(2),
							val_Unused(3)
							}
		MAX-ACCESS		read-write
		STATUS			current
		DESCRIPTION
				"TYPE: - RadiobuttonList
				 PAGE: - Setup- GPI I/O
					Output Selection  cmdID= 2877
					Input Present  value= 0
					Standard 625  value= 1
					Video Delay  value= 2
					Unused  value= 3  "
		::= { iqdmx01CmdEntry 2877 }


	iqdmx01SetupRollTrackRollTrackIndex OBJECT-TYPE
		SYNTAX		INTEGER
		MAX-ACCESS		read-write
		STATUS			current
		DESCRIPTION
				"TYPE: - Number
				 PAGE: - Setup- RollTrack
					RollTrack Index  cmdID= 1495  min= 0  max= 69  step= 1  format= %.0f  div_scale= 1
					Min = 0  Max = 69  Step = 1 "
		::= { iqdmx01CmdEntry 1495 }


	iqdmx01SetupRollTrackRollTrackSource OBJECT-TYPE
		SYNTAX		INTEGER
		MAX-ACCESS		read-write
		STATUS			current
		DESCRIPTION
				"TYPE: - Number
				 PAGE: - Setup- RollTrack
					RollTrack Source  cmdID= 1496  min= -1  max= 40  step= 1  format= %.0f  div_scale= 1
					Min = -1  Max = 40  Step = 1 "
		::= { iqdmx01CmdEntry 1496 }


	iqdmx01SetupRollTrackRollTrackDisable OBJECT-TYPE
		SYNTAX		INTEGER { disable(0), enable(1) }
		MAX-ACCESS		read-write
		STATUS			current
		DESCRIPTION
				"TYPE: - Checkbox
				 PAGE: - Setup- RollTrack
					RollTrack Disable  cmdID= 1513 "
		::= { iqdmx01CmdEntry 1513 }


	iqdmx01SetupRollTrackRollTrackAddress OBJECT-TYPE
		SYNTAX		RollCallString
		MAX-ACCESS		read-write
		STATUS			current
		DESCRIPTION
				"TYPE: - Editstring
				 PAGE: - Setup- RollTrack
					RollTrack Address  cmdID= 1497  "
		::= { iqdmx01CmdEntry 1497 }


	iqdmx01SetupRollTrackRollTrackCommand OBJECT-TYPE
		SYNTAX		RollCallString
		MAX-ACCESS		read-write
		STATUS			current
		DESCRIPTION
				"TYPE: - Editstring
				 PAGE: - Setup- RollTrack
					RollTrack Command  cmdID= 1498  "
		::= { iqdmx01CmdEntry 1498 }


	iqdmx01SetupRollTrackRollTrackSending OBJECT-TYPE
		SYNTAX		RollCallString
		MAX-ACCESS		read-only
		STATUS			current
		DESCRIPTION
				"TYPE: - Display
				 PAGE: - Setup- RollTrack
					RollTrack Sending  cmdID= 1514  format=   "
		::= { iqdmx01CmdEntry 1514 }


	iqdmx01SetupRollTrackRollTrackStatus OBJECT-TYPE
		SYNTAX		RollCallString
		MAX-ACCESS		read-only
		STATUS			current
		DESCRIPTION
				"TYPE: - Display
				 PAGE: - Setup- RollTrack
					RollTrack Status  cmdID= 1511  format=   "
		::= { iqdmx01CmdEntry 1511 }


	iqdmx01SetupRollTrackRollTrack_Index OBJECT-TYPE
		SYNTAX		INTEGER
		MAX-ACCESS		read-write
		STATUS			current
		DESCRIPTION
				"TYPE: - Number
				 PAGE: - Setup- RollTrack
					RollTrack Index  cmdID= 2870  min= 0  max= 69  step= 1  format= %.0f  div_scale= 1
					Min = 0  Max = 69  Step = 1 "
		::= { iqdmx01CmdEntry 2870 }


	iqdmx01SetupRollTrackRollTrack_Source OBJECT-TYPE
		SYNTAX		INTEGER
		MAX-ACCESS		read-write
		STATUS			current
		DESCRIPTION
				"TYPE: - Number
				 PAGE: - Setup- RollTrack
					RollTrack Source  cmdID= 2871  min= -1  max= 40  step= 1  format= %.0f  div_scale= 1
					Min = -1  Max = 40  Step = 1 "
		::= { iqdmx01CmdEntry 2871 }


	iqdmx01SetupRollTrackRollTrack_Address OBJECT-TYPE
		SYNTAX		RollCallString
		MAX-ACCESS		read-write
		STATUS			current
		DESCRIPTION
				"TYPE: - Editstring
				 PAGE: - Setup- RollTrack
					RollTrack Address  cmdID= 2872  "
		::= { iqdmx01CmdEntry 2872 }


	iqdmx01SetupRollTrackRollTrack_Command OBJECT-TYPE
		SYNTAX		RollCallString
		MAX-ACCESS		read-write
		STATUS			current
		DESCRIPTION
				"TYPE: - Editstring
				 PAGE: - Setup- RollTrack
					RollTrack Command  cmdID= 2873  "
		::= { iqdmx01CmdEntry 2873 }


	iqdmx01SetupLoggingInput OBJECT-TYPE
		SYNTAX		INTEGER { disable(0), enable(1) }
		MAX-ACCESS		read-write
		STATUS			current
		DESCRIPTION
				"TYPE: - Checkbox
				 PAGE: - Setup- Logging
					Input  cmdID= 1060 "
		::= { iqdmx01CmdEntry 1060 }


	iqdmx01SetupLoggingStd OBJECT-TYPE
		SYNTAX		INTEGER { disable(0), enable(1) }
		MAX-ACCESS		read-write
		STATUS			current
		DESCRIPTION
				"TYPE: - Checkbox
				 PAGE: - Setup- Logging
					Std  cmdID= 1061 "
		::= { iqdmx01CmdEntry 1061 }


	iqdmx01SetupLoggingInput1 OBJECT-TYPE
		SYNTAX		INTEGER { disable(0), enable(1) }
		MAX-ACCESS		read-write
		STATUS			current
		DESCRIPTION
				"TYPE: - Checkbox
				 PAGE: - Setup- Logging
					Input1  cmdID= 1094 "
		::= { iqdmx01CmdEntry 1094 }


	iqdmx01SetupLoggingStd1 OBJECT-TYPE
		SYNTAX		INTEGER { disable(0), enable(1) }
		MAX-ACCESS		read-write
		STATUS			current
		DESCRIPTION
				"TYPE: - Checkbox
				 PAGE: - Setup- Logging
					Std1  cmdID= 1097 "
		::= { iqdmx01CmdEntry 1097 }


	iqdmx01SetupLoggingInput2 OBJECT-TYPE
		SYNTAX		INTEGER { disable(0), enable(1) }
		MAX-ACCESS		read-write
		STATUS			current
		DESCRIPTION
				"TYPE: - Checkbox
				 PAGE: - Setup- Logging
					Input2  cmdID= 1095 "
		::= { iqdmx01CmdEntry 1095 }


	iqdmx01SetupLoggingStd2 OBJECT-TYPE
		SYNTAX		INTEGER { disable(0), enable(1) }
		MAX-ACCESS		read-write
		STATUS			current
		DESCRIPTION
				"TYPE: - Checkbox
				 PAGE: - Setup- Logging
					Std2  cmdID= 1098 "
		::= { iqdmx01CmdEntry 1098 }


	iqdmx01SetupLoggingEDH OBJECT-TYPE
		SYNTAX		INTEGER { disable(0), enable(1) }
		MAX-ACCESS		read-write
		STATUS			current
		DESCRIPTION
				"TYPE: - Checkbox
				 PAGE: - Setup- Logging
					EDH  cmdID= 1064 "
		::= { iqdmx01CmdEntry 1064 }


	iqdmx01SetupLoggingEDHErrors OBJECT-TYPE
		SYNTAX		INTEGER { disable(0), enable(1) }
		MAX-ACCESS		read-write
		STATUS			current
		DESCRIPTION
				"TYPE: - Checkbox
				 PAGE: - Setup- Logging
					EDH Errors  cmdID= 1070 "
		::= { iqdmx01CmdEntry 1070 }


	iqdmx01SetupLoggingRollTrack OBJECT-TYPE
		SYNTAX		INTEGER { disable(0), enable(1) }
		MAX-ACCESS		read-write
		STATUS			current
		DESCRIPTION
				"TYPE: - Checkbox
				 PAGE: - Setup- Logging
					RollTrack  cmdID= 1106 "
		::= { iqdmx01CmdEntry 1106 }


	iqdmx01SetupLoggingDeembed1 OBJECT-TYPE
		SYNTAX		INTEGER { disable(0), enable(1) }
		MAX-ACCESS		read-write
		STATUS			current
		DESCRIPTION
				"TYPE: - Checkbox
				 PAGE: - Setup- Logging
					De-embed 1  cmdID= 1120 "
		::= { iqdmx01CmdEntry 1120 }


	iqdmx01SetupLoggingDeembed2 OBJECT-TYPE
		SYNTAX		INTEGER { disable(0), enable(1) }
		MAX-ACCESS		read-write
		STATUS			current
		DESCRIPTION
				"TYPE: - Checkbox
				 PAGE: - Setup- Logging
					De-embed 2  cmdID= 1121 "
		::= { iqdmx01CmdEntry 1121 }


	iqdmx01SetupLoggingDeembed3 OBJECT-TYPE
		SYNTAX		INTEGER { disable(0), enable(1) }
		MAX-ACCESS		read-write
		STATUS			current
		DESCRIPTION
				"TYPE: - Checkbox
				 PAGE: - Setup- Logging
					De-embed 3  cmdID= 1122 "
		::= { iqdmx01CmdEntry 1122 }


	iqdmx01SetupLoggingDeembed4 OBJECT-TYPE
		SYNTAX		INTEGER { disable(0), enable(1) }
		MAX-ACCESS		read-write
		STATUS			current
		DESCRIPTION
				"TYPE: - Checkbox
				 PAGE: - Setup- Logging
					De-embed 4  cmdID= 1123 "
		::= { iqdmx01CmdEntry 1123 }


	iqdmx01SetupLoggingDeembed5 OBJECT-TYPE
		SYNTAX		INTEGER { disable(0), enable(1) }
		MAX-ACCESS		read-write
		STATUS			current
		DESCRIPTION
				"TYPE: - Checkbox
				 PAGE: - Setup- Logging
					De-embed 5  cmdID= 1124 "
		::= { iqdmx01CmdEntry 1124 }


	iqdmx01SetupLoggingDeembed6 OBJECT-TYPE
		SYNTAX		INTEGER { disable(0), enable(1) }
		MAX-ACCESS		read-write
		STATUS			current
		DESCRIPTION
				"TYPE: - Checkbox
				 PAGE: - Setup- Logging
					De-embed 6  cmdID= 1125 "
		::= { iqdmx01CmdEntry 1125 }


	iqdmx01SetupLoggingDeembed7 OBJECT-TYPE
		SYNTAX		INTEGER { disable(0), enable(1) }
		MAX-ACCESS		read-write
		STATUS			current
		DESCRIPTION
				"TYPE: - Checkbox
				 PAGE: - Setup- Logging
					De-embed 7  cmdID= 1126 "
		::= { iqdmx01CmdEntry 1126 }


	iqdmx01SetupLoggingDeembed8 OBJECT-TYPE
		SYNTAX		INTEGER { disable(0), enable(1) }
		MAX-ACCESS		read-write
		STATUS			current
		DESCRIPTION
				"TYPE: - Checkbox
				 PAGE: - Setup- Logging
					De-embed 8  cmdID= 1127 "
		::= { iqdmx01CmdEntry 1127 }


	iqdmx01SetupLoggingnPCM1 OBJECT-TYPE
		SYNTAX		INTEGER { disable(0), enable(1) }
		MAX-ACCESS		read-write
		STATUS			current
		DESCRIPTION
				"TYPE: - Checkbox
				 PAGE: - Setup- Logging
					nPCM 1  cmdID= 1128 "
		::= { iqdmx01CmdEntry 1128 }


	iqdmx01SetupLoggingnPCM2 OBJECT-TYPE
		SYNTAX		INTEGER { disable(0), enable(1) }
		MAX-ACCESS		read-write
		STATUS			current
		DESCRIPTION
				"TYPE: - Checkbox
				 PAGE: - Setup- Logging
					nPCM 2  cmdID= 1129 "
		::= { iqdmx01CmdEntry 1129 }


	iqdmx01SetupLoggingnPCM3 OBJECT-TYPE
		SYNTAX		INTEGER { disable(0), enable(1) }
		MAX-ACCESS		read-write
		STATUS			current
		DESCRIPTION
				"TYPE: - Checkbox
				 PAGE: - Setup- Logging
					nPCM 3  cmdID= 1130 "
		::= { iqdmx01CmdEntry 1130 }


	iqdmx01SetupLoggingnPCM4 OBJECT-TYPE
		SYNTAX		INTEGER { disable(0), enable(1) }
		MAX-ACCESS		read-write
		STATUS			current
		DESCRIPTION
				"TYPE: - Checkbox
				 PAGE: - Setup- Logging
					nPCM 4  cmdID= 1131 "
		::= { iqdmx01CmdEntry 1131 }


	iqdmx01SetupLoggingnPCM5 OBJECT-TYPE
		SYNTAX		INTEGER { disable(0), enable(1) }
		MAX-ACCESS		read-write
		STATUS			current
		DESCRIPTION
				"TYPE: - Checkbox
				 PAGE: - Setup- Logging
					nPCM 5  cmdID= 1132 "
		::= { iqdmx01CmdEntry 1132 }


	iqdmx01SetupLoggingnPCM6 OBJECT-TYPE
		SYNTAX		INTEGER { disable(0), enable(1) }
		MAX-ACCESS		read-write
		STATUS			current
		DESCRIPTION
				"TYPE: - Checkbox
				 PAGE: - Setup- Logging
					nPCM 6  cmdID= 1133 "
		::= { iqdmx01CmdEntry 1133 }


	iqdmx01SetupLoggingnPCM7 OBJECT-TYPE
		SYNTAX		INTEGER { disable(0), enable(1) }
		MAX-ACCESS		read-write
		STATUS			current
		DESCRIPTION
				"TYPE: - Checkbox
				 PAGE: - Setup- Logging
					nPCM 7  cmdID= 1134 "
		::= { iqdmx01CmdEntry 1134 }


	iqdmx01SetupLoggingnPCM8 OBJECT-TYPE
		SYNTAX		INTEGER { disable(0), enable(1) }
		MAX-ACCESS		read-write
		STATUS			current
		DESCRIPTION
				"TYPE: - Checkbox
				 PAGE: - Setup- Logging
					nPCM 8  cmdID= 1135 "
		::= { iqdmx01CmdEntry 1135 }


	iqdmx01SetupLoggingBusAL OBJECT-TYPE
		SYNTAX		INTEGER { disable(0), enable(1) }
		MAX-ACCESS		read-write
		STATUS			current
		DESCRIPTION
				"TYPE: - Checkbox
				 PAGE: - Setup- Logging
					Bus AL  cmdID= 1112 "
		::= { iqdmx01CmdEntry 1112 }


	iqdmx01SetupLoggingBusAR OBJECT-TYPE
		SYNTAX		INTEGER { disable(0), enable(1) }
		MAX-ACCESS		read-write
		STATUS			current
		DESCRIPTION
				"TYPE: - Checkbox
				 PAGE: - Setup- Logging
					Bus AR  cmdID= 1113 "
		::= { iqdmx01CmdEntry 1113 }


	iqdmx01SetupLoggingBusBL OBJECT-TYPE
		SYNTAX		INTEGER { disable(0), enable(1) }
		MAX-ACCESS		read-write
		STATUS			current
		DESCRIPTION
				"TYPE: - Checkbox
				 PAGE: - Setup- Logging
					Bus BL  cmdID= 1114 "
		::= { iqdmx01CmdEntry 1114 }


	iqdmx01SetupLoggingBusBR OBJECT-TYPE
		SYNTAX		INTEGER { disable(0), enable(1) }
		MAX-ACCESS		read-write
		STATUS			current
		DESCRIPTION
				"TYPE: - Checkbox
				 PAGE: - Setup- Logging
					Bus BR  cmdID= 1115 "
		::= { iqdmx01CmdEntry 1115 }


	iqdmx01SetupLoggingBusCL OBJECT-TYPE
		SYNTAX		INTEGER { disable(0), enable(1) }
		MAX-ACCESS		read-write
		STATUS			current
		DESCRIPTION
				"TYPE: - Checkbox
				 PAGE: - Setup- Logging
					Bus CL  cmdID= 1116 "
		::= { iqdmx01CmdEntry 1116 }


	iqdmx01SetupLoggingBusCR OBJECT-TYPE
		SYNTAX		INTEGER { disable(0), enable(1) }
		MAX-ACCESS		read-write
		STATUS			current
		DESCRIPTION
				"TYPE: - Checkbox
				 PAGE: - Setup- Logging
					Bus CR  cmdID= 1117 "
		::= { iqdmx01CmdEntry 1117 }


	iqdmx01SetupLoggingBusDL OBJECT-TYPE
		SYNTAX		INTEGER { disable(0), enable(1) }
		MAX-ACCESS		read-write
		STATUS			current
		DESCRIPTION
				"TYPE: - Checkbox
				 PAGE: - Setup- Logging
					Bus DL  cmdID= 1118 "
		::= { iqdmx01CmdEntry 1118 }


	iqdmx01SetupLoggingBusDR OBJECT-TYPE
		SYNTAX		INTEGER { disable(0), enable(1) }
		MAX-ACCESS		read-write
		STATUS			current
		DESCRIPTION
				"TYPE: - Checkbox
				 PAGE: - Setup- Logging
					Bus DR  cmdID= 1119 "
		::= { iqdmx01CmdEntry 1119 }


	iqdmx01SetupLoggingFault OBJECT-TYPE
		SYNTAX		INTEGER { disable(0), enable(1) }
		MAX-ACCESS		read-write
		STATUS			current
		DESCRIPTION
				"TYPE: - Checkbox
				 PAGE: - Setup- Logging
					Fault  cmdID= 1069 "
		::= { iqdmx01CmdEntry 1069 }


	iqdmx01SetupLoggingStatusINPUT OBJECT-TYPE
		SYNTAX		RollCallString
		MAX-ACCESS		read-only
		STATUS			current
		DESCRIPTION
				"TYPE: - Display
				 PAGE: - Setup- Logging Status
					INPUT=  cmdID= 2980  format=   "
		::= { iqdmx01CmdEntry 2980 }


	iqdmx01SetupLoggingStatusSTD OBJECT-TYPE
		SYNTAX		RollCallString
		MAX-ACCESS		read-only
		STATUS			current
		DESCRIPTION
				"TYPE: - Display
				 PAGE: - Setup- Logging Status
					STD=  cmdID= 2981  format=   "
		::= { iqdmx01CmdEntry 2981 }


	iqdmx01SetupLoggingStatusINPUT1 OBJECT-TYPE
		SYNTAX		RollCallString
		MAX-ACCESS		read-only
		STATUS			current
		DESCRIPTION
				"TYPE: - Display
				 PAGE: - Setup- Logging Status
					INPUT1=  cmdID= 2982  format=   "
		::= { iqdmx01CmdEntry 2982 }


	iqdmx01SetupLoggingStatusSTD1 OBJECT-TYPE
		SYNTAX		RollCallString
		MAX-ACCESS		read-only
		STATUS			current
		DESCRIPTION
				"TYPE: - Display
				 PAGE: - Setup- Logging Status
					STD1=  cmdID= 2983  format=   "
		::= { iqdmx01CmdEntry 2983 }


	iqdmx01SetupLoggingStatusINPUT2 OBJECT-TYPE
		SYNTAX		RollCallString
		MAX-ACCESS		read-only
		STATUS			current
		DESCRIPTION
				"TYPE: - Display
				 PAGE: - Setup- Logging Status
					INPUT2=  cmdID= 2984  format=   "
		::= { iqdmx01CmdEntry 2984 }


	iqdmx01SetupLoggingStatusSTD2 OBJECT-TYPE
		SYNTAX		RollCallString
		MAX-ACCESS		read-only
		STATUS			current
		DESCRIPTION
				"TYPE: - Display
				 PAGE: - Setup- Logging Status
					STD2=  cmdID= 2985  format=   "
		::= { iqdmx01CmdEntry 2985 }


	iqdmx01SetupLoggingStatusEDH OBJECT-TYPE
		SYNTAX		RollCallString
		MAX-ACCESS		read-only
		STATUS			current
		DESCRIPTION
				"TYPE: - Display
				 PAGE: - Setup- Logging Status
					EDH=  cmdID= 2987  format=   "
		::= { iqdmx01CmdEntry 2987 }


	iqdmx01SetupLoggingStatusERRSEC OBJECT-TYPE
		SYNTAX		RollCallString
		MAX-ACCESS		read-only
		STATUS			current
		DESCRIPTION
				"TYPE: - Display
				 PAGE: - Setup- Logging Status
					ERRSEC=  cmdID= 2988  format=   "
		::= { iqdmx01CmdEntry 2988 }


	iqdmx01SetupLoggingStatusROLLTRACK OBJECT-TYPE
		SYNTAX		RollCallString
		MAX-ACCESS		read-only
		STATUS			current
		DESCRIPTION
				"TYPE: - Display
				 PAGE: - Setup- Logging Status
					ROLLTRACK=  cmdID= 2989  format=   "
		::= { iqdmx01CmdEntry 2989 }


	iqdmx01SetupLoggingStatusDEEMBED1 OBJECT-TYPE
		SYNTAX		RollCallString
		MAX-ACCESS		read-only
		STATUS			current
		DESCRIPTION
				"TYPE: - Display
				 PAGE: - Setup- Logging Status
					DEEMBED1=  cmdID= 3014  format=   "
		::= { iqdmx01CmdEntry 3014 }


	iqdmx01SetupLoggingStatusDEEMBED2 OBJECT-TYPE
		SYNTAX		RollCallString
		MAX-ACCESS		read-only
		STATUS			current
		DESCRIPTION
				"TYPE: - Display
				 PAGE: - Setup- Logging Status
					DEEMBED2=  cmdID= 3015  format=   "
		::= { iqdmx01CmdEntry 3015 }


	iqdmx01SetupLoggingStatusDEEMBED3 OBJECT-TYPE
		SYNTAX		RollCallString
		MAX-ACCESS		read-only
		STATUS			current
		DESCRIPTION
				"TYPE: - Display
				 PAGE: - Setup- Logging Status
					DEEMBED3=  cmdID= 3016  format=   "
		::= { iqdmx01CmdEntry 3016 }


	iqdmx01SetupLoggingStatusDEEMBED4 OBJECT-TYPE
		SYNTAX		RollCallString
		MAX-ACCESS		read-only
		STATUS			current
		DESCRIPTION
				"TYPE: - Display
				 PAGE: - Setup- Logging Status
					DEEMBED4=  cmdID= 3017  format=   "
		::= { iqdmx01CmdEntry 3017 }


	iqdmx01SetupLoggingStatusDEEMBED5 OBJECT-TYPE
		SYNTAX		RollCallString
		MAX-ACCESS		read-only
		STATUS			current
		DESCRIPTION
				"TYPE: - Display
				 PAGE: - Setup- Logging Status
					DEEMBED5=  cmdID= 3018  format=   "
		::= { iqdmx01CmdEntry 3018 }


	iqdmx01SetupLoggingStatusDEEMBED6 OBJECT-TYPE
		SYNTAX		RollCallString
		MAX-ACCESS		read-only
		STATUS			current
		DESCRIPTION
				"TYPE: - Display
				 PAGE: - Setup- Logging Status
					DEEMBED6=  cmdID= 3019  format=   "
		::= { iqdmx01CmdEntry 3019 }


	iqdmx01SetupLoggingStatusDEEMBED7 OBJECT-TYPE
		SYNTAX		RollCallString
		MAX-ACCESS		read-only
		STATUS			current
		DESCRIPTION
				"TYPE: - Display
				 PAGE: - Setup- Logging Status
					DEEMBED7=  cmdID= 3020  format=   "
		::= { iqdmx01CmdEntry 3020 }


	iqdmx01SetupLoggingStatusDEEMBED8 OBJECT-TYPE
		SYNTAX		RollCallString
		MAX-ACCESS		read-only
		STATUS			current
		DESCRIPTION
				"TYPE: - Display
				 PAGE: - Setup- Logging Status
					DEEMBED8=  cmdID= 3021  format=   "
		::= { iqdmx01CmdEntry 3021 }


	iqdmx01SetupLoggingStatusNPCM1 OBJECT-TYPE
		SYNTAX		RollCallString
		MAX-ACCESS		read-only
		STATUS			current
		DESCRIPTION
				"TYPE: - Display
				 PAGE: - Setup- Logging Status
					NPCM1=  cmdID= 3022  format=   "
		::= { iqdmx01CmdEntry 3022 }


	iqdmx01SetupLoggingStatusNPCM2 OBJECT-TYPE
		SYNTAX		RollCallString
		MAX-ACCESS		read-only
		STATUS			current
		DESCRIPTION
				"TYPE: - Display
				 PAGE: - Setup- Logging Status
					NPCM2=  cmdID= 3023  format=   "
		::= { iqdmx01CmdEntry 3023 }


	iqdmx01SetupLoggingStatusNPCM3 OBJECT-TYPE
		SYNTAX		RollCallString
		MAX-ACCESS		read-only
		STATUS			current
		DESCRIPTION
				"TYPE: - Display
				 PAGE: - Setup- Logging Status
					NPCM3=  cmdID= 3024  format=   "
		::= { iqdmx01CmdEntry 3024 }


	iqdmx01SetupLoggingStatusNPCM4 OBJECT-TYPE
		SYNTAX		RollCallString
		MAX-ACCESS		read-only
		STATUS			current
		DESCRIPTION
				"TYPE: - Display
				 PAGE: - Setup- Logging Status
					NPCM4=  cmdID= 3025  format=   "
		::= { iqdmx01CmdEntry 3025 }


	iqdmx01SetupLoggingStatusNPCM5 OBJECT-TYPE
		SYNTAX		RollCallString
		MAX-ACCESS		read-only
		STATUS			current
		DESCRIPTION
				"TYPE: - Display
				 PAGE: - Setup- Logging Status
					NPCM5=  cmdID= 3026  format=   "
		::= { iqdmx01CmdEntry 3026 }


	iqdmx01SetupLoggingStatusNPCM6 OBJECT-TYPE
		SYNTAX		RollCallString
		MAX-ACCESS		read-only
		STATUS			current
		DESCRIPTION
				"TYPE: - Display
				 PAGE: - Setup- Logging Status
					NPCM6=  cmdID= 3027  format=   "
		::= { iqdmx01CmdEntry 3027 }


	iqdmx01SetupLoggingStatusNPCM7 OBJECT-TYPE
		SYNTAX		RollCallString
		MAX-ACCESS		read-only
		STATUS			current
		DESCRIPTION
				"TYPE: - Display
				 PAGE: - Setup- Logging Status
					NPCM7=  cmdID= 3028  format=   "
		::= { iqdmx01CmdEntry 3028 }


	iqdmx01SetupLoggingStatusNPCM8 OBJECT-TYPE
		SYNTAX		RollCallString
		MAX-ACCESS		read-only
		STATUS			current
		DESCRIPTION
				"TYPE: - Display
				 PAGE: - Setup- Logging Status
					NPCM8=  cmdID= 3029  format=   "
		::= { iqdmx01CmdEntry 3029 }


	iqdmx01SetupLoggingStatusBUSAL OBJECT-TYPE
		SYNTAX		RollCallString
		MAX-ACCESS		read-only
		STATUS			current
		DESCRIPTION
				"TYPE: - Display
				 PAGE: - Setup- Logging Status
					BUSAL=  cmdID= 2998  format=   "
		::= { iqdmx01CmdEntry 2998 }


	iqdmx01SetupLoggingStatusBUSAR OBJECT-TYPE
		SYNTAX		RollCallString
		MAX-ACCESS		read-only
		STATUS			current
		DESCRIPTION
				"TYPE: - Display
				 PAGE: - Setup- Logging Status
					BUSAR=  cmdID= 2999  format=   "
		::= { iqdmx01CmdEntry 2999 }


	iqdmx01SetupLoggingStatusBUSBL OBJECT-TYPE
		SYNTAX		RollCallString
		MAX-ACCESS		read-only
		STATUS			current
		DESCRIPTION
				"TYPE: - Display
				 PAGE: - Setup- Logging Status
					BUSBL=  cmdID= 3000  format=   "
		::= { iqdmx01CmdEntry 3000 }


	iqdmx01SetupLoggingStatusBUSBR OBJECT-TYPE
		SYNTAX		RollCallString
		MAX-ACCESS		read-only
		STATUS			current
		DESCRIPTION
				"TYPE: - Display
				 PAGE: - Setup- Logging Status
					BUSBR=  cmdID= 3001  format=   "
		::= { iqdmx01CmdEntry 3001 }


	iqdmx01SetupLoggingStatusBUSCL OBJECT-TYPE
		SYNTAX		RollCallString
		MAX-ACCESS		read-only
		STATUS			current
		DESCRIPTION
				"TYPE: - Display
				 PAGE: - Setup- Logging Status
					BUSCL=  cmdID= 3002  format=   "
		::= { iqdmx01CmdEntry 3002 }


	iqdmx01SetupLoggingStatusBUSCR OBJECT-TYPE
		SYNTAX		RollCallString
		MAX-ACCESS		read-only
		STATUS			current
		DESCRIPTION
				"TYPE: - Display
				 PAGE: - Setup- Logging Status
					BUSCR=  cmdID= 3003  format=   "
		::= { iqdmx01CmdEntry 3003 }


	iqdmx01SetupLoggingStatusBUSDL OBJECT-TYPE
		SYNTAX		RollCallString
		MAX-ACCESS		read-only
		STATUS			current
		DESCRIPTION
				"TYPE: - Display
				 PAGE: - Setup- Logging Status
					BUSDL=  cmdID= 3004  format=   "
		::= { iqdmx01CmdEntry 3004 }


	iqdmx01SetupLoggingStatusBUSDR OBJECT-TYPE
		SYNTAX		RollCallString
		MAX-ACCESS		read-only
		STATUS			current
		DESCRIPTION
				"TYPE: - Display
				 PAGE: - Setup- Logging Status
					BUSDR=  cmdID= 3005  format=   "
		::= { iqdmx01CmdEntry 3005 }


	iqdmx01SetupLoggingStatusFAULT OBJECT-TYPE
		SYNTAX		RollCallString
		MAX-ACCESS		read-only
		STATUS			current
		DESCRIPTION
				"TYPE: - Display
				 PAGE: - Setup- Logging Status
					FAULT=  cmdID= 2990  format=   "
		::= { iqdmx01CmdEntry 2990 }


	iqdmx01SetupInformationWindow OBJECT-TYPE
		SYNTAX		INTEGER {
							val_Input_Status(0),
							val_EDH_ANC_Status(1),
							val_Audio_Input_Status(2)
							}
		MAX-ACCESS		read-write
		STATUS			current
		DESCRIPTION
				"TYPE: - Button
				 PAGE: - Setup- Information Window
					Input Status  cmdID= 1915  value= 0
					EDH & ANC Status  cmdID= 1915  value= 1
					Audio Input Status  cmdID= 1915  value= 2  "
		::= { iqdmx01CmdEntry 1915 }


	iqdmx01SetupInformationWindowResetErrors OBJECT-TYPE
		SYNTAX		INTEGER { noAction(0),val_Reset_Errors(1) }
		MAX-ACCESS		read-write
		STATUS			current
		DESCRIPTION
				"TYPE: - Button
				 PAGE: - Setup- Information Window
					Reset Errors  cmdID= 2978  value= 1  "
		::= { iqdmx01CmdEntry 2978 }


	iqdmx01SetupDefaultOutput OBJECT-TYPE
		SYNTAX		INTEGER {
							val_Video(1),
							val_Freeze(2),
							val_Pattern(3)
							}
		MAX-ACCESS		read-write
		STATUS			current
		DESCRIPTION
				"TYPE: - Button
				 PAGE: - Setup- Default Output
					Video  cmdID= 1202  value= 1
					Freeze  cmdID= 1202  value= 2
					Pattern  cmdID= 1202  value= 3  "
		::= { iqdmx01CmdEntry 1202 }


	iqdmx01SetupDefaultPattern OBJECT-TYPE
		SYNTAX		INTEGER {
							val_Black(0),
							val_EBU_Colour_Bars(1),
							val_100_Colour_Bars(2),
							val_Ramp(3),
							val_Multiburst(4),
							val_Pulse_Bar(5)
							}
		MAX-ACCESS		read-write
		STATUS			current
		DESCRIPTION
				"TYPE: - Button
				 PAGE: - Setup- Default Output
					Black  cmdID= 1038  value= 0
					EBU Colour Bars  cmdID= 1038  value= 1
					100% Colour Bars  cmdID= 1038  value= 2
					Ramp  cmdID= 1038  value= 3
					Multiburst  cmdID= 1038  value= 4
					Pulse & Bar  cmdID= 1038  value= 5  "
		::= { iqdmx01CmdEntry 1038 }


	iqdmx01SetupUnitSoftwareVersion OBJECT-TYPE
		SYNTAX		RollCallString
		MAX-ACCESS		read-only
		STATUS			current
		DESCRIPTION
				"TYPE: - Display
				 PAGE: - Setup- Unit
					Software Version  cmdID= 2  format=   "
		::= { iqdmx01CmdEntry 2 }


	iqdmx01SetupUnitSerialNo OBJECT-TYPE
		SYNTAX		RollCallString
		MAX-ACCESS		read-only
		STATUS			current
		DESCRIPTION
				"TYPE: - Display
				 PAGE: - Setup- Unit
					Serial No  cmdID= 1  format=   "
		::= { iqdmx01CmdEntry 1 }


	iqdmx01SetupUnitPresetUnit OBJECT-TYPE
		SYNTAX		INTEGER { noAction(0),val_Preset_Unit(1) }
		MAX-ACCESS		read-write
		STATUS			current
		DESCRIPTION
				"TYPE: - Button
				 PAGE: - Setup- Unit
					Preset Unit  cmdID= 3  value= 1  "
		::= { iqdmx01CmdEntry 3 }


	iqdmx01SetupUnitRestart OBJECT-TYPE
		SYNTAX		INTEGER { noAction(0),val_Restart(1) }
		MAX-ACCESS		read-write
		STATUS			current
		DESCRIPTION
				"TYPE: - Button
				 PAGE: - Setup- Unit
					Restart  cmdID= 4  value= 1  "
		::= { iqdmx01CmdEntry 4 }


	iqdmx01SetupUnitBuildNo OBJECT-TYPE
		SYNTAX		RollCallString
		MAX-ACCESS		read-only
		STATUS			current
		DESCRIPTION
				"TYPE: - Display
				 PAGE: - Setup- Unit
					Build No  cmdID= 5  format=   "
		::= { iqdmx01CmdEntry 5 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: xxxxxxxxxxxxxxxxxxx
--				:
-- Comments		: Serial Number   Runtime string
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE              The unit is not locked to the input signal
--				: FAIL              EDH errors have been found on the input signal
--              : OK                No EDH errors found on the input signal
--              : RESET             EDH statistics have been reset
-- Comments		:
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		:
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: STDERR            Input signal standard not recognized or no signal
--				: UNKNOWN           Not a selected input standard
--              : 525               Input standard 525
--              : 625               Input standard 625
-- Comments		:
--
---------------------------------------------------------------------------------------------------
-- Header		: STD1
--
-- MIB ref		: swCardEventLogSlotXX       .4.83.84.68.49
-- absolute OID	: 1.3.6.1.4.1.7995.2.6.1.1.XX.4.83.84.68.49
-- Vary			: YES
--
-- Value(s)		: ERR               Not a selected input standard Input 1
--				: 525               Input 1 standard 525
--              : 625               Input 1 standard 625
-- Comments		:
--
---------------------------------------------------------------------------------------------------
-- Header		: STD2
--
-- MIB ref		: swCardEventLogSlotXX       .4.83.84.68.50
-- absolute OID	: 1.3.6.1.4.1.7995.2.6.1.1.XX.4.83.84.68.50
-- Vary			: YES
--
-- Value(s)		: ERR               Not a selected input standard Input 2
--				: 525               Input 2 standard 525
--              : 625               Input 2 standard 625
-- Comments		:
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: NONE              No Internal errors detected
--				: FAIL              Internal error detected
--              : FAIL.FPGA_LOAD    Fpga load failure detected
-- Comments		:
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: OK                Valid input signal
--				: ERR               Invalid input signal
--              : LOST              Input signal lost
-- Comments		:
--
---------------------------------------------------------------------------------------------------
-- Header		: BUS_AL
--
-- MIB ref		: swCardEventLogSlotXX       .6.66.85.83.95.65.76
-- absolute OID	: 1.3.6.1.4.1.7995.2.6.1.1.XX.6.66.85.83.95.65.76
-- Vary			: YES
--
-- Value(s)		: OK                Router BUS A Left channel has valid signal selected
--              : WARNING           Router BUS A Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_AR
--
-- MIB ref		: swCardEventLogSlotXX       .6.66.85.83.95.65.82
-- absolute OID	: 1.3.6.1.4.1.7995.2.6.1.1.XX.6.66.85.83.95.65.82
-- Vary			: YES
--
-- Value(s)		: OK                Router BUS A Right channel has valid signal selected
--              : WARNING           Router BUS A Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_BL
--
-- MIB ref		: swCardEventLogSlotXX       .6.66.85.83.95.66.76
-- absolute OID	: 1.3.6.1.4.1.7995.2.6.1.1.XX.6.66.85.83.95.66.76
-- Vary			: YES
--
-- Value(s)		: OK                Router BUS B Left channel has valid signal selected
--              : WARNING           Router BUS B Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_BR
--
-- MIB ref		: swCardEventLogSlotXX       .6.66.85.83.95.66.82
-- absolute OID	: 1.3.6.1.4.1.7995.2.6.1.1.XX.6.66.85.83.95.66.82
-- Vary			: YES
--
-- Value(s)		: OK                Router BUS B Right channel has valid signal selected
--              : WARNING           Router BUS B Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_CL
--
-- MIB ref		: swCardEventLogSlotXX       .6.66.85.83.95.67.76
-- absolute OID	: 1.3.6.1.4.1.7995.2.6.1.1.XX.6.66.85.83.95.67.76
-- Vary			: YES
--
-- Value(s)		: OK                Router BUS C Left channel has valid signal selected
--              : WARNING           Router BUS C Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_CR
--
-- MIB ref		: swCardEventLogSlotXX       .6.66.85.83.95.67.82
-- absolute OID	: 1.3.6.1.4.1.7995.2.6.1.1.XX.6.66.85.83.95.67.82
-- Vary			: YES
--
-- Value(s)		: OK                Router BUS C Right channel has valid signal selected
--              : WARNING           Router BUS C Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_DL
--
-- MIB ref		: swCardEventLogSlotXX       .6.66.85.83.95.68.76
-- absolute OID	: 1.3.6.1.4.1.7995.2.6.1.1.XX.6.66.85.83.95.68.76
-- Vary			: YES
--
-- Value(s)		: OK                Router BUS D Left channel has valid signal selected
--              : WARNING           Router BUS D Left channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: BUS_DR
--
-- MIB ref		: swCardEventLogSlotXX       .6.66.85.83.95.68.82
-- absolute OID	: 1.3.6.1.4.1.7995.2.6.1.1.XX.6.66.85.83.95.68.82
-- Vary			: YES
--
-- Value(s)		: OK                Router BUS D Right channel has valid signal selected
--              : WARNING           Router BUS D Right channel warning
--              : WARNING.SILENT    Receiving silence
--              : WARNING.QUIET     Receiving Low level signal
--              : WARNING.NON_PCM   Non PCM signal detected
--              : WARNING.HIGH      Receiving High level signal
--              : WARNING.OVERLOAD  Receiving Overload level signal
-- Comments		:
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary			: YES
--
-- Value(s)		: 0s                Number or Errored Seconds
--				:
-- Comments		: Runtime string
--
---------------------------------------------------------------------------------------------------
-- Header		: INPUT1
--
-- MIB ref		: swCardEventLogSlotXX       .6.73.78.80.85.84.49
-- absolute OID	: 1.3.6.1.4.1.7995.2.6.1.1.XX.6.73.78.80.85.84.49
-- Vary			: YES
--
-- Value(s)		: OK                Valid input 1 signal
--				: ERR               Invalid input 1 signal
--              : LOST              Input 1 signal lost
-- Comments		:
--
---------------------------------------------------------------------------------------------------
-- Header		: INPUT2
--
-- MIB ref		: swCardEventLogSlotXX       .6.73.78.80.85.84.50
-- absolute OID	: 1.3.6.1.4.1.7995.2.6.1.1.XX.6.73.78.80.85.84.50
-- Vary			: YES
--
-- Value(s)		: OK                Valid input 2 signal
--				: ERR               Invalid input 2 signal
--              : LOST              Input 2 signal lost
-- Comments		:
--
---------------------------------------------------------------------------------------------------
-- Header		: NPCM_1
--
-- MIB ref		: swCardEventLogSlotXX       .6.78.80.67.77.95.49
-- absolute OID	: 1.3.6.1.4.1.7995.2.6.1.1.XX.6.78.80.67.77.95.49
-- Vary			: YES
--
-- Value(s)		: NONE              Non-PCM not present on pair 1 of selected SDI input
--				: OK                Non-PCM present on pair 1 of selected SDI input
-- Comments		:
--
---------------------------------------------------------------------------------------------------
-- Header		: NPCM_2
--
-- MIB ref		: swCardEventLogSlotXX       .6.78.80.67.77.95.50
-- absolute OID	: 1.3.6.1.4.1.7995.2.6.1.1.XX.6.78.80.67.77.95.50
-- Vary			: YES
--
-- Value(s)		: NONE              Non-PCM not present on pair 2 of selected SDI input
--				: OK                Non-PCM present on pair 2 of selected SDI input
-- Comments		:
--
---------------------------------------------------------------------------------------------------
-- Header		: NPCM_3
--
-- MIB ref		: swCardEventLogSlotXX       .6.78.80.67.77.95.51
-- absolute OID	: 1.3.6.1.4.1.7995.2.6.1.1.XX.6.78.80.67.77.95.51
-- Vary			: YES
--
-- Value(s)		: NONE              Non-PCM not present on pair 3 of selected SDI input
--				: OK                Non-PCM present on pair 3 of selected SDI input
-- Comments		:
--
---------------------------------------------------------------------------------------------------
-- Header		: NPCM_4
--
-- MIB ref		: swCardEventLogSlotXX       .6.78.80.67.77.95.52
-- absolute OID	: 1.3.6.1.4.1.7995.2.6.1.1.XX.6.78.80.67.77.95.52
-- Vary			: YES
--
-- Value(s)		: NONE              Non-PCM not present on pair 4 of selected SDI input
--				: OK                Non-PCM present on pair 4 of selected SDI input
-- Comments		:
--
---------------------------------------------------------------------------------------------------
-- Header		: NPCM_5
--
-- MIB ref		: swCardEventLogSlotXX       .6.78.80.67.77.95.53
-- absolute OID	: 1.3.6.1.4.1.7995.2.6.1.1.XX.6.78.80.67.77.95.53
-- Vary			: YES
--
-- Value(s)		: NONE              Non-PCM not present on pair 5 of selected SDI input
--				: OK                Non-PCM present on pair 5 of selected SDI input
-- Comments		:
--
---------------------------------------------------------------------------------------------------
-- Header		: NPCM_6
--
-- MIB ref		: swCardEventLogSlotXX       .6.78.80.67.77.95.54
-- absolute OID	: 1.3.6.1.4.1.7995.2.6.1.1.XX.6.78.80.67.77.95.54
-- Vary			: YES
--
-- Value(s)		: NONE              Non-PCM not present on pair 6 of selected SDI input
--				: OK                Non-PCM present on pair 6 of selected SDI input
-- Comments		:
--
---------------------------------------------------------------------------------------------------
-- Header		: NPCM_7
--
-- MIB ref		: swCardEventLogSlotXX       .6.78.80.67.77.95.55
-- absolute OID	: 1.3.6.1.4.1.7995.2.6.1.1.XX.6.78.80.67.77.95.55
-- Vary			: YES
--
-- Value(s)		: NONE              Non-PCM not present on pair 7 of selected SDI input
--				: OK                Non-PCM present on pair 7 of selected SDI input
-- Comments		:
--
---------------------------------------------------------------------------------------------------
-- Header		: NPCM_8
--
-- MIB ref		: swCardEventLogSlotXX       .6.78.80.67.77.95.56
-- absolute OID	: 1.3.6.1.4.1.7995.2.6.1.1.XX.6.78.80.67.77.95.56
-- Vary			: YES
--
-- Value(s)		: NONE              Non-PCM not present on pair 8 of selected SDI input
--				: OK                Non-PCM present on pair 8 of selected SDI input
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
-- Vary			: YES
--
-- Value(s)		: 0
--				:
-- Comments		: Number of current control sessions
--
---------------------------------------------------------------------------------------------------
-- Header		: DEEMBED_1
--
-- MIB ref		: swCardEventLogSlotXX       .9.68.69.69.77.66.69.68.95.49
-- absolute OID	: 1.3.6.1.4.1.7995.2.6.1.1.XX.9.68.69.69.77.66.69.68.95.49
-- Vary			: YES
--
-- Value(s)		: NONE              Nothing present on pair 1
--				: OK                Embedded pair 1 present on selected SDI input
-- Comments		:
--
---------------------------------------------------------------------------------------------------
-- Header		: DEEMBED_2
--
-- MIB ref		: swCardEventLogSlotXX       .9.68.69.69.77.66.69.68.95.50
-- absolute OID	: 1.3.6.1.4.1.7995.2.6.1.1.XX.9.68.69.69.77.66.69.68.95.50
-- Vary			: YES
--
-- Value(s)		: NONE              Nothing present on pair 2
--				: OK                Embedded pair 2 present on selected SDI input
-- Comments		:
--
---------------------------------------------------------------------------------------------------
-- Header		: DEEMBED_3
--
-- MIB ref		: swCardEventLogSlotXX       .9.68.69.69.77.66.69.68.95.51
-- absolute OID	: 1.3.6.1.4.1.7995.2.6.1.1.XX.9.68.69.69.77.66.69.68.95.51
-- Vary			: YES
--
-- Value(s)		: NONE              Nothing present on pair 3
--				: OK                Embedded pair 3 present on selected SDI input
-- Comments		:
--
---------------------------------------------------------------------------------------------------
-- Header		: DEEMBED_4
--
-- MIB ref		: swCardEventLogSlotXX       .9.68.69.69.77.66.69.68.95.52
-- absolute OID	: 1.3.6.1.4.1.7995.2.6.1.1.XX.9.68.69.69.77.66.69.68.95.52
-- Vary			: YES
--
-- Value(s)		: NONE              Nothing present on pair 4
--				: OK                Embedded pair 4 present on selected SDI input
-- Comments		:
--
---------------------------------------------------------------------------------------------------
-- Header		: DEEMBED_5
--
-- MIB ref		: swCardEventLogSlotXX       .9.68.69.69.77.66.69.68.95.53
-- absolute OID	: 1.3.6.1.4.1.7995.2.6.1.1.XX.9.68.69.69.77.66.69.68.95.53
-- Vary			: YES
--
-- Value(s)		: NONE              Nothing present on pair 5
--				: OK                Embedded pair 5 present on selected SDI input
-- Comments		:
--
---------------------------------------------------------------------------------------------------
-- Header		: DEEMBED_6
--
-- MIB ref		: swCardEventLogSlotXX       .9.68.69.69.77.66.69.68.95.54
-- absolute OID	: 1.3.6.1.4.1.7995.2.6.1.1.XX.9.68.69.69.77.66.69.68.95.54
-- Vary			: YES
--
-- Value(s)		: NONE              Nothing present on pair 6
--				: OK                Embedded pair 6 present on selected SDI input
-- Comments		:
--
---------------------------------------------------------------------------------------------------
-- Header		: DEEMBED_7
--
-- MIB ref		: swCardEventLogSlotXX       .9.68.69.69.77.66.69.68.95.55
-- absolute OID	: 1.3.6.1.4.1.7995.2.6.1.1.XX.9.68.69.69.77.66.69.68.95.55
-- Vary			: YES
--
-- Value(s)		: NONE              Nothing present on pair 7
--				: OK                Embedded pair 7 present on selected SDI input
-- Comments		:
--
---------------------------------------------------------------------------------------------------
-- Header		: DEEMBED_8
--
-- MIB ref		: swCardEventLogSlotXX       .9.68.69.69.77.66.69.68.95.56
-- absolute OID	: 1.3.6.1.4.1.7995.2.6.1.1.XX.9.68.69.69.77.66.69.68.95.56
-- Vary			: YES
--
-- Value(s)		: NONE              Nothing present on pair 8
--				: OK                Embedded pair 8 present on selected SDI input
-- Comments		:
--
---------------------------------------------------------------------------------------------------
-- Header		: ROL_STATES
--
-- MIB ref		: swCardEventLogSlotXX       .10.82.79.76.95.83.84.65.84.69.83
-- absolute OID	: 1.3.6.1.4.1.7995.2.6.1.1.XX.10.82.79.76.95.83.84.65.84.69.83
-- Vary			: YES
--
-- Value(s)		: OK                RollTrack message sent and received OK
--				: FAIL              RollTrack message not acknowledged
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
-- Vary			: YES
--
-- Value(s)		: 2008-01-08T16:58:51Z
--				:
-- Comments		: Time of last restart
--
---------------------------------------------------------------------------------------------------
-- Header		: LAST_MODIFIED
--
-- MIB ref		: swCardEventLogSlotXX       .13.76.65.83.84.95.77.79.68.73.70.73.69.68
-- absolute OID	: 1.3.6.1.4.1.7995.2.6.1.1.XX.13.76.65.83.84.95.77.79.68.73.70.73.69.68
-- Vary			: YES
--
-- Value(s)		: -
--				:
-- Comments		: Time of last control modify command
--
---------------------------------------------------------------------------------------------------
