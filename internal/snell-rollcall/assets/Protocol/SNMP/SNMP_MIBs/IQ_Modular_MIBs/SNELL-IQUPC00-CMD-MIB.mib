-- ************************************************************************************
--        Snell Card:IQUPC00
--        Module Id#:539
--       Command Set:12
--          Filename:SNELL-IQUPC00-CMD-MIB.mib
--       Source File:nemocombined.xml
--        Source Ver:5.7..12
--    Logging Source:nemologging.csv
--            Author:jonathanriches
--              Date:12/10/2011
--              Time:17:40
--
-- Copyright (c) 2010 Snell Ltd
-- All rights reserved.
--
-- ************************************************************************************

SNELL-IQUPC00-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQUPC00,
    moduleIQUPC00MIB
        FROM SNELL-WILCOX-PRODUCT-REG;

moduleIQUPC00CmdMi MODULE-IDENTITY
    LAST-UPDATED "1110121740Z"
    ORGANIZATION "Snell Ltd"
    CONTACT-INFO
        "Primary Author:jonathanriches

         postal:    Hartman House
                    Danehill
                    Lower Earley,
                    Reading, Berks
                    RG6 4PB
         phone:     +44 (0)118 9866123
         email:     support.uk@snellgroup.com"
    DESCRIPTION
        "This file defines the Snell card, command set translations."
    ::= { moduleIQUPC00MIB 1 }




--********************************************************************************
--*
--*  Snell Card:
--*  command set:
--*  list commands/menus:
--*
--******************************************************************************
    iqupc00CmdTable OBJECT-TYPE
        SYNTAX          SEQUENCE OF Iqupc00CmdEntry
        MAX-ACCESS      not-accessible
        STATUS          current
        DESCRIPTION
                "Note the instance of this table is relected in the command set Version"
        ::= { moduleIQUPC00 1 }

    iqupc00CmdEntry OBJECT-TYPE
        SYNTAX          Iqupc00CmdEntry
        MAX-ACCESS      not-accessible
        STATUS          current
        DESCRIPTION
                "Entry in command table."
        INDEX   { iqupc00SlotIndex }
        ::= { iqupc00CmdTable 1 }

    Iqupc00CmdEntry ::=
        SEQUENCE {
            iqupc00SlotIndex
                Unsigned32,
            iqupc00Video1VideoInputInput1Std
                RollCallString,
            iqupc00Video1VideoInputInput2Std
                RollCallString,
            iqupc00Video1VideoInputIPSelect
                INTEGER,
            iqupc00VideoInputValidStandards108050p
                INTEGER,
            iqupc00VideoInputValidStandards108059p
                INTEGER,
            iqupc00VideoInputValidStandards108025i
                INTEGER,
            iqupc00VideoInputValidStandards108029i
                INTEGER,
            iqupc00VideoInputValidStandards72050p
                INTEGER,
            iqupc00VideoInputValidStandards72059p
                INTEGER,
            iqupc00VideoInputValidStandards62525i
                INTEGER,
            iqupc00VideoInputValidStandards52529i
                INTEGER,
            iqupc00VideoInputValidStandards108023psf
                INTEGER,
            iqupc00VideoInputValidStandards108025psf
                INTEGER,
            iqupc00VideoInputValidStandards108025p
                INTEGER,
            iqupc00VideoInputValidStandards108029p
                INTEGER,
            iqupc00VideoInputErrorsErrorReset
                INTEGER,
            iqupc00VideoInputErrorsResetSec
                RollCallString,
            iqupc00VideoInputErrorsCRCErrs1
                RollCallString,
            iqupc00VideoInputErrorsANCErrs1
                RollCallString,
            iqupc00VideoInputErrorsCRCErrs2
                RollCallString,
            iqupc00VideoInputErrorsANCErrs2
                RollCallString,
            iqupc00VideoInputErrorsCRCErrSec1
                RollCallString,
            iqupc00VideoInputErrorsANCErrSec1
                RollCallString,
            iqupc00VideoInputErrorsCRCErrSec2
                RollCallString,
            iqupc00VideoInputErrorsANCErrSec2
                RollCallString,
            iqupc00Video1VideoInputYCDelay
                INTEGER,
            iqupc00Video1BackupEnable
                INTEGER,
            iqupc00Video1BackupORInput1State
                RollCallString,
            iqupc00Video1BackupORInput2State
                RollCallString,
            iqupc00Video1BackupRevertDelay
                INTEGER,
            iqupc00Video1BackupPriority
                INTEGER,
            iqupc00Video1BackupQualifyInvStd
                INTEGER,
            iqupc00Video1BackupQualifyCRCErr
                INTEGER,
            iqupc00Video1BackupQualifyANCErr
                INTEGER,
            iqupc00Video1BackupQualifyAudioFail
                INTEGER,
            iqupc00BackupInput1SelStatInp1OK
                RollCallString,
            iqupc00BackupInput1SelStatInp2FAIL
                RollCallString,
            iqupc00BackupInput1SelStatInp2Err
                RollCallString,
            iqupc00BackupInput1SelStatAUDFail2
                RollCallString,
            iqupc00BackupInput1SelStatStd2
                RollCallString,
            iqupc00BackupInput1SelStatGPI1
                RollCallString,
            iqupc00BackupInput1SelStatGPI2
                RollCallString,
            iqupc00BackupInput1SelEnblInp1OK
                INTEGER,
            iqupc00BackupInput1SelEnblInp2FAIL
                INTEGER,
            iqupc00BackupInput1SelEnblInp2Err
                INTEGER,
            iqupc00BackupInput1SelEnblGPI1
                INTEGER,
            iqupc00BackupInput1SelEnblGPI2
                INTEGER,
            iqupc00BackupInput1SelEnblStdInp2
                INTEGER,
            iqupc00BackupInput1SelDlyInp1OK
                INTEGER,
            iqupc00BackupInput1SelDlyInp2FAIL
                INTEGER,
            iqupc00BackupInput1SelDlyInp2Err
                INTEGER,
            iqupc00BackupInput1SelDlyGPI1
                INTEGER,
            iqupc00BackupInput1SelDlyGPI2
                INTEGER,
            iqupc00BackupInput1SelDlyAud2FAIL
                INTEGER,
            iqupc00BackupInput1SelDlyStd2
                INTEGER,
            iqupc00BackupInput1SelGPI1State
                INTEGER,
            iqupc00BackupInput1SelGPI2State
                INTEGER,
            iqupc00BackupInput1SelInp12AudFailG1C1
                INTEGER,
            iqupc00BackupInput1SelInp12AudFailG1C2
                INTEGER,
            iqupc00BackupInput1SelInp12AudFailG2C1
                INTEGER,
            iqupc00BackupInput1SelInp12AudFailG2C2
                INTEGER,
            iqupc00BackupInput1SelInp12AudFailG3C1
                INTEGER,
            iqupc00BackupInput1SelInp12AudFailG3C2
                INTEGER,
            iqupc00BackupInput1SelInp12AudFailG4C1
                INTEGER,
            iqupc00BackupInput1SelInp12AudFailG4C2
                INTEGER,
            iqupc00BackupInput1SelInp12AudFailLockGrp
                INTEGER,
            iqupc00BackupInput1SelSelAll
                INTEGER,
            iqupc00BackupInput1SelSelNone
                INTEGER,
            iqupc00BackupInput2SelStatInp2OK
                RollCallString,
            iqupc00BackupInput2SelStatInp1FAIL
                RollCallString,
            iqupc00BackupInput2SelStatInp1Err
                RollCallString,
            iqupc00BackupInput2SelStatAUDFail1
                RollCallString,
            iqupc00BackupInput2SelStatStd1
                RollCallString,
            iqupc00BackupInput2SelStatGPI1
                RollCallString,
            iqupc00BackupInput2SelStatGPI2
                RollCallString,
            iqupc00BackupInput2SelEnblInp2OK
                INTEGER,
            iqupc00BackupInput2SelEnblInp1FAIL
                INTEGER,
            iqupc00BackupInput2SelEnblInp1Err
                INTEGER,
            iqupc00BackupInput2SelEnblGPI1
                INTEGER,
            iqupc00BackupInput2SelEnblGPI2
                INTEGER,
            iqupc00BackupInput2SelEnblAudInp1Err
                INTEGER,
            iqupc00BackupInput2SelEnblStdInp1
                INTEGER,
            iqupc00BackupInput2SelInp21AudFailG1C1
                INTEGER,
            iqupc00BackupInput2SelInp21AudFailG1C2
                INTEGER,
            iqupc00BackupInput2SelInp21AudFailG2C1
                INTEGER,
            iqupc00BackupInput2SelInp21AudFailG2C2
                INTEGER,
            iqupc00BackupInput2SelInp21AudFailG3C1
                INTEGER,
            iqupc00BackupInput2SelInp21AudFailG3C2
                INTEGER,
            iqupc00BackupInput2SelInp21AudFailG4C1
                INTEGER,
            iqupc00BackupInput2SelInp21AudFailG4C2
                INTEGER,
            iqupc00BackupInput2SelDlyInp2OK
                INTEGER,
            iqupc00BackupInput2SelDlyInp1FAIL
                INTEGER,
            iqupc00BackupInput2SelDlyInp1Err
                INTEGER,
            iqupc00BackupInput2SelDlyGPI1
                INTEGER,
            iqupc00BackupInput2SelDlyGPI2
                INTEGER,
            iqupc00BackupInput2SelDlyAud1FAIL
                INTEGER,
            iqupc00BackupInput2SelDlyStd1
                INTEGER,
            iqupc00BackupInput2SelGPI1State
                INTEGER,
            iqupc00BackupInput2SelGPI2State
                INTEGER,
            iqupc00BackupInput2SelInp21AudFailLockGrp
                INTEGER,
            iqupc00BackupInput2SelSelAll
                INTEGER,
            iqupc00BackupInput2SelSelNone
                INTEGER,
            iqupc00Video2VideoOutputConversionStandard
                INTEGER,
            iqupc00Video2VideoOutputOutputAType
                INTEGER,
            iqupc00Video2VideoOutputOutputBType
                INTEGER,
            iqupc00Video2VideoOutputOutput1Std
                RollCallString,
            iqupc00VideoOutputVideoProcMasterGain
                INTEGER,
            iqupc00VideoOutputVideoProcYGain
                INTEGER,
            iqupc00VideoOutputVideoProcCGain
                INTEGER,
            iqupc00VideoOutputVideoProcBlackLevel
                INTEGER,
            iqupc00VideoOutputVideoProcHueLevel
                INTEGER,
            iqupc00Video2VideoOutputDefaultOutput
                INTEGER,
            iqupc00Video2VideoOutputOutputMode
                INTEGER,
            iqupc00Video2VideoOutputPatternType
                INTEGER,
            iqupc00VideoOutputUserCaptionsEnable
                INTEGER,
            iqupc00VideoOutputUserCaptionsEnableAlt
                INTEGER,
            iqupc00VideoOutputUserCaptionsText
                RollCallString,
            iqupc00VideoOutputUserCaptionsTextAlt
                RollCallString,
            iqupc00VideoOutputUserCaptionsXPos
                INTEGER,
            iqupc00VideoOutputUserCaptionsYPos
                INTEGER,
            iqupc00VideoOutputUserCaptionsXSize
                INTEGER,
            iqupc00VideoOutputUserCaptionsYSize
                INTEGER,
            iqupc00Video2VideoOutputLastRefStd
                INTEGER,
            iqupc00Video2VideoOutputLastFrameRate
                INTEGER,
            iqupc00PictureAdvancedHEnhanceEnable
                INTEGER,
            iqupc00PictureAdvancedHEnhanceFrequencyBand
                INTEGER,
            iqupc00PictureAdvancedHEnhancePreset
                INTEGER,
            iqupc00PictureAdvancedHEnhanceGain
                INTEGER,
            iqupc00PictureAdvancedHEnhanceNoiseRejection
                INTEGER,
            iqupc00PictureRGBLegaliserRange
                INTEGER,
            iqupc00PictureLumaClipperEnable
                INTEGER,
            iqupc00PictureLumaClipperWhitemax
                INTEGER,
            iqupc00PictureLumaClipperBlackmin
                INTEGER,
            iqupc00PictureOutputPictureColorimetry
                INTEGER,
            iqupc00PictureEnhanceNoiseThreshold
                INTEGER,
            iqupc00PictureEnhanceSharpnessThreshold
                INTEGER,
            iqupc00PictureEnhanceSharpnessAmplitude
                INTEGER,
            iqupc00PictureOutputPictureFilmCadence
                RollCallString,
            iqupc00PictureOutputColorCorrectGreenOffset
                INTEGER,
            iqupc00PictureOutputColorCorrectBlueOffset
                INTEGER,
            iqupc00PictureOutputColorCorrectRedOffset
                INTEGER,
            iqupc00PictureOutputColorCorrectGangOffset
                INTEGER,
            iqupc00PictureOutputColorCorrectGreenGain
                INTEGER,
            iqupc00PictureOutputColorCorrectBlueGain
                INTEGER,
            iqupc00PictureOutputColorCorrectRedGain
                INTEGER,
            iqupc00PictureOutputColorCorrectGangGain
                INTEGER,
            iqupc00PictureOutputColorCorrectGreenGamma
                INTEGER,
            iqupc00PictureOutputColorCorrectBlueGamma
                INTEGER,
            iqupc00PictureOutputColorCorrectRedGamma
                INTEGER,
            iqupc00PictureOutputColorCorrectGangGamma
                INTEGER,
            iqupc00PictureOutputOutputBorderLeft
                INTEGER,
            iqupc00PictureOutputOutputBorderRight
                INTEGER,
            iqupc00PictureOutputOutputBorderTop
                INTEGER,
            iqupc00PictureOutputOutputBorderBottom
                INTEGER,
            iqupc00PictureOutputOutputBorderRed
                INTEGER,
            iqupc00PictureOutputOutputBorderGreen
                INTEGER,
            iqupc00PictureOutputOutputBorderBlue
                INTEGER,
            iqupc00ARCCtrlRecallDisplayMemory
                INTEGER,
            iqupc00ARCCtrlSelDisplayMemory
                INTEGER,
            iqupc00ARCCtrlSaveset
                INTEGER,
            iqupc00ARCCtrlSaveDispMemory
                INTEGER,
            iqupc00ARCCtrlDispMemoryNameChangeName
                RollCallString,
            iqupc00ARCCtrlARCSize
                INTEGER,
            iqupc00ARCCtrlARCApect
                INTEGER,
            iqupc00ARCCtrlARCTilt
                INTEGER,
            iqupc00ARCCtrlARCPan
                INTEGER,
            iqupc00ARCCtrlInputCropLeft
                INTEGER,
            iqupc00ARCCtrlInputCropRight
                INTEGER,
            iqupc00ARCCtrlInputCropTop
                INTEGER,
            iqupc00ARCCtrlInputCropBottom
                INTEGER,
            iqupc00ARCCtrlSelStdPreset
                INTEGER,
            iqupc00ARCCtrlRecallStdPreset
                INTEGER,
            iqupc00ARCCtrlDefaultALLMemory
                INTEGER,
            iqupc00ARCCtrlLastDisplayMemory
                RollCallString,
            iqupc00ARCCtrl43AFDMapping2
                INTEGER,
            iqupc00ARCCtrl43AFDMapping3
                INTEGER,
            iqupc00ARCCtrl43AFDMapping4
                INTEGER,
            iqupc00ARCCtrl43AFDMapping8
                INTEGER,
            iqupc00ARCCtrl43AFDMapping9
                INTEGER,
            iqupc00ARCCtrl43AFDMapping10
                INTEGER,
            iqupc00ARCCtrl43AFDMapping11
                INTEGER,
            iqupc00ARCCtrl43AFDMapping12
                INTEGER,
            iqupc00ARCCtrl43AFDMapping13
                INTEGER,
            iqupc00ARCCtrl43AFDMapping14
                INTEGER,
            iqupc00ARCCtrl43AFDMapping15
                INTEGER,
            iqupc00ARCCtrl43AFDMapping16
                INTEGER,
            iqupc00ARCCtrl169AFDMapping2
                INTEGER,
            iqupc00ARCCtrl169AFDMapping3
                INTEGER,
            iqupc00ARCCtrl169AFDMapping4
                INTEGER,
            iqupc00ARCCtrl169AFDMapping8
                INTEGER,
            iqupc00ARCCtrl169AFDMapping9
                INTEGER,
            iqupc00ARCCtrl169AFDMapping10
                INTEGER,
            iqupc00ARCCtrl169AFDMapping11
                INTEGER,
            iqupc00ARCCtrl169AFDMapping12
                INTEGER,
            iqupc00ARCCtrl169AFDMapping13
                INTEGER,
            iqupc00ARCCtrl169AFDMapping14
                INTEGER,
            iqupc00ARCCtrl169AFDMapping15
                INTEGER,
            iqupc00ARCCtrl169AFDMapping16
                INTEGER,
            iqupc00ARCCtrlNoSignalMapping
                INTEGER,
            iqupc00ARCCtrlForceMapping
                INTEGER,
            iqupc00ARCCtrl43ARCMapping2
                INTEGER,
            iqupc00ARCCtrl43ARCMapping3
                INTEGER,
            iqupc00ARCCtrl43ARCMapping4
                INTEGER,
            iqupc00ARCCtrl43ARCMapping8
                INTEGER,
            iqupc00ARCCtrl43ARCMapping9
                INTEGER,
            iqupc00ARCCtrl43ARCMapping10
                INTEGER,
            iqupc00ARCCtrl43ARCMapping11
                INTEGER,
            iqupc00ARCCtrl43ARCMapping12
                INTEGER,
            iqupc00ARCCtrl43ARCMapping13
                INTEGER,
            iqupc00ARCCtrl43ARCMapping14
                INTEGER,
            iqupc00ARCCtrl43ARCMapping15
                INTEGER,
            iqupc00ARCCtrl43ARCMapping16
                INTEGER,
            iqupc00ARCCtrl169ARCMapping2
                INTEGER,
            iqupc00ARCCtrl169ARCMapping3
                INTEGER,
            iqupc00ARCCtrl169ARCMapping4
                INTEGER,
            iqupc00ARCCtrl169ARCMapping8
                INTEGER,
            iqupc00ARCCtrl169ARCMapping9
                INTEGER,
            iqupc00ARCCtrl169ARCMapping10
                INTEGER,
            iqupc00ARCCtrl169ARCMapping11
                INTEGER,
            iqupc00ARCCtrl169ARCMapping12
                INTEGER,
            iqupc00ARCCtrl169ARCMapping13
                INTEGER,
            iqupc00ARCCtrl169ARCMapping14
                INTEGER,
            iqupc00ARCCtrl169ARCMapping15
                INTEGER,
            iqupc00ARCCtrl169ARCMapping16
                INTEGER,
            iqupc00ARCCtrlNoSignalARCMapping
                INTEGER,
            iqupc00ARCCtrlForceARCMapping
                INTEGER,
            iqupc00GenlockBlankingGenlockStandard
                INTEGER,
            iqupc00GenlockBlankingGenlockDelayMode
                INTEGER,
            iqupc00GenlockSetDelayDelayFrames
                INTEGER,
            iqupc00GenlockSetDelayVerticalPhase
                INTEGER,
            iqupc00GenlockSetDelayHorizontalPhase
                INTEGER,
            iqupc00GenlockSetDelayVerticalDelay
                INTEGER,
            iqupc00GenlockSetDelayHorizontalDelay
                INTEGER,
            iqupc00GenlockBlankingGenlockRefLogHide
                RollCallString,
            iqupc00GenlockDolbyELineStandard
                INTEGER,
            iqupc00GenlockDolbyELineAutoLineNo
                INTEGER,
            iqupc00DolbyELineUserDolbyELinePair1
                INTEGER,
            iqupc00DolbyELineUserDolbyELinePair2
                INTEGER,
            iqupc00DolbyELineUserDolbyELinePair3
                INTEGER,
            iqupc00DolbyELineUserDolbyELinePair4
                INTEGER,
            iqupc00DolbyELineUserDolbyELinePair5
                INTEGER,
            iqupc00DolbyELineUserDolbyELinePair6
                INTEGER,
            iqupc00DolbyELineUserDolbyELinePair7
                INTEGER,
            iqupc00DolbyELineUserDolbyELinePair8
                INTEGER,
            iqupc00GenlockDolbyELineUserLine525i29
                INTEGER,
            iqupc00GenlockDolbyELineUserLine625i25
                INTEGER,
            iqupc00GenlockDolbyELineUserLine720p23
                INTEGER,
            iqupc00GenlockDolbyELineUserLine720p24
                INTEGER,
            iqupc00GenlockDolbyELineUserLine720p25
                INTEGER,
            iqupc00GenlockDolbyELineUserLine720p29
                INTEGER,
            iqupc00GenlockDolbyELineUserLine720p30
                INTEGER,
            iqupc00GenlockDolbyELineUserLine720p50
                INTEGER,
            iqupc00GenlockDolbyELineUserLine720p59
                INTEGER,
            iqupc00GenlockDolbyELineUserLine720p60
                INTEGER,
            iqupc00GenlockDolbyELineUserLine1080i25
                INTEGER,
            iqupc00GenlockDolbyELineUserLine1080i29
                INTEGER,
            iqupc00GenlockDolbyELineUserLine1080i30
                INTEGER,
            iqupc00GenlockDolbyELineUserLine1080p23sf
                INTEGER,
            iqupc00GenlockDolbyELineUserLine1080p24sf
                INTEGER,
            iqupc00GenlockDolbyELineUserLine1080p25sf
                INTEGER,
            iqupc00GenlockDolbyELineUserLine1080p23
                INTEGER,
            iqupc00GenlockDolbyELineUserLine1080p24
                INTEGER,
            iqupc00GenlockDolbyELineUserLine1080p25
                INTEGER,
            iqupc00GenlockDolbyELineUserLine1080p29
                INTEGER,
            iqupc00GenlockDolbyELineUserLine1080p30
                INTEGER,
            iqupc00GenlockDolbyELineUserLine1080p50
                INTEGER,
            iqupc00GenlockDolbyELineUserLine1080p59
                INTEGER,
            iqupc00GenlockDolbyELineUserLine1080p60
                INTEGER,
            iqupc00GenlockDolbyELineAutoAlign1
                INTEGER,
            iqupc00GenlockDolbyELineAutoAlign2
                INTEGER,
            iqupc00GenlockDolbyELineAutoAlign3
                INTEGER,
            iqupc00GenlockDolbyELineAutoAlign4
                INTEGER,
            iqupc00GenlockDolbyELineAutoAlign5
                INTEGER,
            iqupc00GenlockDolbyELineAutoAlign6
                INTEGER,
            iqupc00GenlockDolbyELineAutoAlign7
                INTEGER,
            iqupc00GenlockDolbyELineAutoAlign8
                INTEGER,
            iqupc00WSSCtrlEnableMapper
                INTEGER,
            iqupc00WSSCtrlIPWSSSignal
                INTEGER,
            iqupc00WSSCtrlOPWSS43
                INTEGER,
            iqupc00WSSCtrlDispMem43
                INTEGER,
            iqupc00WSSCtrlWidescreenIP2016
                INTEGER,
            iqupc00WSSCtrlWidescreenIPPriority
                INTEGER,
            iqupc00WSSCtrlWidescreenIPWSSInEnable
                INTEGER,
            iqupc00WSSCtrlWidescreenIPVIInEnable
                INTEGER,
            iqupc00WSSCtrlWidescreenOP2016
                INTEGER,
            iqupc00WSSCtrlLine1ReadAFD
                RollCallString,
            iqupc00WSSCtrlLine1ReadAR
                RollCallString,
            iqupc00WSSCtrlLine1WriteAFD
                RollCallString,
            iqupc00WSSCtrlLine1WriteAR
                RollCallString,
            iqupc00WSSCtrlPreset
                INTEGER,
            iqupc00WSSCtrlPreset43
                INTEGER,
            iqupc00WSSCtrlPreset169
                INTEGER,
            iqupc00WSSCtrlNewNumber
                INTEGER,
            iqupc00WSSCtrlBlank62523
                INTEGER,
            iqupc00WSSCtrlBlank625336
                INTEGER,
            iqupc00WSSCtrlBlank52521
                INTEGER,
            iqupc00WSSCtrlBlank52522
                INTEGER,
            iqupc00WSSCtrlBlank525283
                INTEGER,
            iqupc00WSSCtrlBlank525284
                INTEGER,
            iqupc00AncillaryDataSMPTE20162016IPF1Status
                RollCallString,
            iqupc00AncillaryDataSMPTE20162016OPF1Line
                INTEGER,
            iqupc00AncillaryDataSMPTE20162016OPF2Line
                INTEGER,
            iqupc00AncillaryDataSMPTE20162016Follow
                INTEGER,
            iqupc00AncillaryDataSDVBILine7
                INTEGER,
            iqupc00AncillaryDataSDVBILine8
                INTEGER,
            iqupc00AncillaryDataSDVBILine9
                INTEGER,
            iqupc00AncillaryDataSDVBILine10
                INTEGER,
            iqupc00AncillaryDataSDVBILine11
                INTEGER,
            iqupc00AncillaryDataSDVBILine12
                INTEGER,
            iqupc00AncillaryDataSDVBILine13
                INTEGER,
            iqupc00AncillaryDataSDVBILine14
                INTEGER,
            iqupc00AncillaryDataSDVBILine15
                INTEGER,
            iqupc00AncillaryDataSDVBILine16
                INTEGER,
            iqupc00AncillaryDataSDVBILine17
                INTEGER,
            iqupc00AncillaryDataSDVBILine18
                INTEGER,
            iqupc00AncillaryDataSDVBILine19
                INTEGER,
            iqupc00AncillaryDataSDVBILine20
                INTEGER,
            iqupc00AncillaryDataSDVBILine21
                INTEGER,
            iqupc00AncillaryDataSDVBILine22
                INTEGER,
            iqupc00AncillaryDataSDVBILine23
                INTEGER,
            iqupc00AncillaryDataSDVBIVIIPStatus
                INTEGER,
            iqupc00AncillaryDataSDVBIWSSIPStatus
                INTEGER,
            iqupc00AncillaryDataSDVBIVITCIPStatus
                INTEGER,
            iqupc00AncillaryDataSDVBIWSTIPStatus
                INTEGER,
            iqupc00AncillaryDataSDVBICC608IPStatus
                INTEGER,
            iqupc00AncillaryDataHDVANCATCEnable
                INTEGER,
            iqupc00AncillaryDataHDVANCATCIPF1Line
                RollCallString,
            iqupc00AncillaryDataHDVANCATCOPF1Line
                INTEGER,
            iqupc00AncillaryDataHDVANCATCOPF2Line
                INTEGER,
            iqupc00AncillaryDataHDVANCATCFollow
                INTEGER,
            iqupc00AncillaryDataHDVANCHDCaptionEnable
                INTEGER,
            iqupc00AncillaryDataHDVANCHDCaptionIPLine
                RollCallString,
            iqupc00AncillaryDataHDVANCHDCaptionOPLine
                INTEGER,
            iqupc00HDVANCHDCaptionHDFollowIPLine
                INTEGER,
            iqupc00AudioInputDisembed18Disembed11procamp
                INTEGER,
            iqupc00AudioInputDisembed18Disembed12procamp
                INTEGER,
            iqupc00Disembed18Disembed1Mute11
                INTEGER,
            iqupc00Disembed18Disembed1Mute12
                INTEGER,
            iqupc00Disembed18Disembed1Stereo1
                INTEGER,
            iqupc00AudioInputDisembed18Disembed11invert
                INTEGER,
            iqupc00AudioInputDisembed18Disembed12invert
                INTEGER,
            iqupc00Disembed18Disembed1dolbyLine
                RollCallString,
            iqupc00AudioInputDisembed18Disembed21procamp
                INTEGER,
            iqupc00AudioInputDisembed18Disembed22procamp
                INTEGER,
            iqupc00Disembed18Disembed2Mute21
                INTEGER,
            iqupc00Disembed18Disembed2Mute22
                INTEGER,
            iqupc00Disembed18Disembed2Stereo2
                INTEGER,
            iqupc00AudioInputDisembed18Disembed21invert
                INTEGER,
            iqupc00AudioInputDisembed18Disembed22invert
                INTEGER,
            iqupc00Disembed18Disembed2dolbyLine
                RollCallString,
            iqupc00AudioInputDisembed18Disembed31procamp
                INTEGER,
            iqupc00AudioInputDisembed18Disembed32procamp
                INTEGER,
            iqupc00Disembed18Disembed3Mute31
                INTEGER,
            iqupc00Disembed18Disembed3Mute32
                INTEGER,
            iqupc00Disembed18Disembed3Stereo3
                INTEGER,
            iqupc00AudioInputDisembed18Disembed31invert
                INTEGER,
            iqupc00AudioInputDisembed18Disembed32invert
                INTEGER,
            iqupc00Disembed18Disembed3dolbyLine
                RollCallString,
            iqupc00AudioInputDisembed18Disembed41procamp
                INTEGER,
            iqupc00AudioInputDisembed18Disembed42procamp
                INTEGER,
            iqupc00Disembed18Disembed4Mute41
                INTEGER,
            iqupc00Disembed18Disembed4Mute42
                INTEGER,
            iqupc00Disembed18Disembed4Stereo4
                INTEGER,
            iqupc00AudioInputDisembed18Disembed41invert
                INTEGER,
            iqupc00AudioInputDisembed18Disembed42invert
                INTEGER,
            iqupc00Disembed18Disembed4dolbyLine
                RollCallString,
            iqupc00AudioInputDisembed18Disembed51procamp
                INTEGER,
            iqupc00AudioInputDisembed18Disembed52procamp
                INTEGER,
            iqupc00Disembed18Disembed5Mute51
                INTEGER,
            iqupc00Disembed18Disembed5Mute52
                INTEGER,
            iqupc00Disembed18Disembed5Stereo5
                INTEGER,
            iqupc00AudioInputDisembed18Disembed51invert
                INTEGER,
            iqupc00AudioInputDisembed18Disembed52invert
                INTEGER,
            iqupc00Disembed18Disembed5dolbyLine
                RollCallString,
            iqupc00AudioInputDisembed18Disembed61procamp
                INTEGER,
            iqupc00AudioInputDisembed18Disembed62procamp
                INTEGER,
            iqupc00Disembed18Disembed6Mute61
                INTEGER,
            iqupc00Disembed18Disembed6Mute62
                INTEGER,
            iqupc00Disembed18Disembed6Stereo6
                INTEGER,
            iqupc00AudioInputDisembed18Disembed61invert
                INTEGER,
            iqupc00AudioInputDisembed18Disembed62invert
                INTEGER,
            iqupc00Disembed18Disembed6dolbyLine
                RollCallString,
            iqupc00AudioInputDisembed18Disembed71procamp
                INTEGER,
            iqupc00AudioInputDisembed18Disembed72procamp
                INTEGER,
            iqupc00Disembed18Disembed7Mute71
                INTEGER,
            iqupc00Disembed18Disembed7Mute72
                INTEGER,
            iqupc00Disembed18Disembed7Stereo7
                INTEGER,
            iqupc00AudioInputDisembed18Disembed71invert
                INTEGER,
            iqupc00AudioInputDisembed18Disembed72invert
                INTEGER,
            iqupc00Disembed18Disembed7dolbyLine
                RollCallString,
            iqupc00AudioInputDisembed18Disembed81procamp
                INTEGER,
            iqupc00AudioInputDisembed18Disembed82procamp
                INTEGER,
            iqupc00Disembed18Disembed8Mute81
                INTEGER,
            iqupc00Disembed18Disembed8Mute82
                INTEGER,
            iqupc00Disembed18Disembed8Stereo8
                INTEGER,
            iqupc00AudioInputDisembed18Disembed81invert
                INTEGER,
            iqupc00AudioInputDisembed18Disembed82invert
                INTEGER,
            iqupc00Disembed18Disembed8dolbyLine
                RollCallString,
            iqupc00AudioInputDisembed18ProcampSaveset
                INTEGER,
            iqupc00AudioOutputEmbed18Embed11procamp
                INTEGER,
            iqupc00AudioOutputEmbed18Embed12procamp
                INTEGER,
            iqupc00Embed18Embed1Mute11
                INTEGER,
            iqupc00Embed18Embed1Mute12
                INTEGER,
            iqupc00Embed18Embed1Stereo1
                INTEGER,
            iqupc00Embed18Embed1dolbyLine
                RollCallString,
            iqupc00AudioOutputEmbed18Embed21procamp
                INTEGER,
            iqupc00AudioOutputEmbed18Embed22procamp
                INTEGER,
            iqupc00Embed18Embed2Mute21
                INTEGER,
            iqupc00Embed18Embed2Mute22
                INTEGER,
            iqupc00Embed18Embed2Stereo2
                INTEGER,
            iqupc00Embed18Embed2dolbyLine
                RollCallString,
            iqupc00AudioOutputEmbed18Embed31procamp
                INTEGER,
            iqupc00AudioOutputEmbed18Embed32procamp
                INTEGER,
            iqupc00Embed18Embed3Mute31
                INTEGER,
            iqupc00Embed18Embed3Mute32
                INTEGER,
            iqupc00Embed18Embed3Stereo3
                INTEGER,
            iqupc00Embed18Embed3dolbyLine
                RollCallString,
            iqupc00AudioOutputEmbed18Embed41procamp
                INTEGER,
            iqupc00AudioOutputEmbed18Embed42procamp
                INTEGER,
            iqupc00Embed18Embed4Mute41
                INTEGER,
            iqupc00Embed18Embed4Mute42
                INTEGER,
            iqupc00Embed18Embed4Stereo4
                INTEGER,
            iqupc00Embed18Embed4dolbyLine
                RollCallString,
            iqupc00AudioOutputEmbed18Embed51procamp
                INTEGER,
            iqupc00AudioOutputEmbed18Embed52procamp
                INTEGER,
            iqupc00Embed18Embed5Mute51
                INTEGER,
            iqupc00Embed18Embed5Mute52
                INTEGER,
            iqupc00Embed18Embed5Stereo5
                INTEGER,
            iqupc00Embed18Embed5dolbyLine
                RollCallString,
            iqupc00AudioOutputEmbed18Embed61procamp
                INTEGER,
            iqupc00AudioOutputEmbed18Embed62procamp
                INTEGER,
            iqupc00Embed18Embed6Mute61
                INTEGER,
            iqupc00Embed18Embed6Mute62
                INTEGER,
            iqupc00Embed18Embed6Stereo6
                INTEGER,
            iqupc00Embed18Embed6dolbyLine
                RollCallString,
            iqupc00AudioOutputEmbed18Embed71procamp
                INTEGER,
            iqupc00AudioOutputEmbed18Embed72procamp
                INTEGER,
            iqupc00Embed18Embed7Mute71
                INTEGER,
            iqupc00Embed18Embed7Mute72
                INTEGER,
            iqupc00Embed18Embed7Stereo7
                INTEGER,
            iqupc00Embed18Embed7dolbyLine
                RollCallString,
            iqupc00AudioOutputEmbed18Embed81procamp
                INTEGER,
            iqupc00AudioOutputEmbed18Embed82procamp
                INTEGER,
            iqupc00Embed18Embed8Mute81
                INTEGER,
            iqupc00Embed18Embed8Mute82
                INTEGER,
            iqupc00Embed18Embed8Stereo8
                INTEGER,
            iqupc00Embed18Embed8dolbyLine
                RollCallString,
            iqupc00Embed18GroupEmbGroup1
                INTEGER,
            iqupc00Embed18GroupEmbGroup2
                INTEGER,
            iqupc00Embed18GroupEmbGroup3
                INTEGER,
            iqupc00Embed18GroupEmbGroup4
                INTEGER,
            iqupc00AudSetupDelaySelectTotalDelayBus1
                RollCallString,
            iqupc00AudSetupDelaySelectTotalDelayBus2
                RollCallString,
            iqupc00AudSetupDelaySelectTotalDelayBus3
                RollCallString,
            iqupc00AudSetupDelaySelectTotalDelayBus4
                RollCallString,
            iqupc00AudSetupDelaySelectTotalDelayBus5
                RollCallString,
            iqupc00AudSetupDelaySelectTotalDelayBus6
                RollCallString,
            iqupc00AudSetupDelaySelectTotalDelayBus7
                RollCallString,
            iqupc00AudSetupDelaySelectTotalDelayBus8
                RollCallString,
            iqupc00AudSetupDelaySelectBus1Delay
                INTEGER,
            iqupc00AudSetupDelaySelectBus2Delay
                INTEGER,
            iqupc00AudSetupDelaySelectBus3Delay
                INTEGER,
            iqupc00AudSetupDelaySelectBus4Delay
                INTEGER,
            iqupc00AudSetupDelaySelectBus5Delay
                INTEGER,
            iqupc00AudSetupDelaySelectBus6Delay
                INTEGER,
            iqupc00AudSetupDelaySelectBus7Delay
                INTEGER,
            iqupc00AudSetupDelaySelectBus8Delay
                INTEGER,
            iqupc00AudSetupDelaySelectBus1Fine
                INTEGER,
            iqupc00AudSetupDelaySelectBus2Fine
                INTEGER,
            iqupc00AudSetupDelaySelectBus3Fine
                INTEGER,
            iqupc00AudSetupDelaySelectBus4Fine
                INTEGER,
            iqupc00AudSetupDelaySelectBus5Fine
                INTEGER,
            iqupc00AudSetupDelaySelectBus6Fine
                INTEGER,
            iqupc00AudSetupDelaySelectBus7Fine
                INTEGER,
            iqupc00AudSetupDelaySelectBus8Fine
                INTEGER,
            iqupc00AudSetupDelaySelectBusBulkDelay
                INTEGER,
            iqupc00AudSetupDelaySelectThreshold
                INTEGER,
            iqupc00AudSetupDelaySelectRtrack14
                INTEGER,
            iqupc00AudSetupDelaySelectRtrack15
                INTEGER,
            iqupc00AudSetupDelaySelectRtrack16
                INTEGER,
            iqupc00AudSetupDelaySelectRtrack17
                INTEGER,
            iqupc00AudSetupDelaySelectEnableBulk
                INTEGER,
            iqupc00AudSetupDelaySelectEnableVideo
                INTEGER,
            iqupc00AudioAudSetupRollTrack14
                RollCallString,
            iqupc00AudioAudSetupRollTrack15
                RollCallString,
            iqupc00AudioAudSetupRollTrack16
                RollCallString,
            iqupc00AudioAudSetupRollTrack17
                RollCallString,
            iqupc00AudioAudSetupCurrentVidDelay
                RollCallString,
            iqupc00AudioAudSetupMinVidAudDelay
                RollCallString,
            iqupc00AudioAudSetupCurrRTrack14Delay
                RollCallString,
            iqupc00AudioAudSetupCurrRlTrack15Delay
                RollCallString,
            iqupc00AudioAudSetupCurrRTrack16Delay
                RollCallString,
            iqupc00AudioAudSetupCurrRTrack17Delay
                RollCallString,
            iqupc00AudSetupTonesFreq0
                INTEGER,
            iqupc00AudSetupTonesFreq1
                INTEGER,
            iqupc00AudSetupTonesFreq2
                INTEGER,
            iqupc00AudSetupTonesFreq3
                INTEGER,
            iqupc00AudSetupTonesFreq4
                INTEGER,
            iqupc00AudSetupTonesFreq5
                INTEGER,
            iqupc00AudSetupTonesFreq6
                INTEGER,
            iqupc00AudSetupTonesFreq7
                INTEGER,
            iqupc00AudSetupTonesIdent0
                INTEGER,
            iqupc00AudSetupTonesIdent1
                INTEGER,
            iqupc00AudSetupTonesIdent2
                INTEGER,
            iqupc00AudSetupTonesIdent3
                INTEGER,
            iqupc00AudSetupTonesIdent4
                INTEGER,
            iqupc00AudSetupTonesIdent5
                INTEGER,
            iqupc00AudSetupTonesIdent6
                INTEGER,
            iqupc00AudSetupTonesIdent7
                INTEGER,
            iqupc00AudioAudSetupNeg1Frame
                INTEGER,
            iqupc00AudioAudSetupNeg1ms
                INTEGER,
            iqupc00AudioAudSetupNeg4samp
                INTEGER,
            iqupc00AudioAudSetupPos4samp
                INTEGER,
            iqupc00AudioAudSetupPos1ms
                INTEGER,
            iqupc00AudioAudSetupPos1Frame
                INTEGER,
            iqupc00AudioAudSetupSilentLevel
                INTEGER,
            iqupc00AudioAudSetupOverloadLevel
                INTEGER,
            iqupc00AudioAudSetupLevelTimeout
                INTEGER,
            iqupc00AudioAudSetupLevelUpdateEnb
                INTEGER,
            iqupc00AudioAudSetupAudLevel
                RollCallString,
            iqupc00AudioRoutingInputRouteDest1
                INTEGER,
            iqupc00AudioRoutingInputRouteDest2
                INTEGER,
            iqupc00AudioRoutingInputRouteDest3
                INTEGER,
            iqupc00AudioRoutingInputRouteDest4
                INTEGER,
            iqupc00AudioRoutingInputRouteDest5
                INTEGER,
            iqupc00AudioRoutingInputRouteDest6
                INTEGER,
            iqupc00AudioRoutingInputRouteDest7
                INTEGER,
            iqupc00AudioRoutingInputRouteDest8
                INTEGER,
            iqupc00AudioRoutingInputNameAnalog
                RollCallString,
            iqupc00AudioRoutingInputNameDlby1
                RollCallString,
            iqupc00AudioRoutingInputNameDlby2
                RollCallString,
            iqupc00AudioRoutingInputNameDlby3
                RollCallString,
            iqupc00AudioRoutingInputNameDlby4
                RollCallString,
            iqupc00AudioRoutingInputNameDlby5
                RollCallString,
            iqupc00AudioRoutingInputHideAES1
                RollCallString,
            iqupc00AudioRoutingInputHideAES2
                RollCallString,
            iqupc00AudioRoutingInputHideAES3
                RollCallString,
            iqupc00AudioRoutingInputHideAES4
                RollCallString,
            iqupc00AudioRoutingInputHideAES5
                RollCallString,
            iqupc00AudioRoutingInputHideAES6
                RollCallString,
            iqupc00AudioRoutingInputHideAES7
                RollCallString,
            iqupc00AudioRoutingInputHideAES8
                RollCallString,
            iqupc00AudioRoutingOutputHideAES1
                RollCallString,
            iqupc00AudioRoutingOutputHideAES2
                RollCallString,
            iqupc00AudioRoutingOutputHideAES3
                RollCallString,
            iqupc00AudioRoutingOutputHideAES4
                RollCallString,
            iqupc00AudioRoutingOutputHideAES5
                RollCallString,
            iqupc00AudioRoutingOutputHideAES6
                RollCallString,
            iqupc00AudioRoutingOutputHideAES7
                RollCallString,
            iqupc00AudioRoutingOutputHideAES8
                RollCallString,
            iqupc00AudioRoutingDolbyDecodeSource
                INTEGER,
            iqupc00AudioRoutingDolbyDecodeNum
                INTEGER,
            iqupc00AudioOutputRoutingOutDest1
                INTEGER,
            iqupc00AudioOutputRoutingOutDest2
                INTEGER,
            iqupc00AudioOutputRoutingOutDest3
                INTEGER,
            iqupc00AudioOutputRoutingOutDest4
                INTEGER,
            iqupc00AudioOutputRoutingOutDest5
                INTEGER,
            iqupc00AudioOutputRoutingOutDest6
                INTEGER,
            iqupc00AudioOutputRoutingOutDest7
                INTEGER,
            iqupc00AudioOutputRoutingOutDest8
                INTEGER,
            iqupc00AudioOutputRoutingOutDest9
                INTEGER,
            iqupc00AudioOutputRoutingOutDest10
                INTEGER,
            iqupc00AudioOutputRoutingOutDest11
                INTEGER,
            iqupc00AudioOutputRoutingOutDest12
                INTEGER,
            iqupc00AudioOutputRoutingOutDest13
                INTEGER,
            iqupc00AudioOutputRoutingOutDest14
                INTEGER,
            iqupc00AudioOutputRoutingOutDest15
                INTEGER,
            iqupc00AudioOutputRoutingOutDest16
                INTEGER,
            iqupc00AudioOutputRoutingDolbyEncEnb
                RollCallString,
            iqupc00AudioOutputRoutingUpmixEnb
                RollCallString,
            iqupc00AudioProcDefaultEmbed
                INTEGER,
            iqupc00AudioRoutingMatrixBus1audsel
                INTEGER,
            iqupc00AudioRoutingMatrixBus2audsel
                INTEGER,
            iqupc00AudioRoutingMatrixBus3audsel
                INTEGER,
            iqupc00AudioRoutingMatrixBus4audsel
                INTEGER,
            iqupc00AudioRoutingMatrixBus5audsel
                INTEGER,
            iqupc00AudioRoutingMatrixBus6audsel
                INTEGER,
            iqupc00AudioRoutingMatrixBus7audsel
                INTEGER,
            iqupc00AudioRoutingMatrixBus8audsel
                INTEGER,
            iqupc00AudioOutRouteMatrixEmbed12MatrixEmbed11audsel
                INTEGER,
            iqupc00AudioOutRouteMatrixEmbed12MatrixEmbed12audsel
                INTEGER,
            iqupc00AudioOutRouteMatrixEmbed12MatrixEmbed21audsel
                INTEGER,
            iqupc00AudioOutRouteMatrixEmbed12MatrixEmbed22audsel
                INTEGER,
            iqupc00AudioOutRouteMatrixEmbed34MatrixEmbed31audsel
                INTEGER,
            iqupc00AudioOutRouteMatrixEmbed34MatrixEmbed32audsel
                INTEGER,
            iqupc00AudioOutRouteMatrixEmbed34MatrixEmbed41audsel
                INTEGER,
            iqupc00AudioOutRouteMatrixEmbed34MatrixEmbed42audsel
                INTEGER,
            iqupc00AudioOutRouteMatrixEmbed56MatrixEmbed51audsel
                INTEGER,
            iqupc00AudioOutRouteMatrixEmbed56MatrixEmbed52audsel
                INTEGER,
            iqupc00AudioOutRouteMatrixEmbed56MatrixEmbed61audsel
                INTEGER,
            iqupc00AudioOutRouteMatrixEmbed56MatrixEmbed62audsel
                INTEGER,
            iqupc00AudioOutRouteMatrixEmbed78MatrixEmbed71audsel
                INTEGER,
            iqupc00AudioOutRouteMatrixEmbed78MatrixEmbed72audsel
                INTEGER,
            iqupc00AudioOutRouteMatrixEmbed78MatrixEmbed81audsel
                INTEGER,
            iqupc00AudioOutRouteMatrixEmbed78MatrixEmbed82audsel
                INTEGER,
            iqupc00AudioOutRouteMatrixDefaultsEmbOut
                INTEGER,
            iqupc00UpMixerLoud14Source1ProcGain
                INTEGER,
            iqupc00UpMixerLoud14Source1Mute
                INTEGER,
            iqupc00UpMixerLoud14Source1Src
                INTEGER,
            iqupc00UpMixerLoud14Source2ProcGain
                INTEGER,
            iqupc00UpMixerLoud14Source2Mute
                INTEGER,
            iqupc00UpMixerLoud14Source2Src
                INTEGER,
            iqupc00UpMixerLoud14Source3ProcGain
                INTEGER,
            iqupc00UpMixerLoud14Source3Mute
                INTEGER,
            iqupc00UpMixerLoud14Source3Src
                INTEGER,
            iqupc00UpMixerLoud14Source4ProcGain
                INTEGER,
            iqupc00UpMixerLoud14Source4Mute
                INTEGER,
            iqupc00UpMixerLoud14Source4Src
                INTEGER,
            iqupc00UpMixerLoud14Mode
                INTEGER,
            iqupc00UpMixerLoud14Status
                RollCallString,
            iqupc00UpMixerLoud14XfadeBypass
                INTEGER,
            iqupc00UpMixerLoud14XfadeUpmix
                INTEGER,
            iqupc00UpMixerLoud14Detect
                INTEGER,
            iqupc00UpMixerLoud14CenterWidth
                INTEGER,
            iqupc00UpMixerLoud14Surround
                INTEGER,
            iqupc00UpMixerLoud14AlgorithmType
                INTEGER,
            iqupc00UpMixerLoud58LoudnessPreset1
                INTEGER,
            iqupc00UpMixerLoud58LoudnessMasterLevel1
                INTEGER,
            iqupc00UpMixerLoud58LoudnessName1
                RollCallString,
            iqupc00UpMixerLoud58LoudnessBypass1
                INTEGER,
            iqupc00UpMixerLoud58LoudnessPreset2
                INTEGER,
            iqupc00UpMixerLoud58LoudnessMasterLevel2
                INTEGER,
            iqupc00UpMixerLoud58LoudnessName2
                RollCallString,
            iqupc00UpMixerLoud58LoudnessBypass2
                INTEGER,
            iqupc00UpMixerLoud58Source5ProcGain
                INTEGER,
            iqupc00UpMixerLoud58Source5Mute
                INTEGER,
            iqupc00UpMixerLoud58Source5Src
                INTEGER,
            iqupc00UpMixerLoud58Source6ProcGain
                INTEGER,
            iqupc00UpMixerLoud58Source6Mute
                INTEGER,
            iqupc00UpMixerLoud58Source6Src
                INTEGER,
            iqupc00UpMixerLoud58Source7ProcGain
                INTEGER,
            iqupc00UpMixerLoud58Source7Mute
                INTEGER,
            iqupc00UpMixerLoud58Source7Src
                INTEGER,
            iqupc00UpMixerLoud58Source8ProcGain
                INTEGER,
            iqupc00UpMixerLoud58Source8Mute
                INTEGER,
            iqupc00UpMixerLoud58Source8Src
                INTEGER,
            iqupc00UpMixerLoud58UpmixHide
                RollCallString,
            iqupc00UpMixerLoud58Chan1Name
                RollCallString,
            iqupc00UpMixerLoud58Chan2Name
                RollCallString,
            iqupc00UpMixerLoud58Chan3Name
                RollCallString,
            iqupc00UpMixerLoud58Chan4Name
                RollCallString,
            iqupc00UpMixerLoud58Chan5Name
                RollCallString,
            iqupc00UpMixerLoud58Chan6Name
                RollCallString,
            iqupc00UpMixerLoud58Chan7Name
                RollCallString,
            iqupc00UpMixerLoud58Chan8Name
                RollCallString,
            iqupc00UpMixerLoud58Chan1NameIn
                RollCallString,
            iqupc00UpMixerLoud58Chan2NameIn
                RollCallString,
            iqupc00UpMixerLoud58Chan3NameIn
                RollCallString,
            iqupc00UpMixerLoud58Chan4NameIn
                RollCallString,
            iqupc00UpMixerLoud58Chan5NameIn
                RollCallString,
            iqupc00UpMixerLoud58Chan6NameIn
                RollCallString,
            iqupc00UpMixerLoud58Chan7NameIn
                RollCallString,
            iqupc00UpMixerLoud58Chan8NameIn
                RollCallString,
            iqupc00UpMixerLoud58DialogHide
                RollCallString,
            iqupc00LoudCustomBlock1Name
                RollCallString,
            iqupc00LoudCustomBlock1inagcfreeze
                INTEGER,
            iqupc00LoudCustomBlock1inagcgate
                INTEGER,
            iqupc00LoudCustomBlock1inagcratio
                INTEGER,
            iqupc00LoudCustomBlock1inagcrange
                INTEGER,
            iqupc00LoudCustomBlock1inagcthresh
                INTEGER,
            iqupc00LoudCustomBlock1inagcattack
                INTEGER,
            iqupc00LoudCustomBlock1inagcrelease
                INTEGER,
            iqupc00LoudCustomBlock1peqfreq1
                INTEGER,
            iqupc00LoudCustomBlock1peqq1
                INTEGER,
            iqupc00LoudCustomBlock1peqlevel1
                INTEGER,
            iqupc00LoudCustomBlock1peqfreq2
                INTEGER,
            iqupc00LoudCustomBlock1peqq2
                INTEGER,
            iqupc00LoudCustomBlock1peqlevel2
                INTEGER,
            iqupc00LoudCustomBlock1peqfreq3
                INTEGER,
            iqupc00LoudCustomBlock1peqq3
                INTEGER,
            iqupc00LoudCustomBlock1peqlevel3
                INTEGER,
            iqupc00LoudCustomBlock1mbagcatk1
                INTEGER,
            iqupc00LoudCustomBlock1mbagcrel1
                INTEGER,
            iqupc00LoudCustomBlock1mbagcthresh1
                INTEGER,
            iqupc00LoudCustomBlock1mbagcoutlev1
                INTEGER,
            iqupc00LoudCustomBlock1mbagclimthresh1
                INTEGER,
            iqupc00LoudCustomBlock1mbagcinfthr1
                INTEGER,
            iqupc00LoudCustomBlock1mbagcatk2
                INTEGER,
            iqupc00LoudCustomBlock1mbagcrel2
                INTEGER,
            iqupc00LoudCustomBlock1mbagcthresh2
                INTEGER,
            iqupc00LoudCustomBlock1mbagcoutlev2
                INTEGER,
            iqupc00LoudCustomBlock1mbagclimthresh2
                INTEGER,
            iqupc00LoudCustomBlock1mbagcinfthr2
                INTEGER,
            iqupc00LoudCustomBlock1mbagcatk3
                INTEGER,
            iqupc00LoudCustomBlock1mbagcrel3
                INTEGER,
            iqupc00LoudCustomBlock1mbagcthresh3
                INTEGER,
            iqupc00LoudCustomBlock1mbagcoutlev3
                INTEGER,
            iqupc00LoudCustomBlock1mbagclimthresh3
                INTEGER,
            iqupc00LoudCustomBlock1mbagcinfthr3
                INTEGER,
            iqupc00LoudCustomBlock1mbagcatk4
                INTEGER,
            iqupc00LoudCustomBlock1mbagcrel4
                INTEGER,
            iqupc00LoudCustomBlock1mbagcthresh4
                INTEGER,
            iqupc00LoudCustomBlock1mbagcoutlev4
                INTEGER,
            iqupc00LoudCustomBlock1mbagclimthresh4
                INTEGER,
            iqupc00LoudCustomBlock1mbagcinfthr4
                INTEGER,
            iqupc00LoudCustomBlock1mbagcatk5
                INTEGER,
            iqupc00LoudCustomBlock1mbagcrel5
                INTEGER,
            iqupc00LoudCustomBlock1mbagcthresh5
                INTEGER,
            iqupc00LoudCustomBlock1mbagcoutlev5
                INTEGER,
            iqupc00LoudCustomBlock1mbagclimthresh5
                INTEGER,
            iqupc00LoudCustomBlock1mbagcinfthr5
                INTEGER,
            iqupc00LoudCustomBlock1mbrange
                INTEGER,
            iqupc00LoudCustomBlock1mbprogrise
                INTEGER,
            iqupc00LoudCustomBlock1mbsoftclip1
                INTEGER,
            iqupc00LoudCustomBlock1mbsoftclip2
                INTEGER,
            iqupc00LoudCustomBlock1mbratio
                INTEGER,
            iqupc00LoudCustomBlock1mblimdrive
                INTEGER,
            iqupc00LoudCustomBlock1CustomPreset
                INTEGER,
            iqupc00LoudCustomBlock1Copyto2
                INTEGER,
            iqupc00LoudCustomBlock2Name
                RollCallString,
            iqupc00LoudCustomBlock2inagcfreeze
                INTEGER,
            iqupc00LoudCustomBlock2inagcgate
                INTEGER,
            iqupc00LoudCustomBlock2inagcratio
                INTEGER,
            iqupc00LoudCustomBlock2inagcrange
                INTEGER,
            iqupc00LoudCustomBlock2inagcthresh
                INTEGER,
            iqupc00LoudCustomBlock2inagcattack
                INTEGER,
            iqupc00LoudCustomBlock2inagcrelease
                INTEGER,
            iqupc00LoudCustomBlock2peqfreq1
                INTEGER,
            iqupc00LoudCustomBlock2peqq1
                INTEGER,
            iqupc00LoudCustomBlock2peqlevel1
                INTEGER,
            iqupc00LoudCustomBlock2peqfreq2
                INTEGER,
            iqupc00LoudCustomBlock2peqq2
                INTEGER,
            iqupc00LoudCustomBlock2peqlevel2
                INTEGER,
            iqupc00LoudCustomBlock2peqfreq3
                INTEGER,
            iqupc00LoudCustomBlock2peqq3
                INTEGER,
            iqupc00LoudCustomBlock2peqlevel3
                INTEGER,
            iqupc00LoudCustomBlock2mbagcatk1
                INTEGER,
            iqupc00LoudCustomBlock2mbagcrel1
                INTEGER,
            iqupc00LoudCustomBlock2mbagcthresh1
                INTEGER,
            iqupc00LoudCustomBlock2mbagcoutlev1
                INTEGER,
            iqupc00LoudCustomBlock2mbagclimthresh1
                INTEGER,
            iqupc00LoudCustomBlock2mbagcinfthr1
                INTEGER,
            iqupc00LoudCustomBlock2mbagcatk2
                INTEGER,
            iqupc00LoudCustomBlock2mbagcrel2
                INTEGER,
            iqupc00LoudCustomBlock2mbagcthresh2
                INTEGER,
            iqupc00LoudCustomBlock2mbagcoutlev2
                INTEGER,
            iqupc00LoudCustomBlock2mbagclimthresh2
                INTEGER,
            iqupc00LoudCustomBlock2mbagcinfthr2
                INTEGER,
            iqupc00LoudCustomBlock2mbagcatk3
                INTEGER,
            iqupc00LoudCustomBlock2mbagcrel3
                INTEGER,
            iqupc00LoudCustomBlock2mbagcthresh3
                INTEGER,
            iqupc00LoudCustomBlock2mbagcoutlev3
                INTEGER,
            iqupc00LoudCustomBlock2mbagclimthresh3
                INTEGER,
            iqupc00LoudCustomBlock2mbagcinfthr3
                INTEGER,
            iqupc00LoudCustomBlock2mbagcatk4
                INTEGER,
            iqupc00LoudCustomBlock2mbagcrel4
                INTEGER,
            iqupc00LoudCustomBlock2mbagcthresh4
                INTEGER,
            iqupc00LoudCustomBlock2mbagcoutlev4
                INTEGER,
            iqupc00LoudCustomBlock2mbagclimthresh4
                INTEGER,
            iqupc00LoudCustomBlock2mbagcinfthr4
                INTEGER,
            iqupc00LoudCustomBlock2mbagcatk5
                INTEGER,
            iqupc00LoudCustomBlock2mbagcrel5
                INTEGER,
            iqupc00LoudCustomBlock2mbagcthresh5
                INTEGER,
            iqupc00LoudCustomBlock2mbagcoutlev5
                INTEGER,
            iqupc00LoudCustomBlock2mbagclimthresh5
                INTEGER,
            iqupc00LoudCustomBlock2mbagcinfthr5
                INTEGER,
            iqupc00LoudCustomBlock2mbrange
                INTEGER,
            iqupc00LoudCustomBlock2mbprogrise
                INTEGER,
            iqupc00LoudCustomBlock2mbsoftclip1
                INTEGER,
            iqupc00LoudCustomBlock2mbsoftclip2
                INTEGER,
            iqupc00LoudCustomBlock2mbratio
                INTEGER,
            iqupc00LoudCustomBlock2mblimdrive
                INTEGER,
            iqupc00LoudCustomBlock2CustomPreset
                INTEGER,
            iqupc00LoudCustomBlock2Copyto1
                INTEGER,
            iqupc00LoudCustomMasterLevelCustom1
                INTEGER,
            iqupc00LoudCustomMasterLevelCustom2
                INTEGER,
            iqupc00LoudCustomMasterLevelGen51
                INTEGER,
            iqupc00LoudCustomMasterLevelLight51
                INTEGER,
            iqupc00LoudCustomMasterLevelHeavy51
                INTEGER,
            iqupc00LoudCustomMasterLevelLoud51
                INTEGER,
            iqupc00LoudCustomMasterLevelLoudLimit51
                INTEGER,
            iqupc00LoudCustomMasterLevelProtect51
                INTEGER,
            iqupc00LoudCustomMasterLevelGenSterA
                INTEGER,
            iqupc00LoudCustomMasterLevelLightSterA
                INTEGER,
            iqupc00LoudCustomMasterLevelHeavySterA
                INTEGER,
            iqupc00LoudCustomMasterLevelLoudSterA
                INTEGER,
            iqupc00LoudCustomMasterLevelLoudLimitSterA
                INTEGER,
            iqupc00LoudCustomMasterLevelProtectSterA
                INTEGER,
            iqupc00LoudCustomMasterLevelGenSterB
                INTEGER,
            iqupc00LoudCustomMasterLevelLightSterB
                INTEGER,
            iqupc00LoudCustomMasterLevelHeavySterB
                INTEGER,
            iqupc00LoudCustomMasterLevelLoudSterB
                INTEGER,
            iqupc00LoudCustomMasterLevelLoudLimitSterB
                INTEGER,
            iqupc00LoudCustomMasterLevelProtectSterB
                INTEGER,
            iqupc00Mixers13Select
                INTEGER,
            iqupc00Mixers13Source1ProcGain
                INTEGER,
            iqupc00Mixers13Source1Invert
                INTEGER,
            iqupc00Mixers13Source1Mute
                INTEGER,
            iqupc00Mixers13Source1Src
                INTEGER,
            iqupc00Mixers13Source1Name
                RollCallString,
            iqupc00Mixers13Source2ProcGain
                INTEGER,
            iqupc00Mixers13Source2Invert
                INTEGER,
            iqupc00Mixers13Source2Mute
                INTEGER,
            iqupc00Mixers13Source2Src
                INTEGER,
            iqupc00Mixers13Source2Name
                RollCallString,
            iqupc00Mixers13Source3ProcGain
                INTEGER,
            iqupc00Mixers13Source3Invert
                INTEGER,
            iqupc00Mixers13Source3Mute
                INTEGER,
            iqupc00Mixers13Source3Src
                INTEGER,
            iqupc00Mixers13Source3Name
                RollCallString,
            iqupc00Mixers13MixerLoRo
                INTEGER,
            iqupc00Mixers46Source4ProcGain
                INTEGER,
            iqupc00Mixers46Source4Invert
                INTEGER,
            iqupc00Mixers46Source4Mute
                INTEGER,
            iqupc00Mixers46Source4Src
                INTEGER,
            iqupc00Mixers46Source4Name
                RollCallString,
            iqupc00Mixers46Source5ProcGain
                INTEGER,
            iqupc00Mixers46Source5Invert
                INTEGER,
            iqupc00Mixers46Source5Mute
                INTEGER,
            iqupc00Mixers46Source5Src
                INTEGER,
            iqupc00Mixers46Source5Name
                RollCallString,
            iqupc00Mixers46Source6ProcGain
                INTEGER,
            iqupc00Mixers46Source6Invert
                INTEGER,
            iqupc00Mixers46Source6Mute
                INTEGER,
            iqupc00Mixers46Source6Src
                INTEGER,
            iqupc00Mixers46Source6Name
                RollCallString,
            iqupc00DolbyDecodeDolbyDecoderDetectMode
                INTEGER,
            iqupc00DolbyDecodeDolbyDecoderAESChannelSelect
                INTEGER,
            iqupc00DolbyDecodeDolbyDecoderPCMLatency
                INTEGER,
            iqupc00DolbyDecodeDolbyDecoderListeningModeDolbyD
                INTEGER,
            iqupc00DolbyDecodeDolbyDecoderDynamicRange
                INTEGER,
            iqupc00DolbyDecoderAuxChannelProgramSelect
                INTEGER,
            iqupc00DolbyDecoderAuxChannelDynamicRange
                INTEGER,
            iqupc00DolbyDecoderAuxChannelOutputMode
                INTEGER,
            iqupc00DolbyDecoderDecoderStatusBitstreamFormat
                RollCallString,
            iqupc00DolbyDecoderDecoderStatusBitstreamStatus
                RollCallString,
            iqupc00DolbyDecoderDecoderStatusDCRCErrorCount
                RollCallString,
            iqupc00DolbyDecoderDecoderStatusDCRCErrorTime
                RollCallString,
            iqupc00DolbyDecoderDecoderStatusECRCErrorCount
                RollCallString,
            iqupc00DolbyDecoderDecoderStatusECRCErrorTime
                RollCallString,
            iqupc00DolbyDecoderDecoderStatusResetErrors
                INTEGER,
            iqupc00DolbyDecoderDecoderStatusResetTime
                RollCallString,
            iqupc00DolbyDecoderOutputsA1A2A1Gain
                INTEGER,
            iqupc00DolbyDecoderOutputsA1A2A2Gain
                INTEGER,
            iqupc00DolbyDecoderOutputsA1A2MuteA1
                INTEGER,
            iqupc00DolbyDecoderOutputsA1A2MuteA2
                INTEGER,
            iqupc00DolbyDecoderOutputsA1A2StereoA
                INTEGER,
            iqupc00DolbyDecoderOutputsB3B4B3Gain
                INTEGER,
            iqupc00DolbyDecoderOutputsB3B4B4Gain
                INTEGER,
            iqupc00DolbyDecoderOutputsB3B4MuteB3
                INTEGER,
            iqupc00DolbyDecoderOutputsB3B4MuteB4
                INTEGER,
            iqupc00DolbyDecoderOutputsB3B4StereoB
                INTEGER,
            iqupc00DolbyDecoderOutputsC5C6C5Gain
                INTEGER,
            iqupc00DolbyDecoderOutputsC5C6C6Gain
                INTEGER,
            iqupc00DolbyDecoderOutputsC5C6MuteC5
                INTEGER,
            iqupc00DolbyDecoderOutputsC5C6MuteC6
                INTEGER,
            iqupc00DolbyDecoderOutputsC5C6StereoC
                INTEGER,
            iqupc00DolbyDecoderOutputsD7D8D7Gain
                INTEGER,
            iqupc00DolbyDecoderOutputsD7D8D8Gain
                INTEGER,
            iqupc00DolbyDecoderOutputsD7D8MuteD7
                INTEGER,
            iqupc00DolbyDecoderOutputsD7D8MuteD8
                INTEGER,
            iqupc00DolbyDecoderOutputsD7D8StereoD
                INTEGER,
            iqupc00DolbyDecoderOutputsMLMRMLGain
                INTEGER,
            iqupc00DolbyDecoderOutputsMLMRMRGain
                INTEGER,
            iqupc00DolbyDecoderOutputsMLMRMuteML
                INTEGER,
            iqupc00DolbyDecoderOutputsMLMRMuteMR
                INTEGER,
            iqupc00DolbyDecoderOutputsMLMRStereoM
                INTEGER,
            iqupc00DolbyDecodeDolbyDecoderOutputsMasterGain
                INTEGER,
            iqupc00DolbyDecodeDolbyDecoderOutputsMasterMute
                INTEGER,
            iqupc00DolbyEncInp14Source1ProcGain
                INTEGER,
            iqupc00DolbyEncInp14Source1Mute
                INTEGER,
            iqupc00DolbyEncInp14Source1Src
                INTEGER,
            iqupc00DolbyEncInp14Source2ProcGain
                INTEGER,
            iqupc00DolbyEncInp14Source2Mute
                INTEGER,
            iqupc00DolbyEncInp14Source2Src
                INTEGER,
            iqupc00DolbyEncInp14Source3ProcGain
                INTEGER,
            iqupc00DolbyEncInp14Source3Mute
                INTEGER,
            iqupc00DolbyEncInp14Source3Src
                INTEGER,
            iqupc00DolbyEncInp14Source4ProcGain
                INTEGER,
            iqupc00DolbyEncInp14Source4Mute
                INTEGER,
            iqupc00DolbyEncInp14Source4Src
                INTEGER,
            iqupc00DolbyEncInp58Source5ProcGain
                INTEGER,
            iqupc00DolbyEncInp58Source5Mute
                INTEGER,
            iqupc00DolbyEncInp58Source5Src
                INTEGER,
            iqupc00DolbyEncInp58Source6ProcGain
                INTEGER,
            iqupc00DolbyEncInp58Source6Mute
                INTEGER,
            iqupc00DolbyEncInp58Source6Src
                INTEGER,
            iqupc00DolbyEncInp58Source7ProcGain
                INTEGER,
            iqupc00DolbyEncInp58Source7Mute
                INTEGER,
            iqupc00DolbyEncInp58Source7Src
                INTEGER,
            iqupc00DolbyEncInp58Source8ProcGain
                INTEGER,
            iqupc00DolbyEncInp58Source8Mute
                INTEGER,
            iqupc00DolbyEncInp58Source8Src
                INTEGER,
            iqupc00DolbyControlDolbyEncoderControlSampleRateConversion
                INTEGER,
            iqupc00DolbyControlDolbyEncoderControlMetaRevertMode
                INTEGER,
            iqupc00DolbyControlDolbyEncoderControlEncodingMode
                INTEGER,
            iqupc00DolbyControlDolbyEEncoderCntrlBitDepth
                INTEGER,
            iqupc00DolbyControlDolbyEEncoderCntrlMetadataSource
                INTEGER,
            iqupc00DolbyControlDolbyEEncoderCntrlInternalConfig
                INTEGER,
            iqupc00DolbyControlDolbyEEncoderCntrlDefaultAllMeta
                INTEGER,
            iqupc00DolbyControlDolbyIntMetaCntrlCopyExtMetadata
                INTEGER,
            iqupc00DolbyControlDolbyIntMetaCntrlDefaultProgramMeta
                INTEGER,
            iqupc00DolbyControlDolbyIntMetaCntrlDialogueNorm
                INTEGER,
            iqupc00DolbyControlDolbyIntMetaCntrlChannelMode
                INTEGER,
            iqupc00DolbyControlDolbyIntMetaCntrlLFEChannel
                INTEGER,
            iqupc00DolbyControlDolbyIntMetaCntrlBitstreamMode
                INTEGER,
            iqupc00DolbyControlDolbyIntMetaCntrlRFMode
                INTEGER,
            iqupc00DolbyControlDolbyIntMetaCntrlLineMode
                INTEGER,
            iqupc00DolbyIntMetaCntrlAudioProductionInfoExists
                INTEGER,
            iqupc00DolbyIntMetaCntrlAudioProductionInfoMixLevel
                INTEGER,
            iqupc00DolbyIntMetaCntrlAudioProductionInfoRoomType
                INTEGER,
            iqupc00DolbyControlDolbyIntMetaCntrlCentreMixLevel
                INTEGER,
            iqupc00DolbyControlDolbyIntMetaCntrlSurroundMixLevel
                INTEGER,
            iqupc00DolbyControlDolbyIntMetaCntrlSurroundMode
                INTEGER,
            iqupc00DolbyControlDolbyIntMetaCntrlCopyright
                INTEGER,
            iqupc00DolbyIntMetaCntrlExtendedBSI1Exists
                INTEGER,
            iqupc00DolbyIntMetaCntrlExtendedBSI1StereoDownmixMode
                INTEGER,
            iqupc00DolbyIntMetaCntrlExtendedBSI1LtRtCentreMixLevel
                INTEGER,
            iqupc00DolbyIntMetaCntrlExtendedBSI1LtRtSurrMixLevel
                INTEGER,
            iqupc00DolbyIntMetaCntrlExtendedBSI1LoRoCentreMixLevel
                INTEGER,
            iqupc00DolbyIntMetaCntrlExtendedBSI1LoRoSurrMixLevel
                INTEGER,
            iqupc00DolbyIntMetaCntrlExtendedBSI2Exists
                INTEGER,
            iqupc00DolbyIntMetaCntrlExtendedBSI2SurroundEXMode
                INTEGER,
            iqupc00DolbyIntMetaCntrlExtendedBSI2LowpassFilter
                INTEGER,
            iqupc00DolbyIntMetaCntrlExtendedBSI2LFEFIlter
                INTEGER,
            iqupc00DolbyIntMetaCntrlExtendedBSI2SurrPhaseShiftFltr
                INTEGER,
            iqupc00DolbyIntMetaCntrlExtendedBSI2Surr3dBAttenuator
                INTEGER,
            iqupc00DolbyControlDolbyIntMetaCntrlProgramDescriptionL
                RollCallString,
            iqupc00DolbyControlDolbyIntMetaCntrlProgramDescriptionR
                RollCallString,
            iqupc00DolbyControlDolbyIntMetaCntrlIntMetaSaveset
                INTEGER,
            iqupc00DolbyControlDolbyDEncoderCntrlInternalMode
                INTEGER,
            iqupc00DolbyControlDolbyDEncoderCntrlBitstreamFormat
                INTEGER,
            iqupc00DolbyControlDolbyDEncoderCntrlMetadataSource
                INTEGER,
            iqupc00DolbyControlDolbyDEncoderCntrlIntMetaDataRate
                INTEGER,
            iqupc00DolbyControlDolbyDEncoderCntrlExtMetaDataRate
                INTEGER,
            iqupc00DolbyControlDolbyDEncoderCntrlStreamNumber
                INTEGER,
            iqupc00DolbyControlDolbyMetaProgSelMetaProgramSelect
                INTEGER,
            iqupc00DolbyStatusDolbyCommonStatusVideoSync
                RollCallString,
            iqupc00DolbyStatusDolbyCommonStatusFrameRate
                RollCallString,
            iqupc00DolbyStatusDolbyCommonStatusProgramConfig
                RollCallString,
            iqupc00DolbyStatusDolbyCommonStatusFWVersion
                RollCallString,
            iqupc00DolbyStatusDolbyCommonStatusDeviceName
                RollCallString,
            iqupc00DolbyCommonStatusChannelAssignmentDolbyA1
                RollCallString,
            iqupc00DolbyCommonStatusChannelAssignmentDolbyA2
                RollCallString,
            iqupc00DolbyCommonStatusChannelAssignmentDolbyB3
                RollCallString,
            iqupc00DolbyCommonStatusChannelAssignmentDolbyB4
                RollCallString,
            iqupc00DolbyCommonStatusChannelAssignmentDolbyC5
                RollCallString,
            iqupc00DolbyCommonStatusChannelAssignmentDolbyC6
                RollCallString,
            iqupc00DolbyCommonStatusChannelAssignmentDolbyD7
                RollCallString,
            iqupc00DolbyCommonStatusChannelAssignmentDolbyD8
                RollCallString,
            iqupc00DolbyCommonStatusChnlPairAssignmentDolby12
                RollCallString,
            iqupc00DolbyCommonStatusChnlPairAssignmentDolby34
                RollCallString,
            iqupc00DolbyCommonStatusChnlPairAssignmentDolby56
                RollCallString,
            iqupc00DolbyCommonStatusChnlPairAssignmentDolby78
                RollCallString,
            iqupc00DolbyStatusDolbyExtProgStatusP1Status
                RollCallString,
            iqupc00DolbyStatusDolbyExtProgStatusP2Status
                RollCallString,
            iqupc00DolbyStatusDolbyExtProgStatusP3Status
                RollCallString,
            iqupc00DolbyStatusDolbyExtProgStatusP4Status
                RollCallString,
            iqupc00DolbyStatusDolbyExtProgStatusP5Status
                RollCallString,
            iqupc00DolbyStatusDolbyExtProgStatusP6Status
                RollCallString,
            iqupc00DolbyStatusDolbyExtProgStatusP7Status
                RollCallString,
            iqupc00DolbyStatusDolbyExtProgStatusP8Status
                RollCallString,
            iqupc00DolbyStatusDolbyMetadataStatusProgramDescriptionL
                RollCallString,
            iqupc00DolbyStatusDolbyMetadataStatusProgramDescriptionR
                RollCallString,
            iqupc00DolbyStatusDolbyMetadataStatusDialogueNorm
                RollCallString,
            iqupc00DolbyStatusDolbyMetadataStatusChannelMode
                RollCallString,
            iqupc00DolbyStatusDolbyMetadataStatusLFE
                RollCallString,
            iqupc00DolbyStatusDolbyMetadataStatusBitstreamMode
                RollCallString,
            iqupc00DolbyStatusDolbyMetadataStatusRFMode
                RollCallString,
            iqupc00DolbyStatusDolbyMetadataStatusLineMode
                RollCallString,
            iqupc00DolbyStatusDolbyMetadataStatusCentreMixLevel
                RollCallString,
            iqupc00DolbyStatusDolbyMetadataStatusSurroundMixLevel
                RollCallString,
            iqupc00DolbyStatusDolbyMetadataStatusSurroundMode
                RollCallString,
            iqupc00DolbyStatusDolbyMetadataStatusCopyright
                RollCallString,
            iqupc00DolbyMetadataStatusAudioProductionInfoAudioProdInfoExists
                RollCallString,
            iqupc00DolbyMetadataStatusAudioProductionInfoMixLevel
                RollCallString,
            iqupc00DolbyMetadataStatusAudioProductionInfoRoomType
                RollCallString,
            iqupc00DolbyStatusDolbyMetadataStatusExtendedBSI1Exists
                RollCallString,
            iqupc00DolbyMetadataStatusExtendedBSI1StereoDownmixMode
                RollCallString,
            iqupc00DolbyMetadataStatusExtendedBSI1LtRtCentreMixLevel
                RollCallString,
            iqupc00DolbyMetadataStatusExtendedBSI1LtRtSurrMixLevel
                RollCallString,
            iqupc00DolbyMetadataStatusExtendedBSI1LoRoCentreMixLevel
                RollCallString,
            iqupc00DolbyMetadataStatusExtendedBSI1LoRoSurrMixLevel
                RollCallString,
            iqupc00DolbyStatusDolbyMetadataStatusExtendedBSI2Exists
                RollCallString,
            iqupc00DolbyMetadataStatusExtendedBSI2SurroundEXMode
                RollCallString,
            iqupc00DolbyMetadataStatusExtendedBSI2LowpassFilter
                RollCallString,
            iqupc00DolbyMetadataStatusExtendedBSI2LFEFilter
                RollCallString,
            iqupc00DolbyMetadataStatusExtendedBSI2SurrPhaseShiftFltr
                RollCallString,
            iqupc00DolbyMetadataStatusExtendedBSI2Surr3dBAtten
                RollCallString,
            iqupc00DolbyStatusDolbyEncoderStatusStatus
                RollCallString,
            iqupc00DolbyStatusDolbyEncoderStatusBitstreamStatus
                RollCallString,
            iqupc00DolbyStatusDolbyEncoderStatusReversionStatus
                RollCallString,
            iqupc00DolbyStatusDolbyEncoderStatusHWVersion
                RollCallString,
            iqupc00DolbyStatusDolbyEncoderStatusOPProgramConfig
                RollCallString,
            iqupc00RollCallMemoriesMemoriesABCRecallMemory
                INTEGER,
            iqupc00RollCallMemoriesMemoriesABCSelMemory
                INTEGER,
            iqupc00RollCallMemoriesMemoriesABCSaveMemory
                INTEGER,
            iqupc00RollCallMemoriesMemoriesABCClearMemory
                INTEGER,
            iqupc00MemoriesABCMemoryNameChangeName
                RollCallString,
            iqupc00MemoriesABCMemoryNameLastUserMemory
                RollCallString,
            iqupc00RollCallMemoriesMemoriesABCMemoryName1
                RollCallString,
            iqupc00RollCallMemoriesMemoriesABCMemoryName2
                RollCallString,
            iqupc00RollCallMemoriesMemoriesABCMemoryName3
                RollCallString,
            iqupc00RollCallMemoriesMemoriesABCMemoryName4
                RollCallString,
            iqupc00RollCallMemoriesMemoriesABCMemoryName5
                RollCallString,
            iqupc00RollCallMemoriesMemoriesABCMemoryName6
                RollCallString,
            iqupc00RollCallMemoriesMemoriesABCMemoryName7
                RollCallString,
            iqupc00RollCallMemoriesMemoriesABCMemoryName8
                RollCallString,
            iqupc00RollCallMemoriesMemoriesABCMemoryName9
                RollCallString,
            iqupc00RollCallMemoriesMemoriesABCMemoryName10
                RollCallString,
            iqupc00RollCallMemoriesMemoriesABCMemoryName11
                RollCallString,
            iqupc00RollCallMemoriesMemoriesABCMemoryName12
                RollCallString,
            iqupc00RollCallMemoriesMemoriesABCMemoryName13
                RollCallString,
            iqupc00RollCallMemoriesMemoriesABCMemoryName14
                RollCallString,
            iqupc00RollCallMemoriesMemoriesABCMemoryName15
                RollCallString,
            iqupc00RollCallMemoriesMemoriesABCMemoryName16
                RollCallString,
            iqupc00Logging1OutEmbAudLoggingLogOutEmb11state
                INTEGER,
            iqupc00Logging1OutEmbAudLoggingOutEmb11state
                RollCallString,
            iqupc00Logging1OutEmbAudLoggingLogOutEmb12state
                INTEGER,
            iqupc00Logging1OutEmbAudLoggingOutEmb12state
                RollCallString,
            iqupc00Logging1OutEmbAudLoggingLogOutEmb21state
                INTEGER,
            iqupc00Logging1OutEmbAudLoggingOutEmb21state
                RollCallString,
            iqupc00Logging1OutEmbAudLoggingLogOutEmb22state
                INTEGER,
            iqupc00Logging1OutEmbAudLoggingOutEmb22state
                RollCallString,
            iqupc00Logging1OutEmbAudLoggingLogOutEmb31state
                INTEGER,
            iqupc00Logging1OutEmbAudLoggingOutEmb31state
                RollCallString,
            iqupc00Logging1OutEmbAudLoggingLogOutEmb32state
                INTEGER,
            iqupc00Logging1OutEmbAudLoggingOutEmb32state
                RollCallString,
            iqupc00Logging1OutEmbAudLoggingLogOutEmb41state
                INTEGER,
            iqupc00Logging1OutEmbAudLoggingOutEmb41state
                RollCallString,
            iqupc00Logging1OutEmbAudLoggingLogOutEmb42state
                INTEGER,
            iqupc00Logging1OutEmbAudLoggingOutEmb42state
                RollCallString,
            iqupc00Logging1OutEmbAudLoggingLogOutEmb51state
                INTEGER,
            iqupc00Logging1OutEmbAudLoggingOutEmb51state
                RollCallString,
            iqupc00Logging1OutEmbAudLoggingLogOutEmb52state
                INTEGER,
            iqupc00Logging1OutEmbAudLoggingOutEmb52state
                RollCallString,
            iqupc00Logging1OutEmbAudLoggingLogOutEmb61state
                INTEGER,
            iqupc00Logging1OutEmbAudLoggingOutEmb61state
                RollCallString,
            iqupc00Logging1OutEmbAudLoggingLogOutEmb62state
                INTEGER,
            iqupc00Logging1OutEmbAudLoggingOutEmb62state
                RollCallString,
            iqupc00Logging1OutEmbAudLoggingLogOutEmb71state
                INTEGER,
            iqupc00Logging1OutEmbAudLoggingOutEmb71state
                RollCallString,
            iqupc00Logging1OutEmbAudLoggingLogOutEmb72state
                INTEGER,
            iqupc00Logging1OutEmbAudLoggingOutEmb72state
                RollCallString,
            iqupc00Logging1OutEmbAudLoggingLogOutEmb81state
                INTEGER,
            iqupc00Logging1OutEmbAudLoggingOutEmb81state
                RollCallString,
            iqupc00Logging1OutEmbAudLoggingLogOutEmb82state
                INTEGER,
            iqupc00Logging1OutEmbAudLoggingOutEmb82state
                RollCallString,
            iqupc00Logging1DolbyDecoderLoggingLogBitstreamFormat
                INTEGER,
            iqupc00Logging1DolbyDecoderLoggingBitstreamFormat
                RollCallString,
            iqupc00Logging1DolbyDecoderLoggingLogBitstreamStatus
                INTEGER,
            iqupc00Logging1DolbyDecoderLoggingBitstreamStatus
                RollCallString,
            iqupc00Logging1DolbyDecoderLoggingLogDCRCErrors
                INTEGER,
            iqupc00Logging1DolbyDecoderLoggingDCRCErrorCount
                RollCallString,
            iqupc00Logging1DolbyDecoderLoggingLogECRCErrors
                INTEGER,
            iqupc00Logging1DolbyDecoderLoggingECRCErrorCount
                RollCallString,
            iqupc00Logging1DolbyEncoderLoggingLogEncoderStatus
                INTEGER,
            iqupc00Logging1DolbyEncoderLoggingEncoderStatus
                RollCallString,
            iqupc00Logging1DolbyEncoderLoggingLogBitstreamStatus
                INTEGER,
            iqupc00Logging1DolbyEncoderLoggingBitstreamStatus
                RollCallString,
            iqupc00Logging1DolbyEncoderLoggingLogReversionStatus
                INTEGER,
            iqupc00Logging1DolbyEncoderLoggingReversionStatus
                RollCallString,
            iqupc00Logging1DolbyLoggingLogVideoSync
                INTEGER,
            iqupc00Logging1DolbyLoggingVideoSync
                RollCallString,
            iqupc00Logging1DolbyLoggingLogFrameRate
                INTEGER,
            iqupc00Logging1DolbyLoggingFrameRate
                RollCallString,
            iqupc00Logging1DolbyLoggingLogProgramConfig
                INTEGER,
            iqupc00Logging1DolbyLoggingProgramConfig
                RollCallString,
            iqupc00Logging1DolbyMetadataLoggingLogSelectedProgram
                INTEGER,
            iqupc00Logging1DolbyMetadataLoggingSelectedProgram
                RollCallString,
            iqupc00Logging1DolbyMetadataLoggingLogProgramDescriptor
                INTEGER,
            iqupc00Logging1DolbyMetadataLoggingProgramDescriptor
                RollCallString,
            iqupc00Logging1DolbyMetadataLoggingProgramDescPt2
                RollCallString,
            iqupc00Logging1DolbyMetadataLoggingLogChannelMode
                INTEGER,
            iqupc00Logging1DolbyMetadataLoggingChannelMode
                RollCallString,
            iqupc00Logging1DolbyMetadataLoggingLogLFEChannel
                INTEGER,
            iqupc00Logging1DolbyMetadataLoggingLFEChannel
                RollCallString,
            iqupc00Logging1DolbyMetadataLoggingLogDialogueNorm
                INTEGER,
            iqupc00Logging1DolbyMetadataLoggingDialogueNorm
                RollCallString,
            iqupc00Logging1AncillaryDataLoggingLogVIInp1
                INTEGER,
            iqupc00Logging1AncillaryDataLoggingVIInp1
                RollCallString,
            iqupc00Logging1AncillaryDataLoggingLogWSSInp1
                INTEGER,
            iqupc00Logging1AncillaryDataLoggingWSSInp1
                RollCallString,
            iqupc00Logging1AncillaryDataLoggingLogVITCInp1
                INTEGER,
            iqupc00Logging1AncillaryDataLoggingVITCInp1
                RollCallString,
            iqupc00Logging1AncillaryDataLoggingLogWSTInp1
                INTEGER,
            iqupc00Logging1AncillaryDataLoggingWSTInp1
                RollCallString,
            iqupc00Logging1AncillaryDataLoggingLogCC608Inp1
                INTEGER,
            iqupc00Logging1AncillaryDataLoggingCC608Inp1
                RollCallString,
            iqupc00Logging1AncillaryDataLoggingLog2016Inp1
                INTEGER,
            iqupc00Logging1AncillaryDataLogging2016Inp1
                RollCallString,
            iqupc00Logging1AncillaryDataLoggingLogATCInp1
                INTEGER,
            iqupc00Logging1AncillaryDataLoggingATCInp1
                RollCallString,
            iqupc00Logging1AncillaryDataLoggingLogCC708Inp1
                INTEGER,
            iqupc00Logging1AncillaryDataLoggingCC708Inp1
                RollCallString,
            iqupc00Logging1AncillaryDataLoggingLogARInp1
                INTEGER,
            iqupc00Logging1AncillaryDataLoggingARInp1
                RollCallString,
            iqupc00Logging1AncillaryDataLoggingLogAFDInp1
                INTEGER,
            iqupc00Logging1AncillaryDataLoggingAFDInp1
                RollCallString,
            iqupc00Logging1AncillaryDataLoggingLogVIInp2
                INTEGER,
            iqupc00Logging1AncillaryDataLoggingVIInp2
                RollCallString,
            iqupc00Logging1AncillaryDataLoggingLogWSSInp2
                INTEGER,
            iqupc00Logging1AncillaryDataLoggingWSSInp2
                RollCallString,
            iqupc00Logging1AncillaryDataLoggingLogVITCInp2
                INTEGER,
            iqupc00Logging1AncillaryDataLoggingVITCInp2
                RollCallString,
            iqupc00Logging1AncillaryDataLoggingLogWSTInp2
                INTEGER,
            iqupc00Logging1AncillaryDataLoggingWSTInp2
                RollCallString,
            iqupc00Logging1AncillaryDataLoggingLogCC608Inp2
                INTEGER,
            iqupc00Logging1AncillaryDataLoggingCC608Inp2
                RollCallString,
            iqupc00Logging1AncillaryDataLoggingLog2016Inp2
                INTEGER,
            iqupc00Logging1AncillaryDataLogging2016Inp2
                RollCallString,
            iqupc00Logging1AncillaryDataLoggingLogATCInp2
                INTEGER,
            iqupc00Logging1AncillaryDataLoggingATCInp2
                RollCallString,
            iqupc00Logging1AncillaryDataLoggingLogCC708Inp2
                INTEGER,
            iqupc00Logging1AncillaryDataLoggingCC708Inp2
                RollCallString,
            iqupc00Logging1AncillaryDataLoggingLogARInp2
                INTEGER,
            iqupc00Logging1AncillaryDataLoggingARInp2
                RollCallString,
            iqupc00Logging1AncillaryDataLoggingLogAFDInp2
                INTEGER,
            iqupc00Logging1AncillaryDataLoggingAFDInp2
                RollCallString,
            iqupc00Logging1AncillaryDataLoggingLogOutput
                INTEGER,
            iqupc00Logging1AncillaryDataLoggingOutput
                RollCallString,
            iqupc00Logging1AncillaryDataLoggingLogOPAR
                INTEGER,
            iqupc00Logging1AncillaryDataLoggingOPAR
                RollCallString,
            iqupc00Logging1AncillaryDataLoggingLogOPAFD
                INTEGER,
            iqupc00Logging1AncillaryDataLoggingOPAFD
                RollCallString,
            iqupc00Logging2VideoRefLogInp1Type
                INTEGER,
            iqupc00Logging2VideoRefInp1Type
                RollCallString,
            iqupc00Logging2VideoRefLogInp1State
                INTEGER,
            iqupc00Logging2VideoRefInp1State
                RollCallString,
            iqupc00Logging2VideoRefLogInp1Std
                INTEGER,
            iqupc00Logging2VideoRefInp1Std
                RollCallString,
            iqupc00Logging2VideoRefLogInp1SDIErrs
                INTEGER,
            iqupc00Logging2VideoRefInp1SDIErrs
                RollCallString,
            iqupc00Logging2VideoRefLogInp1SDIErrSec
                INTEGER,
            iqupc00Logging2VideoRefInp1SDIErrSec
                RollCallString,
            iqupc00Logging2VideoRefLogInp1ANCerrs
                INTEGER,
            iqupc00Logging2VideoRefInp1ANCerrs
                RollCallString,
            iqupc00Logging2VideoRefLogInp1ANCerrSec
                INTEGER,
            iqupc00Logging2VideoRefInp1ANCerrSec
                RollCallString,
            iqupc00Logging2VideoRefLogInp2Type
                INTEGER,
            iqupc00Logging2VideoRefInp2Type
                RollCallString,
            iqupc00Logging2VideoRefLogInp2State
                INTEGER,
            iqupc00Logging2VideoRefInp2State
                RollCallString,
            iqupc00Logging2VideoRefLogInp2Std
                INTEGER,
            iqupc00Logging2VideoRefInp2Std
                RollCallString,
            iqupc00Logging2VideoRefLogInp2SDIErrs
                INTEGER,
            iqupc00Logging2VideoRefInp2SDIErrs
                RollCallString,
            iqupc00Logging2VideoRefLogInp2SDIErrSec
                INTEGER,
            iqupc00Logging2VideoRefInp2SDIErrSec
                RollCallString,
            iqupc00Logging2VideoRefLogInp2ANCerrs
                INTEGER,
            iqupc00Logging2VideoRefInp2ANCerrs
                RollCallString,
            iqupc00Logging2VideoRefLogInp2ANCerrSec
                INTEGER,
            iqupc00Logging2VideoRefInp2ANCerrSec
                RollCallString,
            iqupc00Logging2VideoRefLogOutp1Type
                INTEGER,
            iqupc00Logging2VideoRefOutp1Type
                RollCallString,
            iqupc00Logging2VideoRefLogOutp1State
                INTEGER,
            iqupc00Logging2VideoRefOutp1State
                RollCallString,
            iqupc00Logging2VideoRefLogOutp1Std
                INTEGER,
            iqupc00Logging2VideoRefOutp1Std
                RollCallString,
            iqupc00Logging2VideoRefLogOutp2State
                INTEGER,
            iqupc00Logging2VideoRefOutp2State
                RollCallString,
            iqupc00Logging2VideoRefLogOutp2Std
                INTEGER,
            iqupc00Logging2VideoRefOutp2Std
                RollCallString,
            iqupc00Logging2VideoRefLogOutp1
                INTEGER,
            iqupc00Logging2VideoRefOutp1
                RollCallString,
            iqupc00Logging2VideoRefLogOutp1Capt
                INTEGER,
            iqupc00Logging2VideoRefOutp1Capt
                RollCallString,
            iqupc00Logging2VideoRefLogRefType
                INTEGER,
            iqupc00Logging2VideoRefRefType
                RollCallString,
            iqupc00Logging2VideoRefLogRefState
                INTEGER,
            iqupc00Logging2VideoRefRefState
                RollCallString,
            iqupc00Logging2VideoRefLogRefStd
                INTEGER,
            iqupc00Logging2VideoRefRefStd
                RollCallString,
            iqupc00Logging2VideoRefLogGenlockState
                INTEGER,
            iqupc00Logging2VideoRefGenlocState
                RollCallString,
            iqupc00Logging2VideoRefLogInp1Ident
                INTEGER,
            iqupc00Logging2VideoRefInp1Ident
                RollCallString,
            iqupc00Logging2VideoRefLogInp1Name
                INTEGER,
            iqupc00Logging2VideoRefInp1Name
                RollCallString,
            iqupc00Logging2VideoRefLogInp2Ident
                INTEGER,
            iqupc00Logging2VideoRefInp2Ident
                RollCallString,
            iqupc00Logging2VideoRefLogInp2Name
                INTEGER,
            iqupc00Logging2VideoRefInp2Name
                RollCallString,
            iqupc00Logging2VideoRefLogOutp2Type
                INTEGER,
            iqupc00Logging2VideoRefOutp2Type
                RollCallString,
            iqupc00Logging2VideoRefLogOutp2
                INTEGER,
            iqupc00Logging2VideoRefOutp2
                RollCallString,
            iqupc00Logging2VideoRefLogOutp2Capt
                INTEGER,
            iqupc00Logging2VideoRefOutp2Capt
                RollCallString,
            iqupc00Logging2InEmbAudLoggingInpEmb1state
                RollCallString,
            iqupc00Logging2InEmbAudLoggingInpEmb2state
                RollCallString,
            iqupc00Logging2InEmbAudLoggingInpEmb3state
                RollCallString,
            iqupc00Logging2InEmbAudLoggingInpEmb4state
                RollCallString,
            iqupc00Logging2InEmbAudLoggingInpEmb5state
                RollCallString,
            iqupc00Logging2InEmbAudLoggingInpEmb6state
                RollCallString,
            iqupc00Logging2InEmbAudLoggingInpEmb7state
                RollCallString,
            iqupc00Logging2InEmbAudLoggingInpEmb8state
                RollCallString,
            iqupc00Logging2In1EmbAudLoggingLogInp1Emb1state
                INTEGER,
            iqupc00Logging2In1EmbAudLoggingInp1Emb1state
                RollCallString,
            iqupc00Logging2In1EmbAudLoggingLogInp1Emb2state
                INTEGER,
            iqupc00Logging2In1EmbAudLoggingInp1Emb2state
                RollCallString,
            iqupc00Logging2In1EmbAudLoggingLogInp1Emb3state
                INTEGER,
            iqupc00Logging2In1EmbAudLoggingInp1Emb3state
                RollCallString,
            iqupc00Logging2In1EmbAudLoggingLogInp1Emb4state
                INTEGER,
            iqupc00Logging2In1EmbAudLoggingInp1Emb4state
                RollCallString,
            iqupc00Logging2In1EmbAudLoggingLogInp1Emb5state
                INTEGER,
            iqupc00Logging2In1EmbAudLoggingInp1Emb5state
                RollCallString,
            iqupc00Logging2In1EmbAudLoggingLogInp1Emb6state
                INTEGER,
            iqupc00Logging2In1EmbAudLoggingInp1Emb6state
                RollCallString,
            iqupc00Logging2In1EmbAudLoggingLogInp1Emb7state
                INTEGER,
            iqupc00Logging2In1EmbAudLoggingInp1Emb7state
                RollCallString,
            iqupc00Logging2In1EmbAudLoggingLogInp1Emb8state
                INTEGER,
            iqupc00Logging2In1EmbAudLoggingInp1Emb8state
                RollCallString,
            iqupc00Logging2In2EmbAudLoggingLogInp2Emb1state
                INTEGER,
            iqupc00Logging2In2EmbAudLoggingInp2Emb1state
                RollCallString,
            iqupc00Logging2In2EmbAudLoggingLogInp2Emb2state
                INTEGER,
            iqupc00Logging2In2EmbAudLoggingInp2Emb2state
                RollCallString,
            iqupc00Logging2In2EmbAudLoggingLogInp2Emb3state
                INTEGER,
            iqupc00Logging2In2EmbAudLoggingInp2Emb3state
                RollCallString,
            iqupc00Logging2In2EmbAudLoggingLogInp2Emb4state
                INTEGER,
            iqupc00Logging2In2EmbAudLoggingInp2Emb4state
                RollCallString,
            iqupc00Logging2In2EmbAudLoggingLogInp2Emb5state
                INTEGER,
            iqupc00Logging2In2EmbAudLoggingInp2Emb5state
                RollCallString,
            iqupc00Logging2In2EmbAudLoggingLogInp2Emb6state
                INTEGER,
            iqupc00Logging2In2EmbAudLoggingInp2Emb6state
                RollCallString,
            iqupc00Logging2In2EmbAudLoggingLogInp2Emb7state
                INTEGER,
            iqupc00Logging2In2EmbAudLoggingInp2Emb7state
                RollCallString,
            iqupc00Logging2In2EmbAudLoggingLogInp2Emb8state
                INTEGER,
            iqupc00Logging2In2EmbAudLoggingInp2Emb8state
                RollCallString,
            iqupc00Logging2DolbyEAlignLogOutEmb1dolby
                INTEGER,
            iqupc00Logging2DolbyEAlignOutEmb1Dolby
                RollCallString,
            iqupc00Logging2DolbyEAlignLogOutEmb2dolby
                INTEGER,
            iqupc00Logging2DolbyEAlignOutEmb2Dolby
                RollCallString,
            iqupc00Logging2DolbyEAlignLogOutEmb3dolby
                INTEGER,
            iqupc00Logging2DolbyEAlignOutEmb3Dolby
                RollCallString,
            iqupc00Logging2DolbyEAlignLogOutEmb4dolby
                INTEGER,
            iqupc00Logging2DolbyEAlignOutEmb4Dolby
                RollCallString,
            iqupc00Logging2DolbyEAlignLogOutEmb5dolby
                INTEGER,
            iqupc00Logging2DolbyEAlignOutEmb5Dolby
                RollCallString,
            iqupc00Logging2DolbyEAlignLogOutEmb6dolby
                INTEGER,
            iqupc00Logging2DolbyEAlignOutEmb6Dolby
                RollCallString,
            iqupc00Logging2DolbyEAlignLogOutEmb7dolby
                INTEGER,
            iqupc00Logging2DolbyEAlignOutEmb7Dolby
                RollCallString,
            iqupc00Logging2DolbyEAlignLogOutEmb8dolby
                INTEGER,
            iqupc00Logging2DolbyEAlignOutEmb8Dolby
                RollCallString,
            iqupc00Logging2MiscLoggingLogSerialNo
                INTEGER,
            iqupc00Logging2MiscLoggingSerialNo
                RollCallString,
            iqupc00Logging2MiscLoggingLogOSVersion
                INTEGER,
            iqupc00Logging2MiscLoggingOSVersion
                RollCallString,
            iqupc00Logging2MiscLoggingLogBuildNo
                INTEGER,
            iqupc00Logging2MiscLoggingBuildNo
                RollCallString,
            iqupc00Logging2MiscLoggingLogHardwareVer
                INTEGER,
            iqupc00Logging2MiscLoggingHardwareVer
                RollCallString,
            iqupc00Logging2MiscLoggingLogFirmwareVer
                INTEGER,
            iqupc00Logging2MiscLoggingFirmwareVer
                RollCallString,
            iqupc00Logging2MiscLoggingLogUpTime
                INTEGER,
            iqupc00Logging2MiscLoggingUpTime
                RollCallString,
            iqupc00Logging2MiscLoggingLogLicensedOpt
                INTEGER,
            iqupc00Logging2MiscLoggingLicensedOptions
                RollCallString,
            iqupc00Logging2MiscLoggingLogLicensedOpt2
                INTEGER,
            iqupc00Logging2MiscLoggingLicensedOptions2
                RollCallString,
            iqupc00Logging2MiscLoggingLogTemp1State
                INTEGER,
            iqupc00Logging2MiscLoggingTemp1State
                RollCallString,
            iqupc00Logging2MiscLoggingLogTemp1Name
                INTEGER,
            iqupc00Logging2MiscLoggingTemp1Name
                RollCallString,
            iqupc00Logging2MiscLoggingLogRearId
                INTEGER,
            iqupc00Logging2MiscLoggingRearID
                RollCallString,
            iqupc00Logging2MiscLoggingLogSlotWidth
                INTEGER,
            iqupc00Logging2MiscLoggingSlotWidth
                RollCallString,
            iqupc00Logging2MiscLoggingLogSlotStart
                INTEGER,
            iqupc00Logging2MiscLoggingSlotStart
                RollCallString,
            iqupc00Logging2MiscLoggingLogRearStatus
                INTEGER,
            iqupc00Logging2MiscLoggingRearSTATUS
                RollCallString,
            iqupc00RollCallMemoriesRollTrackDisableAll
                INTEGER,
            iqupc00RollCallMemoriesRollTrackIndex
                INTEGER,
            iqupc00RollCallMemoriesRollTrackSource
                INTEGER,
            iqupc00RollCallMemoriesRollTrackAddress
                RollCallString,
            iqupc00RollCallMemoriesRollTrackCommand
                RollCallString,
            iqupc00RollCallMemoriesRollTrackStatus
                RollCallString,
            iqupc00RollCallMemoriesRollTrackSending
                RollCallString,
            iqupc00RollCallMemoriesHideGpio
                INTEGER,
            iqupc00RollCallMemoriesHideInpAES14
                INTEGER,
            iqupc00RollCallMemoriesHideInpAES18
                INTEGER,
            iqupc00RollCallMemoriesHideInpLogAES14
                INTEGER,
            iqupc00RollCallMemoriesHideInpLogAES18
                INTEGER,
            iqupc00RollCallMemoriesHideOutAES14
                INTEGER,
            iqupc00RollCallMemoriesHideOutAES18
                INTEGER,
            iqupc00RollCallMemoriesHideOutLogAES14
                INTEGER,
            iqupc00RollCallMemoriesHideOutLogAES18
                INTEGER,
            iqupc00GPIOGPI1GPIO1Mode
                INTEGER,
            iqupc00GPIOGPI1GPI1IPHighSelect
                INTEGER,
            iqupc00GPIOGPI1GPI1IPLowSelect
                INTEGER,
            iqupc00GPIOGPI1GPO1OPSelect
                INTEGER,
            iqupc00GPIOGPI1InvertGPIO1
                INTEGER,
            iqupc00GPIOGPI1Status
                RollCallString,
            iqupc00GPIOGPI2GPIO2Mode
                INTEGER,
            iqupc00GPIOGPI2GPI2IPHighSelect
                INTEGER,
            iqupc00GPIOGPI2GPI2IPLowSelect
                INTEGER,
            iqupc00GPIOGPI2GPO2OPSelect
                INTEGER,
            iqupc00GPIOGPI2InvertGPIO2
                INTEGER,
            iqupc00GPIOGPI2Status
                RollCallString,
            iqupc00SetupDisplay
                INTEGER,
            iqupc00SetupProduct
                RollCallString,
            iqupc00SetupRelease
                RollCallString,
            iqupc00SetupBuild
                RollCallString,
            iqupc00SetupKOS
                RollCallString,
            iqupc00SetupSerialNo
                RollCallString,
            iqupc00SetupFactoryDefault
                INTEGER,
            iqupc00SetupRestart
                INTEGER,
            iqupc00SetupDefaultSettings
                INTEGER,
            iqupc00SetupSerialNumber
                RollCallString,
            iqupc00SetupBoardID
                INTEGER,
            iqupc00SetupSaveID
                INTEGER,
            iqupc00SetupFpgaBoardType
                RollCallString,
            iqupc00SetupFpgaSerialNo
                RollCallString,
            iqupc00SetupFpgaSoftVer
                RollCallString,
            iqupc00SetupFpgaVer
                RollCallString,
            iqupc00SetupFpgaTIVer
                RollCallString,
            iqupc00SetupFpgaDolbyModId
                RollCallString,
            iqupc00SetupFpgaProtVer
                RollCallString,
            iqupc00SetupFpgaProgCRC
                RollCallString,
            iqupc00SetupFpgaUptime
                RollCallString,
            iqupc00SetupFpgaENGVXPVer
                RollCallString,
            iqupc00SetupFpgaENGSharcVer
                RollCallString,
            iqupc00SetupFpgaENGAlteraVer
                RollCallString,
            iqupc00SetupFpgaENGVCCint
                RollCallString,
            iqupc00SetupFpgaENGVCCaux
                RollCallString,
            iqupc00SetupOptionsOption1
                RollCallString,
            iqupc00SetupOptionsOption2
                RollCallString,
            iqupc00SetupOptionsOption3
                RollCallString,
            iqupc00SetupOptionsOption4
                RollCallString,
            iqupc00SetupOptionsOption5
                RollCallString,
            iqupc00SetupOptionsOption6
                RollCallString,
            iqupc00SetupOptionsOption7
                RollCallString,
            iqupc00SetupOptionsOption8
                RollCallString,
            iqupc00SetupOptionsOption9
                RollCallString,
            iqupc00SetupOptionsMask
                INTEGER,
            iqupc00SetupDemoNonDemoRestart
                INTEGER,
            iqupc00SetupDemoPeriod
                INTEGER,
            iqupc00SetupDemoRestartMode
                INTEGER,
            iqupc00SetupDemoRemainingDemo
                INTEGER,
            iqupc00SetupDemoRemaining24h
                INTEGER,
            iqupc00SetupDemoStatus
                INTEGER,
            iqupc00SetupRestartHard
                INTEGER,
            iqupc00SetupInput1Name
                RollCallString,
            iqupc00SetupInput2Name
                RollCallString,
            iqupc00SetupInput3Name
                RollCallString,
            iqupc00SetupCalibrationVideoOut8
                INTEGER,
            iqupc00SetupCalibrationVideoOut10
                INTEGER,
            iqupc00SetupCalibrationVideoOut11
                INTEGER,
            iqupc00LKFS1SourceLSrc
                INTEGER,
            iqupc00LKFS1SourceRSrc
                INTEGER,
            iqupc00LKFS1SourceLSSrc
                INTEGER,
            iqupc00LKFS1SourceRSSrc
                INTEGER,
            iqupc00LKFS1SourceCSrc
                INTEGER,
            iqupc00LKFS1ResetSession
                INTEGER,
            iqupc00LKFS1SessLevel
                RollCallString,
            iqupc00LKFS1SessTime
                RollCallString,
            iqupc00LKFS1currrate
                INTEGER,
            iqupc00LKFS1CurrLevelTime
                RollCallString,
            iqupc00LKFS1CurrLevel
                RollCallString,
            iqupc00LKFS1CurrLevel2
                RollCallString,
            iqupc00LKFS1RollMapUpd
                RollCallString,
            iqupc00LKFS1UpdateRate
                INTEGER,
            iqupc00LKFS2SourceLSrc
                INTEGER,
            iqupc00LKFS2SourceRSrc
                INTEGER,
            iqupc00LKFS2SourceLSSrc
                INTEGER,
            iqupc00LKFS2SourceRSSrc
                INTEGER,
            iqupc00LKFS2SourceCSrc
                INTEGER,
            iqupc00LKFS2SessLevel
                RollCallString,
            iqupc00LKFS2CurrLevel
                RollCallString,
            iqupc00LKFS2CurrLevel2
                RollCallString
        }

    iqupc00SlotIndex OBJECT-TYPE
        SYNTAX            Unsigned32
        MAX-ACCESS        not-accessible
        STATUS            current
        DESCRIPTION
                "The unique Index value for each slot.  Its value
                ranges between 1 and the value of slotNumber."
        ::= { iqupc00CmdEntry 99999 }


    iqupc00Video1VideoInputInput1Std OBJECT-TYPE
        SYNTAX            RollCallString
        MAX-ACCESS        read-only
        STATUS            current
        DESCRIPTION
                "CMNT: - Input 1 Standard
                 TYPE: - Display
                 PAGE: - Video1
                    Input 1 Std  cmdID= 40703  "
        ::= { iqupc00CmdEntry 40703 }


    iqupc00Video1VideoInputInput2Std OBJECT-TYPE
        SYNTAX            RollCallString
        MAX-ACCESS        read-only
        STATUS            current
        DESCRIPTION
                "CMNT: - Input 2 Standard
                 TYPE: - Display
                 PAGE: - Video1
                    Input 2 Std  cmdID= 40704  "
        ::= { iqupc00CmdEntry 40704 }


    iqupc00Video1VideoInputIPSelect OBJECT-TYPE
        SYNTAX            INTEGER {
                            valInput1(0),
                            valInput2(1)
                            }
        MAX-ACCESS        read-write
        STATUS            current
        DESCRIPTION
                "CMNT: - Select video input
                 TYPE: - RadiobuttonList
                 PAGE: - Video1
                    I/P Select  cmdID= 33024
                    Input 1  value= 0
                    Input 2  value= 1  "
        ::= { iqupc00CmdEntry 33024 }


    iqupc00VideoInputValidStandards108050p OBJECT-TYPE
        SYNTAX            INTEGER { disable(0), enable(1)  }
        MAX-ACCESS        read-write
        STATUS            current
        DESCRIPTION
                "CMNT: - Select valid input standards
                 TYPE: - Checkbox
                 PAGE: - Video Input
                    1080/50p  cmdID= 33004  "
        ::= { iqupc00CmdEntry 33004 }


    iqupc00VideoInputValidStandards108059p OBJECT-TYPE
        SYNTAX            INTEGER { disable(0), enable(1)  }
        MAX-ACCESS        read-write
        STATUS            current
        DESCRIPTION
                "CMNT: - Select valid input standards
                 TYPE: - Checkbox
                 PAGE: - Video Input
                    1080/59p  cmdID= 33005  "
        ::= { iqupc00CmdEntry 33005 }


    iqupc00VideoInputValidStandards108025i OBJECT-TYPE
        SYNTAX            INTEGER { disable(0), enable(1)  }
        MAX-ACCESS        read-write
        STATUS            current
        DESCRIPTION
                "CMNT: - Select valid input standards
                 TYPE: - Checkbox
                 PAGE: - Video Input
                    1080/25i  cmdID= 33006  "
        ::= { iqupc00CmdEntry 33006 }


    iqupc00VideoInputValidStandards108029i OBJECT-TYPE
        SYNTAX            INTEGER { disable(0), enable(1)  }
        MAX-ACCESS        read-write
        STATUS            current
        DESCRIPTION
                "CMNT: - Select valid input standards
                 TYPE: - Checkbox
                 PAGE: - Video Input
                    1080/29i  cmdID= 33007  "
        ::= { iqupc00CmdEntry 33007 }


    iqupc00VideoInputValidStandards72050p OBJECT-TYPE
        SYNTAX            INTEGER { disable(0), enable(1)  }
        MAX-ACCESS        read-write
        STATUS            current
        DESCRIPTION
                "CMNT: - Select valid input standards
                 TYPE: - Checkbox
                 PAGE: - Video Input
                    720/50p  cmdID= 33010  "
        ::= { iqupc00CmdEntry 33010 }


    iqupc00VideoInputValidStandards72059p OBJECT-TYPE
        SYNTAX            INTEGER { disable(0), enable(1)  }
        MAX-ACCESS        read-write
        STATUS            current
        DESCRIPTION
                "CMNT: - Select valid input standards
                 TYPE: - Checkbox
                 PAGE: - Video Input
                    720/59p  cmdID= 33011  "
        ::= { iqupc00CmdEntry 33011 }


    iqupc00VideoInputValidStandards62525i OBJECT-TYPE
        SYNTAX            INTEGER { disable(0), enable(1)  }
        MAX-ACCESS        read-write
        STATUS            current
        DESCRIPTION
                "CMNT: - Select valid input standards
                 TYPE: - Checkbox
                 PAGE: - Video Input
                    625/25i  cmdID= 33009  "
        ::= { iqupc00CmdEntry 33009 }


    iqupc00VideoInputValidStandards52529i OBJECT-TYPE
        SYNTAX            INTEGER { disable(0), enable(1)  }
        MAX-ACCESS        read-write
        STATUS            current
        DESCRIPTION
                "CMNT: - Select valid input standards
                 TYPE: - Checkbox
                 PAGE: - Video Input
                    525/29i  cmdID= 33008  "
        ::= { iqupc00CmdEntry 33008 }


    iqupc00VideoInputValidStandards108023psf OBJECT-TYPE
        SYNTAX            INTEGER { disable(0), enable(1)  }
        MAX-ACCESS        read-write
        STATUS            current
        DESCRIPTION
                "CMNT: - Select valid input standards
                 TYPE: - Checkbox
                 PAGE: - Video Input
                    1080/23psf  cmdID= 33046  "
        ::= { iqupc00CmdEntry 33046 }


    iqupc00VideoInputValidStandards108025psf OBJECT-TYPE
        SYNTAX            INTEGER { disable(0), enable(1)  }
        MAX-ACCESS        read-write
        STATUS            current
        DESCRIPTION
                "CMNT: - Select valid input standards
                 TYPE: - Checkbox
                 PAGE: - Video Input
                    1080/25psf  cmdID= 33047  "
        ::= { iqupc00CmdEntry 33047 }


    iqupc00VideoInputValidStandards108025p OBJECT-TYPE
        SYNTAX            INTEGER { disable(0), enable(1)  }
        MAX-ACCESS        read-write
        STATUS            current
        DESCRIPTION
                "CMNT: - Select valid input standards
                 TYPE: - Checkbox
                 PAGE: - Video Input
                    1080/25p  cmdID= 33048  "
        ::= { iqupc00CmdEntry 33048 }


    iqupc00VideoInputValidStandards108029p OBJECT-TYPE
        SYNTAX            INTEGER { disable(0), enable(1)  }
        MAX-ACCESS        read-write
        STATUS            current
        DESCRIPTION
                "CMNT: - Select valid input standards
                 TYPE: - Checkbox
                 PAGE: - Video Input
                    1080/29p  cmdID= 33049  "
        ::= { iqupc00CmdEntry 33049 }


    iqupc00VideoInputErrorsErrorReset OBJECT-TYPE
        SYNTAX            INTEGER { noAction(0),valErrorReset(1) }
        MAX-ACCESS        read-write
        STATUS            current
        DESCRIPTION
                "CMNT: - 
                 TYPE: - Button
                 PAGE: - Video Input
                    Error Reset  cmdID= 33014
                    value= 1  "
        ::= { iqupc00CmdEntry 33014 }


    iqupc00VideoInputErrorsResetSec OBJECT-TYPE
        SYNTAX            RollCallString
        MAX-ACCESS        read-only
        STATUS            current
        DESCRIPTION
                "CMNT: - 
                 TYPE: - Display
                 PAGE: - Video Input
                    ResetSec  cmdID= 33015  "
        ::= { iqupc00CmdEntry 33015 }


    iqupc00VideoInputErrorsCRCErrs1 OBJECT-TYPE
        SYNTAX            RollCallString
        MAX-ACCESS        read-only
        STATUS            current
        DESCRIPTION
                "CMNT: - 
                 TYPE: - Display
                 PAGE: - Video Input
                    CRC Errs1  cmdID= 33016  "
        ::= { iqupc00CmdEntry 33016 }


    iqupc00VideoInputErrorsANCErrs1 OBJECT-TYPE
        SYNTAX            RollCallString
        MAX-ACCESS        read-only
        STATUS            current
        DESCRIPTION
                "CMNT: - 
                 TYPE: - Display
                 PAGE: - Video Input
                    ANC Errs1  cmdID= 33020  "
        ::= { iqupc00CmdEntry 33020 }


    iqupc00VideoInputErrorsCRCErrs2 OBJECT-TYPE
        SYNTAX            RollCallString
        MAX-ACCESS        read-only
        STATUS            current
        DESCRIPTION
                "CMNT: - 
                 TYPE: - Display
                 PAGE: - Video Input
                    CRC Errs2  cmdID= 33018  "
        ::= { iqupc00CmdEntry 33018 }


    iqupc00VideoInputErrorsANCErrs2 OBJECT-TYPE
        SYNTAX            RollCallString
        MAX-ACCESS        read-only
        STATUS            current
        DESCRIPTION
                "CMNT: - 
                 TYPE: - Display
                 PAGE: - Video Input
                    ANC Errs2  cmdID= 33022  "
        ::= { iqupc00CmdEntry 33022 }


    iqupc00VideoInputErrorsCRCErrSec1 OBJECT-TYPE
        SYNTAX            RollCallString
        MAX-ACCESS        read-only
        STATUS            current
        DESCRIPTION
                "CMNT: - 
                 TYPE: - Display
                 PAGE: - Video Input
                    CRC ErrSec1  cmdID= 33017  "
        ::= { iqupc00CmdEntry 33017 }


    iqupc00VideoInputErrorsANCErrSec1 OBJECT-TYPE
        SYNTAX            RollCallString
        MAX-ACCESS        read-only
        STATUS            current
        DESCRIPTION
                "CMNT: - 
                 TYPE: - Display
                 PAGE: - Video Input
                    ANC ErrSec1  cmdID= 33021  "
        ::= { iqupc00CmdEntry 33021 }


    iqupc00VideoInputErrorsCRCErrSec2 OBJECT-TYPE
        SYNTAX            RollCallString
        MAX-ACCESS        read-only
        STATUS            current
        DESCRIPTION
                "CMNT: - 
                 TYPE: - Display
                 PAGE: - Video Input
                    CRC ErrSec2  cmdID= 33019  "
        ::= { iqupc00CmdEntry 33019 }


    iqupc00VideoInputErrorsANCErrSec2 OBJECT-TYPE
        SYNTAX            RollCallString
        MAX-ACCESS        read-only
        STATUS            current
        DESCRIPTION
                "CMNT: - 
                 TYPE: - Display
                 PAGE: - Video Input
                    ANC ErrSec2  cmdID= 33023  "
        ::= { iqupc00CmdEntry 33023 }


    iqupc00Video1VideoInputYCDelay OBJECT-TYPE
        SYNTAX            INTEGER
        MAX-ACCESS        read-write
        STATUS            current
        DESCRIPTION
                "CMNT: - 
                 TYPE: - Number
                 PAGE: - Video1
                    YC Delay  cmdID= 32999
                    min= -8  max= 7  step= 1  format= %0.0f  div_scale= 1  preset= 0
                    Min = -8  Max = 7  Step = 1  Preset = 0  "
        ::= { iqupc00CmdEntry 32999 }


    iqupc00Video1BackupEnable OBJECT-TYPE
        SYNTAX            INTEGER { disable(0), enable(1)  }
        MAX-ACCESS        read-write
        STATUS            current
        DESCRIPTION
                "CMNT: - Input Backup Enable
                 TYPE: - Checkbox
                 PAGE: - Video1
                    Backup Enable  cmdID= 39100  "
        ::= { iqupc00CmdEntry 39100 }


    iqupc00Video1BackupORInput1State OBJECT-TYPE
        SYNTAX            RollCallString
        MAX-ACCESS        read-only
        STATUS            current
        DESCRIPTION
                "CMNT: - Input 1 OR State
                 TYPE: - Display
                 PAGE: - Video1
                    OR Input1 State  cmdID= 39101  "
        ::= { iqupc00CmdEntry 39101 }


    iqupc00Video1BackupORInput2State OBJECT-TYPE
        SYNTAX            RollCallString
        MAX-ACCESS        read-only
        STATUS            current
        DESCRIPTION
                "CMNT: - Input 2 OR State
                 TYPE: - Display
                 PAGE: - Video1
                    OR Input2 State  cmdID= 39102  "
        ::= { iqupc00CmdEntry 39102 }


    iqupc00Video1BackupRevertDelay OBJECT-TYPE
        SYNTAX            INTEGER
        MAX-ACCESS        read-write
        STATUS            current
        DESCRIPTION
                "CMNT: - Backup Reversion Delay
                 TYPE: - Number
                 PAGE: - Video1
                    Revert Delay  cmdID= 39141
                    min= 0  max= 1000  step= 10  format= %0.0f s  div_scale= 10  preset= 0
                    Min = 0 s  Max = 100 s  Step = 1 s  Preset = 0 s  "
        ::= { iqupc00CmdEntry 39141 }


    iqupc00Video1BackupPriority OBJECT-TYPE
        SYNTAX            INTEGER {
                            valNone(0),
                            valPriority1(1),
                            valPriority2(2)
                            }
        MAX-ACCESS        read-write
        STATUS            current
        DESCRIPTION
                "CMNT: - Input Backup Priority
                 TYPE: - RadiobuttonList
                 PAGE: - Video1
                    Priority  cmdID= 39103
                    None  value= 0
                    Priority 1  value= 1
                    Priority 2  value= 2  "
        ::= { iqupc00CmdEntry 39103 }


    iqupc00Video1BackupQualifyInvStd OBJECT-TYPE
        SYNTAX            INTEGER { disable(0), enable(1)  }
        MAX-ACCESS        read-write
        STATUS            current
        DESCRIPTION
                "CMNT: - Backup Invalid Standard
                 TYPE: - Checkbox
                 PAGE: - Video1
                    Qualify Inv Std  cmdID= 39104  "
        ::= { iqupc00CmdEntry 39104 }


    iqupc00Video1BackupQualifyCRCErr OBJECT-TYPE
        SYNTAX            INTEGER { disable(0), enable(1)  }
        MAX-ACCESS        read-write
        STATUS            current
        DESCRIPTION
                "CMNT: - Backup CRC Error
                 TYPE: - Checkbox
                 PAGE: - Video1
                    Qualify CRC Err  cmdID= 39105  "
        ::= { iqupc00CmdEntry 39105 }


    iqupc00Video1BackupQualifyANCErr OBJECT-TYPE
        SYNTAX            INTEGER { disable(0), enable(1)  }
        MAX-ACCESS        read-write
        STATUS            current
        DESCRIPTION
                "CMNT: - Backup ANC Error
                 TYPE: - Checkbox
                 PAGE: - Video1
                    Qualify ANC Err  cmdID= 39106  "
        ::= { iqupc00CmdEntry 39106 }


    iqupc00Video1BackupQualifyAudioFail OBJECT-TYPE
        SYNTAX            INTEGER { disable(0), enable(1)  }
        MAX-ACCESS        read-write
        STATUS            current
        DESCRIPTION
                "CMNT: - Backup Qual Audio Lost
                 TYPE: - Checkbox
                 PAGE: - Video1
                    Qualify Audio Fail  cmdID= 39142  "
        ::= { iqupc00CmdEntry 39142 }


    iqupc00BackupInput1SelStatInp1OK OBJECT-TYPE
        SYNTAX            RollCallString
        MAX-ACCESS        read-only
        STATUS            current
        DESCRIPTION
                "CMNT: - Backup Sel 1 Inp 1 OK Status
                 TYPE: - Display
                 PAGE: - Backup
                    Stat Inp1 OK  cmdID= 39127  "
        ::= { iqupc00CmdEntry 39127 }


    iqupc00BackupInput1SelStatInp2FAIL OBJECT-TYPE
        SYNTAX            RollCallString
        MAX-ACCESS        read-only
        STATUS            current
        DESCRIPTION
                "CMNT: - Backup Sel 1 Inp 2 FAIL Status
                 TYPE: - Display
                 PAGE: - Backup
                    Stat Inp2 FAIL  cmdID= 39128  "
        ::= { iqupc00CmdEntry 39128 }


    iqupc00BackupInput1SelStatInp2Err OBJECT-TYPE
        SYNTAX            RollCallString
        MAX-ACCESS        read-only
        STATUS            current
        DESCRIPTION
                "CMNT: - Backup Sel 1 Inp 2 ERR Status
                 TYPE: - Display
                 PAGE: - Backup
                    Stat Inp2 Err  cmdID= 39139  "
        ::= { iqupc00CmdEntry 39139 }


    iqupc00BackupInput1SelStatAUDFail2 OBJECT-TYPE
        SYNTAX            RollCallString
        MAX-ACCESS        read-only
        STATUS            current
        DESCRIPTION
                "CMNT: - Backup Reversion Delay
                 TYPE: - Display
                 PAGE: - Backup
                    Stat AUD Fail 2  cmdID= 39144  "
        ::= { iqupc00CmdEntry 39144 }


    iqupc00BackupInput1SelStatStd2 OBJECT-TYPE
        SYNTAX            RollCallString
        MAX-ACCESS        read-only
        STATUS            current
        DESCRIPTION
                "CMNT: - 
                 TYPE: - Display
                 PAGE: - Backup
                    Stat Std 2  cmdID= 39173  "
        ::= { iqupc00CmdEntry 39173 }


    iqupc00BackupInput1SelStatGPI1 OBJECT-TYPE
        SYNTAX            RollCallString
        MAX-ACCESS        read-only
        STATUS            current
        DESCRIPTION
                "CMNT: - Backup Sel 1 GPI 1 Status
                 TYPE: - Display
                 PAGE: - Backup
                    Stat GPI 1  cmdID= 39129  "
        ::= { iqupc00CmdEntry 39129 }


    iqupc00BackupInput1SelStatGPI2 OBJECT-TYPE
        SYNTAX            RollCallString
        MAX-ACCESS        read-only
        STATUS            current
        DESCRIPTION
                "CMNT: - Backup Sel 1 GPI 2 Status
                 TYPE: - Display
                 PAGE: - Backup
                    Stat GPI 2  cmdID= 39130  "
        ::= { iqupc00CmdEntry 39130 }


    iqupc00BackupInput1SelEnblInp1OK OBJECT-TYPE
        SYNTAX            INTEGER { disable(0), enable(1)  }
        MAX-ACCESS        read-write
        STATUS            current
        DESCRIPTION
                "CMNT: - Backup Sel 1 Inp 1 OK
                 TYPE: - Checkbox
                 PAGE: - Backup
                    Enbl Inp1 OK  cmdID= 39107  "
        ::= { iqupc00CmdEntry 39107 }


    iqupc00BackupInput1SelEnblInp2FAIL OBJECT-TYPE
        SYNTAX            INTEGER { disable(0), enable(1)  }
        MAX-ACCESS        read-write
        STATUS            current
        DESCRIPTION
                "CMNT: - Backup Sel 1 Inp 2 FAIL
                 TYPE: - Checkbox
                 PAGE: - Backup
                    Enbl Inp2 FAIL  cmdID= 39108  "
        ::= { iqupc00CmdEntry 39108 }


    iqupc00BackupInput1SelEnblInp2Err OBJECT-TYPE
        SYNTAX            INTEGER { disable(0), enable(1)  }
        MAX-ACCESS        read-write
        STATUS            current
        DESCRIPTION
                "CMNT: - Backup Sel 1 Inp 2 ERR
                 TYPE: - Checkbox
                 PAGE: - Backup
                    Enbl Inp2 Err  cmdID= 39135  "
        ::= { iqupc00CmdEntry 39135 }


    iqupc00BackupInput1SelEnblGPI1 OBJECT-TYPE
        SYNTAX            INTEGER { disable(0), enable(1)  }
        MAX-ACCESS        read-write
        STATUS            current
        DESCRIPTION
                "CMNT: - Backup Sel 1 GPI 1
                 TYPE: - Checkbox
                 PAGE: - Backup
                    Enbl GPI 1  cmdID= 39109  "
        ::= { iqupc00CmdEntry 39109 }


    iqupc00BackupInput1SelEnblGPI2 OBJECT-TYPE
        SYNTAX            INTEGER { disable(0), enable(1)  }
        MAX-ACCESS        read-write
        STATUS            current
        DESCRIPTION
                "CMNT: - Backup Sel 1 GPI 2
                 TYPE: - Checkbox
                 PAGE: - Backup
                    Enbl GPI 2  cmdID= 39110  "
        ::= { iqupc00CmdEntry 39110 }


    iqupc00BackupInput1SelEnblStdInp2 OBJECT-TYPE
        SYNTAX            INTEGER { disable(0), enable(1)  }
        MAX-ACCESS        read-write
        STATUS            current
        DESCRIPTION
                "CMNT: - 
                 TYPE: - Checkbox
                 PAGE: - Backup
                    Enbl Std Inp2  cmdID= 39172  "
        ::= { iqupc00CmdEntry 39172 }


    iqupc00BackupInput1SelDlyInp1OK OBJECT-TYPE
        SYNTAX            INTEGER
        MAX-ACCESS        read-write
        STATUS            current
        DESCRIPTION
                "CMNT: - Backup Sel 1 Inp 1 OK Delay
                 TYPE: - Number
                 PAGE: - Backup
                    Dly Inp1 OK  cmdID= 39115
                    min= 10  max= 100  step= 1  format= %0.1f s  div_scale= 10  preset= 10
                    Min = 1.0 s  Max = 10.0 s  Step = 0.1 s  Preset = 1.0 s  "
        ::= { iqupc00CmdEntry 39115 }


    iqupc00BackupInput1SelDlyInp2FAIL OBJECT-TYPE
        SYNTAX            INTEGER
        MAX-ACCESS        read-write
        STATUS            current
        DESCRIPTION
                "CMNT: - Backup Sel 1 Inp 2 FAIL Delay
                 TYPE: - Number
                 PAGE: - Backup
                    Dly Inp2 FAIL  cmdID= 39116
                    min= 0  max= 100  step= 1  format= %0.1f s  div_scale= 10  preset= 1
                    Min = 0.0 s  Max = 10.0 s  Step = 0.1 s  Preset = 0.1 s  "
        ::= { iqupc00CmdEntry 39116 }


    iqupc00BackupInput1SelDlyInp2Err OBJECT-TYPE
        SYNTAX            INTEGER
        MAX-ACCESS        read-write
        STATUS            current
        DESCRIPTION
                "CMNT: - Backup Sel 1 Inp 2 ERR Delay
                 TYPE: - Number
                 PAGE: - Backup
                    Dly Inp2 Err  cmdID= 39137
                    min= 10  max= 100  step= 10  format= %0.0f s  div_scale= 10  preset= 50
                    Min = 1 s  Max = 10 s  Step = 1 s  Preset = 5 s  "
        ::= { iqupc00CmdEntry 39137 }


    iqupc00BackupInput1SelDlyGPI1 OBJECT-TYPE
        SYNTAX            INTEGER
        MAX-ACCESS        read-write
        STATUS            current
        DESCRIPTION
                "CMNT: - Backup Sel 1 GPI 1 Delay
                 TYPE: - Number
                 PAGE: - Backup
                    Dly GPI 1  cmdID= 39117
                    min= 0  max= 100  step= 1  format= %0.1f s  div_scale= 10  preset= 0
                    Min = 0.0 s  Max = 10.0 s  Step = 0.1 s  Preset = 0.0 s  "
        ::= { iqupc00CmdEntry 39117 }


    iqupc00BackupInput1SelDlyGPI2 OBJECT-TYPE
        SYNTAX            INTEGER
        MAX-ACCESS        read-write
        STATUS            current
        DESCRIPTION
                "CMNT: - Backup Sel 1 GPI 2 Delay
                 TYPE: - Number
                 PAGE: - Backup
                    Dly GPI 2  cmdID= 39118
                    min= 0  max= 100  step= 1  format= %0.1f s  div_scale= 10  preset= 0
                    Min = 0.0 s  Max = 10.0 s  Step = 0.1 s  Preset = 0.0 s  "
        ::= { iqupc00CmdEntry 39118 }


    iqupc00BackupInput1SelDlyAud2FAIL OBJECT-TYPE
        SYNTAX            INTEGER
        MAX-ACCESS        read-write
        STATUS            current
        DESCRIPTION
                "CMNT: - Backup Inp1 2 aud Fail Delay
                 TYPE: - Number
                 PAGE: - Backup
                    Dly Aud2 FAIL  cmdID= 39145
                    min= 10  max= 100  step= 1  format= %0.1f s  div_scale= 10  preset= 10
                    Min = 1.0 s  Max = 10.0 s  Step = 0.1 s  Preset = 1.0 s  "
        ::= { iqupc00CmdEntry 39145 }


    iqupc00BackupInput1SelDlyStd2 OBJECT-TYPE
        SYNTAX            INTEGER
        MAX-ACCESS        read-write
        STATUS            current
        DESCRIPTION
                "CMNT: - 
                 TYPE: - Number
                 PAGE: - Backup
                    Dly Std 2  cmdID= 39171
                    min= 0  max= 100  step= 1  format= %0.1f s  div_scale= 10  preset= 10
                    Min = 0.0 s  Max = 10.0 s  Step = 0.1 s  Preset = 1.0 s  "
        ::= { iqupc00CmdEntry 39171 }


    iqupc00BackupInput1SelGPI1State OBJECT-TYPE
        SYNTAX            INTEGER {
                            valHigh(1),
                            valLow(0)
                            }
        MAX-ACCESS        read-write
        STATUS            current
        DESCRIPTION
                "CMNT: - Backup Sel 1 GPI 1 val
                 TYPE: - RadiobuttonList
                 PAGE: - Backup
                    GPI 1 State  cmdID= 39123
                    High  value= 1
                    Low  value= 0  "
        ::= { iqupc00CmdEntry 39123 }


    iqupc00BackupInput1SelGPI2State OBJECT-TYPE
        SYNTAX            INTEGER {
                            valHigh(1),
                            valLow(0)
                            }
        MAX-ACCESS        read-write
        STATUS            current
        DESCRIPTION
                "CMNT: - Backup Sel 1 GPI 2 val
                 TYPE: - RadiobuttonList
                 PAGE: - Backup
                    GPI 2 State  cmdID= 39124
                    High  value= 1
                    Low  value= 0  "
        ::= { iqupc00CmdEntry 39124 }


    iqupc00BackupInput1SelInp12AudFailG1C1 OBJECT-TYPE
        SYNTAX            INTEGER { disable(0), enable(1)  }
        MAX-ACCESS        read-write
        STATUS            current
        DESCRIPTION
                "CMNT: - Backup Inp1 2 Aud Fail G1C1
                 TYPE: - Checkbox
                 PAGE: - Backup
                    Inp1 2 Aud Fail G1C1  cmdID= 39149  "
        ::= { iqupc00CmdEntry 39149 }


    iqupc00BackupInput1SelInp12AudFailG1C2 OBJECT-TYPE
        SYNTAX            INTEGER { disable(0), enable(1)  }
        MAX-ACCESS        read-write
        STATUS            current
        DESCRIPTION
                "CMNT: - Backup Inp1 2 Aud Fail G1C2
                 TYPE: - Checkbox
                 PAGE: - Backup
                    Inp1 2 Aud Fail G1C2  cmdID= 39150  "
        ::= { iqupc00CmdEntry 39150 }


    iqupc00BackupInput1SelInp12AudFailG2C1 OBJECT-TYPE
        SYNTAX            INTEGER { disable(0), enable(1)  }
        MAX-ACCESS        read-write
        STATUS            current
        DESCRIPTION
                "CMNT: - Backup Inp1 2 Aud Fail G2C1
                 TYPE: - Checkbox
                 PAGE: - Backup
                    Inp1 2 Aud Fail G2C1  cmdID= 39151  "
        ::= { iqupc00CmdEntry 39151 }


    iqupc00BackupInput1SelInp12AudFailG2C2 OBJECT-TYPE
        SYNTAX            INTEGER { disable(0), enable(1)  }
        MAX-ACCESS        read-write
        STATUS            current
        DESCRIPTION
                "CMNT: - Backup Inp1 2 Aud Fail G2C2
                 TYPE: - Checkbox
                 PAGE: - Backup
                    Inp1 2 Aud Fail G2C2  cmdID= 39152  "
        ::= { iqupc00CmdEntry 39152 }


    iqupc00BackupInput1SelInp12AudFailG3C1 OBJECT-TYPE
        SYNTAX            INTEGER { disable(0), enable(1)  }
        MAX-ACCESS        read-write
        STATUS            current
        DESCRIPTION
                "CMNT: - Backup Inp1 2 Aud Fail G3C1
                 TYPE: - Checkbox
                 PAGE: - Backup
                    Inp1 2 Aud Fail G3C1  cmdID= 39153  "
        ::= { iqupc00CmdEntry 39153 }


    iqupc00BackupInput1SelInp12AudFailG3C2 OBJECT-TYPE
        SYNTAX            INTEGER { disable(0), enable(1)  }
        MAX-ACCESS        read-write
        STATUS            current
        DESCRIPTION
                "CMNT: - Backup Inp1 2 Aud Fail G3C2
                 TYPE: - Checkbox
                 PAGE: - Backup
                    Inp1 2 Aud Fail G3C2  cmdID= 39154  "
        ::= { iqupc00CmdEntry 39154 }


    iqupc00BackupInput1SelInp12AudFailG4C1 OBJECT-TYPE
        SYNTAX            INTEGER { disable(0), enable(1)  }
        MAX-ACCESS        read-write
        STATUS            current
        DESCRIPTION
                "CMNT: - Backup Inp1 2 Aud Fail G4C1
                 TYPE: - Checkbox
                 PAGE: - Backup
                    Inp1 2 Aud Fail G4C1  cmdID= 39155  "
        ::= { iqupc00CmdEntry 39155 }


    iqupc00BackupInput1SelInp12AudFailG4C2 OBJECT-TYPE
        SYNTAX            INTEGER { disable(0), enable(1)  }
        MAX-ACCESS        read-write
        STATUS            current
        DESCRIPTION
                "CMNT: - Backup Inp1 2 Aud Fail G4C2
                 TYPE: - Checkbox
                 PAGE: - Backup
                    Inp1 2 Aud Fail G4C2  cmdID= 39156  "
        ::= { iqupc00CmdEntry 39156 }


    iqupc00BackupInput1SelInp12AudFailLockGrp OBJECT-TYPE
        SYNTAX            INTEGER { disable(0), enable(1)  }
        MAX-ACCESS        read-write
        STATUS            current
        DESCRIPTION
                "CMNT: - Backup Inp1 2 Aud Fail Lock Grp
                 TYPE: - Checkbox
                 PAGE: - Backup
                    Inp1 2 Aud Fail Lock Grp  cmdID= 39148  "
        ::= { iqupc00CmdEntry 39148 }


    iqupc00BackupInput1SelSelAll OBJECT-TYPE
        SYNTAX            INTEGER { noAction(0),valSelAll(1) }
        MAX-ACCESS        read-write
        STATUS            current
        DESCRIPTION
                "CMNT: - Backup Inp1 2 Aud Fail Sel All
                 TYPE: - Button
                 PAGE: - Backup
                    Sel All  cmdID= 39146
                    value= 1  "
        ::= { iqupc00CmdEntry 39146 }


    iqupc00BackupInput1SelSelNone OBJECT-TYPE
        SYNTAX            INTEGER { noAction(0),valSelNone(1) }
        MAX-ACCESS        read-write
        STATUS            current
        DESCRIPTION
                "CMNT: - Backup Inp1 2 Aud Fail Sel None
                 TYPE: - Button
                 PAGE: - Backup
                    Sel None  cmdID= 39147
                    value= 1  "
        ::= { iqupc00CmdEntry 39147 }


    iqupc00BackupInput2SelStatInp2OK OBJECT-TYPE
        SYNTAX            RollCallString
        MAX-ACCESS        read-only
        STATUS            current
        DESCRIPTION
                "CMNT: - Backup Sel 2 Inp 2 OK Status
                 TYPE: - Display
                 PAGE: - Backup
                    Stat Inp2 OK  cmdID= 39131  "
        ::= { iqupc00CmdEntry 39131 }


    iqupc00BackupInput2SelStatInp1FAIL OBJECT-TYPE
        SYNTAX            RollCallString
        MAX-ACCESS        read-only
        STATUS            current
        DESCRIPTION
                "CMNT: - Backup Sel 2 Inp 1 FAIL Status
                 TYPE: - Display
                 PAGE: - Backup
                    Stat Inp1 FAIL  cmdID= 39132  "
        ::= { iqupc00CmdEntry 39132 }


    iqupc00BackupInput2SelStatInp1Err OBJECT-TYPE
        SYNTAX            RollCallString
        MAX-ACCESS        read-only
        STATUS            current
        DESCRIPTION
                "CMNT: - Backup Sel 2 Inp 1 ERR Status
                 TYPE: - Display
                 PAGE: - Backup
                    Stat Inp1 Err  cmdID= 39140  "
        ::= { iqupc00CmdEntry 39140 }


    iqupc00BackupInput2SelStatAUDFail1 OBJECT-TYPE
        SYNTAX            RollCallString
        MAX-ACCESS        read-only
        STATUS            current
        DESCRIPTION
                "CMNT: - Backup Reversion Delay
                 TYPE: - Display
                 PAGE: - Backup
                    Stat AUD Fail 1  cmdID= 39158  "
        ::= { iqupc00CmdEntry 39158 }


    iqupc00BackupInput2SelStatStd1 OBJECT-TYPE
        SYNTAX            RollCallString
        MAX-ACCESS        read-only
        STATUS            current
        DESCRIPTION
                "CMNT: - 
                 TYPE: - Display
                 PAGE: - Backup
                    Stat Std 1  cmdID= 39176  "
        ::= { iqupc00CmdEntry 39176 }


    iqupc00BackupInput2SelStatGPI1 OBJECT-TYPE
        SYNTAX            RollCallString
        MAX-ACCESS        read-only
        STATUS            current
        DESCRIPTION
                "CMNT: - Backup Sel 2 GPI 1 Status
                 TYPE: - Display
                 PAGE: - Backup
                    Stat GPI 1  cmdID= 39133  "
        ::= { iqupc00CmdEntry 39133 }


    iqupc00BackupInput2SelStatGPI2 OBJECT-TYPE
        SYNTAX            RollCallString
        MAX-ACCESS        read-only
        STATUS            current
        DESCRIPTION
                "CMNT: - Backup Sel 2 GPI 2 Status
                 TYPE: - Display
                 PAGE: - Backup
                    Stat GPI 2  cmdID= 39134  "
        ::= { iqupc00CmdEntry 39134 }


    iqupc00BackupInput2SelEnblInp2OK OBJECT-TYPE
        SYNTAX            INTEGER { disable(0), enable(1)  }
        MAX-ACCESS        read-write
        STATUS            current
        DESCRIPTION
                "CMNT: - Backup Sel 2 Inp 2 OK
                 TYPE: - Checkbox
                 PAGE: - Backup
                    Enbl Inp2 OK  cmdID= 39111  "
        ::= { iqupc00CmdEntry 39111 }


    iqupc00BackupInput2SelEnblInp1FAIL OBJECT-TYPE
        SYNTAX            INTEGER { disable(0), enable(1)  }
        MAX-ACCESS        read-write
        STATUS            current
        DESCRIPTION
                "CMNT: - Backup Sel 2 Inp 1 FAIL
                 TYPE: - Checkbox
                 PAGE: - Backup
                    Enbl Inp1 FAIL  cmdID= 39112  "
        ::= { iqupc00CmdEntry 39112 }


    iqupc00BackupInput2SelEnblInp1Err OBJECT-TYPE
        SYNTAX            INTEGER { disable(0), enable(1)  }
        MAX-ACCESS        read-write
        STATUS            current
        DESCRIPTION
                "CMNT: - Backup Sel 2 Inp 1 ERR
                 TYPE: - Checkbox
                 PAGE: - Backup
                    Enbl Inp1 Err  cmdID= 39136  "
        ::= { iqupc00CmdEntry 39136 }


    iqupc00BackupInput2SelEnblGPI1 OBJECT-TYPE
        SYNTAX            INTEGER { disable(0), enable(1)  }
        MAX-ACCESS        read-write
        STATUS            current
        DESCRIPTION
                "CMNT: - Backup Sel 2 GPI 1
                 TYPE: - Checkbox
                 PAGE: - Backup
                    Enbl GPI 1  cmdID= 39113  "
        ::= { iqupc00CmdEntry 39113 }


    iqupc00BackupInput2SelEnblGPI2 OBJECT-TYPE
        SYNTAX            INTEGER { disable(0), enable(1)  }
        MAX-ACCESS        read-write
        STATUS            current
        DESCRIPTION
                "CMNT: - Backup Sel 2 GPI 2
                 TYPE: - Checkbox
                 PAGE: - Backup
                    Enbl GPI 2  cmdID= 39114  "
        ::= { iqupc00CmdEntry 39114 }


    iqupc00BackupInput2SelEnblAudInp1Err OBJECT-TYPE
        SYNTAX            INTEGER { disable(0), enable(1)  }
        MAX-ACCESS        read-write
        STATUS            current
        DESCRIPTION
                "CMNT: - Backup Inp2 1 Aud Fail Enable
                 TYPE: - Checkbox
                 PAGE: - Backup
                    Enbl Aud Inp1 Err  cmdID= 39157  "
        ::= { iqupc00CmdEntry 39157 }


    iqupc00BackupInput2SelEnblStdInp1 OBJECT-TYPE
        SYNTAX            INTEGER { disable(0), enable(1)  }
        MAX-ACCESS        read-write
        STATUS            current
        DESCRIPTION
                "CMNT: - 
                 TYPE: - Checkbox
                 PAGE: - Backup
                    Enbl Std Inp 1  cmdID= 39175  "
        ::= { iqupc00CmdEntry 39175 }


    iqupc00BackupInput2SelInp21AudFailG1C1 OBJECT-TYPE
        SYNTAX            INTEGER { disable(0), enable(1)  }
        MAX-ACCESS        read-write
        STATUS            current
        DESCRIPTION
                "CMNT: - Backup Inp2 1 Aud Fail G1C1
                 TYPE: - Checkbox
                 PAGE: - Backup
                    Inp2 1 Aud Fail G1C1  cmdID= 39163  "
        ::= { iqupc00CmdEntry 39163 }


    iqupc00BackupInput2SelInp21AudFailG1C2 OBJECT-TYPE
        SYNTAX            INTEGER { disable(0), enable(1)  }
        MAX-ACCESS        read-write
        STATUS            current
        DESCRIPTION
                "CMNT: - Backup Inp2 1 Aud Fail G1C2
                 TYPE: - Checkbox
                 PAGE: - Backup
                    Inp2 1 Aud Fail G1C2  cmdID= 39164  "
        ::= { iqupc00CmdEntry 39164 }


    iqupc00BackupInput2SelInp21AudFailG2C1 OBJECT-TYPE
        SYNTAX            INTEGER { disable(0), enable(1)  }
        MAX-ACCESS        read-write
        STATUS            current
        DESCRIPTION
                "CMNT: - Backup Inp2 1 Aud Fail G2C1
                 TYPE: - Checkbox
                 PAGE: - Backup
                    Inp2 1 Aud Fail G2C1  cmdID= 39165  "
        ::= { iqupc00CmdEntry 39165 }


    iqupc00BackupInput2SelInp21AudFailG2C2 OBJECT-TYPE
        SYNTAX            INTEGER { disable(0), enable(1)  }
        MAX-ACCESS        read-write
        STATUS            current
        DESCRIPTION
                "CMNT: - Backup Inp2 1 Aud Fail G2C2
                 TYPE: - Checkbox
                 PAGE: - Backup
                    Inp2 1 Aud Fail G2C2  cmdID= 39166  "
        ::= { iqupc00CmdEntry 39166 }


    iqupc00BackupInput2SelInp21AudFailG3C1 OBJECT-TYPE
        SYNTAX            INTEGER { disable(0), enable(1)  }
        MAX-ACCESS        read-write
        STATUS            current
        DESCRIPTION
                "CMNT: - Backup Inp2 1 Aud Fail G3C1
                 TYPE: - Checkbox
                 PAGE: - Backup
                    Inp2 1 Aud Fail G3C1  cmdID= 39167  "
        ::= { iqupc00CmdEntry 39167 }


    iqupc00BackupInput2SelInp21AudFailG3C2 OBJECT-TYPE
        SYNTAX            INTEGER { disable(0), enable(1)  }
        MAX-ACCESS        read-write
        STATUS            current
        DESCRIPTION
                "CMNT: - Backup Inp2 1 Aud Fail G3C2
                 TYPE: - Checkbox
                 PAGE: - Backup
                    Inp2 1 Aud Fail G3C2  cmdID= 39168  "
        ::= { iqupc00CmdEntry 39168 }


    iqupc00BackupInput2SelInp21AudFailG4C1 OBJECT-TYPE
        SYNTAX            INTEGER { disable(0), enable(1)  }
        MAX-ACCESS        read-write
        STATUS            current
        DESCRIPTION
                "CMNT: - Backup Inp2 1 Aud Fail G4C1
                 TYPE: - Checkbox
                 PAGE: - Backup
                    Inp2 1 Aud Fail G4C1  cmdID= 39169  "
        ::= { iqupc00CmdEntry 39169 }


    iqupc00BackupInput2SelInp21AudFailG4C2 OBJECT-TYPE
        SYNTAX            INTEGER { disable(0), enable(1)  }
        MAX-ACCESS        read-write
        STATUS            current
        DESCRIPTION
                "CMNT: - Backup Inp2 1 Aud Fail G4C2
                 TYPE: - Checkbox
                 PAGE: - Backup
                    Inp2 1 Aud Fail G4C2  cmdID= 39170  "
        ::= { iqupc00CmdEntry 39170 }


    iqupc00BackupInput2SelDlyInp2OK OBJECT-TYPE
        SYNTAX            INTEGER
        MAX-ACCESS        read-write
        STATUS            current
        DESCRIPTION
                "CMNT: - Backup Sel 2 Inp 2 OK Delay
                 TYPE: - Number
                 PAGE: - Backup
                    Dly Inp2 OK  cmdID= 39119
                    min= 10  max= 100  step= 1  format= %0.1f s  div_scale= 10  preset= 10
                    Min = 1.0 s  Max = 10.0 s  Step = 0.1 s  Preset = 1.0 s  "
        ::= { iqupc00CmdEntry 39119 }


    iqupc00BackupInput2SelDlyInp1FAIL OBJECT-TYPE
        SYNTAX            INTEGER
        MAX-ACCESS        read-write
        STATUS            current
        DESCRIPTION
                "CMNT: - Backup Sel 2 Inp 1 FAIL Delay
                 TYPE: - Number
                 PAGE: - Backup
                    Dly Inp1 FAIL  cmdID= 39120
                    min= 0  max= 100  step= 1  format= %0.1f s  div_scale= 10  preset= 1
                    Min = 0.0 s  Max = 10.0 s  Step = 0.1 s  Preset = 0.1 s  "
        ::= { iqupc00CmdEntry 39120 }


    iqupc00BackupInput2SelDlyInp1Err OBJECT-TYPE
        SYNTAX            INTEGER
        MAX-ACCESS        read-write
        STATUS            current
        DESCRIPTION
                "CMNT: - Backup Sel 2 Inp 1 ERR Delay
                 TYPE: - Number
                 PAGE: - Backup
                    Dly Inp1 Err  cmdID= 39138
                    min= 10  max= 100  step= 10  format= %0.0f s  div_scale= 10  preset= 50
                    Min = 1 s  Max = 10 s  Step = 1 s  Preset = 5 s  "
        ::= { iqupc00CmdEntry 39138 }


    iqupc00BackupInput2SelDlyGPI1 OBJECT-TYPE
        SYNTAX            INTEGER
        MAX-ACCESS        read-write
        STATUS            current
        DESCRIPTION
                "CMNT: - Backup Sel 2 GPI 1 Delay
                 TYPE: - Number
                 PAGE: - Backup
                    Dly GPI 1  cmdID= 39121
                    min= 0  max= 100  step= 1  format= %0.1f s  div_scale= 10  preset= 0
                    Min = 0.0 s  Max = 10.0 s  Step = 0.1 s  Preset = 0.0 s  "
        ::= { iqupc00CmdEntry 39121 }


    iqupc00BackupInput2SelDlyGPI2 OBJECT-TYPE
        SYNTAX            INTEGER
        MAX-ACCESS        read-write
        STATUS            current
        DESCRIPTION
                "CMNT: - Backup Sel 2 GPI 2 Delay
                 TYPE: - Number
                 PAGE: - Backup
                    Dly GPI 2  cmdID= 39122
                    min= 0  max= 100  step= 1  format= %0.1f s  div_scale= 10  preset= 0
                    Min = 0.0 s  Max = 10.0 s  Step = 0.1 s  Preset = 0.0 s  "
        ::= { iqupc00CmdEntry 39122 }


    iqupc00BackupInput2SelDlyAud1FAIL OBJECT-TYPE
        SYNTAX            INTEGER
        MAX-ACCESS        read-write
        STATUS            current
        DESCRIPTION
                "CMNT: - Backup Inp2 1 Aud Fail Delay
                 TYPE: - Number
                 PAGE: - Backup
                    Dly Aud1 FAIL  cmdID= 39159
                    min= 10  max= 100  step= 1  format= %0.1f s  div_scale= 10  preset= 10
                    Min = 1.0 s  Max = 10.0 s  Step = 0.1 s  Preset = 1.0 s  "
        ::= { iqupc00CmdEntry 39159 }


    iqupc00BackupInput2SelDlyStd1 OBJECT-TYPE
        SYNTAX            INTEGER
        MAX-ACCESS        read-write
        STATUS            current
        DESCRIPTION
                "CMNT: - 
                 TYPE: - Number
                 PAGE: - Backup
                    Dly Std 1  cmdID= 39174
                    min= 0  max= 100  step= 1  format= %0.1f s  div_scale= 10  preset= 10
                    Min = 0.0 s  Max = 10.0 s  Step = 0.1 s  Preset = 1.0 s  "
        ::= { iqupc00CmdEntry 39174 }


    iqupc00BackupInput2SelGPI1State OBJECT-TYPE
        SYNTAX            INTEGER {
                            valOn(0),
                            valOff(1)
                            }
        MAX-ACCESS        read-write
        STATUS            current
        DESCRIPTION
                "CMNT: - Backup Sel 2 GPI 1 val
                 TYPE: - RadiobuttonList
                 PAGE: - Backup
                    GPI 1 State  cmdID= 39125
                    On  value= 0
                    Off  value= 1  "
        ::= { iqupc00CmdEntry 39125 }


    iqupc00BackupInput2SelGPI2State OBJECT-TYPE
        SYNTAX            INTEGER {
                            valOn(0),
                            valOff(1)
                            }
        MAX-ACCESS        read-write
        STATUS            current
        DESCRIPTION
                "CMNT: - Backup Sel 2 GPI 2 val
                 TYPE: - RadiobuttonList
                 PAGE: - Backup
                    GPI 2 State  cmdID= 39126
                    On  value= 0
                    Off  value= 1  "
        ::= { iqupc00CmdEntry 39126 }


    iqupc00BackupInput2SelInp21AudFailLockGrp OBJECT-TYPE
        SYNTAX            INTEGER { disable(0), enable(1)  }
        MAX-ACCESS        read-write
        STATUS            current
        DESCRIPTION
                "CMNT: - Backup Inp2 1 Aud Fail Lock Grp
                 TYPE: - Checkbox
                 PAGE: - Backup
                    Inp2 1 Aud Fail Lock Grp  cmdID= 39162  "
        ::= { iqupc00CmdEntry 39162 }


    iqupc00BackupInput2SelSelAll OBJECT-TYPE
        SYNTAX            INTEGER { noAction(0),valSelAll(1) }
        MAX-ACCESS        read-write
        STATUS            current
        DESCRIPTION
                "CMNT: - Backup Inp2 1 Aud Fail Sel All
                 TYPE: - Button
                 PAGE: - Backup
                    Sel All  cmdID= 39160
                    value= 1  "
        ::= { iqupc00CmdEntry 39160 }


    iqupc00BackupInput2SelSelNone OBJECT-TYPE
        SYNTAX            INTEGER { noAction(0),valSelNone(1) }
        MAX-ACCESS        read-write
        STATUS            current
        DESCRIPTION
                "CMNT: - Backup Inp2 1 Aud Fail Sel None
                 TYPE: - Button
                 PAGE: - Backup
                    Sel None  cmdID= 39161
                    value= 1  "
        ::= { iqupc00CmdEntry 39161 }


    iqupc00Video2VideoOutputConversionStandard OBJECT-TYPE
        SYNTAX            INTEGER {
                            val1080p(3),
                            val1080i(1),
                            val720p(2),
                            valSD(0),
                            val1080p2529(5),
                            val1080psf(4)
                            }
        MAX-ACCESS        read-write
        STATUS            current
        DESCRIPTION
                "CMNT: - Conversion standard
                 TYPE: - RadiobuttonList
                 PAGE: - Video2
                    Conversion Standard  cmdID= 40700
                    1080p  value= 3
                    1080i  value= 1
                    720p  value= 2
                    SD  value= 0
                    1080p25/29  value= 5
                    1080psf  value= 4  "
        ::= { iqupc00CmdEntry 40700 }


    iqupc00Video2VideoOutputOutputAType OBJECT-TYPE
        SYNTAX            INTEGER {
                            valProcessed(0),
                            valReclocked(1)
                            }
        MAX-ACCESS        read-write
        STATUS            current
        DESCRIPTION
                "CMNT: - Output A type
                 TYPE: - RadiobuttonList
                 PAGE: - Video2
                    Output A Type  cmdID= 40701
                    Processed  value= 0
                    Reclocked  value= 1  "
        ::= { iqupc00CmdEntry 40701 }


    iqupc00Video2VideoOutputOutputBType OBJECT-TYPE
        SYNTAX            INTEGER {
                            valProcessed(0),
                            valReclocked(1)
                            }
        MAX-ACCESS        read-write
        STATUS            current
        DESCRIPTION
                "CMNT: - Output B type
                 TYPE: - RadiobuttonList
                 PAGE: - Video2
                    Output B Type  cmdID= 40702
                    Processed  value= 0
                    Reclocked  value= 1  "
        ::= { iqupc00CmdEntry 40702 }


    iqupc00Video2VideoOutputOutput1Std OBJECT-TYPE
        SYNTAX            RollCallString
        MAX-ACCESS        read-only
        STATUS            current
        DESCRIPTION
                "CMNT: - Output 1 Standard
                 TYPE: - Display
                 PAGE: - Video2
                    Output 1 Std  cmdID= 40706  "
        ::= { iqupc00CmdEntry 40706 }


    iqupc00VideoOutputVideoProcMasterGain OBJECT-TYPE
        SYNTAX            INTEGER
        MAX-ACCESS        read-write
        STATUS            current
        DESCRIPTION
                "CMNT: - Video Master Gain
                 TYPE: - Number
                 PAGE: - Video Output
                    Master Gain  cmdID= 33000
                    min= 0  max= 2000  step= 1  format= %d  div_scale= 1  preset= 1000
                    Min = 0  Max = 0  Step = 0  Preset = 0  "
        ::= { iqupc00CmdEntry 33000 }


    iqupc00VideoOutputVideoProcYGain OBJECT-TYPE
        SYNTAX            INTEGER
        MAX-ACCESS        read-write
        STATUS            current
        DESCRIPTION
                "CMNT: - Video Luminance gain
                 TYPE: - Number
                 PAGE: - Video Output
                    Y Gain  cmdID= 33001
                    min= 0  max= 2000  step= 1  format= %d  div_scale= 1  preset= 1000
                    Min = 0  Max = 0  Step = 0  Preset = 0  "
        ::= { iqupc00CmdEntry 33001 }


    iqupc00VideoOutputVideoProcCGain OBJECT-TYPE
        SYNTAX            INTEGER
        MAX-ACCESS        read-write
        STATUS            current
        DESCRIPTION
                "CMNT: - Video CbCr Gain
                 TYPE: - Number
                 PAGE: - Video Output
                    C Gain  cmdID= 33003
                    min= 0  max= 2000  step= 1  format= %d  div_scale= 1  preset= 1000
                    Min = 0  Max = 0  Step = 0  Preset = 0  "
        ::= { iqupc00CmdEntry 33003 }


    iqupc00VideoOutputVideoProcBlackLevel OBJECT-TYPE
        SYNTAX            INTEGER
        MAX-ACCESS        read-write
        STATUS            current
        DESCRIPTION
                "CMNT: - Video Black Level
                 TYPE: - Number
                 PAGE: - Video Output
                    Black Level  cmdID= 33002
                    min= -200  max= 200  step= 1  format= %0.0f mV  div_scale= 1  preset= 0
                    Min = -200 mV  Max = 200 mV  Step = 1 mV  Preset = 0 mV  "
        ::= { iqupc00CmdEntry 33002 }


    iqupc00VideoOutputVideoProcHueLevel OBJECT-TYPE
        SYNTAX            INTEGER
        MAX-ACCESS        read-write
        STATUS            current
        DESCRIPTION
                "CMNT: - Video Hue
                 TYPE: - Number
                 PAGE: - Video Output
                    Hue Level  cmdID= 33025
                    min= -180  max= 180  step= 1  format= %0.0f degrees  div_scale= 1  preset= 0
                    Min = -180 degrees  Max = 180 degrees  Step = 1 degrees  Preset = 0 degrees  "
        ::= { iqupc00CmdEntry 33025 }


    iqupc00Video2VideoOutputDefaultOutput OBJECT-TYPE
        SYNTAX            INTEGER {
                            valBlack(1),
                            valFreeze(2),
                            valOutPattern(3)
                            }
        MAX-ACCESS        read-write
        STATUS            current
        DESCRIPTION
                "CMNT: - What to do on input loss
                 TYPE: - RadiobuttonList
                 PAGE: - Video2
                    Default Output  cmdID= 33026
                    Black  value= 1
                    Freeze  value= 2
                    Out Pattern  value= 3  "
        ::= { iqupc00CmdEntry 33026 }


    iqupc00Video2VideoOutputOutputMode OBJECT-TYPE
        SYNTAX            INTEGER {
                            valDefaultVideo(0),
                            valBlack(1),
                            valFreeze(2),
                            valOutPattern(3)
                            }
        MAX-ACCESS        read-write
        STATUS            current
        DESCRIPTION
                "CMNT: - Video Output mode
                 TYPE: - RadiobuttonList
                 PAGE: - Video2
                    Output Mode  cmdID= 33027
                    Default Video  value= 0
                    Black  value= 1
                    Freeze  value= 2
                    Out Pattern  value= 3  "
        ::= { iqupc00CmdEntry 33027 }


    iqupc00Video2VideoOutputPatternType OBJECT-TYPE
        SYNTAX            INTEGER {
                            val75ColorBars(0),
                            val100ColorBars(1),
                            valSMPTEBars(2),
                            valTartanBars(9),
                            valBlack(8),
                            valPluge(3),
                            valRamp(4),
                            valSweep(5),
                            valPulseBar(6),
                            valBurst(7)
                            }
        MAX-ACCESS        read-write
        STATUS            current
        DESCRIPTION
                "CMNT: - TPG pattern type
                 TYPE: - RadiobuttonList
                 PAGE: - Video2
                    Pattern Type  cmdID= 33028
                    75% Color Bars  value= 0
                    100% Color Bars  value= 1
                    SMPTE Bars  value= 2
                    Tartan Bars  value= 9
                    Black  value= 8
                    Pluge  value= 3
                    Ramp  value= 4
                    Sweep  value= 5
                    Pulse & Bar  value= 6
                    Burst  value= 7  "
        ::= { iqupc00CmdEntry 33028 }


    iqupc00VideoOutputUserCaptionsEnable OBJECT-TYPE
        SYNTAX            INTEGER { disable(0), enable(1)  }
        MAX-ACCESS        read-write
        STATUS            current
        DESCRIPTION
                "CMNT: - 
                 TYPE: - Checkbox
                 PAGE: - Video Output
                    Enable  cmdID= 6080  "
        ::= { iqupc00CmdEntry 6080 }


    iqupc00VideoOutputUserCaptionsEnableAlt OBJECT-TYPE
        SYNTAX            INTEGER { disable(0), enable(1)  }
        MAX-ACCESS        read-write
        STATUS            current
        DESCRIPTION
                "CMNT: - 
                 TYPE: - Checkbox
                 PAGE: - Video Output
                    EnableAlt  cmdID= 6087  "
        ::= { iqupc00CmdEntry 6087 }


    iqupc00VideoOutputUserCaptionsText OBJECT-TYPE
        SYNTAX            RollCallString
        MAX-ACCESS        read-write
        STATUS            current
        DESCRIPTION
                "CMNT: - 
                 TYPE: - Editstring
                 PAGE: - Video Output
                    Text  cmdID= 6085
                    preset= IQUAV10"
        ::= { iqupc00CmdEntry 6085 }


    iqupc00VideoOutputUserCaptionsTextAlt OBJECT-TYPE
        SYNTAX            RollCallString
        MAX-ACCESS        read-write
        STATUS            current
        DESCRIPTION
                "CMNT: - 
                 TYPE: - Editstring
                 PAGE: - Video Output
                    TextAlt  cmdID= 6086
                    preset= IQUAV10*"
        ::= { iqupc00CmdEntry 6086 }


    iqupc00VideoOutputUserCaptionsXPos OBJECT-TYPE
        SYNTAX            INTEGER
        MAX-ACCESS        read-write
        STATUS            current
        DESCRIPTION
                "CMNT: - 
                 TYPE: - Number
                 PAGE: - Video Output
                    X Pos  cmdID= 6081
                    min= 0  max= 1000  step= 1  format= %0.1f  div_scale= 10  preset= 0
                    Min = 0.0  Max = 100.0  Step = 0.1  Preset = 0.0  "
        ::= { iqupc00CmdEntry 6081 }


    iqupc00VideoOutputUserCaptionsYPos OBJECT-TYPE
        SYNTAX            INTEGER
        MAX-ACCESS        read-write
        STATUS            current
        DESCRIPTION
                "CMNT: - 
                 TYPE: - Number
                 PAGE: - Video Output
                    Y Pos  cmdID= 6082
                    min= -1000  max= 0  step= 1  format= %0.1f  div_scale= 10  preset= 0
                    Min = -100.0  Max = 0.0  Step = 0.1  Preset = 0.0  "
        ::= { iqupc00CmdEntry 6082 }


    iqupc00VideoOutputUserCaptionsXSize OBJECT-TYPE
        SYNTAX            INTEGER
        MAX-ACCESS        read-write
        STATUS            current
        DESCRIPTION
                "CMNT: - 
                 TYPE: - Number
                 PAGE: - Video Output
                    X Size  cmdID= 6083
                    min= 1  max= 10  step= 1  format= %0.0f  div_scale= 1  preset= 1
                    Min = 1  Max = 10  Step = 1  Preset = 1  "
        ::= { iqupc00CmdEntry 6083 }


    iqupc00VideoOutputUserCaptionsYSize OBJECT-TYPE
        SYNTAX            INTEGER
        MAX-ACCESS        read-write
        STATUS            current
        DESCRIPTION
                "CMNT: - 
                 TYPE: - Number
                 PAGE: - Video Output
                    Y Size  cmdID= 6084
                    min= 1  max= 10  step= 1  format= %0.0f  div_scale= 1  preset= 1
                    Min = 1  Max = 10  Step = 1  Preset = 1  "
        ::= { iqupc00CmdEntry 6084 }


    iqupc00Video2VideoOutputLastRefStd OBJECT-TYPE
        SYNTAX            INTEGER
        MAX-ACCESS        read-write
        STATUS            current
        DESCRIPTION
                "CMNT: - Last Known ref std
                 TYPE: - Number
                 PAGE: - Video2
                    LastRefStd  cmdID= 36145
                    min= 0  max= 10  step= 1  format= %d  div_scale= 1  preset= 0
                    Min = 0  Max = 0  Step = 0  Preset = 0  "
        ::= { iqupc00CmdEntry 36145 }


    iqupc00Video2VideoOutputLastFrameRate OBJECT-TYPE
        SYNTAX            INTEGER
        MAX-ACCESS        read-write
        STATUS            current
        DESCRIPTION
                "CMNT: - Last Known Input rate
                 TYPE: - Number
                 PAGE: - Video2
                    LastFrameRate  cmdID= 36146
                    min= 0  max= 2  step= 1  format= %d  div_scale= 1  preset= 0
                    Min = 0  Max = 0  Step = 0  Preset = 0  "
        ::= { iqupc00CmdEntry 36146 }


    iqupc00PictureAdvancedHEnhanceEnable OBJECT-TYPE
        SYNTAX            INTEGER { disable(0), enable(1)  }
        MAX-ACCESS        read-write
        STATUS            current
        DESCRIPTION
                "CMNT: - 
                 TYPE: - Checkbox
                 PAGE: - Picture
                    Enable  cmdID= 6030  "
        ::= { iqupc00CmdEntry 6030 }


    iqupc00PictureAdvancedHEnhanceFrequencyBand OBJECT-TYPE
        SYNTAX            INTEGER {
                            valLow(2),
                            valMedium(1),
                            valHigh(0)
                            }
        MAX-ACCESS        read-write
        STATUS            current
        DESCRIPTION
                "CMNT: - 
                 TYPE: - RadiobuttonList
                 PAGE: - Picture
                    Frequency Band  cmdID= 6031
                    Low  value= 2
                    Medium  value= 1
                    High  value= 0  "
        ::= { iqupc00CmdEntry 6031 }


    iqupc00PictureAdvancedHEnhancePreset OBJECT-TYPE
        SYNTAX            INTEGER {
                            valLow(1),
                            valMedium(2),
                            valHigh(3),
                            valSuper(4),
                            valCustom(0)
                            }
        MAX-ACCESS        read-write
        STATUS            current
        DESCRIPTION
                "CMNT: - 
                 TYPE: - RadiobuttonList
                 PAGE: - Picture
                    Preset  cmdID= 6034
                    Low  value= 1
                    Medium  value= 2
                    High  value= 3
                    Super  value= 4
                    Custom  value= 0  "
        ::= { iqupc00CmdEntry 6034 }


    iqupc00PictureAdvancedHEnhanceGain OBJECT-TYPE
        SYNTAX            INTEGER
        MAX-ACCESS        read-write
        STATUS            current
        DESCRIPTION
                "CMNT: - 
                 TYPE: - Number
                 PAGE: - Picture
                    Gain  cmdID= 6032
                    min= 0  max= 192  step= 8  format= %0.1f  div_scale= 16  preset= 0
                    Min = 0.0  Max = 12.0  Step = 0.5  Preset = 0.0  "
        ::= { iqupc00CmdEntry 6032 }


    iqupc00PictureAdvancedHEnhanceNoiseRejection OBJECT-TYPE
        SYNTAX            INTEGER
        MAX-ACCESS        read-write
        STATUS            current
        DESCRIPTION
                "CMNT: - 
                 TYPE: - Number
                 PAGE: - Picture
                    Noise Rejection  cmdID= 6033
                    min= 0  max= 100  step= 1  format= %0.0f%%  div_scale= 1  preset= 0
                    Min = 0%  Max = 100%  Step = 1%  Preset = 0%  "
        ::= { iqupc00CmdEntry 6033 }


    iqupc00PictureRGBLegaliserRange OBJECT-TYPE
        SYNTAX            INTEGER {
                            val700mV(0),
                            val721mV(1),
                            val735mV(2),
                            val746mV(3)
                            }
        MAX-ACCESS        read-write
        STATUS            current
        DESCRIPTION
                "CMNT: - 
                 TYPE: - RadiobuttonList
                 PAGE: - Picture
                    Range  cmdID= 6061
                    700 mV  value= 0
                    721 mV  value= 1
                    735 mV  value= 2
                    746 mV  value= 3  "
        ::= { iqupc00CmdEntry 6061 }


    iqupc00PictureLumaClipperEnable OBJECT-TYPE
        SYNTAX            INTEGER { disable(0), enable(1)  }
        MAX-ACCESS        read-write
        STATUS            current
        DESCRIPTION
                "CMNT: - 
                 TYPE: - Checkbox
                 PAGE: - Picture
                    Enable  cmdID= 6070  "
        ::= { iqupc00CmdEntry 6070 }


    iqupc00PictureLumaClipperWhitemax OBJECT-TYPE
        SYNTAX            INTEGER
        MAX-ACCESS        read-write
        STATUS            current
        DESCRIPTION
                "CMNT: - 
                 TYPE: - Number
                 PAGE: - Picture
                    White max  cmdID= 6071
                    min= 90  max= 109  step= 1  format= %0.0f %%  div_scale= 1  preset= 103
                    Min = 90 %  Max = 109 %  Step = 1 %  Preset = 103 %  "
        ::= { iqupc00CmdEntry 6071 }


    iqupc00PictureLumaClipperBlackmin OBJECT-TYPE
        SYNTAX            INTEGER
        MAX-ACCESS        read-write
        STATUS            current
        DESCRIPTION
                "CMNT: - 
                 TYPE: - Number
                 PAGE: - Picture
                    Black min  cmdID= 6072
                    min= -7  max= 10  step= 1  format= %0.0f %%  div_scale= 1  preset= -1
                    Min = -7 %  Max = 10 %  Step = 1 %  Preset = -1 %  "
        ::= { iqupc00CmdEntry 6072 }


    iqupc00PictureOutputPictureColorimetry OBJECT-TYPE
        SYNTAX            INTEGER {
                            valAuto(0),
                            valNone(1),
                            valBT709toRec601(2),
                            valRec601toBT709(3)
                            }
        MAX-ACCESS        read-write
        STATUS            current
        DESCRIPTION
                "CMNT: - 
                 TYPE: - RadiobuttonList
                 PAGE: - Picture Output
                    Colorimetry  cmdID= 6043
                    Auto  value= 0
                    None  value= 1
                    BT709toRec601  value= 2
                    Rec601toBT709  value= 3  "
        ::= { iqupc00CmdEntry 6043 }


    iqupc00PictureEnhanceNoiseThreshold OBJECT-TYPE
        SYNTAX            INTEGER
        MAX-ACCESS        read-write
        STATUS            current
        DESCRIPTION
                "CMNT: - 
                 TYPE: - Number
                 PAGE: - Picture
                    Noise Threshold  cmdID= 6041
                    min= 0  max= 255  step= 1  format= %0.0f  div_scale= 1  preset= 0
                    Min = 0  Max = 255  Step = 1  Preset = 0  "
        ::= { iqupc00CmdEntry 6041 }


    iqupc00PictureEnhanceSharpnessThreshold OBJECT-TYPE
        SYNTAX            INTEGER
        MAX-ACCESS        read-write
        STATUS            current
        DESCRIPTION
                "CMNT: - 
                 TYPE: - Number
                 PAGE: - Picture
                    Sharpness Threshold  cmdID= 6042
                    min= 0  max= 255  step= 1  format= %0.0f  div_scale= 1  preset= 0
                    Min = 0  Max = 255  Step = 1  Preset = 0  "
        ::= { iqupc00CmdEntry 6042 }


    iqupc00PictureEnhanceSharpnessAmplitude OBJECT-TYPE
        SYNTAX            INTEGER
        MAX-ACCESS        read-write
        STATUS            current
        DESCRIPTION
                "CMNT: - 
                 TYPE: - Number
                 PAGE: - Picture
                    Sharpness Amplitude  cmdID= 6044
                    min= 0  max= 255  step= 1  format= %0.0f  div_scale= 1  preset= 0
                    Min = 0  Max = 255  Step = 1  Preset = 0  "
        ::= { iqupc00CmdEntry 6044 }


    iqupc00PictureOutputPictureFilmCadence OBJECT-TYPE
        SYNTAX            RollCallString
        MAX-ACCESS        read-only
        STATUS            current
        DESCRIPTION
                "CMNT: - Film cadence
                 TYPE: - Display
                 PAGE: - Picture Output
                    Film Cadence  cmdID= 40707  "
        ::= { iqupc00CmdEntry 40707 }


    iqupc00PictureOutputColorCorrectGreenOffset OBJECT-TYPE
        SYNTAX            INTEGER
        MAX-ACCESS        read-write
        STATUS            current
        DESCRIPTION
                "CMNT: - COLOR correct offset Green
                 TYPE: - Number
                 PAGE: - Picture Output
                    GreenOffset  cmdID= 40861
                    min= 0  max= 203200  step= 100  format= %0.2f%%  div_scale= 1016  preset= 101600
                    Min = 0.00%  Max = 200.00%  Step = 0.10%  Preset = 100.00%  "
        ::= { iqupc00CmdEntry 40861 }


    iqupc00PictureOutputColorCorrectBlueOffset OBJECT-TYPE
        SYNTAX            INTEGER
        MAX-ACCESS        read-write
        STATUS            current
        DESCRIPTION
                "CMNT: - COLOR correct offset Blue
                 TYPE: - Number
                 PAGE: - Picture Output
                    BlueOffset  cmdID= 40862
                    min= 0  max= 203200  step= 100  format= %0.2f%%  div_scale= 1016  preset= 101600
                    Min = 0.00%  Max = 200.00%  Step = 0.10%  Preset = 100.00%  "
        ::= { iqupc00CmdEntry 40862 }


    iqupc00PictureOutputColorCorrectRedOffset OBJECT-TYPE
        SYNTAX            INTEGER
        MAX-ACCESS        read-write
        STATUS            current
        DESCRIPTION
                "CMNT: - COLOR correct offset Red
                 TYPE: - Number
                 PAGE: - Picture Output
                    RedOffset  cmdID= 40863
                    min= 0  max= 203200  step= 100  format= %0.2f%%  div_scale= 1016  preset= 101600
                    Min = 0.00%  Max = 200.00%  Step = 0.10%  Preset = 100.00%  "
        ::= { iqupc00CmdEntry 40863 }


    iqupc00PictureOutputColorCorrectGangOffset OBJECT-TYPE
        SYNTAX            INTEGER { disable(0), enable(1)  }
        MAX-ACCESS        read-write
        STATUS            current
        DESCRIPTION
                "CMNT: - COLOR correct offset gang
                 TYPE: - Checkbox
                 PAGE: - Picture Output
                    GangOffset  cmdID= 40870  "
        ::= { iqupc00CmdEntry 40870 }


    iqupc00PictureOutputColorCorrectGreenGain OBJECT-TYPE
        SYNTAX            INTEGER
        MAX-ACCESS        read-write
        STATUS            current
        DESCRIPTION
                "CMNT: - COLOR correct gain Green
                 TYPE: - Number
                 PAGE: - Picture Output
                    GreenGain  cmdID= 40864
                    min= 0  max= 2000  step= 1  format= %0.1f%%  div_scale= 10  preset= 1000
                    Min = 0.0%  Max = 200.0%  Step = 0.1%  Preset = 100.0%  "
        ::= { iqupc00CmdEntry 40864 }


    iqupc00PictureOutputColorCorrectBlueGain OBJECT-TYPE
        SYNTAX            INTEGER
        MAX-ACCESS        read-write
        STATUS            current
        DESCRIPTION
                "CMNT: - COLOR correct gain Blue
                 TYPE: - Number
                 PAGE: - Picture Output
                    BlueGain  cmdID= 40865
                    min= 0  max= 2000  step= 1  format= %0.1f%%  div_scale= 10  preset= 1000
                    Min = 0.0%  Max = 200.0%  Step = 0.1%  Preset = 100.0%  "
        ::= { iqupc00CmdEntry 40865 }


    iqupc00PictureOutputColorCorrectRedGain OBJECT-TYPE
        SYNTAX            INTEGER
        MAX-ACCESS        read-write
        STATUS            current
        DESCRIPTION
                "CMNT: - COLOR correct gain Red
                 TYPE: - Number
                 PAGE: - Picture Output
                    RedGain  cmdID= 40866
                    min= 0  max= 2000  step= 1  format= %0.1f%%  div_scale= 10  preset= 1000
                    Min = 0.0%  Max = 200.0%  Step = 0.1%  Preset = 100.0%  "
        ::= { iqupc00CmdEntry 40866 }


    iqupc00PictureOutputColorCorrectGangGain OBJECT-TYPE
        SYNTAX            INTEGER { disable(0), enable(1)  }
        MAX-ACCESS        read-write
        STATUS            current
        DESCRIPTION
                "CMNT: - COLOR correct gain gang
                 TYPE: - Checkbox
                 PAGE: - Picture Output
                    GangGain  cmdID= 40871  "
        ::= { iqupc00CmdEntry 40871 }


    iqupc00PictureOutputColorCorrectGreenGamma OBJECT-TYPE
        SYNTAX            INTEGER
        MAX-ACCESS        read-write
        STATUS            current
        DESCRIPTION
                "CMNT: - COLOR correct gamma Green
                 TYPE: - Number
                 PAGE: - Picture Output
                    GreenGamma  cmdID= 40867
                    min= 0  max= 1000  step= 1  format= %0.0f  div_scale= 1  preset= 500
                    Min = 0  Max = 1000  Step = 1  Preset = 500  "
        ::= { iqupc00CmdEntry 40867 }


    iqupc00PictureOutputColorCorrectBlueGamma OBJECT-TYPE
        SYNTAX            INTEGER
        MAX-ACCESS        read-write
        STATUS            current
        DESCRIPTION
                "CMNT: - COLOR correct gamma Blue
                 TYPE: - Number
                 PAGE: - Picture Output
                    BlueGamma  cmdID= 40868
                    min= 0  max= 1000  step= 1  format= %0.0f  div_scale= 1  preset= 500
                    Min = 0  Max = 1000  Step = 1  Preset = 500  "
        ::= { iqupc00CmdEntry 40868 }


    iqupc00PictureOutputColorCorrectRedGamma OBJECT-TYPE
        SYNTAX            INTEGER
        MAX-ACCESS        read-write
        STATUS            current
        DESCRIPTION
                "CMNT: - COLOR correct gamma Red
                 TYPE: - Number
                 PAGE: - Picture Output
                    RedGamma  cmdID= 40869
                    min= 0  max= 1000  step= 1  format= %0.0f  div_scale= 1  preset= 500
                    Min = 0  Max = 1000  Step = 1  Preset = 500  "
        ::= { iqupc00CmdEntry 40869 }


    iqupc00PictureOutputColorCorrectGangGamma OBJECT-TYPE
        SYNTAX            INTEGER { disable(0), enable(1)  }
        MAX-ACCESS        read-write
        STATUS            current
        DESCRIPTION
                "CMNT: - COLOR correct gamma gang
                 TYPE: - Checkbox
                 PAGE: - Picture Output
                    GangGamma  cmdID= 40872  "
        ::= { iqupc00CmdEntry 40872 }


    iqupc00PictureOutputOutputBorderLeft OBJECT-TYPE
        SYNTAX            INTEGER
        MAX-ACCESS        read-write
        STATUS            current
        DESCRIPTION
                "CMNT: - 
                 TYPE: - Number
                 PAGE: - Picture Output
                    Left  cmdID= 6009
                    min= 0  max= 1920  step= 1  format= %0.0f  div_scale= 1  preset= 0
                    Min = 0  Max = 1920  Step = 1  Preset = 0  "
        ::= { iqupc00CmdEntry 6009 }


    iqupc00PictureOutputOutputBorderRight OBJECT-TYPE
        SYNTAX            INTEGER
        MAX-ACCESS        read-write
        STATUS            current
        DESCRIPTION
                "CMNT: - 
                 TYPE: - Number
                 PAGE: - Picture Output
                    Right  cmdID= 6010
                    min= 0  max= 1920  step= 1  format= %0.0f  div_scale= 1  preset= 0
                    Min = 0  Max = 1920  Step = 1  Preset = 0  "
        ::= { iqupc00CmdEntry 6010 }


    iqupc00PictureOutputOutputBorderTop OBJECT-TYPE
        SYNTAX            INTEGER
        MAX-ACCESS        read-write
        STATUS            current
        DESCRIPTION
                "CMNT: - 
                 TYPE: - Number
                 PAGE: - Picture Output
                    Top  cmdID= 6011
                    min= 0  max= 1080  step= 1  format= %0.0f  div_scale= 1  preset= 0
                    Min = 0  Max = 1080  Step = 1  Preset = 0  "
        ::= { iqupc00CmdEntry 6011 }


    iqupc00PictureOutputOutputBorderBottom OBJECT-TYPE
        SYNTAX            INTEGER
        MAX-ACCESS        read-write
        STATUS            current
        DESCRIPTION
                "CMNT: - 
                 TYPE: - Number
                 PAGE: - Picture Output
                    Bottom  cmdID= 6012
                    min= 0  max= 1080  step= 1  format= %0.0f  div_scale= 1  preset= 0
                    Min = 0  Max = 1080  Step = 1  Preset = 0  "
        ::= { iqupc00CmdEntry 6012 }


    iqupc00PictureOutputOutputBorderRed OBJECT-TYPE
        SYNTAX            INTEGER
        MAX-ACCESS        read-write
        STATUS            current
        DESCRIPTION
                "CMNT: - 
                 TYPE: - Number
                 PAGE: - Picture Output
                    Red  cmdID= 6013
                    min= 0  max= 255  step= 1  format= %0.0f  div_scale= 1  preset= 127
                    Min = 0  Max = 255  Step = 1  Preset = 127  "
        ::= { iqupc00CmdEntry 6013 }


    iqupc00PictureOutputOutputBorderGreen OBJECT-TYPE
        SYNTAX            INTEGER
        MAX-ACCESS        read-write
        STATUS            current
        DESCRIPTION
                "CMNT: - 
                 TYPE: - Number
                 PAGE: - Picture Output
                    Green  cmdID= 6014
                    min= 0  max= 255  step= 1  format= %0.0f  div_scale= 1  preset= 127
                    Min = 0  Max = 255  Step = 1  Preset = 127  "
        ::= { iqupc00CmdEntry 6014 }


    iqupc00PictureOutputOutputBorderBlue OBJECT-TYPE
        SYNTAX            INTEGER
        MAX-ACCESS        read-write
        STATUS            current
        DESCRIPTION
                "CMNT: - 
                 TYPE: - Number
                 PAGE: - Picture Output
                    Blue  cmdID= 6015
                    min= 0  max= 255  step= 1  format= %0.0f  div_scale= 1  preset= 127
                    Min = 0  Max = 255  Step = 1  Preset = 127  "
        ::= { iqupc00CmdEntry 6015 }


    iqupc00ARCCtrlRecallDisplayMemory OBJECT-TYPE
        SYNTAX            INTEGER {
                            valNoneSelected(0),
                            valDisplayMemory1(1),
                            valDisplayMemory2(2),
                            valDisplayMemory3(3),
                            valDisplayMemory4(4),
                            valDisplayMemory5(5),
                            valDisplayMemory6(6),
                            valDisplayMemory7(7),
                            valDisplayMemory8(8),
                            valDisplayMemory9(9),
                            valDisplayMemory10(10),
                            valDisplayMemory11(11),
                            valDisplayMemory12(12),
                            valDisplayMemory13(13),
                            valDisplayMemory14(14),
                            valDisplayMemory15(15),
                            valDisplayMemory16(16),
                            valDisplayMemory17(17),
                            valDisplayMemory18(18),
                            valDisplayMemory19(19),
                            valDisplayMemory20(20),
                            valDisplayMemory21(21),
                            valDisplayMemory22(22),
                            valDisplayMemory23(23),
                            valDisplayMemory24(24),
                            valDisplayMemory25(25),
                            valDisplayMemory26(26),
                            valDisplayMemory27(27),
                            valDisplayMemory28(28),
                            valDisplayMemory29(29),
                            valDisplayMemory30(30),
                            valDisplayMemory31(31),
                            valDisplayMemory32(32)
                            }
        MAX-ACCESS        read-write
        STATUS            current
        DESCRIPTION
                "CMNT: - 
                 TYPE: - RadiobuttonList
                 PAGE: - ARC Ctrl
                    Recall Display Memory  cmdID= 38701
                    None Selected  value= 0
                    Display Memory 1  value= 1
                    Display Memory 2  value= 2
                    Display Memory 3  value= 3
                    Display Memory 4  value= 4
                    Display Memory 5  value= 5
                    Display Memory 6  value= 6
                    Display Memory 7  value= 7
                    Display Memory 8  value= 8
                    Display Memory 9  value= 9
                    Display Memory 10  value= 10
                    Display Memory 11  value= 11
                    Display Memory 12  value= 12
                    Display Memory 13  value= 13
                    Display Memory 14  value= 14
                    Display Memory 15  value= 15
                    Display Memory 16  value= 16
                    Display Memory 17  value= 17
                    Display Memory 18  value= 18
                    Display Memory 19  value= 19
                    Display Memory 20  value= 20
                    Display Memory 21  value= 21
                    Display Memory 22  value= 22
                    Display Memory 23  value= 23
                    Display Memory 24  value= 24
                    Display Memory 25  value= 25
                    Display Memory 26  value= 26
                    Display Memory 27  value= 27
                    Display Memory 28  value= 28
                    Display Memory 29  value= 29
                    Display Memory 30  value= 30
                    Display Memory 31  value= 31
                    Display Memory 32  value= 32  "
        ::= { iqupc00CmdEntry 38701 }


    iqupc00ARCCtrlSelDisplayMemory OBJECT-TYPE
        SYNTAX            INTEGER {
                            valDisplayMemory1(1),
                            valDisplayMemory2(2),
                            valDisplayMemory3(3),
                            valDisplayMemory4(4),
                            valDisplayMemory5(5),
                            valDisplayMemory6(6),
                            valDisplayMemory7(7),
                            valDisplayMemory8(8),
                            valDisplayMemory9(9),
                            valDisplayMemory10(10),
                            valDisplayMemory11(11),
                            valDisplayMemory12(12),
                            valDisplayMemory13(13),
                            valDisplayMemory14(14),
                            valDisplayMemory15(15),
                            valDisplayMemory16(16),
                            valDisplayMemory17(17),
                            valDisplayMemory18(18),
                            valDisplayMemory19(19),
                            valDisplayMemory20(20),
                            valDisplayMemory21(21),
                            valDisplayMemory22(22),
                            valDisplayMemory23(23),
                            valDisplayMemory24(24),
                            valDisplayMemory25(25),
                            valDisplayMemory26(26),
                            valDisplayMemory27(27),
                            valDisplayMemory28(28),
                            valDisplayMemory29(29),
                            valDisplayMemory30(30),
                            valDisplayMemory31(31),
                            valDisplayMemory32(32)
                            }
        MAX-ACCESS        read-write
        STATUS            current
        DESCRIPTION
                "CMNT: - 
                 TYPE: - RadiobuttonList
                 PAGE: - ARC Ctrl
                    Sel Display Memory  cmdID= 6040
                    Display Memory 1  value= 1
                    Display Memory 2  value= 2
                    Display Memory 3  value= 3
                    Display Memory 4  value= 4
                    Display Memory 5  value= 5
                    Display Memory 6  value= 6
                    Display Memory 7  value= 7
                    Display Memory 8  value= 8
                    Display Memory 9  value= 9
                    Display Memory 10  value= 10
                    Display Memory 11  value= 11
                    Display Memory 12  value= 12
                    Display Memory 13  value= 13
                    Display Memory 14  value= 14
                    Display Memory 15  value= 15
                    Display Memory 16  value= 16
                    Display Memory 17  value= 17
                    Display Memory 18  value= 18
                    Display Memory 19  value= 19
                    Display Memory 20  value= 20
                    Display Memory 21  value= 21
                    Display Memory 22  value= 22
                    Display Memory 23  value= 23
                    Display Memory 24  value= 24
                    Display Memory 25  value= 25
                    Display Memory 26  value= 26
                    Display Memory 27  value= 27
                    Display Memory 28  value= 28
                    Display Memory 29  value= 29
                    Display Memory 30  value= 30
                    Display Memory 31  value= 31
                    Display Memory 32  value= 32  "
        ::= { iqupc00CmdEntry 6040 }


    iqupc00ARCCtrlSaveset OBJECT-TYPE
        SYNTAX            INTEGER
        MAX-ACCESS        read-write
        STATUS            current
        DESCRIPTION
                "CMNT: - 
                 TYPE: - Number
                 PAGE: - ARC Ctrl
                    Saveset  cmdID= 6045
                    min= 0  max= 33  step= 1  format= %d  div_scale= 1  preset= 0
                    Min = 0  Max = 0  Step = 0  Preset = 0  "
        ::= { iqupc00CmdEntry 6045 }


    iqupc00ARCCtrlSaveDispMemory OBJECT-TYPE
        SYNTAX            INTEGER { noAction(0),valSaveDispMemory(1) }
        MAX-ACCESS        read-write
        STATUS            current
        DESCRIPTION
                "CMNT: - 
                 TYPE: - Button
                 PAGE: - ARC Ctrl
                    Save Disp Memory  cmdID= 38705
                    value= 1  "
        ::= { iqupc00CmdEntry 38705 }


    iqupc00ARCCtrlDispMemoryNameChangeName OBJECT-TYPE
        SYNTAX            RollCallString
        MAX-ACCESS        read-write
        STATUS            current
        DESCRIPTION
                "CMNT: - 
                 TYPE: - Editstring
                 PAGE: - ARC Ctrl
                    Change Name  cmdID= 38703
                    preset= Display Memory"
        ::= { iqupc00CmdEntry 38703 }


    iqupc00ARCCtrlARCSize OBJECT-TYPE
        SYNTAX            INTEGER
        MAX-ACCESS        read-write
        STATUS            current
        DESCRIPTION
                "CMNT: - 
                 TYPE: - Number
                 PAGE: - ARC Ctrl
                    Size  cmdID= 6000
                    min= 600  max= 1500  step= 1  format= %0.1f%  div_scale= 10  preset= 1000
                    Min = 60.0  Max = 150.0  Step = 0.1  Preset = 100.0  "
        ::= { iqupc00CmdEntry 6000 }


    iqupc00ARCCtrlARCApect OBJECT-TYPE
        SYNTAX            INTEGER
        MAX-ACCESS        read-write
        STATUS            current
        DESCRIPTION
                "CMNT: - 
                 TYPE: - Number
                 PAGE: - ARC Ctrl
                    Apect  cmdID= 6001
                    min= 600  max= 2000  step= 1  format= %0.1f%  div_scale= 10  preset= 1000
                    Min = 60.0  Max = 200.0  Step = 0.1  Preset = 100.0  "
        ::= { iqupc00CmdEntry 6001 }


    iqupc00ARCCtrlARCTilt OBJECT-TYPE
        SYNTAX            INTEGER
        MAX-ACCESS        read-write
        STATUS            current
        DESCRIPTION
                "CMNT: - 
                 TYPE: - Number
                 PAGE: - ARC Ctrl
                    Tilt  cmdID= 6002
                    min= -750  max= 750  step= 1  format= %0.1f%  div_scale= 10  preset= 0
                    Min = -75.0  Max = 75.0  Step = 0.1  Preset = 0.0  "
        ::= { iqupc00CmdEntry 6002 }


    iqupc00ARCCtrlARCPan OBJECT-TYPE
        SYNTAX            INTEGER
        MAX-ACCESS        read-write
        STATUS            current
        DESCRIPTION
                "CMNT: - 
                 TYPE: - Number
                 PAGE: - ARC Ctrl
                    Pan  cmdID= 6003
                    min= -750  max= 750  step= 1  format= %0.1f%  div_scale= 10  preset= 0
                    Min = -75.0  Max = 75.0  Step = 0.1  Preset = 0.0  "
        ::= { iqupc00CmdEntry 6003 }


    iqupc00ARCCtrlInputCropLeft OBJECT-TYPE
        SYNTAX            INTEGER
        MAX-ACCESS        read-write
        STATUS            current
        DESCRIPTION
                "CMNT: - 
                 TYPE: - Number
                 PAGE: - ARC Ctrl
                    Left  cmdID= 6005
                    min= 0  max= 4095  step= 1  format= %0.0f  div_scale= 1  preset= 0
                    Min = 0  Max = 4095  Step = 1  Preset = 0  "
        ::= { iqupc00CmdEntry 6005 }


    iqupc00ARCCtrlInputCropRight OBJECT-TYPE
        SYNTAX            INTEGER
        MAX-ACCESS        read-write
        STATUS            current
        DESCRIPTION
                "CMNT: - 
                 TYPE: - Number
                 PAGE: - ARC Ctrl
                    Right  cmdID= 6006
                    min= 0  max= 4095  step= 1  format= %0.0f  div_scale= 1  preset= 0
                    Min = 0  Max = 4095  Step = 1  Preset = 0  "
        ::= { iqupc00CmdEntry 6006 }


    iqupc00ARCCtrlInputCropTop OBJECT-TYPE
        SYNTAX            INTEGER
        MAX-ACCESS        read-write
        STATUS            current
        DESCRIPTION
                "CMNT: - 
                 TYPE: - Number
                 PAGE: - ARC Ctrl
                    Top  cmdID= 6007
                    min= 0  max= 2047  step= 1  format= %0.0f  div_scale= 1  preset= 0
                    Min = 0  Max = 2047  Step = 1  Preset = 0  "
        ::= { iqupc00CmdEntry 6007 }


    iqupc00ARCCtrlInputCropBottom OBJECT-TYPE
        SYNTAX            INTEGER
        MAX-ACCESS        read-write
        STATUS            current
        DESCRIPTION
                "CMNT: - 
                 TYPE: - Number
                 PAGE: - ARC Ctrl
                    Bottom  cmdID= 6008
                    min= 0  max= 2047  step= 1  format= %0.0f  div_scale= 1  preset= 0
                    Min = 0  Max = 2047  Step = 1  Preset = 0  "
        ::= { iqupc00CmdEntry 6008 }


    iqupc00ARCCtrlSelStdPreset OBJECT-TYPE
        SYNTAX            INTEGER {
                            valFullFrame(0),
                            valBox169Top169(1),
                            val43Box149Top169(2),
                            valBox169169(3),
                            valBox4343(4),
                            val43box169(5),
                            val169box43(6),
                            val43box149169(7),
                            val169box14943(8)
                            }
        MAX-ACCESS        read-write
        STATUS            current
        DESCRIPTION
                "CMNT: - 
                 TYPE: - RadiobuttonList
                 PAGE: - ARC Ctrl
                    Sel Std. Preset  cmdID= 38704
                    Full Frame  value= 0
                    Box 16:9 Top > 16:9  value= 1
                    4:3 Box14:9Top>16:9  value= 2
                    Box 16:9 > 16:9  value= 3
                    Box 4:3 > 4:3  value= 4
                    4:3 > box 16:9  value= 5
                    16:9 > box 4:3  value= 6
                    4:3 box 14:9 > 16:9  value= 7
                    16:9 box 14:9 > 4:3  value= 8  "
        ::= { iqupc00CmdEntry 38704 }


    iqupc00ARCCtrlRecallStdPreset OBJECT-TYPE
        SYNTAX            INTEGER { noAction(0),valRecallStdPreset(1) }
        MAX-ACCESS        read-write
        STATUS            current
        DESCRIPTION
                "CMNT: - 
                 TYPE: - Button
                 PAGE: - ARC Ctrl
                    Recall Std Preset  cmdID= 38700
                    value= 1  "
        ::= { iqupc00CmdEntry 38700 }


    iqupc00ARCCtrlDefaultALLMemory OBJECT-TYPE
        SYNTAX            INTEGER { noAction(0),valDefaultALLMemory(1) }
        MAX-ACCESS        read-write
        STATUS            current
        DESCRIPTION
                "CMNT: - 
                 TYPE: - Button
                 PAGE: - ARC Ctrl
                    Default ALL Memory  cmdID= 38702
                    value= 1  "
        ::= { iqupc00CmdEntry 38702 }


    iqupc00ARCCtrlLastDisplayMemory OBJECT-TYPE
        SYNTAX            RollCallString
        MAX-ACCESS        read-only
        STATUS            current
        DESCRIPTION
                "CMNT: - 
                 TYPE: - Display
                 PAGE: - ARC Ctrl
                    Last Display Memory  cmdID= 38706  "
        ::= { iqupc00CmdEntry 38706 }


    iqupc00ARCCtrl43AFDMapping2 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 2  cmdID= 39017
                    min= 2  max= 143  step= 1  format= 0  div_scale= 1  preset= 2
                    Min = 0  Max = 0  Step = 0  Preset = 0  "
        ::= { iqupc00CmdEntry 39017 }


    iqupc00ARCCtrl43AFDMapping3 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 3  cmdID= 39018
                    min= 2  max= 143  step= 1  format= 0  div_scale= 1  preset= 3
                    Min = 0  Max = 0  Step = 0  Preset = 0  "
        ::= { iqupc00CmdEntry 39018 }


    iqupc00ARCCtrl43AFDMapping4 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 4  cmdID= 39019
                    min= 2  max= 143  step= 1  format= 0  div_scale= 1  preset= 4
                    Min = 0  Max = 0  Step = 0  Preset = 0  "
        ::= { iqupc00CmdEntry 39019 }


    iqupc00ARCCtrl43AFDMapping8 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 8  cmdID= 39023
                    min= 2  max= 143  step= 1  format= 0  div_scale= 1  preset= 8
                    Min = 0  Max = 0  Step = 0  Preset = 0  "
        ::= { iqupc00CmdEntry 39023 }


    iqupc00ARCCtrl43AFDMapping9 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 9  cmdID= 39024
                    min= 2  max= 143  step= 1  format= 0  div_scale= 1  preset= 9
                    Min = 0  Max = 0  Step = 0  Preset = 0  "
        ::= { iqupc00CmdEntry 39024 }


    iqupc00ARCCtrl43AFDMapping10 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 10  cmdID= 39025
                    min= 2  max= 143  step= 1  format= 0  div_scale= 1  preset= 10
                    Min = 0  Max = 0  Step = 0  Preset = 0  "
        ::= { iqupc00CmdEntry 39025 }


    iqupc00ARCCtrl43AFDMapping11 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 11  cmdID= 39026
                    min= 2  max= 143  step= 1  format= 0  div_scale= 1  preset= 11
                    Min = 0  Max = 0  Step = 0  Preset = 0  "
        ::= { iqupc00CmdEntry 39026 }


    iqupc00ARCCtrl43AFDMapping12 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 12  cmdID= 39027
                    min= 2  max= 143  step= 1  format= 0  div_scale= 1  preset= 12
                    Min = 0  Max = 0  Step = 0  Preset = 0  "
        ::= { iqupc00CmdEntry 39027 }


    iqupc00ARCCtrl43AFDMapping13 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 13  cmdID= 39028
                    min= 2  max= 143  step= 1  format= 0  div_scale= 1  preset= 13
                    Min = 0  Max = 0  Step = 0  Preset = 0  "
        ::= { iqupc00CmdEntry 39028 }


    iqupc00ARCCtrl43AFDMapping14 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 14  cmdID= 39029
                    min= 2  max= 143  step= 1  format= 0  div_scale= 1  preset= 14
                    Min = 0  Max = 0  Step = 0  Preset = 0  "
        ::= { iqupc00CmdEntry 39029 }


    iqupc00ARCCtrl43AFDMapping15 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 15  cmdID= 39030
                    min= 2  max= 143  step= 1  format= 0  div_scale= 1  preset= 15
                    Min = 0  Max = 0  Step = 0  Preset = 0  "
        ::= { iqupc00CmdEntry 39030 }


    iqupc00ARCCtrl43AFDMapping16 OBJECT-TYPE
        SYNTAX            INTEGER
        MAX-ACCESS        read-write
        STATUS            current
        DESCRIPTION
                "CMNT: - SMTPE2016 4:3 AFD Mapping
                 TYPE: - Number
                 PAGE: - ARC Ctrl
                    4:3 AFD Mapping 16  cmdID= 39031
                    min= 2  max= 143  step= 1  format= 0  div_scale= 1  preset= 8
                    Min = 0  Max = 0  Step = 0  Preset = 0  "
        ::= { iqupc00CmdEntry 39031 }


    iqupc00ARCCtrl169AFDMapping2 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 2  cmdID= 39034
                    min= 2  max= 143  step= 1  format= 0  div_scale= 1  preset= 130
                    Min = 0  Max = 0  Step = 0  Preset = 0  "
        ::= { iqupc00CmdEntry 39034 }


    iqupc00ARCCtrl169AFDMapping3 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 3  cmdID= 39035
                    min= 2  max= 143  step= 1  format= 0  div_scale= 1  preset= 131
                    Min = 0  Max = 0  Step = 0  Preset = 0  "
        ::= { iqupc00CmdEntry 39035 }


    iqupc00ARCCtrl169AFDMapping4 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 4  cmdID= 39036
                    min= 2  max= 143  step= 1  format= 0  div_scale= 1  preset= 132
                    Min = 0  Max = 0  Step = 0  Preset = 0  "
        ::= { iqupc00CmdEntry 39036 }


    iqupc00ARCCtrl169AFDMapping8 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 8  cmdID= 39040
                    min= 2  max= 143  step= 1  format= 0  div_scale= 1  preset= 136
                    Min = 0  Max = 0  Step = 0  Preset = 0  "
        ::= { iqupc00CmdEntry 39040 }


    iqupc00ARCCtrl169AFDMapping9 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 9  cmdID= 39041
                    min= 2  max= 143  step= 1  format= 0  div_scale= 1  preset= 137
                    Min = 0  Max = 0  Step = 0  Preset = 0  "
        ::= { iqupc00CmdEntry 39041 }


    iqupc00ARCCtrl169AFDMapping10 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 10  cmdID= 39042
                    min= 2  max= 143  step= 1  format= 0  div_scale= 1  preset= 138
                    Min = 0  Max = 0  Step = 0  Preset = 0  "
        ::= { iqupc00CmdEntry 39042 }


    iqupc00ARCCtrl169AFDMapping11 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 11  cmdID= 39043
                    min= 2  max= 143  step= 1  format= 0  div_scale= 1  preset= 139
                    Min = 0  Max = 0  Step = 0  Preset = 0  "
        ::= { iqupc00CmdEntry 39043 }


    iqupc00ARCCtrl169AFDMapping12 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 12  cmdID= 39044
                    min= 2  max= 143  step= 1  format= 0  div_scale= 1  preset= 140
                    Min = 0  Max = 0  Step = 0  Preset = 0  "
        ::= { iqupc00CmdEntry 39044 }


    iqupc00ARCCtrl169AFDMapping13 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 13  cmdID= 39045
                    min= 2  max= 143  step= 1  format= 0  div_scale= 1  preset= 141
                    Min = 0  Max = 0  Step = 0  Preset = 0  "
        ::= { iqupc00CmdEntry 39045 }


    iqupc00ARCCtrl169AFDMapping14 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 14  cmdID= 39046
                    min= 2  max= 143  step= 1  format= 0  div_scale= 1  preset= 142
                    Min = 0  Max = 0  Step = 0  Preset = 0  "
        ::= { iqupc00CmdEntry 39046 }


    iqupc00ARCCtrl169AFDMapping15 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 15  cmdID= 39047
                    min= 2  max= 143  step= 1  format= 0  div_scale= 1  preset= 143
                    Min = 0  Max = 0  Step = 0  Preset = 0  "
        ::= { iqupc00CmdEntry 39047 }


    iqupc00ARCCtrl169AFDMapping16 OBJECT-TYPE
        SYNTAX            INTEGER
        MAX-ACCESS        read-write
        STATUS            current
        DESCRIPTION
                "CMNT: - SMTPE2016 16:9 AFD Mapping
                 TYPE: - Number
                 PAGE: - ARC Ctrl
                    16:9 AFD Mapping 16  cmdID= 39048
                    min= 2  max= 143  step= 1  format= 0  div_scale= 1  preset= 136
                    Min = 0  Max = 0  Step = 0  Preset = 0  "
        ::= { iqupc00CmdEntry 39048 }


    iqupc00ARCCtrlNoSignalMapping OBJECT-TYPE
        SYNTAX            INTEGER
        MAX-ACCESS        read-write
        STATUS            current
        DESCRIPTION
                "CMNT: - No signal AFD Mapping
                 TYPE: - Number
                 PAGE: - ARC Ctrl
                    No Signal Mapping  cmdID= 39049
                    min= 2  max= 143  step= 1  format= 0  div_scale= 1  preset= 8
                    Min = 0  Max = 0  Step = 0  Preset = 0  "
        ::= { iqupc00CmdEntry 39049 }


    iqupc00ARCCtrlForceMapping OBJECT-TYPE
        SYNTAX            INTEGER
        MAX-ACCESS        read-write
        STATUS            current
        DESCRIPTION
                "CMNT: - Force AFD Mapping
                 TYPE: - Number
                 PAGE: - ARC Ctrl
                    Force Mapping  cmdID= 39079
                    min= 2  max= 143  step= 1  format= 0  div_scale= 1  preset= 8
                    Min = 0  Max = 0  Step = 0  Preset = 0  "
        ::= { iqupc00CmdEntry 39079 }


    iqupc00ARCCtrl43ARCMapping2 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  2  cmdID= 39050
                    min= 0  max= 32  step= 1  format= 0  div_scale= 1  preset= 1
                    Min = 0  Max = 0  Step = 0  Preset = 0  "
        ::= { iqupc00CmdEntry 39050 }


    iqupc00ARCCtrl43ARCMapping3 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  3  cmdID= 39051
                    min= 0  max= 32  step= 1  format= 0  div_scale= 1  preset= 1
                    Min = 0  Max = 0  Step = 0  Preset = 0  "
        ::= { iqupc00CmdEntry 39051 }


    iqupc00ARCCtrl43ARCMapping4 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  4  cmdID= 39052
                    min= 0  max= 32  step= 1  format= 0  div_scale= 1  preset= 1
                    Min = 0  Max = 0  Step = 0  Preset = 0  "
        ::= { iqupc00CmdEntry 39052 }


    iqupc00ARCCtrl43ARCMapping8 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  8  cmdID= 39053
                    min= 0  max= 32  step= 1  format= 0  div_scale= 1  preset= 1
                    Min = 0  Max = 0  Step = 0  Preset = 0  "
        ::= { iqupc00CmdEntry 39053 }


    iqupc00ARCCtrl43ARCMapping9 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  9  cmdID= 39054
                    min= 0  max= 32  step= 1  format= 0  div_scale= 1  preset= 1
                    Min = 0  Max = 0  Step = 0  Preset = 0  "
        ::= { iqupc00CmdEntry 39054 }


    iqupc00ARCCtrl43ARCMapping10 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  10  cmdID= 39055
                    min= 0  max= 32  step= 1  format= 0  div_scale= 1  preset= 1
                    Min = 0  Max = 0  Step = 0  Preset = 0  "
        ::= { iqupc00CmdEntry 39055 }


    iqupc00ARCCtrl43ARCMapping11 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  11  cmdID= 39056
                    min= 0  max= 32  step= 1  format= 0  div_scale= 1  preset= 1
                    Min = 0  Max = 0  Step = 0  Preset = 0  "
        ::= { iqupc00CmdEntry 39056 }


    iqupc00ARCCtrl43ARCMapping12 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  12  cmdID= 39057
                    min= 0  max= 32  step= 1  format= 0  div_scale= 1  preset= 0
                    Min = 0  Max = 0  Step = 0  Preset = 0  "
        ::= { iqupc00CmdEntry 39057 }


    iqupc00ARCCtrl43ARCMapping13 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  13  cmdID= 39058
                    min= 0  max= 32  step= 1  format= 0  div_scale= 1  preset= 1
                    Min = 0  Max = 0  Step = 0  Preset = 0  "
        ::= { iqupc00CmdEntry 39058 }


    iqupc00ARCCtrl43ARCMapping14 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  14  cmdID= 39059
                    min= 0  max= 32  step= 1  format= 0  div_scale= 1  preset= 1
                    Min = 0  Max = 0  Step = 0  Preset = 0  "
        ::= { iqupc00CmdEntry 39059 }


    iqupc00ARCCtrl43ARCMapping15 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  15  cmdID= 39060
                    min= 0  max= 32  step= 1  format= 0  div_scale= 1  preset= 1
                    Min = 0  Max = 0  Step = 0  Preset = 0  "
        ::= { iqupc00CmdEntry 39060 }


    iqupc00ARCCtrl43ARCMapping16 OBJECT-TYPE
        SYNTAX            INTEGER
        MAX-ACCESS        read-write
        STATUS            current
        DESCRIPTION
                "CMNT: - SMTPE2016 4:3 ARC Mapping
                 TYPE: - Number
                 PAGE: - ARC Ctrl
                    4:3 ARC Mapping  16  cmdID= 39061
                    min= 0  max= 32  step= 1  format= 0  div_scale= 1  preset= 0
                    Min = 0  Max = 0  Step = 0  Preset = 0  "
        ::= { iqupc00CmdEntry 39061 }


    iqupc00ARCCtrl169ARCMapping2 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  2  cmdID= 39062
                    min= 0  max= 32  step= 1  format= 0  div_scale= 1  preset= 1
                    Min = 0  Max = 0  Step = 0  Preset = 0  "
        ::= { iqupc00CmdEntry 39062 }


    iqupc00ARCCtrl169ARCMapping3 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  3  cmdID= 39063
                    min= 0  max= 32  step= 1  format= 0  div_scale= 1  preset= 1
                    Min = 0  Max = 0  Step = 0  Preset = 0  "
        ::= { iqupc00CmdEntry 39063 }


    iqupc00ARCCtrl169ARCMapping4 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  4  cmdID= 39064
                    min= 0  max= 32  step= 1  format= 0  div_scale= 1  preset= 1
                    Min = 0  Max = 0  Step = 0  Preset = 0  "
        ::= { iqupc00CmdEntry 39064 }


    iqupc00ARCCtrl169ARCMapping8 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  8  cmdID= 39065
                    min= 0  max= 32  step= 1  format= 0  div_scale= 1  preset= 1
                    Min = 0  Max = 0  Step = 0  Preset = 0  "
        ::= { iqupc00CmdEntry 39065 }


    iqupc00ARCCtrl169ARCMapping9 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  9  cmdID= 39066
                    min= 0  max= 32  step= 1  format= 0  div_scale= 1  preset= 1
                    Min = 0  Max = 0  Step = 0  Preset = 0  "
        ::= { iqupc00CmdEntry 39066 }


    iqupc00ARCCtrl169ARCMapping10 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  10  cmdID= 39067
                    min= 0  max= 32  step= 1  format= 0  div_scale= 1  preset= 1
                    Min = 0  Max = 0  Step = 0  Preset = 0  "
        ::= { iqupc00CmdEntry 39067 }


    iqupc00ARCCtrl169ARCMapping11 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  11  cmdID= 39068
                    min= 0  max= 32  step= 1  format= 0  div_scale= 1  preset= 1
                    Min = 0  Max = 0  Step = 0  Preset = 0  "
        ::= { iqupc00CmdEntry 39068 }


    iqupc00ARCCtrl169ARCMapping12 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  12  cmdID= 39069
                    min= 0  max= 32  step= 1  format= 0  div_scale= 1  preset= 0
                    Min = 0  Max = 0  Step = 0  Preset = 0  "
        ::= { iqupc00CmdEntry 39069 }


    iqupc00ARCCtrl169ARCMapping13 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  13  cmdID= 39070
                    min= 0  max= 32  step= 1  format= 0  div_scale= 1  preset= 1
                    Min = 0  Max = 0  Step = 0  Preset = 0  "
        ::= { iqupc00CmdEntry 39070 }


    iqupc00ARCCtrl169ARCMapping14 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  14  cmdID= 39071
                    min= 0  max= 32  step= 1  format= 0  div_scale= 1  preset= 1
                    Min = 0  Max = 0  Step = 0  Preset = 0  "
        ::= { iqupc00CmdEntry 39071 }


    iqupc00ARCCtrl169ARCMapping15 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping  15  cmdID= 39072
                    min= 0  max= 32  step= 1  format= 0  div_scale= 1  preset= 1
                    Min = 0  Max = 0  Step = 0  Preset = 0  "
        ::= { iqupc00CmdEntry 39072 }


    iqupc00ARCCtrl169ARCMapping16 OBJECT-TYPE
        SYNTAX            INTEGER
        MAX-ACCESS        read-write
        STATUS            current
        DESCRIPTION
                "CMNT: - SMTPE2016 16:9 ARC Mapping
                 TYPE: - Number
                 PAGE: - ARC Ctrl
                    16:9 ARC Mapping 16  cmdID= 39073
                    min= 0  max= 32  step= 1  format= 0  div_scale= 1  preset= 0
                    Min = 0  Max = 0  Step = 0  Preset = 0  "
        ::= { iqupc00CmdEntry 39073 }


    iqupc00ARCCtrlNoSignalARCMapping OBJECT-TYPE
        SYNTAX            INTEGER
        MAX-ACCESS        read-write
        STATUS            current
        DESCRIPTION
                "CMNT: - No signal ARC Mapping
                 TYPE: - Number
                 PAGE: - ARC Ctrl
                    No Signal ARC Mapping  cmdID= 39074
                    min= 0  max= 32  step= 1  format= 0  div_scale= 1  preset= 1
                    Min = 0  Max = 0  Step = 0  Preset = 0  "
        ::= { iqupc00CmdEntry 39074 }


    iqupc00ARCCtrlForceARCMapping OBJECT-TYPE
        SYNTAX            INTEGER
        MAX-ACCESS        read-write
        STATUS            current
        DESCRIPTION
                "CMNT: - Force ARC Mapping
                 TYPE: - Number
                 PAGE: - ARC Ctrl
                    Force ARC Mapping  cmdID= 39078
                    min= 0  max= 32  step= 1  format= 0  div_scale= 1  preset= 1
                    Min = 0  Max = 0  Step = 0  Preset = 0  "
        ::= { iqupc00CmdEntry 39078 }


    iqupc00GenlockBlankingGenlockStandard OBJECT-TYPE
        SYNTAX            INTEGER {
                            val52529i(1),
                            val62525i(2),
                            val72023p(3),
                            val72024p(4),
                            val72025p(5),
                            val72029p(6),
                            val72030p(7),
                            val72059p(8),
                            val72050p(9),
                            val72060p(10),
                            val108025i(11),
                            val108029i(12),
                            val108030i(13),
                            val108023sf(14),
                            val108024sf(15),
                            val108025sf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select std for Ref display/set
                 TYPE: - RadiobuttonList
                 PAGE: - Genlock/Blanking
                    Standard  cmdID= 37203
                    525/29i  value= 1
                    625/25i  value= 2
                    720/23p  value= 3
                    720/24p  value= 4
                    720/25p  value= 5
                    720/29p  value= 6
                    720/30p  value= 7
                    720/59p  value= 8
                    720/50p  value= 9
                    720/60p  value= 10
                    1080/25i  value= 11
                    1080/29i  value= 12
                    1080/30i  value= 13
                    1080/23sf  value= 14
                    1080/24sf  value= 15
                    1080/25sf  value= 16
                    1080/23p  value= 17
                    1080/24p  value= 18
                    1080/25p  value= 19
                    1080/29p  value= 20
                    1080/30p  value= 21
                    1080/50p  value= 22
                    1080/59p  value= 23
                    1080/60p  value= 24  "
        ::= { iqupc00CmdEntry 37203 }


    iqupc00GenlockBlankingGenlockDelayMode OBJECT-TYPE
        SYNTAX            INTEGER {
                            valFreeRun(0),
                            valLocktoReference(1),
                            valManualHV(2)
                            }
        MAX-ACCESS        read-write
        STATUS            current
        DESCRIPTION
                "CMNT: - Video Reference Mode source: Free Run/LockRef/LockRef(Delay Mismatch)/Minimum/Frames/Manual/Manual ms
                 TYPE: - RadiobuttonList
                 PAGE: - Genlock/Blanking
                    Delay Mode  cmdID= 33029
                    Free Run  value= 0
                    Lock to Reference  value= 1
                    Manual H/V  value= 2  "
        ::= { iqupc00CmdEntry 33029 }


    iqupc00GenlockSetDelayDelayFrames OBJECT-TYPE
        SYNTAX            INTEGER
        MAX-ACCESS        read-write
        STATUS            current
        DESCRIPTION
                "CMNT: - Set video delay in frames
                 TYPE: - Number
                 PAGE: - Genlock
                    Delay Frames  cmdID= 33031
                    min= 0  max= 147  step= 1  format= %0.0f frames  div_scale= 1  preset= 1
                    Min = 0 frames  Max = 147 frames  Step = 1 frames  Preset = 1 frames  "
        ::= { iqupc00CmdEntry 33031 }


    iqupc00GenlockSetDelayVerticalPhase OBJECT-TYPE
        SYNTAX            INTEGER
        MAX-ACCESS        read-write
        STATUS            current
        DESCRIPTION
                "CMNT: - Reference vertical timing
                 TYPE: - Number
                 PAGE: - Genlock
                    Vertical Phase  cmdID= 33033
                    min= -1125  max= 1125  step= 1  format= %0.0f lines  div_scale= 1  preset= 0
                    Min = -1125 lines  Max = 1125 lines  Step = 1 lines  Preset = 0 lines  "
        ::= { iqupc00CmdEntry 33033 }


    iqupc00GenlockSetDelayHorizontalPhase OBJECT-TYPE
        SYNTAX            INTEGER
        MAX-ACCESS        read-write
        STATUS            current
        DESCRIPTION
                "CMNT: - Reference horizontal timing
                 TYPE: - Number
                 PAGE: - Genlock
                    Horizontal Phase  cmdID= 33032
                    min= -4125  max= 4125  step= 1  format= %0.0f pixels  div_scale= 1  preset= 0
                    Min = -4125 pixels  Max = 4125 pixels  Step = 1 pixels  Preset = 0 pixels  "
        ::= { iqupc00CmdEntry 33032 }


    iqupc00GenlockSetDelayVerticalDelay OBJECT-TYPE
        SYNTAX            INTEGER
        MAX-ACCESS        read-write
        STATUS            current
        DESCRIPTION
                "CMNT: - Reference vertical timing
                 TYPE: - Number
                 PAGE: - Genlock
                    Vertical Delay  cmdID= 33045
                    min= 0  max= 1125  step= 1  format= %0.0f lines  div_scale= 1  preset= 0
                    Min = 0 lines  Max = 1125 lines  Step = 1 lines  Preset = 0 lines  "
        ::= { iqupc00CmdEntry 33045 }


    iqupc00GenlockSetDelayHorizontalDelay OBJECT-TYPE
        SYNTAX            INTEGER
        MAX-ACCESS        read-write
        STATUS            current
        DESCRIPTION
                "CMNT: - Reference horizontal timing
                 TYPE: - Number
                 PAGE: - Genlock
                    Horizontal Delay  cmdID= 33044
                    min= 0  max= 4125  step= 1  format= %0.0f pixels  div_scale= 1  preset= 0
                    Min = 0 pixels  Max = 4125 pixels  Step = 1 pixels  Preset = 0 pixels  "
        ::= { iqupc00CmdEntry 33044 }


    iqupc00GenlockBlankingGenlockRefLogHide OBJECT-TYPE
        SYNTAX            RollCallString
        MAX-ACCESS        read-only
        STATUS            current
        DESCRIPTION
                "CMNT: - Hide logging for Reference
                 TYPE: - Display
                 PAGE: - Genlock/Blanking
                    RefLogHide  cmdID= 33175  "
        ::= { iqupc00CmdEntry 33175 }


    iqupc00GenlockDolbyELineStandard OBJECT-TYPE
        SYNTAX            INTEGER {
                            val52529i(1),
                            val62525i(2),
                            val72023p(3),
                            val72024p(4),
                            val72025p(5),
                            val72029p(6),
                            val72030p(7),
                            val72050p(8),
                            val72059p(9),
                            val72060p(10),
                            val108025i(11),
                            val108029i(12),
                            val108030i(13),
                            val108023psf(14),
                            val108024psf(15),
                            val108025psf(16),
                            val108023p(17),
                            val108024p(18),
                            val108025p(19),
                            val108029p(20),
                            val108030p(21),
                            val108050p(22),
                            val108059p(23),
                            val108060p(24)
                            }
        MAX-ACCESS        read-write
        STATUS            current
        DESCRIPTION
                "CMNT: - Select standard to display Dolby E Auto-Line for
                 TYPE: - RadiobuttonList
                 PAGE: - Genlock
                    Standard  cmdID= 38655
                    525/29i  value= 1
                    625/25i  value= 2
                    720/23p  value= 3
                    720/24p  value= 4
                    720/25p  value= 5
                    720/29p  value= 6
                    720/30p  value= 7
                    720/50p  value= 8
                    720/59p  value= 9
                    720/60p  value= 10
                    1080/25i  value= 11
                    1080/29i  value= 12
                    1080/30i  value= 13
                    1080/23psf  value= 14
                    1080/24psf  value= 15
                    1080/25psf  value= 16
                    1080/23p  value= 17
                    1080/24p  value= 18
                    1080/25p  value= 19
                    1080/29p  value= 20
                    1080/30p  value= 21
                    1080/50p  value= 22
                    1080/59p  value= 23
                    1080/60p  value= 24  "
        ::= { iqupc00CmdEntry 38655 }


    iqupc00GenlockDolbyELineAutoLineNo OBJECT-TYPE
        SYNTAX            INTEGER
        MAX-ACCESS        read-write
        STATUS            current
        DESCRIPTION
                "CMNT: - Select standard to display Dolby E Auto-Line for
                 TYPE: - Number
                 PAGE: - Genlock
                    Auto Line No.  cmdID= 38656
                    min= 0  max= 1125  step= 1  format= %0.0f  div_scale= 1  preset= 1
                    Min = 0  Max = 1125  Step = 1  Preset = 1  "
        ::= { iqupc00CmdEntry 38656 }


    iqupc00DolbyELineUserDolbyELinePair1 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair1  cmdID= 38670
                    Default  value= 0
                    User  value= 1  "
        ::= { iqupc00CmdEntry 38670 }


    iqupc00DolbyELineUserDolbyELinePair2 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair2  cmdID= 38671
                    Default  value= 0
                    User  value= 1  "
        ::= { iqupc00CmdEntry 38671 }


    iqupc00DolbyELineUserDolbyELinePair3 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair3  cmdID= 38672
                    Default  value= 0
                    User  value= 1  "
        ::= { iqupc00CmdEntry 38672 }


    iqupc00DolbyELineUserDolbyELinePair4 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair4  cmdID= 38673
                    Default  value= 0
                    User  value= 1  "
        ::= { iqupc00CmdEntry 38673 }


    iqupc00DolbyELineUserDolbyELinePair5 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair5  cmdID= 38674
                    Default  value= 0
                    User  value= 1  "
        ::= { iqupc00CmdEntry 38674 }


    iqupc00DolbyELineUserDolbyELinePair6 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair6  cmdID= 38675
                    Default  value= 0
                    User  value= 1  "
        ::= { iqupc00CmdEntry 38675 }


    iqupc00DolbyELineUserDolbyELinePair7 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair7  cmdID= 38676
                    Default  value= 0
                    User  value= 1  "
        ::= { iqupc00CmdEntry 38676 }


    iqupc00DolbyELineUserDolbyELinePair8 OBJECT-TYPE
        SYNTAX            INTEGER {
                            valDefault(0),
                            valUser(1)
                            }
        MAX-ACCESS        read-write
        STATUS            current
        DESCRIPTION
                "CMNT: - 
                 TYPE: - RadiobuttonList
                 PAGE: - Dolby E Line
                    Pair8  cmdID= 38677
                    Default  value= 0
                    User  value= 1  "
        ::= { iqupc00CmdEntry 38677 }


    iqupc00GenlockDolbyELineUserLine525i29 OBJECT-TYPE
        SYNTAX            INTEGER
        MAX-ACCESS        read-write
        STATUS            current
        DESCRIPTION
                "CMNT: - 
                 TYPE: - Number
                 PAGE: - Genlock
                    UserLine525i29  cmdID= 38684
                    min= 1  max= 525  step= 1  format= %d  div_scale= 1  preset= 14
                    Min = 0  Max = 0  Step = 0  Preset = 0  "
        ::= { iqupc00CmdEntry 38684 }


    iqupc00GenlockDolbyELineUserLine625i25 OBJECT-TYPE
        SYNTAX            INTEGER
        MAX-ACCESS        read-write
        STATUS            current
        DESCRIPTION
                "CMNT: - 
                 TYPE: - Number
                 PAGE: - Genlock
                    UserLine625i25  cmdID= 38685
                    min= 1  max= 625  step= 1  format= %d  div_scale= 1  preset= 12
                    Min = 0  Max = 0  Step = 0  Preset = 0  "
        ::= { iqupc00CmdEntry 38685 }


    iqupc00GenlockDolbyELineUserLine720p23 OBJECT-TYPE
        SYNTAX            INTEGER
        MAX-ACCESS        read-write
        STATUS            current
        DESCRIPTION
                "CMNT: - 
                 TYPE: - Number
                 PAGE: - Genlock
                    UserLine720p23  cmdID= 38686
                    min= 1  max= 750  step= 1  format= %d  div_scale= 1  preset= 28
                    Min = 0  Max = 0  Step = 0  Preset = 0  "
        ::= { iqupc00CmdEntry 38686 }


    iqupc00GenlockDolbyELineUserLine720p24 OBJECT-TYPE
        SYNTAX            INTEGER
        MAX-ACCESS        read-write
        STATUS            current
        DESCRIPTION
                "CMNT: - 
                 TYPE: - Number
                 PAGE: - Genlock
                    UserLine720p24  cmdID= 38687
                    min= 1  max= 750  step= 1  format= %d  div_scale= 1  preset= 28
                    Min = 0  Max = 0  Step = 0  Preset = 0  "
        ::= { iqupc00CmdEntry 38687 }


    iqupc00GenlockDolbyELineUserLine720p25 OBJECT-TYPE
        SYNTAX            INTEGER
        MAX-ACCESS        read-write
        STATUS            current
        DESCRIPTION
                "CMNT: - 
                 TYPE: - Number
                 PAGE: - Genlock
                    UserLine720p25  cmdID= 38688
                    min= 1  max= 750  step= 1  format= %d  div_scale= 1  preset= 28
                    Min = 0  Max = 0  Step = 0  Preset = 0  "
        ::= { iqupc00CmdEntry 38688 }


    iqupc00GenlockDolbyELineUserLine720p29 OBJECT-TYPE
        SYNTAX            INTEGER
        MAX-ACCESS        read-write
        STATUS            current
        DESCRIPTION
                "CMNT: - 
                 TYPE: - Number
                 PAGE: - Genlock
                    UserLine720p29  cmdID= 38689
                    min= 1  max= 750  step= 1  format= %d  div_scale= 1  preset= 28
                    Min = 0  Max = 0  Step = 0  Preset = 0  "
        ::= { iqupc00CmdEntry 38689 }


    iqupc00GenlockDolbyELineUserLine720p30 OBJECT-TYPE
        SYNTAX            INTEGER
        MAX-ACCESS        read-write
        STATUS            current
        DESCRIPTION
                "CMNT: - 
                 TYPE: - Number
                 PAGE: - Genlock
                    UserLine720p30  cmdID= 38690
                    min= 1  max= 750  step= 1  format= %d  div_scale= 1  preset= 28
                    Min = 0  Max = 0  Step = 0  Preset = 0  "
        ::= { iqupc00CmdEntry 38690 }


    iqupc00GenlockDolbyELineUserLine720p50 OBJECT-TYPE
        SYNTAX            INTEGER
        MAX-ACCESS        read-write
        STATUS            current
        DESCRIPTION
                "CMNT: - 
                 TYPE: - Number
                 PAGE: - Genlock
                    UserLine720p50  cmdID= 38683
                    min= 1  max= 750  step= 1  format= %d  div_scale= 1  preset= 28
                    Min = 0  Max = 0  Step = 0  Preset = 0  "
        ::= { iqupc00CmdEntry 38683 }


    iqupc00GenlockDolbyELineUserLine720p59 OBJECT-TYPE
        SYNTAX            INTEGER
        MAX-ACCESS        read-write
        STATUS            current
        DESCRIPTION
                "CMNT: - 
                 TYPE: - Number
                 PAGE: - Genlock
                    UserLine720p59  cmdID= 38682
                    min= 1  max= 750  step= 1  format= %d  div_scale= 1  preset= 32
                    Min = 0  Max = 0  Step = 0  Preset = 0  "
        ::= { iqupc00CmdEntry 38682 }


    iqupc00GenlockDolbyELineUserLine720p60 OBJECT-TYPE
        SYNTAX            INTEGER
        MAX-ACCESS        read-write
        STATUS            current
        DESCRIPTION
                "CMNT: - 
                 TYPE: - Number
                 PAGE: - Genlock
                    UserLine720p60  cmdID= 38691
                    min= 1  max= 750  step= 1  format= %d  div_scale= 1  preset= 32
                    Min = 0  Max = 0  Step = 0  Preset = 0  "
        ::= { iqupc00CmdEntry 38691 }


    iqupc00GenlockDolbyELineUserLine1080i25 OBJECT-TYPE
        SYNTAX            INTEGER
        MAX-ACCESS        read-write
        STATUS            current
        DESCRIPTION
                "CMNT: - 
                 TYPE: - Number
                 PAGE: - Genlock
                    UserLine1080i25  cmdID= 38681
                    min= 1  max= 1125  step= 1  format= %d  div_scale= 1  preset= 21
                    Min = 0  Max = 0  Step = 0  Preset = 0  "
        ::= { iqupc00CmdEntry 38681 }


    iqupc00GenlockDolbyELineUserLine1080i29 OBJECT-TYPE
        SYNTAX            INTEGER
        MAX-ACCESS        read-write
        STATUS            current
        DESCRIPTION
                "CMNT: - 
                 TYPE: - Number
                 PAGE: - Genlock
                    UserLine1080i29  cmdID= 38680
                    min= 1  max= 1125  step= 1  format= %d  div_scale= 1  preset= 24
                    Min = 0  Max = 0  Step = 0  Preset = 0  "
        ::= { iqupc00CmdEntry 38680 }


    iqupc00GenlockDolbyELineUserLine1080i30 OBJECT-TYPE
        SYNTAX            INTEGER
        MAX-ACCESS        read-write
        STATUS            current
        DESCRIPTION
                "CMNT: - 
                 TYPE: - Number
                 PAGE: - Genlock
                    UserLine1080i30  cmdID= 38692
                    min= 1  max= 1125  step= 1  format= %d  div_scale= 1  preset= 24
                    Min = 0  Max = 0  Step = 0  Preset = 0  "
        ::= { iqupc00CmdEntry 38692 }


    iqupc00GenlockDolbyELineUserLine1080p23sf OBJECT-TYPE
        SYNTAX            INTEGER
        MAX-ACCESS        read-write
        STATUS            current
        DESCRIPTION
                "CMNT: - 
                 TYPE: - Number
                 PAGE: - Genlock
                    UserLine1080p23sf  cmdID= 38693
                    min= 1  max= 1125  step= 1  format= %d  div_scale= 1  preset= 42
                    Min = 0  Max = 0  Step = 0  Preset = 0  "
        ::= { iqupc00CmdEntry 38693 }


    iqupc00GenlockDolbyELineUserLine1080p24sf OBJECT-TYPE
        SYNTAX            INTEGER
        MAX-ACCESS        read-write
        STATUS            current
        DESCRIPTION
                "CMNT: - 
                 TYPE: - Number
                 PAGE: - Genlock
                    UserLine1080p24sf  cmdID= 38694
                    min= 1  max= 1125  step= 1  format= %d  div_scale= 1  preset= 42
                    Min = 0  Max = 0  Step = 0  Preset = 0  "
        ::= { iqupc00CmdEntry 38694 }


    iqupc00GenlockDolbyELineUserLine1080p25sf OBJECT-TYPE
        SYNTAX            INTEGER
        MAX-ACCESS        read-write
        STATUS            current
        DESCRIPTION
                "CMNT: - 
                 TYPE: - Number
                 PAGE: - Genlock
                    UserLine1080p25sf  cmdID= 38695
                    min= 1  max= 1125  step= 1  format= %d  div_scale= 1  preset= 42
                    Min = 0  Max = 0  Step = 0  Preset = 0  "
        ::= { iqupc00CmdEntry 38695 }


    iqupc00GenlockDolbyELineUserLine1080p23 OBJECT-TYPE
        SYNTAX            INTEGER
        MAX-ACCESS        read-write
        STATUS            current
        DESCRIPTION
                "CMNT: - 
                 TYPE: - Number
                 PAGE: - Genlock
                    UserLine1080p23  cmdID= 38696
                    min= 1  max= 1125  step= 1  format= %d  div_scale= 1  preset= 42
                    Min = 0  Max = 0  Step = 0  Preset = 0  "
        ::= { iqupc00CmdEntry 38696 }


    iqupc00GenlockDolbyELineUserLine1080p24 OBJECT-TYPE
        SYNTAX            INTEGER
        MAX-ACCESS        read-write
        STATUS            current
        DESCRIPTION
                "CMNT: - 
                 TYPE: - Number
                 PAGE: - Genlock
                    UserLine1080p24  cmdID= 38697
                    min= 1  max= 1125  step= 1  format= %d  div_scale= 1  preset= 42
                    Min = 0  Max = 0  Step = 0  Preset = 0  "
        ::= { iqupc00CmdEntry 38697 }


    iqupc00GenlockDolbyELineUserLine1080p25 OBJECT-TYPE
        SYNTAX            INTEGER
        MAX-ACCESS        read-write
        STATUS            current
        DESCRIPTION
                "CMNT: - 
                 TYPE: - Number
                 PAGE: - Genlock
                    UserLine1080p25  cmdID= 38698
                    min= 1  max= 1125  step= 1  format= %d  div_scale= 1  preset= 42
                    Min = 0  Max = 0  Step = 0  Preset = 0  "
        ::= { iqupc00CmdEntry 38698 }


    iqupc00GenlockDolbyELineUserLine1080p29 OBJECT-TYPE
        SYNTAX            INTEGER
        MAX-ACCESS        read-write
        STATUS            current
        DESCRIPTION
                "CMNT: - 
                 TYPE: - Number
                 PAGE: - Genlock
                    UserLine1080p29  cmdID= 38699
                    min= 1  max= 1125  step= 1  format= %d  div_scale= 1  preset= 42
                    Min = 0  Max = 0  Step = 0  Preset = 0  "
        ::= { iqupc00CmdEntry 38699 }


    iqupc00GenlockDolbyELineUserLine1080p30 OBJECT-TYPE
        SYNTAX            INTEGER
        MAX-ACCESS        read-write
        STATUS            current
        DESCRIPTION
                "CMNT: - 
                 TYPE: - Number
                 PAGE: - Genlock
                    UserLine1080p30  cmdID= 38707
                    min= 1  max= 1125  step= 1  format= %d  div_scale= 1  preset= 42
                    Min = 0  Max = 0  Step = 0  Preset = 0  "
        ::= { iqupc00CmdEntry 38707 }


    iqupc00GenlockDolbyELineUserLine1080p50 OBJECT-TYPE
        SYNTAX            INTEGER
        MAX-ACCESS        read-write
        STATUS            current
        DESCRIPTION
                "CMNT: - 
                 TYPE: - Number
                 PAGE: - Genlock
                    UserLine1080p50  cmdID= 38679
                    min= 1  max= 1125  step= 1  format= %d  div_scale= 1  preset= 42
                    Min = 0  Max = 0  Step = 0  Preset = 0  "
        ::= { iqupc00CmdEntry 38679 }


    iqupc00GenlockDolbyELineUserLine1080p59 OBJECT-TYPE
        SYNTAX            INTEGER
        MAX-ACCESS        read-write
        STATUS            current
        DESCRIPTION
                "CMNT: - 
                 TYPE: - Number
                 PAGE: - Genlock
                    UserLine1080p59  cmdID= 38780
                    min= 1  max= 1125  step= 1  format= %d  div_scale= 1  preset= 47
                    Min = 0  Max = 0  Step = 0  Preset = 0  "
        ::= { iqupc00CmdEntry 38780 }


    iqupc00GenlockDolbyELineUserLine1080p60 OBJECT-TYPE
        SYNTAX            INTEGER
        MAX-ACCESS        read-write
        STATUS            current
        DESCRIPTION
                "CMNT: - 
                 TYPE: - Number
                 PAGE: - Genlock
                    UserLine1080p60  cmdID= 38711
                    min= 1  max= 1125  step= 1  format= %d  div_scale= 1  preset= 47
                    Min = 0  Max = 0  Step = 0  Preset = 0  "
        ::= { iqupc00CmdEntry 38711 }


    iqupc00GenlockDolbyELineAutoAlign1 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign1  cmdID= 38110  "
        ::= { iqupc00CmdEntry 38110 }


    iqupc00GenlockDolbyELineAutoAlign2 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign2  cmdID= 38111  "
        ::= { iqupc00CmdEntry 38111 }


    iqupc00GenlockDolbyELineAutoAlign3 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign3  cmdID= 38112  "
        ::= { iqupc00CmdEntry 38112 }


    iqupc00GenlockDolbyELineAutoAlign4 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign4  cmdID= 38113  "
        ::= { iqupc00CmdEntry 38113 }


    iqupc00GenlockDolbyELineAutoAlign5 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign5  cmdID= 38114  "
        ::= { iqupc00CmdEntry 38114 }


    iqupc00GenlockDolbyELineAutoAlign6 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign6  cmdID= 38115  "
        ::= { iqupc00CmdEntry 38115 }


    iqupc00GenlockDolbyELineAutoAlign7 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign7  cmdID= 38116  "
        ::= { iqupc00CmdEntry 38116 }


    iqupc00GenlockDolbyELineAutoAlign8 OBJECT-TYPE
        SYNTAX            INTEGER { disable(0), enable(1)  }
        MAX-ACCESS        read-write
        STATUS            current
        DESCRIPTION
                "CMNT: - Embedded Audio Delay Auto DolbyE adjust
                 TYPE: - Checkbox
                 PAGE: - Genlock
                    AutoAlign8  cmdID= 38117  "
        ::= { iqupc00CmdEntry 38117 }


    iqupc00WSSCtrlEnableMapper OBJECT-TYPE
        SYNTAX            INTEGER { disable(0), enable(1)  }
        MAX-ACCESS        read-write
        STATUS            current
        DESCRIPTION
                "CMNT: - 
                 TYPE: - Checkbox
                 PAGE: - WSS Ctrl
                    EnableMapper  cmdID= 38747  "
        ::= { iqupc00CmdEntry 38747 }


    iqupc00WSSCtrlIPWSSSignal OBJECT-TYPE
        SYNTAX            INTEGER {
                            val43nbox169top(2),
                            val43nbox149top(3),
                            val43nbox169ctr(4),
                            val43nCodedFrame(8),
                            val43n43(9),
                            val43n169(10),
                            val43n149(11),
                            val43Reserved12(12),
                            val43n43SP149(13),
                            val43n169SP149(14),
                            val43n169SP43(15),
                            val43nUnknownAll(16),
                            val169nbox169top(130),
                            val169nbox149top(131),
                            val169nbox169ctr(132),
                            val169nCodedFrame(136),
                            val169n43(137),
                            val169n169(138),
                            val169n149(139),
                            val169Reserved12(140),
                            val169n43SP149(141),
                            val169n169SP149(142),
                            val169n169SP43(143),
                            val169nUnknownAll(144),
                            valNoSignal(145),
                            valForceMode(146)
                            }
        MAX-ACCESS        read-write
        STATUS            current
        DESCRIPTION
                "CMNT: - 
                 TYPE: - RadiobuttonList
                 PAGE: - WSS Ctrl
                    I/P WSS Signal  cmdID= 38740
                    4:3-box 16:9 top  value= 2
                    4:3-box 14:9 top  value= 3
                    4:3-box>16:9ctr  value= 4
                    4:3-Coded Frame  value= 8
                    4:3-4:3  value= 9
                    4:3-16:9  value= 10
                    4:3-14:9  value= 11
                    4:3 Reserved(12)  value= 12
                    4:3-4:3 SP 14:9  value= 13
                    4:3-16:9 SP 14:9  value= 14
                    4:3-16:9 SP 4:3  value= 15
                    4:3-Unknown(All)  value= 16
                    16:9-box 16:9 top  value= 130
                    16:9-box 14:9 top  value= 131
                    16:9-box>16:9ctr  value= 132
                    16:9-Coded Frame  value= 136
                    16:9-4:3  value= 137
                    16:9-16:9  value= 138
                    16:9-14:9  value= 139
                    16:9 Reserved(12)  value= 140
                    16:9-4:3 SP 14:9  value= 141
                    16:9-16:9 SP14:9  value= 142
                    16:9-16:9 SP 4:3  value= 143
                    16:9-Unknown(All)  value= 144
                    No Signal  value= 145
                    Force Mode  value= 146  "
        ::= { iqupc00CmdEntry 38740 }


    iqupc00WSSCtrlOPWSS43 OBJECT-TYPE
        SYNTAX            INTEGER {
                            val43nbox169top(2),
                            val43nbox149top(3),
                            val43nbox169ctr(4),
                            val43nCodedFrame(8),
                            val43n43(9),
                            val43n169(10),
                            val43n149(11),
                            val43nreservedn12(12),
                            val43n43SP149(13),
                            val43n169SP149(14),
                            val43n169SP43(15),
                            val169nbox169top(130),
                            val169nbox149top(131),
                            val169nbox169ctr(132),
                            val169nCodedFrame(136),
                            val169n43(137),
                            val169n169(138),
                            val169n149(139),
                            val169nreservedn12(140),
                            val169n43SP149(141),
                            val169n169SP149(142),
                            val169n169SP43(143)
                            }
        MAX-ACCESS        read-write
        STATUS            current
        DESCRIPTION
                "CMNT: - 
                 TYPE: - RadiobuttonList
                 PAGE: - WSS Ctrl
                    O/P WSS 4:3  cmdID= 38745
                    4:3-box 16:9 top  value= 2
                    4:3-box 14:9 top  value= 3
                    4:3-box>16:9ctr  value= 4
                    4:3-Coded Frame  value= 8
                    4:3-4:3  value= 9
                    4:3-16:9  value= 10
                    4:3-14:9  value= 11
                    4:3-reserved-12  value= 12
                    4:3-4:3 SP 14:9  value= 13
                    4:3-16:9 SP14:9  value= 14
                    4:3-16:9 SP 4:3  value= 15
                    16:9-box 16:9 top  value= 130
                    16:9-box 14:9 top  value= 131
                    16:9-box>16:9ctr  value= 132
                    16:9-Coded Frame  value= 136
                    16:9-4:3  value= 137
                    16:9-16:9  value= 138
                    16:9-14:9  value= 139
                    16:9-reserved-12  value= 140
                    16:9-4:3 SP 14:9  value= 141
                    16:9-16:9 SP14:9  value= 142
                    16:9-16:9 SP 4:3  value= 143  "
        ::= { iqupc00CmdEntry 38745 }


    iqupc00WSSCtrlDispMem43 OBJECT-TYPE
        SYNTAX            INTEGER {
                            valNoChange(0),
                            valDisplayMemory1(1),
                            valDisplayMemory2(2),
                            valDisplayMemory3(3),
                            valDisplayMemory4(4),
                            valDisplayMemory5(5),
                            valDisplayMemory6(6),
                            valDisplayMemory7(7),
                            valDisplayMemory8(8),
                            valDisplayMemory9(9),
                            valDisplayMemory10(10),
                            valDisplayMemory11(11),
                            valDisplayMemory12(12),
                            valDisplayMemory13(13),
                            valDisplayMemory14(14),
                            valDisplayMemory15(15),
                            valDisplayMemory16(16),
                            valDisplayMemory17(17),
                            valDisplayMemory18(18),
                            valDisplayMemory19(19),
                            valDisplayMemory20(20),
                            valDisplayMemory21(21),
                            valDisplayMemory22(22),
                            valDisplayMemory23(23),
                            valDisplayMemory24(24),
                            valDisplayMemory25(25),
                            valDisplayMemory26(26),
                            valDisplayMemory27(27),
                            valDisplayMemory28(28),
                            valDisplayMemory29(29),
                            valDisplayMemory30(30),
                            valDisplayMemory31(31),
                            valDisplayMemory32(32)
                            }
        MAX-ACCESS        read-write
        STATUS            current
        DESCRIPTION
                "CMNT: - 
                 TYPE: - RadiobuttonList
                 PAGE: - WSS Ctrl
                    Disp Mem 4:3  cmdID= 38748
                    No Change  value= 0
                    Display Memory 1  value= 1
                    Display Memory 2  value= 2
                    Display Memory 3  value= 3
                    Display Memory 4  value= 4
                    Display Memory 5  value= 5
                    Display Memory 6  value= 6
                    Display Memory 7  value= 7
                    Display Memory 8  value= 8
                    Display Memory 9  value= 9
                    Display Memory 10  value= 10
                    Display Memory 11  value= 11
                    Display Memory 12  value= 12
                    Display Memory 13  value= 13
                    Display Memory 14  value= 14
                    Display Memory 15  value= 15
                    Display Memory 16  value= 16
                    Display Memory 17  value= 17
                    Display Memory 18  value= 18
                    Display Memory 19  value= 19
                    Display Memory 20  value= 20
                    Display Memory 21  value= 21
                    Display Memory 22  value= 22
                    Display Memory 23  value= 23
                    Display Memory 24  value= 24
                    Display Memory 25  value= 25
                    Display Memory 26  value= 26
                    Display Memory 27  value= 27
                    Display Memory 28  value= 28
                    Display Memory 29  value= 29
                    Display Memory 30  value= 30
                    Display Memory 31  value= 31
                    Display Memory 32  value= 32  "
        ::= { iqupc00CmdEntry 38748 }


    iqupc00WSSCtrlWidescreenIP2016 OBJECT-TYPE
        SYNTAX            INTEGER { disable(0), enable(1)  }
        MAX-ACCESS        read-write
        STATUS            current
        DESCRIPTION
                "CMNT: - 
                 TYPE: - Checkbox
                 PAGE: - WSS Ctrl
                    2016  cmdID= 38724  "
        ::= { iqupc00CmdEntry 38724 }


    iqupc00WSSCtrlWidescreenIPPriority OBJECT-TYPE
        SYNTAX            INTEGER {
                            valWSS(0),
                            valVI(1)
                            }
        MAX-ACCESS        read-write
        STATUS            current
        DESCRIPTION
                "CMNT: - 
                 TYPE: - RadiobuttonList
                 PAGE: - WSS Ctrl
                    Priority  cmdID= 38750
                    WSS  value= 0
                    VI  value= 1  "
        ::= { iqupc00CmdEntry 38750 }


    iqupc00WSSCtrlWidescreenIPWSSInEnable OBJECT-TYPE
        SYNTAX            INTEGER {
                            valOff(0),
                            valWSSAFD(1),
                            valWSSETSI(2)
                            }
        MAX-ACCESS        read-write
        STATUS            current
        DESCRIPTION
                "CMNT: - 
                 TYPE: - RadiobuttonList
                 PAGE: - WSS Ctrl
                    WSS In Enable  cmdID= 38720
                    Off  value= 0
                    WSS AFD  value= 1
                    WSS ETSI  value= 2  "
        ::= { iqupc00CmdEntry 38720 }


    iqupc00WSSCtrlWidescreenIPVIInEnable OBJECT-TYPE
        SYNTAX            INTEGER {
                            valOff(0),
                            valVISMPTE(1),
                            valVIAFD(2),
                            valVIAFD2008(3)
                            }
        MAX-ACCESS        read-write
        STATUS            current
        DESCRIPTION
                "CMNT: - 
                 TYPE: - RadiobuttonList
                 PAGE: - WSS Ctrl
                    VI In Enable  cmdID= 38723
                    Off  value= 0
                    VI SMPTE  value= 1
                    VI AFD  value= 2
                    VI AFD 2008  value= 3  "
        ::= { iqupc00CmdEntry 38723 }


    iqupc00WSSCtrlWidescreenOP2016 OBJECT-TYPE
        SYNTAX            INTEGER { disable(0), enable(1)  }
        MAX-ACCESS        read-write
        STATUS            current
        DESCRIPTION
                "CMNT: - 
                 TYPE: - Checkbox
                 PAGE: - WSS Ctrl
                    2016  cmdID= 38734  "
        ::= { iqupc00CmdEntry 38734 }


    iqupc00WSSCtrlLine1ReadAFD OBJECT-TYPE
        SYNTAX            RollCallString
        MAX-ACCESS        read-only
        STATUS            current
        DESCRIPTION
                "CMNT: - SMTPE2016 Reader Line 1 AFD
                 TYPE: - Display
                 PAGE: - WSS Ctrl
                    Line1 Read AFD  cmdID= 39002  "
        ::= { iqupc00CmdEntry 39002 }


    iqupc00WSSCtrlLine1ReadAR OBJECT-TYPE
        SYNTAX            RollCallString
        MAX-ACCESS        read-only
        STATUS            current
        DESCRIPTION
                "CMNT: - SMTPE2016 Reader Line 1 AR
                 TYPE: - Display
                 PAGE: - WSS Ctrl
                    Line1 Read AR  cmdID= 39003  "
        ::= { iqupc00CmdEntry 39003 }


    iqupc00WSSCtrlLine1WriteAFD OBJECT-TYPE
        SYNTAX            RollCallString
        MAX-ACCESS        read-only
        STATUS            current
        DESCRIPTION
                "CMNT: - SMTPE2016 Writer Line 1 AFD
                 TYPE: - Display
                 PAGE: - WSS Ctrl
                    Line1 Write AFD  cmdID= 39010  "
        ::= { iqupc00CmdEntry 39010 }


    iqupc00WSSCtrlLine1WriteAR OBJECT-TYPE
        SYNTAX            RollCallString
        MAX-ACCESS        read-only
        STATUS            current
        DESCRIPTION
                "CMNT: - SMTPE2016 Writer Line 1 AR
                 TYPE: - Display
                 PAGE: - WSS Ctrl
                    Line1 Write AR  cmdID= 39011  "
        ::= { iqupc00CmdEntry 39011 }


    iqupc00WSSCtrlPreset OBJECT-TYPE
        SYNTAX            INTEGER { noAction(0),valPreset(1) }
        MAX-ACCESS        read-write
        STATUS            current
        DESCRIPTION
                "CMNT: - 
                 TYPE: - Button
                 PAGE: - WSS Ctrl
                    Preset  cmdID= 39075
                    value= 1  "
        ::= { iqupc00CmdEntry 39075 }


    iqupc00WSSCtrlPreset43 OBJECT-TYPE
        SYNTAX            INTEGER { noAction(0),valPreset43(1) }
        MAX-ACCESS        read-write
        STATUS            current
        DESCRIPTION
                "CMNT: - 
                 TYPE: - Button
                 PAGE: - WSS Ctrl
                    Preset4:3  cmdID= 39076
                    value= 1  "
        ::= { iqupc00CmdEntry 39076 }


    iqupc00WSSCtrlPreset169 OBJECT-TYPE
        SYNTAX            INTEGER { noAction(0),valPreset169(1) }
        MAX-ACCESS        read-write
        STATUS            current
        DESCRIPTION
                "CMNT: - 
                 TYPE: - Button
                 PAGE: - WSS Ctrl
                    Preset16:9  cmdID= 39077
                    value= 1  "
        ::= { iqupc00CmdEntry 39077 }


    iqupc00WSSCtrlNewNumber OBJECT-TYPE
        SYNTAX            INTEGER
        MAX-ACCESS        read-write
        STATUS            current
        DESCRIPTION
                "CMNT: - Force Input AFD store
                 TYPE: - Number
                 PAGE: - WSS Ctrl
                    New Number  cmdID= 43108
                    min= 0  max= 401  step= 1  format= %d  div_scale= 1  preset= 2
                    Min = 0  Max = 0  Step = 0  Preset = 0  "
        ::= { iqupc00CmdEntry 43108 }


    iqupc00WSSCtrlBlank62523 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank625_23  cmdID= 43228  "
        ::= { iqupc00CmdEntry 43228 }


    iqupc00WSSCtrlBlank625336 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank625_336  cmdID= 43229  "
        ::= { iqupc00CmdEntry 43229 }


    iqupc00WSSCtrlBlank52521 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_21  cmdID= 43230  "
        ::= { iqupc00CmdEntry 43230 }


    iqupc00WSSCtrlBlank52522 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_22  cmdID= 43231  "
        ::= { iqupc00CmdEntry 43231 }


    iqupc00WSSCtrlBlank525283 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_283  cmdID= 43232  "
        ::= { iqupc00CmdEntry 43232 }


    iqupc00WSSCtrlBlank525284 OBJECT-TYPE
        SYNTAX            INTEGER { disable(0), enable(1)  }
        MAX-ACCESS        read-write
        STATUS            current
        DESCRIPTION
                "CMNT: - Conversion SD blanking
                 TYPE: - Checkbox
                 PAGE: - WSS Ctrl
                    Blank525_284  cmdID= 43233  "
        ::= { iqupc00CmdEntry 43233 }


    iqupc00AncillaryDataSMPTE20162016IPF1Status OBJECT-TYPE
        SYNTAX            RollCallString
        MAX-ACCESS        read-only
        STATUS            current
        DESCRIPTION
                "CMNT: - Ancillary data SMPTE2016 input line field 1
                 TYPE: - Display
                 PAGE: - Ancillary Data
                    2016 I/P F1 Status  cmdID= 42706  "
        ::= { iqupc00CmdEntry 42706 }


    iqupc00AncillaryDataSMPTE20162016OPF1Line OBJECT-TYPE
        SYNTAX            INTEGER
        MAX-ACCESS        read-write
        STATUS            current
        DESCRIPTION
                "CMNT: - Ancillary data SMPTE2016 output line field 1
                 TYPE: - Number
                 PAGE: - Ancillary Data
                    2016 O/P F1 Line  cmdID= 42707
                    min= 0  max= 63  step= 1  format= Line %0.0f  div_scale= 1  preset= 1
                    Min = Line 0  Max = Line 63  Step = Line 1  Preset = Line 1  "
        ::= { iqupc00CmdEntry 42707 }


    iqupc00AncillaryDataSMPTE20162016OPF2Line OBJECT-TYPE
        SYNTAX            INTEGER
        MAX-ACCESS        read-write
        STATUS            current
        DESCRIPTION
                "CMNT: - Ancillary data SMPTE2016 output line field 2
                 TYPE: - Number
                 PAGE: - Ancillary Data
                    2016 O/P F2 Line  cmdID= 42746
                    min= 0  max= 31  step= 1  format= Line %0.0f  div_scale= 1  preset= 1
                    Min = Line 0  Max = Line 31  Step = Line 1  Preset = Line 1  "
        ::= { iqupc00CmdEntry 42746 }


    iqupc00AncillaryDataSMPTE20162016Follow OBJECT-TYPE
        SYNTAX            INTEGER { disable(0), enable(1)  }
        MAX-ACCESS        read-write
        STATUS            current
        DESCRIPTION
                "CMNT: - Ancillary data SMPTE2016 follow input line
                 TYPE: - Checkbox
                 PAGE: - Ancillary Data
                    2016 Follow  cmdID= 42729  "
        ::= { iqupc00CmdEntry 42729 }


    iqupc00AncillaryDataSDVBILine7 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 7  cmdID= 42708
                    Off  value= 0
                    VI  value= 1
                    WSS  value= 2  "
        ::= { iqupc00CmdEntry 42708 }


    iqupc00AncillaryDataSDVBILine8 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 8  cmdID= 42709
                    Off  value= 0
                    VI  value= 1
                    WSS  value= 2  "
        ::= { iqupc00CmdEntry 42709 }


    iqupc00AncillaryDataSDVBILine9 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 9  cmdID= 42710
                    Off  value= 0
                    VI  value= 1
                    WSS  value= 2  "
        ::= { iqupc00CmdEntry 42710 }


    iqupc00AncillaryDataSDVBILine10 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 10  cmdID= 42711
                    Off  value= 0
                    VI  value= 1
                    WSS  value= 2  "
        ::= { iqupc00CmdEntry 42711 }


    iqupc00AncillaryDataSDVBILine11 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 11  cmdID= 42712
                    Off  value= 0
                    VI  value= 1
                    WSS  value= 2  "
        ::= { iqupc00CmdEntry 42712 }


    iqupc00AncillaryDataSDVBILine12 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 12  cmdID= 42713
                    Off  value= 0
                    VI  value= 1
                    WSS  value= 2  "
        ::= { iqupc00CmdEntry 42713 }


    iqupc00AncillaryDataSDVBILine13 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 13  cmdID= 42714
                    Off  value= 0
                    VI  value= 1
                    WSS  value= 2  "
        ::= { iqupc00CmdEntry 42714 }


    iqupc00AncillaryDataSDVBILine14 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 14  cmdID= 42715
                    Off  value= 0
                    VI  value= 1
                    WSS  value= 2  "
        ::= { iqupc00CmdEntry 42715 }


    iqupc00AncillaryDataSDVBILine15 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 15  cmdID= 42716
                    Off  value= 0
                    VI  value= 1
                    WSS  value= 2  "
        ::= { iqupc00CmdEntry 42716 }


    iqupc00AncillaryDataSDVBILine16 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 16  cmdID= 42717
                    Off  value= 0
                    VI  value= 1
                    WSS  value= 2  "
        ::= { iqupc00CmdEntry 42717 }


    iqupc00AncillaryDataSDVBILine17 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 17  cmdID= 42718
                    Off  value= 0
                    VI  value= 1
                    WSS  value= 2  "
        ::= { iqupc00CmdEntry 42718 }


    iqupc00AncillaryDataSDVBILine18 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 18  cmdID= 42719
                    Off  value= 0
                    VI  value= 1
                    WSS  value= 2  "
        ::= { iqupc00CmdEntry 42719 }


    iqupc00AncillaryDataSDVBILine19 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 19  cmdID= 42720
                    Off  value= 0
                    VI  value= 1
                    WSS  value= 2  "
        ::= { iqupc00CmdEntry 42720 }


    iqupc00AncillaryDataSDVBILine20 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 20  cmdID= 42721
                    Off  value= 0
                    VI  value= 1
                    WSS  value= 2  "
        ::= { iqupc00CmdEntry 42721 }


    iqupc00AncillaryDataSDVBILine21 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 21  cmdID= 42722
                    Off  value= 0
                    VI  value= 1
                    WSS  value= 2  "
        ::= { iqupc00CmdEntry 42722 }


    iqupc00AncillaryDataSDVBILine22 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 22  cmdID= 42723
                    Off  value= 0
                    VI  value= 1
                    WSS  value= 2  "
        ::= { iqupc00CmdEntry 42723 }


    iqupc00AncillaryDataSDVBILine23 OBJECT-TYPE
        SYNTAX            INTEGER {
                            valOff(0),
                            valVI(1),
                            valWSS(2)
                            }
        MAX-ACCESS        read-write
        STATUS            current
        DESCRIPTION
                "CMNT: - 
                 TYPE: - RadiobuttonList
                 PAGE: - Ancillary Data
                    Line 23  cmdID= 42724
                    Off  value= 0
                    VI  value= 1
                    WSS  value= 2  "
        ::= { iqupc00CmdEntry 42724 }


    iqupc00AncillaryDataSDVBIVIIPStatus OBJECT-TYPE
        SYNTAX            INTEGER { disable(0), enable(1)  }
        MAX-ACCESS        read-write
        STATUS            current
        DESCRIPTION
                "CMNT: - Ancillary data video index present
                 TYPE: - Checkbox
                 PAGE: - Ancillary Data
                    VI I/P Status  cmdID= 42744  "
        ::= { iqupc00CmdEntry 42744 }


    iqupc00AncillaryDataSDVBIWSSIPStatus OBJECT-TYPE
        SYNTAX            INTEGER { disable(0), enable(1)  }
        MAX-ACCESS        read-write
        STATUS            current
        DESCRIPTION
                "CMNT: - Ancillary data wide screen signalling present
                 TYPE: - Checkbox
                 PAGE: - Ancillary Data
                    WSS I/P Status  cmdID= 42740  "
        ::= { iqupc00CmdEntry 42740 }


    iqupc00AncillaryDataSDVBIVITCIPStatus OBJECT-TYPE
        SYNTAX            INTEGER { disable(0), enable(1)  }
        MAX-ACCESS        read-write
        STATUS            current
        DESCRIPTION
                "CMNT: - Ancillary data vertical interval time code present
                 TYPE: - Checkbox
                 PAGE: - Ancillary Data
                    VITC I/P Status  cmdID= 42742  "
        ::= { iqupc00CmdEntry 42742 }


    iqupc00AncillaryDataSDVBIWSTIPStatus OBJECT-TYPE
        SYNTAX            INTEGER { disable(0), enable(1)  }
        MAX-ACCESS        read-write
        STATUS            current
        DESCRIPTION
                "CMNT: - Ancillary data world system teletext present
                 TYPE: - Checkbox
                 PAGE: - Ancillary Data
                    WST I/P Status  cmdID= 42741  "
        ::= { iqupc00CmdEntry 42741 }


    iqupc00AncillaryDataSDVBICC608IPStatus OBJECT-TYPE
        SYNTAX            INTEGER { disable(0), enable(1)  }
        MAX-ACCESS        read-write
        STATUS            current
        DESCRIPTION
                "CMNT: - Ancillary data closed caption CC608 present
                 TYPE: - Checkbox
                 PAGE: - Ancillary Data
                    CC608 I/P Status  cmdID= 42743  "
        ::= { iqupc00CmdEntry 42743 }


    iqupc00AncillaryDataHDVANCATCEnable OBJECT-TYPE
        SYNTAX            INTEGER { disable(0), enable(1)  }
        MAX-ACCESS        read-write
        STATUS            current
        DESCRIPTION
                "CMNT: - Ancillary time code enable output
                 TYPE: - Checkbox
                 PAGE: - Ancillary Data
                    ATC Enable  cmdID= 42702  "
        ::= { iqupc00CmdEntry 42702 }


    iqupc00AncillaryDataHDVANCATCIPF1Line OBJECT-TYPE
        SYNTAX            RollCallString
        MAX-ACCESS        read-only
        STATUS            current
        DESCRIPTION
                "CMNT: - Ancillary time code input line field 1
                 TYPE: - Display
                 PAGE: - Ancillary Data
                    ATC I/P F1 Line  cmdID= 42705  "
        ::= { iqupc00CmdEntry 42705 }


    iqupc00AncillaryDataHDVANCATCOPF1Line OBJECT-TYPE
        SYNTAX            INTEGER
        MAX-ACCESS        read-write
        STATUS            current
        DESCRIPTION
                "CMNT: - Ancillary time code output line field 1
                 TYPE: - Number
                 PAGE: - Ancillary Data
                    ATC O/P F1 Line  cmdID= 42703
                    min= 0  max= 63  step= 1  format= Line %0.0f  div_scale= 1  preset= 2
                    Min = Line 0  Max = Line 63  Step = Line 1  Preset = Line 2  "
        ::= { iqupc00CmdEntry 42703 }


    iqupc00AncillaryDataHDVANCATCOPF2Line OBJECT-TYPE
        SYNTAX            INTEGER
        MAX-ACCESS        read-write
        STATUS            current
        DESCRIPTION
                "CMNT: - Ancillary time code output line field 2
                 TYPE: - Number
                 PAGE: - Ancillary Data
                    ATC O/P F2 Line  cmdID= 42748
                    min= 0  max= 31  step= 1  format= Line %0.0f  div_scale= 1  preset= 2
                    Min = Line 0  Max = Line 31  Step = Line 1  Preset = Line 2  "
        ::= { iqupc00CmdEntry 42748 }


    iqupc00AncillaryDataHDVANCATCFollow OBJECT-TYPE
        SYNTAX            INTEGER { disable(0), enable(1)  }
        MAX-ACCESS        read-write
        STATUS            current
        DESCRIPTION
                "CMNT: - Ancillary time code follow input line
                 TYPE: - Checkbox
                 PAGE: - Ancillary Data
                    ATC Follow  cmdID= 42704  "
        ::= { iqupc00CmdEntry 42704 }


    iqupc00AncillaryDataHDVANCHDCaptionEnable OBJECT-TYPE
        SYNTAX            INTEGER { disable(0), enable(1)  }
        MAX-ACCESS        read-write
        STATUS            current
        DESCRIPTION
                "CMNT: - Ancillary data closed caption CC708 enable output
                 TYPE: - Checkbox
                 PAGE: - Ancillary Data
                    HD Caption Enable  cmdID= 42701  "
        ::= { iqupc00CmdEntry 42701 }


    iqupc00AncillaryDataHDVANCHDCaptionIPLine OBJECT-TYPE
        SYNTAX            RollCallString
        MAX-ACCESS        read-only
        STATUS            current
        DESCRIPTION
                "CMNT: - Ancillary data closed caption CC708 input line
                 TYPE: - Display
                 PAGE: - Ancillary Data
                    HD Caption I/P Line  cmdID= 42726  "
        ::= { iqupc00CmdEntry 42726 }


    iqupc00AncillaryDataHDVANCHDCaptionOPLine OBJECT-TYPE
        SYNTAX            INTEGER
        MAX-ACCESS        read-write
        STATUS            current
        DESCRIPTION
                "CMNT: - Ancillary data closed caption CC708 output line
                 TYPE: - Number
                 PAGE: - Ancillary Data
                    HD Caption O/P Line  cmdID= 42725
                    min= 0  max= 63  step= 1  format= Line %0.0f  div_scale= 1  preset= 3
                    Min = Line 0  Max = Line 63  Step = Line 1  Preset = Line 3  "
        ::= { iqupc00CmdEntry 42725 }


    iqupc00HDVANCHDCaptionHDFollowIPLine OBJECT-TYPE
        SYNTAX            INTEGER { disable(0), enable(1)  }
        MAX-ACCESS        read-write
        STATUS            current
        DESCRIPTION
                "CMNT: - Ancillary data closed caption CC708 follow input
                 TYPE: - Checkbox
                 PAGE: - HD VANC
                    HD Follow I/P Line  cmdID= 42700  "
        ::= { iqupc00CmdEntry 42700 }


    iqupc00AudioInputDisembed18Disembed11procamp OBJECT-TYPE
        SYNTAX            INTEGER
        MAX-ACCESS        read-write
        STATUS            current
        DESCRIPTION
                "CMNT: - Disembed Proc Amp Gain
                 TYPE: - Number
                 PAGE: - AudioInput
                    Disembed1_1_procamp  cmdID= 40000
                    min= -801  max= 120  step= 1  format= %0.1f dB  div_scale= 10  preset= 0
                    Min = -80.1 dB  Max = 12.0 dB  Step = 0.1 dB  Preset = 0.0 dB  "
        ::= { iqupc00CmdEntry 40000 }


    iqupc00AudioInputDisembed18Disembed12procamp OBJECT-TYPE
        SYNTAX            INTEGER
        MAX-ACCESS        read-write
        STATUS            current
        DESCRIPTION
                "CMNT: - Disembed Proc Amp Gain
                 TYPE: - Number
                 PAGE: - AudioInput
                    Disembed1_2_procamp  cmdID= 40001
                    min= -801  max= 120  step= 1  format= %0.1f dB  div_scale= 10  preset= 0
                    Min = -80.1 dB  Max = 12.0 dB  Step = 0.1 dB  Preset = 0.0 dB  "
        ::= { iqupc00CmdEntry 40001 }


    iqupc00Disembed18Disembed1Mute11 OBJECT-TYPE
        SYNTAX            INTEGER { disable(0), enable(1)  }
        MAX-ACCESS        read-write
        STATUS            current
        DESCRIPTION
                "CMNT: - 
                 TYPE: - Checkbox
                 PAGE: - Disembed1-8
                    Mute1_1  cmdID= 40032  "
        ::= { iqupc00CmdEntry 40032 }


    iqupc00Disembed18Disembed1Mute12 OBJECT-TYPE
        SYNTAX            INTEGER { disable(0), enable(1)  }
        MAX-ACCESS        read-write
        STATUS            current
        DESCRIPTION
                "CMNT: - 
                 TYPE: - Checkbox
                 PAGE: - Disembed1-8
                    Mute1_2  cmdID= 40033  "
        ::= { iqupc00CmdEntry 40033 }


    iqupc00Disembed18Disembed1Stereo1 OBJECT-TYPE
        SYNTAX            INTEGER { disable(0), enable(1)  }
        MAX-ACCESS        read-write
        STATUS            current
        DESCRIPTION
                "CMNT: - 
                 TYPE: - Checkbox
                 PAGE: - Disembed1-8
                    Stereo1  cmdID= 40048  "
        ::= { iqupc00CmdEntry 40048 }


    iqupc00AudioInputDisembed18Disembed11invert OBJECT-TYPE
        SYNTAX            INTEGER { disable(0), enable(1)  }
        MAX-ACCESS        read-write
        STATUS            current
        DESCRIPTION
                "CMNT: - 
                 TYPE: - Checkbox
                 PAGE: - AudioInput
                    Disembed1_1_invert  cmdID= 40016  "
        ::= { iqupc00CmdEntry 40016 }


    iqupc00AudioInputDisembed18Disembed12invert OBJECT-TYPE
        SYNTAX            INTEGER { disable(0), enable(1)  }
        MAX-ACCESS        read-write
        STATUS            current
        DESCRIPTION
                "CMNT: - 
                 TYPE: - Checkbox
                 PAGE: - AudioInput
                    Disembed1_2_invert  cmdID= 40017  "
        ::= { iqupc00CmdEntry 40017 }


    iqupc00Disembed18Disembed1dolbyLine OBJECT-TYPE
        SYNTAX            RollCallString
        MAX-ACCESS        read-only
        STATUS            current
        DESCRIPTION
                "CMNT: - 
                 TYPE: - Display
                 PAGE: - Disembed1-8
                    dolbyLine  cmdID= 40073  "
        ::= { iqupc00CmdEntry 40073 }


    iqupc00AudioInputDisembed18Disembed21procamp OBJECT-TYPE
        SYNTAX            INTEGER
        MAX-ACCESS        read-write
        STATUS            current
        DESCRIPTION
                "CMNT: - Disembed Proc Amp Gain
                 TYPE: - Number
                 PAGE: - AudioInput
                    Disembed2_1_procamp  cmdID= 40002
                    min= -801  max= 120  step= 1  format= %0.1f dB  div_scale= 10  preset= 0
                    Min = -80.1 dB  Max = 12.0 dB  Step = 0.1 dB  Preset = 0.0 dB  "
        ::= { iqupc00CmdEntry 40002 }


    iqupc00AudioInputDisembed18Disembed22procamp OBJECT-TYPE
        SYNTAX            INTEGER
        MAX-ACCESS        read-write
        STATUS            current
        DESCRIPTION
                "CMNT: - Disembed Proc Amp Gain
                 TYPE: - Number
                 PAGE: - AudioInput
                    Disembed2_2_procamp  cmdID= 40003
                    min= -801  max= 120  step= 1  format= %0.1f dB  div_scale= 10  preset= 0
                    Min = -80.1 dB  Max = 12.0 dB  Step = 0.1 dB  Preset = 0.0 dB  "
        ::= { iqupc00CmdEntry 40003 }


    iqupc00Disembed18Disembed2Mute21 OBJECT-TYPE
        SYNTAX            INTEGER { disable(0), enable(1)  }
        MAX-ACCESS        read-write
        STATUS            current
        DESCRIPTION
                "CMNT: - 
                 TYPE: - Checkbox
                 PAGE: - Disembed1-8
                    Mute2_1  cmdID= 40034  "
        ::= { iqupc00CmdEntry 40034 }


    iqupc00Disembed18Disembed2Mute22 OBJECT-TYPE
        SYNTAX            INTEGER { disable(0), enable(1)  }
        MAX-ACCESS        read-write
        STATUS            current
        DESCRIPTION
                "CMNT: - 
                 TYPE: - Checkbox
                 PAGE: - Disembed1-8
                    Mute2_2  cmdID= 40035  "
        ::= { iqupc00CmdEntry 40035 }


    iqupc00Disembed18Disembed2Stereo2 OBJECT-TYPE
        SYNTAX            INTEGER { disable(0), enable(1)  }
        MAX-ACCESS        read-write
        STATUS            current
        DESCRIPTION
                "CMNT: - 
                 TYPE: - Checkbox
                 PAGE: - Disembed1-8
                    Stereo2  cmdID= 40049  "
        ::= { iqupc00CmdEntry 40049 }


    iqupc00AudioInputDisembed18Disembed21invert OBJECT-TYPE
        SYNTAX            INTEGER { disable(0), enable(1)  }
        MAX-ACCESS        read-write
        STATUS            current
        DESCRIPTION
                "CMNT: - 
                 TYPE: - Checkbox
                 PAGE: - AudioInput
                    Disembed2_1_invert  cmdID= 40018  "
        ::= { iqupc00CmdEntry 40018 }


    iqupc00AudioInputDisembed18Disembed22invert OBJECT-TYPE
        SYNTAX            INTEGER { disable(0), enable(1)  }
        MAX-ACCESS        read-write
        STATUS            current
        DESCRIPTION
                "CMNT: - 
                 TYPE: - Checkbox
                 PAGE: - AudioInput
                    Disembed2_2_invert  cmdID= 40019  "
        ::= { iqupc00CmdEntry 40019 }


    iqupc00Disembed18Disembed2dolbyLine OBJECT-TYPE
        SYNTAX            RollCallString
        MAX-ACCESS        read-only
        STATUS            current
        DESCRIPTION
                "CMNT: - 
                 TYPE: - Display
                 PAGE: - Disembed1-8
                    dolbyLine  cmdID= 40074  "
        ::= { iqupc00CmdEntry 40074 }


    iqupc00AudioInputDisembed18Disembed31procamp OBJECT-TYPE
        SYNTAX            INTEGER
        MAX-ACCESS        read-write
        STATUS            current
        DESCRIPTION
                "CMNT: - Disembed Proc Amp Gain
                 TYPE: - Number
                 PAGE: - AudioInput
                    Disembed3_1_procamp  cmdID= 40004
                    min= -801  max= 120  step= 1  format= %0.1f dB  div_scale= 10  preset= 0
                    Min = -80.1 dB  Max = 12.0 dB  Step = 0.1 dB  Preset = 0.0 dB  "
        ::= { iqupc00CmdEntry 40004 }


    iqupc00AudioInputDisembed18Disembed32procamp OBJECT-TYPE
        SYNTAX            INTEGER
        MAX-ACCESS        read-write
        STATUS            current
        DESCRIPTION
                "CMNT: - Disembed Proc Amp Gain
                 TYPE: - Number
                 PAGE: - AudioInput
                    Disembed3_2_procamp  cmdID= 40005
                    min= -801  max= 120  step= 1  format= %0.1f dB  div_scale= 10  preset= 0
                    Min = -80.1 dB  Max = 12.0 dB  Step = 0.1 dB  Preset = 0.0 dB  "
        ::= { iqupc00CmdEntry 40005 }


    iqupc00Disembed18Disembed3Mute31 OBJECT-TYPE
        SYNTAX            INTEGER { disable(0), enable(1)  }
        MAX-ACCESS        read-write
        STATUS            current
        DESCRIPTION
                "CMNT: - 
                 TYPE: - Checkbox
                 PAGE: - Disembed1-8
                    Mute3_1  cmdID= 40036  "
        ::= { iqupc00CmdEntry 40036 }


    iqupc00Disembed18Disembed3Mute32 OBJECT-TYPE
        SYNTAX            INTEGER { disable(0), enable(1)  }
        MAX-ACCESS        read-write
        STATUS            current
        DESCRIPTION
                "CMNT: - 
                 TYPE: - Checkbox
                 PAGE: - Disembed1-8
                    Mute3_2  cmdID= 40037  "
        ::= { iqupc00CmdEntry 40037 }


    iqupc00Disembed18Disembed3Stereo3 OBJECT-TYPE
        SYNTAX            INTEGER { disable(0), enable(1)  }
        MAX-ACCESS        read-write
        STATUS            current
        DESCRIPTION
                "CMNT: - 
                 TYPE: - Checkbox
                 PAGE: - Disembed1-8
                    Stereo3  cmdID= 40050  "
        ::= { iqupc00CmdEntry 40050 }


    iqupc00AudioInputDisembed18Disembed31invert OBJECT-TYPE
        SYNTAX            INTEGER { disable(0), enable(1)  }
        MAX-ACCESS        read-write
        STATUS            current
        DESCRIPTION
                "CMNT: - 
                 TYPE: - Checkbox
                 PAGE: - AudioInput
                    Disembed3_1_invert  cmdID= 40020  "
        ::= { iqupc00CmdEntry 40020 }


    iqupc00AudioInputDisembed18Disembed32invert OBJECT-TYPE
        SYNTAX            INTEGER { disable(0), enable(1)  }
        MAX-ACCESS        read-write
        STATUS            current
        DESCRIPTION
                "CMNT: - 
                 TYPE: - Checkbox
                 PAGE: - AudioInput
                    Disembed3_2_invert  cmdID= 40021  "
        ::= { iqupc00CmdEntry 40021 }


    iqupc00Disembed18Disembed3dolbyLine OBJECT-TYPE
        SYNTAX            RollCallString
        MAX-ACCESS        read-only
        STATUS            current
        DESCRIPTION
                "CMNT: - 
                 TYPE: - Display
                 PAGE: - Disembed1-8
                    dolbyLine  cmdID= 40075  "
        ::= { iqupc00CmdEntry 40075 }


    iqupc00AudioInputDisembed18Disembed41procamp OBJECT-TYPE
        SYNTAX            INTEGER
        MAX-ACCESS        read-write
        STATUS            current
        DESCRIPTION
                "CMNT: - Disembed Proc Amp Gain
                 TYPE: - Number
                 PAGE: - AudioInput
                    Disembed4_1_procamp  cmdID= 40006
                    min= -801  max= 120  step= 1  format= %0.1f dB  div_scale= 10  preset= 0
                    Min = -80.1 dB  Max = 12.0 dB  Step = 0.1 dB  Preset = 0.0 dB  "
        ::= { iqupc00CmdEntry 40006 }


    iqupc00AudioInputDisembed18Disembed42procamp OBJECT-TYPE
        SYNTAX            INTEGER
        MAX-ACCESS        read-write
        STATUS            current
        DESCRIPTION
                "CMNT: - Disembed Proc Amp Gain
                 TYPE: - Number
                 PAGE: - AudioInput
                    Disembed4_2_procamp  cmdID= 40007
                    min= -801  max= 120  step= 1  format= %0.1f dB  div_scale= 10  preset= 0
                    Min = -80.1 dB  Max = 12.0 dB  Step = 0.1 dB  Preset = 0.0 dB  "
        ::= { iqupc00CmdEntry 40007 }


    iqupc00Disembed18Disembed4Mute41 OBJECT-TYPE
        SYNTAX            INTEGER { disable(0), enable(1)  }
        MAX-ACCESS        read-write
        STATUS            current
        DESCRIPTION
                "CMNT: - 
                 TYPE: - Checkbox
                 PAGE: - Disembed1-8
                    Mute4_1  cmdID= 40038  "
        ::= { iqupc00CmdEntry 40038 }


    iqupc00Disembed18Disembed4Mute42 OBJECT-TYPE
        SYNTAX            INTEGER { disable(0), enable(1)  }
        MAX-ACCESS        read-write
        STATUS            current
        DESCRIPTION
                "CMNT: - 
                 TYPE: - Checkbox
                 PAGE: - Disembed1-8
                    Mute4_2  cmdID= 40039  "
        ::= { iqupc00CmdEntry 40039 }


    iqupc00Disembed18Disembed4Stereo4 OBJECT-TYPE
        SYNTAX            INTEGER { disable(0), enable(1)  }
        MAX-ACCESS        read-write
        STATUS            current
        DESCRIPTION
                "CMNT: - 
                 TYPE: - Checkbox
                 PAGE: - Disembed1-8
                    Stereo4  cmdID= 40051  "
        ::= { iqupc00CmdEntry 40051 }


    iqupc00AudioInputDisembed18Disembed41invert OBJECT-TYPE
        SYNTAX            INTEGER { disable(0), enable(1)  }
        MAX-ACCESS        read-write
        STATUS            current
        DESCRIPTION
                "CMNT: - 
                 TYPE: - Checkbox
                 PAGE: - AudioInput
                    Disembed4_1_invert  cmdID= 40022  "
        ::= { iqupc00CmdEntry 40022 }


    iqupc00AudioInputDisembed18Disembed42invert OBJECT-TYPE
        SYNTAX            INTEGER { disable(0), enable(1)  }
        MAX-ACCESS        read-write
        STATUS            current
        DESCRIPTION
                "CMNT: - 
                 TYPE: - Checkbox
                 PAGE: - AudioInput
                    Disembed4_2_invert  cmdID= 40023  "
        ::= { iqupc00CmdEntry 40023 }


    iqupc00Disembed18Disembed4dolbyLine OBJECT-TYPE
        SYNTAX            RollCallString
        MAX-ACCESS        read-only
        STATUS            current
        DESCRIPTION
                "CMNT: - 
                 TYPE: - Display
                 PAGE: - Disembed1-8
                    dolbyLine  cmdID= 40076  "
        ::= { iqupc00CmdEntry 40076 }


    iqupc00AudioInputDisembed18Disembed51procamp OBJECT-TYPE
        SYNTAX            INTEGER
        MAX-ACCESS        read-write
        STATUS            current
        DESCRIPTION
                "CMNT: - Disembed Proc Amp Gain
                 TYPE: - Number
                 PAGE: - AudioInput
                    Disembed5_1_procamp  cmdID= 40008
                    min= -801  max= 120  step= 1  format= %0.1f dB  div_scale= 10  preset= 0
                    Min = -80.1 dB  Max = 12.0 dB  Step = 0.1 dB  Preset = 0.0 dB  "
        ::= { iqupc00CmdEntry 40008 }


    iqupc00AudioInputDisembed18Disembed52procamp OBJECT-TYPE
        SYNTAX            INTEGER
        MAX-ACCESS        read-write
        STATUS            current
        DESCRIPTION
                "CMNT: - Disembed Proc Amp Gain
                 TYPE: - Number
                 PAGE: - AudioInput
                    Disembed5_2_procamp  cmdID= 40009
                    min= -801  max= 120  step= 1  format= %0.1f dB  div_scale= 10  preset= 0
                    Min = -80.1 dB  Max = 12.0 dB  Step = 0.1 dB  Preset = 0.0 dB  "
        ::= { iqupc00CmdEntry 40009 }


    iqupc00Disembed18Disembed5Mute51 OBJECT-TYPE
        SYNTAX            INTEGER { disable(0), enable(1)  }
        MAX-ACCESS        read-write
        STATUS            current
        DESCRIPTION
                "CMNT: - 
                 TYPE: - Checkbox
                 PAGE: - Disembed1-8
                    Mute5_1  cmdID= 40040  "
        ::= { iqupc00CmdEntry 40040 }


    iqupc00Disembed18Disembed5Mute52 OBJECT-TYPE
        SYNTAX            INTEGER { disable(0), enable(1)  }
        MAX-ACCESS        read-write
        STATUS            current
        DESCRIPTION
                "CMNT: - 
                 TYPE: - Checkbox
                 PAGE: - Disembed1-8
                    Mute5_2  cmdID= 40041  "
        ::= { iqupc00CmdEntry 40041 }


    iqupc00Disembed18Disembed5Stereo5 OBJECT-TYPE
        SYNTAX            INTEGER { disable(0), enable(1)  }
        MAX-ACCESS        read-write
        STATUS            current
        DESCRIPTION
                "CMNT: - 
                 TYPE: - Checkbox
                 PAGE: - Disembed1-8
                    Stereo5  cmdID= 40052  "
        ::= { iqupc00CmdEntry 40052 }


    iqupc00AudioInputDisembed18Disembed51invert OBJECT-TYPE
        SYNTAX            INTEGER { disable(0), enable(1)  }
        MAX-ACCESS        read-write
        STATUS            current
        DESCRIPTION
                "CMNT: - 
                 TYPE: - Checkbox
                 PAGE: - AudioInput
                    Disembed5_1_invert  cmdID= 40024  "
        ::= { iqupc00CmdEntry 40024 }


    iqupc00AudioInputDisembed18Disembed52invert OBJECT-TYPE
        SYNTAX            INTEGER { disable(0), enable(1)  }
        MAX-ACCESS        read-write
        STATUS            current
        DESCRIPTION
                "CMNT: - 
                 TYPE: - Checkbox
                 PAGE: - AudioInput
                    Disembed5_2_invert  cmdID= 40025  "
        ::= { iqupc00CmdEntry 40025 }


    iqupc00Disembed18Disembed5dolbyLine OBJECT-TYPE
        SYNTAX            RollCallString
        MAX-ACCESS        read-only
        STATUS            current
        DESCRIPTION
                "CMNT: - 
                 TYPE: - Display
                 PAGE: - Disembed1-8
                    dolbyLine  cmdID= 40077  "
        ::= { iqupc00CmdEntry 40077 }


    iqupc00AudioInputDisembed18Disembed61procamp OBJECT-TYPE
        SYNTAX            INTEGER
        MAX-ACCESS        read-write
        STATUS            current
        DESCRIPTION
                "CMNT: - Disembed Proc Amp Gain
                 TYPE: - Number
                 PAGE: - AudioInput
                    Disembed6_1_procamp  cmdID= 40010
                    min= -801  max= 120  step= 1  format= %0.1f dB  div_scale= 10  preset= 0
                    Min = -80.1 dB  Max = 12.0 dB  Step = 0.1 dB  Preset = 0.0 dB  "
        ::= { iqupc00CmdEntry 40010 }


    iqupc00AudioInputDisembed18Disembed62procamp OBJECT-TYPE
        SYNTAX            INTEGER
        MAX-ACCESS        read-write
        STATUS            current
        DESCRIPTION
                "CMNT: - Disembed Proc Amp Gain
                 TYPE: - Number
                 PAGE: - AudioInput
                    Disembed6_2_procamp  cmdID= 40011
                    min= -801  max= 120  step= 1  format= %0.1f dB  div_scale= 10  preset= 0
                    Min = -80.1 dB  Max = 12.0 dB  Step = 0.1 dB  Preset = 0.0 dB  "
        ::= { iqupc00CmdEntry 40011 }


    iqupc00Disembed18Disembed6Mute61 OBJECT-TYPE
        SYNTAX            INTEGER { disable(0), enable(1)  }
        MAX-ACCESS        read-write
        STATUS            current
        DESCRIPTION
                "CMNT: - 
                 TYPE: - Checkbox
                 PAGE: - Disembed1-8
                    Mute6_1  cmdID= 40042  "
        ::= { iqupc00CmdEntry 40042 }


    iqupc00Disembed18Disembed6Mute62 OBJECT-TYPE
        SYNTAX            INTEGER { disable(0), enable(1)  }
        MAX-ACCESS        read-write
        STATUS            current
        DESCRIPTION
                "CMNT: - 
                 TYPE: - Checkbox
                 PAGE: - Disembed1-8
                    Mute6_2  cmdID= 40043  "
        ::= { iqupc00CmdEntry 40043 }


    iqupc00Disembed18Disembed6Stereo6 OBJECT-TYPE
        SYNTAX            INTEGER { disable(0), enable(1)  }
        MAX-ACCESS        read-write
        STATUS            current
        DESCRIPTION
                "CMNT: - 
                 TYPE: - Checkbox
                 PAGE: - Disembed1-8
                    Stereo6  cmdID= 40053  "
        ::= { iqupc00CmdEntry 40053 }


    iqupc00AudioInputDisembed18Disembed61invert OBJECT-TYPE
        SYNTAX            INTEGER { disable(0), enable(1)  }
        MAX-ACCESS        read-write
        STATUS            current
        DESCRIPTION
                "CMNT: - 
                 TYPE: - Checkbox
                 PAGE: - AudioInput
                    Disembed6_1_invert  cmdID= 40026  "
        ::= { iqupc00CmdEntry 40026 }


    iqupc00AudioInputDisembed18Disembed62invert OBJECT-TYPE
        SYNTAX            INTEGER { disable(0), enable(1)  }
        MAX-ACCESS        read-write
        STATUS            current
        DESCRIPTION
                "CMNT: - 
                 TYPE: - Checkbox
                 PAGE: - AudioInput
                    Disembed6_2_invert  cmdID= 40027  "
        ::= { iqupc00CmdEntry 40027 }


    iqupc00Disembed18Disembed6dolbyLine OBJECT-TYPE
        SYNTAX            RollCallString
        MAX-ACCESS        read-only
        STATUS            current
        DESCRIPTION
                "CMNT: - 
                 TYPE: - Display
                 PAGE: - Disembed1-8
                    dolbyLine  cmdID= 40078  "
        ::= { iqupc00CmdEntry 40078 }


    iqupc00AudioInputDisembed18Disembed71procamp OBJECT-TYPE
        SYNTAX            INTEGER
        MAX-ACCESS        read-write
        STATUS            current
        DESCRIPTION
                "CMNT: - Disembed Proc Amp Gain
                 TYPE: - Number
                 PAGE: - AudioInput
                    Disembed7_1_procamp  cmdID= 40012
                    min= -801  max= 120  step= 1  format= %0.1f dB  div_scale= 10  preset= 0
                    Min = -80.1 dB  Max = 12.0 dB  Step = 0.1 dB  Preset = 0.0 dB  "
        ::= { iqupc00CmdEntry 40012 }


    iqupc00AudioInputDisembed18Disembed72procamp OBJECT-TYPE
        SYNTAX            INTEGER
        MAX-ACCESS        read-write
        STATUS            current
        DESCRIPTION
                "CMNT: - Disembed Proc Amp Gain
                 TYPE: - Number
                 PAGE: - AudioInput
                    Disembed7_2_procamp  cmdID= 40013
                    min= -801  max= 120  step= 1  format= %0.1f dB  div_scale= 10  preset= 0
                    Min = -80.1 dB  Max = 12.0 dB  Step = 0.1 dB  Preset = 0.0 dB  "
        ::= { iqupc00CmdEntry 40013 }


    iqupc00Disembed18Disembed7Mute71 OBJECT-TYPE
        SYNTAX            INTEGER { disable(0), enable(1)  }
        MAX-ACCESS        read-write
        STATUS            current
        DESCRIPTION
                "CMNT: - 
                 TYPE: - Checkbox
                 PAGE: - Disembed1-8
                    Mute7_1  cmdID= 40044  "
        ::= { iqupc00CmdEntry 40044 }


    iqupc00Disembed18Disembed7Mute72 OBJECT-TYPE
        SYNTAX            INTEGER { disable(0), enable(1)  }
        MAX-ACCESS        read-write
        STATUS            current
        DESCRIPTION
                "CMNT: - 
                 TYPE: - Checkbox
                 PAGE: - Disembed1-8
                    Mute7_2  cmdID= 40045  "
        ::= { iqupc00CmdEntry 40045 }


    iqupc00Disembed18Disembed7Stereo7 OBJECT-TYPE
        SYNTAX            INTEGER { disable(0), enable(1)  }
        MAX-ACCESS        read-write
        STATUS            current
        DESCRIPTION
                "CMNT: - 
                 TYPE: - Checkbox
                 PAGE: - Disembed1-8
                    Stereo7  cmdID= 40054  "
        ::= { iqupc00CmdEntry 40054 }


    iqupc00AudioInputDisembed18Disembed71invert OBJECT-TYPE
        SYNTAX            INTEGER { disable(0), enable(1)  }
        MAX-ACCESS        read-write
        STATUS            current
        DESCRIPTION
                "CMNT: - 
                 TYPE: - Checkbox
                 PAGE: - AudioInput
                    Disembed7_1_invert  cmdID= 40028  "
        ::= { iqupc00CmdEntry 40028 }


    iqupc00AudioInputDisembed18Disembed72invert OBJECT-TYPE
        SYNTAX            INTEGER { disable(0), enable(1)  }
        MAX-ACCESS        read-write
        STATUS            current
        DESCRIPTION
                "CMNT: - 
                 TYPE: - Checkbox
                 PAGE: - AudioInput
                    Disembed7_2_invert  cmdID= 40029  "
        ::= { iqupc00CmdEntry 40029 }


    iqupc00Disembed18Disembed7dolbyLine OBJECT-TYPE
        SYNTAX            RollCallString
        MAX-ACCESS        read-only
        STATUS            current
        DESCRIPTION
                "CMNT: - 
                 TYPE: - Display
                 PAGE: - Disembed1-8
                    dolbyLine  cmdID= 40079  "
        ::= { iqupc00CmdEntry 40079 }


    iqupc00AudioInputDisembed18Disembed81procamp OBJECT-TYPE
        SYNTAX            INTEGER
        MAX-ACCESS        read-write
        STATUS            current
        DESCRIPTION
                "CMNT: - Disembed Proc Amp Gain
                 TYPE: - Number
                 PAGE: - AudioInput
                    Disembed8_1_procamp  cmdID= 40014
                    min= -801  max= 120  step= 1  format= %0.1f dB  div_scale= 10  preset= 0
                    Min = -80.1 dB  Max = 12.0 dB  Step = 0.1 dB  Preset = 0.0 dB  "
        ::= { iqupc00CmdEntry 40014 }


    iqupc00AudioInputDisembed18Disembed82procamp OBJECT-TYPE
        SYNTAX            INTEGER
        MAX-ACCESS        read-write
        STATUS            current
        DESCRIPTION
                "CMNT: - Disembed Proc Amp Gain
                 TYPE: - Number
                 PAGE: - AudioInput
                    Disembed8_2_procamp  cmdID= 40015
                    min= -801  max= 120  step= 1  format= %0.1f dB  div_scale= 10  preset= 0
                    Min = -80.1 dB  Max = 12.0 dB  Step = 0.1 dB  Preset = 0.0 dB  "
        ::= { iqupc00CmdEntry 40015 }


    iqupc00Disembed18Disembed8Mute81 OBJECT-TYPE
        SYNTAX            INTEGER { disable(0), enable(1)  }
        MAX-ACCESS        read-write
        STATUS            current
        DESCRIPTION
                "CMNT: - 
                 TYPE: - Checkbox
                 PAGE: - Disembed1-8
                    Mute8_1  cmdID= 40046  "
        ::= { iqupc00CmdEntry 40046 }


    iqupc00Disembed18Disembed8Mute82 OBJECT-TYPE
        SYNTAX            INTEGER { disable(0), enable(1)  }
        MAX-ACCESS        read-write
        STATUS            current
        DESCRIPTION
                "CMNT: - 
                 TYPE: - Checkbox
                 PAGE: - Disembed1-8
                    Mute8_2  cmdID= 40047  "
        ::= { iqupc00CmdEntry 40047 }


    iqupc00Disembed18Disembed8Stereo8 OBJECT-TYPE
        SYNTAX            INTEGER { disable(0), enable(1)  }
        MAX-ACCESS        read-write
        STATUS            current
        DESCRIPTION
                "CMNT: - 
                 TYPE: - Checkbox
                 PAGE: - Disembed1-8
                    Stereo8  cmdID= 40055  "
        ::= { iqupc00CmdEntry 40055 }


    iqupc00AudioInputDisembed18Disembed81invert OBJECT-TYPE
        SYNTAX            INTEGER { disable(0), enable(1)  }
        MAX-ACCESS        read-write
        STATUS            current
        DESCRIPTION
                "CMNT: - 
                 TYPE: - Checkbox
                 PAGE: - AudioInput
                    Disembed8_1_invert  cmdID= 40030  "
        ::= { iqupc00CmdEntry 40030 }


    iqupc00AudioInputDisembed18Disembed82invert OBJECT-TYPE
        SYNTAX            INTEGER { disable(0), enable(1)  }
        MAX-ACCESS        read-write
        STATUS            current
        DESCRIPTION
                "CMNT: - 
                 TYPE: - Checkbox
                 PAGE: - AudioInput
                    Disembed8_2_invert  cmdID= 40031  "
        ::= { iqupc00CmdEntry 40031 }


    iqupc00Disembed18Disembed8dolbyLine OBJECT-TYPE
        SYNTAX            RollCallString
        MAX-ACCESS        read-only
        STATUS            current
        DESCRIPTION
                "CMNT: - 
                 TYPE: - Display
                 PAGE: - Disembed1-8
                    dolbyLine  cmdID= 40080  "
        ::= { iqupc00CmdEntry 40080 }


    iqupc00AudioInputDisembed18ProcampSaveset OBJECT-TYPE
        SYNTAX            INTEGER
        MAX-ACCESS        read-write
        STATUS            current
        DESCRIPTION
                "CMNT: - Used to correctly restore stereo procamp and mute values.
                 TYPE: - Number
                 PAGE: - AudioInput
                    ProcampSaveset  cmdID= 40072
                    min= 0  max= 1  step= 1  format= %0.0f  div_scale= 1  preset= 0
                    Min = 0  Max = 1  Step = 1  Preset = 0  "
        ::= { iqupc00CmdEntry 40072 }


    iqupc00AudioOutputEmbed18Embed11procamp OBJECT-TYPE
        SYNTAX            INTEGER
        MAX-ACCESS        read-write
        STATUS            current
        DESCRIPTION
                "CMNT: - Embed Proc Amp Gain
                 TYPE: - Number
                 PAGE: - AudioOutput
                    Embed1_1_procamp  cmdID= 40400
                    min= -801  max= 120  step= 1  format= %0.1f dB  div_scale= 10  preset= 0
                    Min = -80.1 dB  Max = 12.0 dB  Step = 0.1 dB  Preset = 0.0 dB  "
        ::= { iqupc00CmdEntry 40400 }


    iqupc00AudioOutputEmbed18Embed12procamp OBJECT-TYPE
        SYNTAX            INTEGER
        MAX-ACCESS        read-write
        STATUS            current
        DESCRIPTION
                "CMNT: - Embed Proc Amp Gain
                 TYPE: - Number
                 PAGE: - AudioOutput
                    Embed1_2_procamp  cmdID= 40401
                    min= -801  max= 120  step= 1  format= %0.1f dB  div_scale= 10  preset= 0
                    Min = -80.1 dB  Max = 12.0 dB  Step = 0.1 dB  Preset = 0.0 dB  "
        ::= { iqupc00CmdEntry 40401 }


    iqupc00Embed18Embed1Mute11 OBJECT-TYPE
        SYNTAX            INTEGER { disable(0), enable(1)  }
        MAX-ACCESS        read-write
        STATUS            current
        DESCRIPTION
                "CMNT: - 
                 TYPE: - Checkbox
                 PAGE: - Embed1-8
                    Mute1_1  cmdID= 40432  "
        ::= { iqupc00CmdEntry 40432 }


    iqupc00Embed18Embed1Mute12 OBJECT-TYPE
        SYNTAX            INTEGER { disable(0), enable(1)  }
        MAX-ACCESS        read-write
        STATUS            current
        DESCRIPTION
                "CMNT: - 
                 TYPE: - Checkbox
                 PAGE: - Embed1-8
                    Mute1_2  cmdID= 40433  "
        ::= { iqupc00CmdEntry 40433 }


    iqupc00Embed18Embed1Stereo1 OBJECT-TYPE
        SYNTAX            INTEGER { disable(0), enable(1)  }
        MAX-ACCESS        read-write
        STATUS            current
        DESCRIPTION
                "CMNT: - 
                 TYPE: - Checkbox
                 PAGE: - Embed1-8
                    Stereo1  cmdID= 40448  "
        ::= { iqupc00CmdEntry 40448 }


    iqupc00Embed18Embed1dolbyLine OBJECT-TYPE
        SYNTAX            RollCallString
        MAX-ACCESS        read-only
        STATUS            current
        DESCRIPTION
                "CMNT: - 
                 TYPE: - Display
                 PAGE: - Embed1-8
                    dolbyLine  cmdID= 40081  "
        ::= { iqupc00CmdEntry 40081 }


    iqupc00AudioOutputEmbed18Embed21procamp OBJECT-TYPE
        SYNTAX            INTEGER
        MAX-ACCESS        read-write
        STATUS            current
        DESCRIPTION
                "CMNT: - Embed Proc Amp Gain
                 TYPE: - Number
                 PAGE: - AudioOutput
                    Embed2_1_procamp  cmdID= 40402
                    min= -801  max= 120  step= 1  format= %0.1f dB  div_scale= 10  preset= 0
                    Min = -80.1 dB  Max = 12.0 dB  Step = 0.1 dB  Preset = 0.0 dB  "
        ::= { iqupc00CmdEntry 40402 }


    iqupc00AudioOutputEmbed18Embed22procamp OBJECT-TYPE
        SYNTAX            INTEGER
        MAX-ACCESS        read-write
        STATUS            current
        DESCRIPTION
                "CMNT: - Embed Proc Amp Gain
                 TYPE: - Number
                 PAGE: - AudioOutput
                    Embed2_2_procamp  cmdID= 40403
                    min= -801  max= 120  step= 1  format= %0.1f dB  div_scale= 10  preset= 0
                    Min = -80.1 dB  Max = 12.0 dB  Step = 0.1 dB  Preset = 0.0 dB  "
        ::= { iqupc00CmdEntry 40403 }


    iqupc00Embed18Embed2Mute21 OBJECT-TYPE
        SYNTAX            INTEGER { disable(0), enable(1)  }
        MAX-ACCESS        read-write
        STATUS            current
        DESCRIPTION
                "CMNT: - 
                 TYPE: - Checkbox
                 PAGE: - Embed1-8
                    Mute2_1  cmdID= 40434  "
        ::= { iqupc00CmdEntry 40434 }


    iqupc00Embed18Embed2Mute22 OBJECT-TYPE
        SYNTAX            INTEGER { disable(0), enable(1)  }
        MAX-ACCESS        read-write
        STATUS            current
        DESCRIPTION
                "CMNT: - 
                 TYPE: - Checkbox
                 PAGE: - Embed1-8
                    Mute2_2  cmdID= 40435  "
        ::= { iqupc00CmdEntry 40435 }


    iqupc00Embed18Embed2Stereo2 OBJECT-TYPE
        SYNTAX            INTEGER { disable(0), enable(1)  }
        MAX-ACCESS        read-write
        STATUS            current
        DESCRIPTION
                "CMNT: - 
                 TYPE: - Checkbox
                 PAGE: - Embed1-8
                    Stereo2  cmdID= 40449  "
        ::= { iqupc00CmdEntry 40449 }


    iqupc00Embed18Embed2dolbyLine OBJECT-TYPE
        SYNTAX            RollCallString
        MAX-ACCESS        read-only
        STATUS            current
        DESCRIPTION
                "CMNT: - 
                 TYPE: - Display
                 PAGE: - Embed1-8
                    dolbyLine  cmdID= 40082  "
        ::= { iqupc00CmdEntry 40082 }


    iqupc00AudioOutputEmbed18Embed31procamp OBJECT-TYPE
        SYNTAX            INTEGER
        MAX-ACCESS        read-write
        STATUS            current
        DESCRIPTION
                "CMNT: - Embed Proc Amp Gain
                 TYPE: - Number
                 PAGE: - AudioOutput
                    Embed3_1_procamp  cmdID= 40404
                    min= -801  max= 120  step= 1  format= %0.1f dB  div_scale= 10  preset= 0
                    Min = -80.1 dB  Max = 12.0 dB  Step = 0.1 dB  Preset = 0.0 dB  "
        ::= { iqupc00CmdEntry 40404 }


    iqupc00AudioOutputEmbed18Embed32procamp OBJECT-TYPE
        SYNTAX            INTEGER
        MAX-ACCESS        read-write
        STATUS            current
        DESCRIPTION
                "CMNT: - Embed Proc Amp Gain
                 TYPE: - Number
                 PAGE: - AudioOutput
                    Embed3_2_procamp  cmdID= 40405
                    min= -801  max= 120  step= 1  format= %0.1f dB  div_scale= 10  preset= 0
                    Min = -80.1 dB  Max = 12.0 dB  Step = 0.1 dB  Preset = 0.0 dB  "
        ::= { iqupc00CmdEntry 40405 }


    iqupc00Embed18Embed3Mute31 OBJECT-TYPE
        SYNTAX            INTEGER { disable(0), enable(1)  }
        MAX-ACCESS        read-write
        STATUS            current
        DESCRIPTION
                "CMNT: - 
                 TYPE: - Checkbox
                 PAGE: - Embed1-8
                    Mute3_1  cmdID= 40436  "
        ::= { iqupc00CmdEntry 40436 }


    iqupc00Embed18Embed3Mute32 OBJECT-TYPE
        SYNTAX            INTEGER { disable(0), enable(1)  }
        MAX-ACCESS        read-write
        STATUS            current
        DESCRIPTION
                "CMNT: - 
                 TYPE: - Checkbox
                 PAGE: - Embed1-8
                    Mute3_2  cmdID= 40437  "
        ::= { iqupc00CmdEntry 40437 }


    iqupc00Embed18Embed3Stereo3 OBJECT-TYPE
        SYNTAX            INTEGER { disable(0), enable(1)  }
        MAX-ACCESS        read-write
        STATUS            current
        DESCRIPTION
                "CMNT: - 
                 TYPE: - Checkbox
                 PAGE: - Embed1-8
                    Stereo3  cmdID= 40450  "
        ::= { iqupc00CmdEntry 40450 }


    iqupc00Embed18Embed3dolbyLine OBJECT-TYPE
        SYNTAX            RollCallString
        MAX-ACCESS        read-only
        STATUS            current
        DESCRIPTION
                "CMNT: - 
                 TYPE: - Display
                 PAGE: - Embed1-8
                    dolbyLine  cmdID= 40083  "
        ::= { iqupc00CmdEntry 40083 }


    iqupc00AudioOutputEmbed18Embed41procamp OBJECT-TYPE
        SYNTAX            INTEGER
        MAX-ACCESS        read-write
        STATUS            current
        DESCRIPTION
                "CMNT: - Embed Proc Amp Gain
                 TYPE: - Number
                 PAGE: - AudioOutput
                    Embed4_1_procamp  cmdID= 40406
                    min= -801  max= 120  step= 1  format= %0.1f dB  div_scale= 10  preset= 0
                    Min = -80.1 dB  Max = 12.0 dB  Step = 0.1 dB  Preset = 0.0 dB  "
        ::= { iqupc00CmdEntry 40406 }


    iqupc00AudioOutputEmbed18Embed42procamp OBJECT-TYPE
        SYNTAX            INTEGER
        MAX-ACCESS        read-write
        STATUS            current
        DESCRIPTION
                "CMNT: - Embed Proc Amp Gain
                 TYPE: - Number
                 PAGE: - AudioOutput
                    Embed4_2_procamp  cmdID= 40407
                    min= -801  max= 120  step= 1  format= %0.1f dB  div_scale= 10  preset= 0
                    Min = -80.1 dB  Max = 12.0 dB  Step = 0.1 dB  Preset = 0.0 dB  "
        ::= { iqupc00CmdEntry 40407 }


    iqupc00Embed18Embed4Mute41 OBJECT-TYPE
        SYNTAX            INTEGER { disable(0), enable(1)  }
        MAX-ACCESS        read-write
        STATUS            current
        DESCRIPTION
                "CMNT: - 
                 TYPE: - Checkbox
                 PAGE: - Embed1-8
                    Mute4_1  cmdID= 40438  "
        ::= { iqupc00CmdEntry 40438 }


    iqupc00Embed18Embed4Mute42 OBJECT-TYPE
        SYNTAX            INTEGER { disable(0), enable(1)  }
        MAX-ACCESS        read-write
        STATUS            current
        DESCRIPTION
                "CMNT: - 
                 TYPE: - Checkbox
                 PAGE: - Embed1-8
                    Mute4_2  cmdID= 40439  "
        ::= { iqupc00CmdEntry 40439 }


    iqupc00Embed18Embed4Stereo4 OBJECT-TYPE
        SYNTAX            INTEGER { disable(0), enable(1)  }
        MAX-ACCESS        read-write
        STATUS            current
        DESCRIPTION
                "CMNT: - 
                 TYPE: - Checkbox
                 PAGE: - Embed1-8
                    Stereo4  cmdID= 40451  "
        ::= { iqupc00CmdEntry 40451 }


    iqupc00Embed18Embed4dolbyLine OBJECT-TYPE
        SYNTAX            RollCallString
        MAX-ACCESS        read-only
        STATUS            current
        DESCRIPTION
                "CMNT: - 
                 TYPE: - Display
                 PAGE: - Embed1-8
                    dolbyLine  cmdID= 40084  "
        ::= { iqupc00CmdEntry 40084 }


    iqupc00AudioOutputEmbed18Embed51procamp OBJECT-TYPE
        SYNTAX            INTEGER
        MAX-ACCESS        read-write
        STATUS            current
        DESCRIPTION
                "CMNT: - Embed Proc Amp Gain
                 TYPE: - Number
                 PAGE: - AudioOutput
                    Embed5_1_procamp  cmdID= 40408
                    min= -801  max= 120  step= 1  format= %0.1f dB  div_scale= 10  preset= 0
                    Min = -80.1 dB  Max = 12.0 dB  Step = 0.1 dB  Preset = 0.0 dB  "
        ::= { iqupc00CmdEntry 40408 }


    iqupc00AudioOutputEmbed18Embed52procamp OBJECT-TYPE
        SYNTAX            INTEGER
        MAX-ACCESS        read-write
        STATUS            current
        DESCRIPTION
                "CMNT: - Embed Proc Amp Gain
                 TYPE: - Number
                 PAGE: - AudioOutput
                    Embed5_2_procamp  cmdID= 40409
                    min= -801  max= 120  step= 1  format= %0.1f dB  div_scale= 10  preset= 0
                    Min = -80.1 dB  Max = 12.0 dB  Step = 0.1 dB  Preset = 0.0 dB  "
        ::= { iqupc00CmdEntry 40409 }


    iqupc00Embed18Embed5Mute51 OBJECT-TYPE
        SYNTAX            INTEGER { disable(0), enable(1)  }
        MAX-ACCESS        read-write
        STATUS            current
        DESCRIPTION
                "CMNT: - 
                 TYPE: - Checkbox
                 PAGE: - Embed1-8
                    Mute5_1  cmdID= 40440  "
        ::= { iqupc00CmdEntry 40440 }


    iqupc00Embed18Embed5Mute52 OBJECT-TYPE
        SYNTAX            INTEGER { disable(0), enable(1)  }
        MAX-ACCESS        read-write
        STATUS            current
        DESCRIPTION
                "CMNT: - 
                 TYPE: - Checkbox
                 PAGE: - Embed1-8
                    Mute5_2  cmdID= 40441  "
        ::= { iqupc00CmdEntry 40441 }


    iqupc00Embed18Embed5Stereo5 OBJECT-TYPE
        SYNTAX            INTEGER { disable(0), enable(1)  }
        MAX-ACCESS        read-write
        STATUS            current
        DESCRIPTION
                "CMNT: - 
                 TYPE: - Checkbox
                 PAGE: - Embed1-8
                    Stereo5  cmdID= 40452  "
        ::= { iqupc00CmdEntry 40452 }


    iqupc00Embed18Embed5dolbyLine OBJECT-TYPE
        SYNTAX            RollCallString
        MAX-ACCESS        read-only
        STATUS            current
        DESCRIPTION
                "CMNT: - 
                 TYPE: - Display
                 PAGE: - Embed1-8
                    dolbyLine  cmdID= 40085  "
        ::= { iqupc00CmdEntry 40085 }


    iqupc00AudioOutputEmbed18Embed61procamp OBJECT-TYPE
        SYNTAX            INTEGER
        MAX-ACCESS        read-write
        STATUS            current
        DESCRIPTION
                "CMNT: - Embed Proc Amp Gain
                 TYPE: - Number
                 PAGE: - AudioOutput
                    Embed6_1_procamp  cmdID= 40410
                    min= -801  max= 120  step= 1  format= %0.1f dB  div_scale= 10  preset= 0
                    Min = -80.1 dB  Max = 12.0 dB  Step = 0.1 dB  Preset = 0.0 dB  "
        ::= { iqupc00CmdEntry 40410 }


    iqupc00AudioOutputEmbed18Embed62procamp OBJECT-TYPE
        SYNTAX            INTEGER
        MAX-ACCESS        read-write
        STATUS            current
        DESCRIPTION
                "CMNT: - Embed Proc Amp Gain
                 TYPE: - Number
                 PAGE: - AudioOutput
                    Embed6_2_procamp  cmdID= 40411
                    min= -801  max= 120  step= 1  format= %0.1f dB  div_scale= 10  preset= 0
                    Min = -80.1 dB  Max = 12.0 dB  Step = 0.1 dB  Preset = 0.0 dB  "
        ::= { iqupc00CmdEntry 40411 }


    iqupc00Embed18Embed6Mute61 OBJECT-TYPE
        SYNTAX            INTEGER { disable(0), enable(1)  }
        MAX-ACCESS        read-write
        STATUS            current
        DESCRIPTION
                "CMNT: - 
                 TYPE: - Checkbox
                 PAGE: - Embed1-8
                    Mute6_1  cmdID= 40442  "
        ::= { iqupc00CmdEntry 40442 }


    iqupc00Embed18Embed6Mute62 OBJECT-TYPE
        SYNTAX            INTEGER { disable(0), enable(1)  }
        MAX-ACCESS        read-write
        STATUS            current
        DESCRIPTION
                "CMNT: - 
                 TYPE: - Checkbox
                 PAGE: - Embed1-8
                    Mute6_2  cmdID= 40443  "
        ::= { iqupc00CmdEntry 40443 }


    iqupc00Embed18Embed6Stereo6 OBJECT-TYPE
        SYNTAX            INTEGER { disable(0), enable(1)  }
        MAX-ACCESS        read-write
        STATUS            current
        DESCRIPTION
                "CMNT: - 
                 TYPE: - Checkbox
                 PAGE: - Embed1-8
                    Stereo6  cmdID= 40453  "
        ::= { iqupc00CmdEntry 40453 }


    iqupc00Embed18Embed6dolbyLine OBJECT-TYPE
        SYNTAX            RollCallString
        MAX-ACCESS        read-only
        STATUS            current
        DESCRIPTION
                "CMNT: - 
                 TYPE: - Display
                 PAGE: - Embed1-8
                    dolbyLine  cmdID= 40086  "
        ::= { iqupc00CmdEntry 40086 }


    iqupc00AudioOutputEmbed18Embed71procamp OBJECT-TYPE
        SYNTAX            INTEGER
        MAX-ACCESS        read-write
        STATUS            current
        DESCRIPTION
                "CMNT: - Embed Proc Amp Gain
                 TYPE: - Number
                 PAGE: - AudioOutput
                    Embed7_1_procamp  cmdID= 40412
                    min= -801  max= 120  step= 1  format= %0.1f dB  div_scale= 10  preset= 0
                    Min = -80.1 dB  Max = 12.0 dB  Step = 0.1 dB  Preset = 0.0 dB  "
        ::= { iqupc00CmdEntry 40412 }


    iqupc00AudioOutputEmbed18Embed72procamp OBJECT-TYPE
        SYNTAX            INTEGER
        MAX-ACCESS        read-write
        STATUS            current
        DESCRIPTION
                "CMNT: - Embed Proc Amp Gain
                 TYPE: - Number
                 PAGE: - AudioOutput
                    Embed7_2_procamp  cmdID= 40413
                    min= -801  max= 120  step= 1  format= %0.1f dB  div_scale= 10  preset= 0
                    Min = -80.1 dB  Max = 12.0 dB  Step = 0.1 dB  Preset = 0.0 dB  "
        ::= { iqupc00CmdEntry 40413 }


    iqupc00Embed18Embed7Mute71 OBJECT-TYPE
        SYNTAX            INTEGER { disable(0), enable(1)  }
        MAX-ACCESS        read-write
        STATUS            current
        DESCRIPTION
                "CMNT: - 
                 TYPE: - Checkbox
                 PAGE: - Embed1-8
                    Mute7_1  cmdID= 40444  "
        ::= { iqupc00CmdEntry 40444 }


    iqupc00Embed18Embed7Mute72 OBJECT-TYPE
        SYNTAX            INTEGER { disable(0), enable(1)  }
        MAX-ACCESS        read-write
        STATUS            current
        DESCRIPTION
                "CMNT: - 
                 TYPE: - Checkbox
                 PAGE: - Embed1-8
                    Mute7_2  cmdID= 40445  "
        ::= { iqupc00CmdEntry 40445 }


    iqupc00Embed18Embed7Stereo7 OBJECT-TYPE
        SYNTAX            INTEGER { disable(0), enable(1)  }
        MAX-ACCESS        read-write
        STATUS            current
        DESCRIPTION
                "CMNT: - 
                 TYPE: - Checkbox
                 PAGE: - Embed1-8
                    Stereo7  cmdID= 40454  "
        ::= { iqupc00CmdEntry 40454 }


    iqupc00Embed18Embed7dolbyLine OBJECT-TYPE
        SYNTAX            RollCallString
        MAX-ACCESS        read-only
        STATUS            current
        DESCRIPTION
                "CMNT: - 
                 TYPE: - Display
                 PAGE: - Embed1-8
                    dolbyLine  cmdID= 40087  "
        ::= { iqupc00CmdEntry 40087 }


    iqupc00AudioOutputEmbed18Embed81procamp OBJECT-TYPE
        SYNTAX            INTEGER
        MAX-ACCESS        read-write
        STATUS            current
        DESCRIPTION
                "CMNT: - Embed Proc Amp Gain
                 TYPE: - Number
                 PAGE: - AudioOutput
                    Embed8_1_procamp  cmdID= 40414
                    min= -801  max= 120  step= 1  format= %0.1f dB  div_scale= 10  preset= 0
                    Min = -80.1 dB  Max = 12.0 dB  Step = 0.1 dB  Preset = 0.0 dB  "
        ::= { iqupc00CmdEntry 40414 }


    iqupc00AudioOutputEmbed18Embed82procamp OBJECT-TYPE
        SYNTAX            INTEGER
        MAX-ACCESS        read-write
        STATUS            current
        DESCRIPTION
                "CMNT: - Embed Proc Amp Gain
                 TYPE: - Number
                 PAGE: - AudioOutput
                    Embed8_2_procamp  cmdID= 40415
                    min= -801  max= 120  step= 1  format= %0.1f dB  div_scale= 10  preset= 0
                    Min = -80.1 dB  Max = 12.0 dB  Step = 0.1 dB  Preset = 0.0 dB  "
        ::= { iqupc00CmdEntry 40415 }


    iqupc00Embed18Embed8Mute81 OBJECT-TYPE
        SYNTAX            INTEGER { disable(0), enable(1)  }
        MAX-ACCESS        read-write
        STATUS            current
        DESCRIPTION
                "CMNT: - 
                 TYPE: - Checkbox
                 PAGE: - Embed1-8
                    Mute8_1  cmdID= 40446  "
        ::= { iqupc00CmdEntry 40446 }


    iqupc00Embed18Embed8Mute82 OBJECT-TYPE
        SYNTAX            INTEGER { disable(0), enable(1)  }
        MAX-ACCESS        read-write
        STATUS            current
        DESCRIPTION
                "CMNT: - 
                 TYPE: - Checkbox
                 PAGE: - Embed1-8
                    Mute8_2  cmdID= 40447  "
        ::= { iqupc00CmdEntry 40447 }


    iqupc00Embed18Embed8Stereo8 OBJECT-TYPE
        SYNTAX            INTEGER { disable(0), enable(1)  }
        MAX-ACCESS        read-write
        STATUS            current
        DESCRIPTION
                "CMNT: - 
                 TYPE: - Checkbox
                 PAGE: - Embed1-8
                    Stereo8  cmdID= 40455  "
        ::= { iqupc00CmdEntry 40455 }


    iqupc00Embed18Embed8dolbyLine OBJECT-TYPE
        SYNTAX            RollCallString
        MAX-ACCESS        read-only
        STATUS            current
        DESCRIPTION
                "CMNT: - 
                 TYPE: - Display
                 PAGE: - Embed1-8
                    dolbyLine  cmdID= 40088  "
        ::= { iqupc00CmdEntry 40088 }


    iqupc00Embed18GroupEmbGroup1 OBJECT-TYPE
        SYNTAX            INTEGER { disable(0), enable(1)  }
        MAX-ACCESS        read-write
        STATUS            current
        DESCRIPTION
                "CMNT: - Audio group 1 enable
                 TYPE: - Checkbox
                 PAGE: - Embed1-8
                    EmbGroup1  cmdID= 36139  "
        ::= { iqupc00CmdEntry 36139 }


    iqupc00Embed18GroupEmbGroup2 OBJECT-TYPE
        SYNTAX            INTEGER { disable(0), enable(1)  }
        MAX-ACCESS        read-write
        STATUS            current
        DESCRIPTION
                "CMNT: - Audio group 2 enable
                 TYPE: - Checkbox
                 PAGE: - Embed1-8
                    EmbGroup2  cmdID= 36140  "
        ::= { iqupc00CmdEntry 36140 }


    iqupc00Embed18GroupEmbGroup3 OBJECT-TYPE
        SYNTAX            INTEGER { disable(0), enable(1)  }
        MAX-ACCESS        read-write
        STATUS            current
        DESCRIPTION
                "CMNT: - Audio group 3 enable
                 TYPE: - Checkbox
                 PAGE: - Embed1-8
                    EmbGroup3  cmdID= 36141  "
        ::= { iqupc00CmdEntry 36141 }


    iqupc00Embed18GroupEmbGroup4 OBJECT-TYPE
        SYNTAX            INTEGER { disable(0), enable(1)  }
        MAX-ACCESS        read-write
        STATUS            current
        DESCRIPTION
                "CMNT: - Audio group 4 enable
                 TYPE: - Checkbox
                 PAGE: - Embed1-8
                    EmbGroup4  cmdID= 36142  "
        ::= { iqupc00CmdEntry 36142 }


    iqupc00AudSetupDelaySelectTotalDelayBus1 OBJECT-TYPE
        SYNTAX            RollCallString
        MAX-ACCESS        read-only
        STATUS            current
        DESCRIPTION
                "CMNT: - Set Manual delay
                 TYPE: - Display
                 PAGE: - AudSetup
                    TotalDelayBus1  cmdID= 40656  "
        ::= { iqupc00CmdEntry 40656 }


    iqupc00AudSetupDelaySelectTotalDelayBus2 OBJECT-TYPE
        SYNTAX            RollCallString
        MAX-ACCESS        read-only
        STATUS            current
        DESCRIPTION
                "CMNT: - Set Manual delay
                 TYPE: - Display
                 PAGE: - AudSetup
                    TotalDelayBus2  cmdID= 40657  "
        ::= { iqupc00CmdEntry 40657 }


    iqupc00AudSetupDelaySelectTotalDelayBus3 OBJECT-TYPE
        SYNTAX            RollCallString
        MAX-ACCESS        read-only
        STATUS            current
        DESCRIPTION
                "CMNT: - Set Manual delay
                 TYPE: - Display
                 PAGE: - AudSetup
                    TotalDelayBus3  cmdID= 40658  "
        ::= { iqupc00CmdEntry 40658 }


    iqupc00AudSetupDelaySelectTotalDelayBus4 OBJECT-TYPE
        SYNTAX            RollCallString
        MAX-ACCESS        read-only
        STATUS            current
        DESCRIPTION
                "CMNT: - Set Manual delay
                 TYPE: - Display
                 PAGE: - AudSetup
                    TotalDelayBus4  cmdID= 40659  "
        ::= { iqupc00CmdEntry 40659 }


    iqupc00AudSetupDelaySelectTotalDelayBus5 OBJECT-TYPE
        SYNTAX            RollCallString
        MAX-ACCESS        read-only
        STATUS            current
        DESCRIPTION
                "CMNT: - Set Manual delay
                 TYPE: - Display
                 PAGE: - AudSetup
                    TotalDelayBus5  cmdID= 40660  "
        ::= { iqupc00CmdEntry 40660 }


    iqupc00AudSetupDelaySelectTotalDelayBus6 OBJECT-TYPE
        SYNTAX            RollCallString
        MAX-ACCESS        read-only
        STATUS            current
        DESCRIPTION
                "CMNT: - Set Manual delay
                 TYPE: - Display
                 PAGE: - AudSetup
                    TotalDelayBus6  cmdID= 40661  "
        ::= { iqupc00CmdEntry 40661 }


    iqupc00AudSetupDelaySelectTotalDelayBus7 OBJECT-TYPE
        SYNTAX            RollCallString
        MAX-ACCESS        read-only
        STATUS            current
        DESCRIPTION
                "CMNT: - Set Manual delay
                 TYPE: - Display
                 PAGE: - AudSetup
                    TotalDelayBus7  cmdID= 40662  "
        ::= { iqupc00CmdEntry 40662 }


    iqupc00AudSetupDelaySelectTotalDelayBus8 OBJECT-TYPE
        SYNTAX            RollCallString
        MAX-ACCESS        read-only
        STATUS            current
        DESCRIPTION
                "CMNT: - Set Manual delay
                 TYPE: - Display
                 PAGE: - AudSetup
                    TotalDelayBus8  cmdID= 40663  "
        ::= { iqupc00CmdEntry 40663 }


    iqupc00AudSetupDelaySelectBus1Delay OBJECT-TYPE
        SYNTAX            INTEGER
        MAX-ACCESS        read-write
        STATUS            current
        DESCRIPTION
                "CMNT: - Set Manual delay
                 TYPE: - Number
                 PAGE: - AudSetup
                    Bus 1 Delay  cmdID= 40648
                    min= -1995  max= 1995  step= 1  format= %d  div_scale= 1  preset= 0
                    Min = 0  Max = 0  Step = 0  Preset = 0  "
        ::= { iqupc00CmdEntry 40648 }


    iqupc00AudSetupDelaySelectBus2Delay OBJECT-TYPE
        SYNTAX            INTEGER
        MAX-ACCESS        read-write
        STATUS            current
        DESCRIPTION
                "CMNT: - Set Manual delay
                 TYPE: - Number
                 PAGE: - AudSetup
                    Bus 2 Delay  cmdID= 40649
                    min= -1995  max= 1995  step= 1  format= %d  div_scale= 1  preset= 0
                    Min = 0  Max = 0  Step = 0  Preset = 0  "
        ::= { iqupc00CmdEntry 40649 }


    iqupc00AudSetupDelaySelectBus3Delay OBJECT-TYPE
        SYNTAX            INTEGER
        MAX-ACCESS        read-write
        STATUS            current
        DESCRIPTION
                "CMNT: - Set Manual delay
                 TYPE: - Number
                 PAGE: - AudSetup
                    Bus 3 Delay  cmdID= 40650
                    min= -1995  max= 1995  step= 1  format= %d  div_scale= 1  preset= 0
                    Min = 0  Max = 0  Step = 0  Preset = 0  "
        ::= { iqupc00CmdEntry 40650 }


    iqupc00AudSetupDelaySelectBus4Delay OBJECT-TYPE
        SYNTAX            INTEGER
        MAX-ACCESS        read-write
        STATUS            current
        DESCRIPTION
                "CMNT: - Set Manual delay
                 TYPE: - Number
                 PAGE: - AudSetup
                    Bus 4 Delay  cmdID= 40651
                    min= -1995  max= 1995  step= 1  format= %d  div_scale= 1  preset= 0
                    Min = 0  Max = 0  Step = 0  Preset = 0  "
        ::= { iqupc00CmdEntry 40651 }


    iqupc00AudSetupDelaySelectBus5Delay OBJECT-TYPE
        SYNTAX            INTEGER
        MAX-ACCESS        read-write
        STATUS            current
        DESCRIPTION
                "CMNT: - Set Manual delay
                 TYPE: - Number
                 PAGE: - AudSetup
                    Bus 5 Delay  cmdID= 40652
                    min= -1995  max= 1995  step= 1  format= %d  div_scale= 1  preset= 0
                    Min = 0  Max = 0  Step = 0  Preset = 0  "
        ::= { iqupc00CmdEntry 40652 }


    iqupc00AudSetupDelaySelectBus6Delay OBJECT-TYPE
        SYNTAX            INTEGER
        MAX-ACCESS        read-write
        STATUS            current
        DESCRIPTION
                "CMNT: - Set Manual delay
                 TYPE: - Number
                 PAGE: - AudSetup
                    Bus 6 Delay  cmdID= 40653
                    min= -1995  max= 1995  step= 1  format= %d  div_scale= 1  preset= 0
                    Min = 0  Max = 0  Step = 0  Preset = 0  "
        ::= { iqupc00CmdEntry 40653 }


    iqupc00AudSetupDelaySelectBus7Delay OBJECT-TYPE
        SYNTAX            INTEGER
        MAX-ACCESS        read-write
        STATUS            current
        DESCRIPTION
                "CMNT: - Set Manual delay
                 TYPE: - Number
                 PAGE: - AudSetup
                    Bus 7 Delay  cmdID= 40654
                    min= -1995  max= 1995  step= 1  format= %d  div_scale= 1  preset= 0
                    Min = 0  Max = 0  Step = 0  Preset = 0  "
        ::= { iqupc00CmdEntry 40654 }


    iqupc00AudSetupDelaySelectBus8Delay OBJECT-TYPE
        SYNTAX            INTEGER
        MAX-ACCESS        read-write
        STATUS            current
        DESCRIPTION
                "CMNT: - Set Manual delay
                 TYPE: - Number
                 PAGE: - AudSetup
                    Bus 8 Delay  cmdID= 40655
                    min= -1995  max= 1995  step= 1  format= %d  div_scale= 1  preset= 0
                    Min = 0  Max = 0  Step = 0  Preset = 0  "
        ::= { iqupc00CmdEntry 40655 }


    iqupc00AudSetupDelaySelectBus1Fine OBJECT-TYPE
        SYNTAX            INTEGER
        MAX-ACCESS        read-write
        STATUS            current
        DESCRIPTION
                "CMNT: - Set Manual delay
                 TYPE: - Number
                 PAGE: - AudSetup
                    Bus 1 Fine  cmdID= 36165
                    min= -240  max= 240  step= 1  format= %d  div_scale= 1  preset= 0
                    Min = 0  Max = 0  Step = 0  Preset = 0  "
        ::= { iqupc00CmdEntry 36165 }


    iqupc00AudSetupDelaySelectBus2Fine OBJECT-TYPE
        SYNTAX            INTEGER
        MAX-ACCESS        read-write
        STATUS            current
        DESCRIPTION
                "CMNT: - Set Manual delay
                 TYPE: - Number
                 PAGE: - AudSetup
                    Bus 2 Fine  cmdID= 36166
                    min= -240  max= 240  step= 1  format= %d  div_scale= 1  preset= 0
                    Min = 0  Max = 0  Step = 0  Preset = 0  "
        ::= { iqupc00CmdEntry 36166 }


    iqupc00AudSetupDelaySelectBus3Fine OBJECT-TYPE
        SYNTAX            INTEGER
        MAX-ACCESS        read-write
        STATUS            current
        DESCRIPTION
                "CMNT: - Set Manual delay
                 TYPE: - Number
                 PAGE: - AudSetup
                    Bus 3 Fine  cmdID= 36167
                    min= -240  max= 240  step= 1  format= %d  div_scale= 1  preset= 0
                    Min = 0  Max = 0  Step = 0  Preset = 0  "
        ::= { iqupc00CmdEntry 36167 }


    iqupc00AudSetupDelaySelectBus4Fine OBJECT-TYPE
        SYNTAX            INTEGER
        MAX-ACCESS        read-write
        STATUS            current
        DESCRIPTION
                "CMNT: - Set Manual delay
                 TYPE: - Number
                 PAGE: - AudSetup
                    Bus 4 Fine  cmdID= 36168
                    min= -240  max= 240  step= 1  format= %d  div_scale= 1  preset= 0
                    Min = 0  Max = 0  Step = 0  Preset = 0  "
        ::= { iqupc00CmdEntry 36168 }


    iqupc00AudSetupDelaySelectBus5Fine OBJECT-TYPE
        SYNTAX            INTEGER
        MAX-ACCESS        read-write
        STATUS            current
        DESCRIPTION
                "CMNT: - Set Manual delay
                 TYPE: - Number
                 PAGE: - AudSetup
                    Bus 5 Fine  cmdID= 36169
                    min= -240  max= 240  step= 1  format= %d  div_scale= 1  preset= 0
                    Min = 0  Max = 0  Step = 0  Preset = 0  "
        ::= { iqupc00CmdEntry 36169 }


    iqupc00AudSetupDelaySelectBus6Fine OBJECT-TYPE
        SYNTAX            INTEGER
        MAX-ACCESS        read-write
        STATUS            current
        DESCRIPTION
                "CMNT: - Set Manual delay
                 TYPE: - Number
                 PAGE: - AudSetup
                    Bus 6 Fine  cmdID= 36170
                    min= -240  max= 240  step= 1  format= %d  div_scale= 1  preset= 0
                    Min = 0  Max = 0  Step = 0  Preset = 0  "
        ::= { iqupc00CmdEntry 36170 }


    iqupc00AudSetupDelaySelectBus7Fine OBJECT-TYPE
        SYNTAX            INTEGER
        MAX-ACCESS        read-write
        STATUS            current
        DESCRIPTION
                "CMNT: - Set Manual delay
                 TYPE: - Number
                 PAGE: - AudSetup
                    Bus 7 Fine  cmdID= 36171
                    min= -240  max= 240  step= 1  format= %d  div_scale= 1  preset= 0
                    Min = 0  Max = 0  Step = 0  Preset = 0  "
        ::= { iqupc00CmdEntry 36171 }


    iqupc00AudSetupDelaySelectBus8Fine OBJECT-TYPE
        SYNTAX            INTEGER
        MAX-ACCESS        read-write
        STATUS            current
        DESCRIPTION
                "CMNT: - Set Manual delay
                 TYPE: - Number
                 PAGE: - AudSetup
                    Bus 8 Fine  cmdID= 36172
                    min= -240  max= 240  step= 1  format= %d  div_scale= 1  preset= 0
                    Min = 0  Max = 0  Step = 0  Preset = 0  "
        ::= { iqupc00CmdEntry 36172 }


    iqupc00AudSetupDelaySelectBusBulkDelay OBJECT-TYPE
        SYNTAX            INTEGER
        MAX-ACCESS        read-write
        STATUS            current
        DESCRIPTION
                "CMNT: - Set Bulk delay
                 TYPE: - Number
                 PAGE: - AudSetup
                    Bus Bulk Delay  cmdID= 40647
                    min= -3210  max= 12000  step= 1  format= %d  div_scale= 1  preset= 0
                    Min = 0  Max = 0  Step = 0  Preset = 0  "
        ::= { iqupc00CmdEntry 40647 }


    iqupc00AudSetupDelaySelectThreshold OBJECT-TYPE
        SYNTAX            INTEGER
        MAX-ACCESS        read-write
        STATUS            current
        DESCRIPTION
                "CMNT: - Set DELAY Threshold
                 TYPE: - Number
                 PAGE: - AudSetup
                    Threshold  cmdID= 40646
                    min= 240  max= 3840  step= 1  format= %d  div_scale= 1  preset= 3840
                    Min = 0  Max = 0  Step = 0  Preset = 0  "
        ::= { iqupc00CmdEntry 40646 }


    iqupc00AudSetupDelaySelectRtrack14 OBJECT-TYPE
        SYNTAX            INTEGER { disable(0), enable(1)  }
        MAX-ACCESS        read-write
        STATUS            current
        DESCRIPTION
                "CMNT: - Use rolltrack14 data for delay
                 TYPE: - Checkbox
                 PAGE: - AudSetup
                    Rtrack14  cmdID= 40600  "
        ::= { iqupc00CmdEntry 40600 }


    iqupc00AudSetupDelaySelectRtrack15 OBJECT-TYPE
        SYNTAX            INTEGER { disable(0), enable(1)  }
        MAX-ACCESS        read-write
        STATUS            current
        DESCRIPTION
                "CMNT: - Use rolltrack15 data for delay
                 TYPE: - Checkbox
                 PAGE: - AudSetup
                    Rtrack15  cmdID= 40608  "
        ::= { iqupc00CmdEntry 40608 }


    iqupc00AudSetupDelaySelectRtrack16 OBJECT-TYPE
        SYNTAX            INTEGER { disable(0), enable(1)  }
        MAX-ACCESS        read-write
        STATUS            current
        DESCRIPTION
                "CMNT: - Use rolltrack16 data for delay
                 TYPE: - Checkbox
                 PAGE: - AudSetup
                    Rtrack16  cmdID= 40616  "
        ::= { iqupc00CmdEntry 40616 }


    iqupc00AudSetupDelaySelectRtrack17 OBJECT-TYPE
        SYNTAX            INTEGER { disable(0), enable(1)  }
        MAX-ACCESS        read-write
        STATUS            current
        DESCRIPTION
                "CMNT: - Use rolltrack17 data for delay
                 TYPE: - Checkbox
                 PAGE: - AudSetup
                    Rtrack17  cmdID= 40624  "
        ::= { iqupc00CmdEntry 40624 }


    iqupc00AudSetupDelaySelectEnableBulk OBJECT-TYPE
        SYNTAX            INTEGER { disable(0), enable(1)  }
        MAX-ACCESS        read-write
        STATUS            current
        DESCRIPTION
                "CMNT: - Use BULK data for delay
                 TYPE: - Checkbox
                 PAGE: - AudSetup
                    EnableBulk  cmdID= 40625  "
        ::= { iqupc00CmdEntry 40625 }


    iqupc00AudSetupDelaySelectEnableVideo OBJECT-TYPE
        SYNTAX            INTEGER { disable(0), enable(1)  }
        MAX-ACCESS        read-write
        STATUS            current
        DESCRIPTION
                "CMNT: - Use BULK data for delay
                 TYPE: - Checkbox
                 PAGE: - AudSetup
                    EnableVideo  cmdID= 40632  "
        ::= { iqupc00CmdEntry 40632 }


    iqupc00AudioAudSetupRollTrack14 OBJECT-TYPE
        SYNTAX            RollCallString
        MAX-ACCESS        read-only
        STATUS            current
        DESCRIPTION
                "CMNT: - Rolltrack input command for delays
                 TYPE: - Display
                 PAGE: - Audio
                    RollTrack14  cmdID= 14  "
        ::= { iqupc00CmdEntry 14 }


    iqupc00AudioAudSetupRollTrack15 OBJECT-TYPE
        SYNTAX            RollCallString
        MAX-ACCESS        read-only
        STATUS            current
        DESCRIPTION
                "CMNT: - Rolltrack input command for delays
                 TYPE: - Display
                 PAGE: - Audio
                    RollTrack15  cmdID= 15  "
        ::= { iqupc00CmdEntry 15 }


    iqupc00AudioAudSetupRollTrack16 OBJECT-TYPE
        SYNTAX            RollCallString
        MAX-ACCESS        read-only
        STATUS            current
        DESCRIPTION
                "CMNT: - Rolltrack input command for delays
                 TYPE: - Display
                 PAGE: - Audio
                    RollTrack16  cmdID= 16  "
        ::= { iqupc00CmdEntry 16 }


    iqupc00AudioAudSetupRollTrack17 OBJECT-TYPE
        SYNTAX            RollCallString
        MAX-ACCESS        read-only
        STATUS            current
        DESCRIPTION
                "CMNT: - Rolltrack input command for delays
                 TYPE: - Display
                 PAGE: - Audio
                    RollTrack17  cmdID= 17  "
        ::= { iqupc00CmdEntry 17 }


    iqupc00AudioAudSetupCurrentVidDelay OBJECT-TYPE
        SYNTAX            RollCallString
        MAX-ACCESS        read-only
        STATUS            current
        DESCRIPTION
                "CMNT: - Internal Video Delay for Synchroniser modules
                 TYPE: - Display
                 PAGE: - Audio
                    CurrentVidDelay  cmdID= 33030  "
        ::= { iqupc00CmdEntry 33030 }


    iqupc00AudioAudSetupMinVidAudDelay OBJECT-TYPE
        SYNTAX            RollCallString
        MAX-ACCESS        read-only
        STATUS            current
        DESCRIPTION
                "CMNT: - Internal Video Delay for Synchroniser modules
                 TYPE: - Display
                 PAGE: - Audio
                    MinVidAudDelay  cmdID= 33043  "
        ::= { iqupc00CmdEntry 33043 }


    iqupc00AudioAudSetupCurrRTrack14Delay OBJECT-TYPE
        SYNTAX            RollCallString
        MAX-ACCESS        read-only
        STATUS            current
        DESCRIPTION
                "CMNT: - Current Delay for Rolltrack 14
                 TYPE: - Display
                 PAGE: - Audio
                    CurrRTrack14Delay  cmdID= 40665  "
        ::= { iqupc00CmdEntry 40665 }


    iqupc00AudioAudSetupCurrRlTrack15Delay OBJECT-TYPE
        SYNTAX            RollCallString
        MAX-ACCESS        read-only
        STATUS            current
        DESCRIPTION
                "CMNT: - Current Delay for Rolltrack 15
                 TYPE: - Display
                 PAGE: - Audio
                    CurrRlTrack15Delay  cmdID= 40666  "
        ::= { iqupc00CmdEntry 40666 }


    iqupc00AudioAudSetupCurrRTrack16Delay OBJECT-TYPE
        SYNTAX            RollCallString
        MAX-ACCESS        read-only
        STATUS            current
        DESCRIPTION
                "CMNT: - Current Delay for Rolltrack 16
                 TYPE: - Display
                 PAGE: - Audio
                    CurrRTrack16Delay  cmdID= 40667  "
        ::= { iqupc00CmdEntry 40667 }


    iqupc00AudioAudSetupCurrRTrack17Delay OBJECT-TYPE
        SYNTAX            RollCallString
        MAX-ACCESS        read-only
        STATUS            current
        DESCRIPTION
                "CMNT: - Current Delay for Rolltrack 17
                 TYPE: - Display
                 PAGE: - Audio
                    CurrRTrack17Delay  cmdID= 40668  "
        ::= { iqupc00CmdEntry 40668 }


    iqupc00AudSetupTonesFreq0 OBJECT-TYPE
        SYNTAX            INTEGER
        MAX-ACCESS        read-write
        STATUS            current
        DESCRIPTION
                "CMNT: - 
                 TYPE: - Number
                 PAGE: - AudSetup
                    Freq0  cmdID= 42600
                    min= 1  max= 160  step= 1  format= %d  div_scale= 1  preset= 4
                    Min = 0  Max = 0  Step = 0  Preset = 0  "
        ::= { iqupc00CmdEntry 42600 }


    iqupc00AudSetupTonesFreq1 OBJECT-TYPE
        SYNTAX            INTEGER
        MAX-ACCESS        read-write
        STATUS            current
        DESCRIPTION
                "CMNT: - 
                 TYPE: - Number
                 PAGE: - AudSetup
                    Freq1  cmdID= 42601
                    min= 1  max= 160  step= 1  format= %d  div_scale= 1  preset= 8
                    Min = 0  Max = 0  Step = 0  Preset = 0  "
        ::= { iqupc00CmdEntry 42601 }


    iqupc00AudSetupTonesFreq2 OBJECT-TYPE
        SYNTAX            INTEGER
        MAX-ACCESS        read-write
        STATUS            current
        DESCRIPTION
                "CMNT: - 
                 TYPE: - Number
                 PAGE: - AudSetup
                    Freq2  cmdID= 42602
                    min= 1  max= 160  step= 1  format= %d  div_scale= 1  preset= 16
                    Min = 0  Max = 0  Step = 0  Preset = 0  "
        ::= { iqupc00CmdEntry 42602 }


    iqupc00AudSetupTonesFreq3 OBJECT-TYPE
        SYNTAX            INTEGER
        MAX-ACCESS        read-write
        STATUS            current
        DESCRIPTION
                "CMNT: - 
                 TYPE: - Number
                 PAGE: - AudSetup
                    Freq3  cmdID= 42603
                    min= 1  max= 160  step= 1  format= %d  div_scale= 1  preset= 32
                    Min = 0  Max = 0  Step = 0  Preset = 0  "
        ::= { iqupc00CmdEntry 42603 }


    iqupc00AudSetupTonesFreq4 OBJECT-TYPE
        SYNTAX            INTEGER
        MAX-ACCESS        read-write
        STATUS            current
        DESCRIPTION
                "CMNT: - 
                 TYPE: - Number
                 PAGE: - AudSetup
                    Freq4  cmdID= 42604
                    min= 1  max= 160  step= 1  format= %d  div_scale= 1  preset= 6
                    Min = 0  Max = 0  Step = 0  Preset = 0  "
        ::= { iqupc00CmdEntry 42604 }


    iqupc00AudSetupTonesFreq5 OBJECT-TYPE
        SYNTAX            INTEGER
        MAX-ACCESS        read-write
        STATUS            current
        DESCRIPTION
                "CMNT: - 
                 TYPE: - Number
                 PAGE: - AudSetup
                    Freq5  cmdID= 42605
                    min= 1  max= 160  step= 1  format= %d  div_scale= 1  preset= 12
                    Min = 0  Max = 0  Step = 0  Preset = 0  "
        ::= { iqupc00CmdEntry 42605 }


    iqupc00AudSetupTonesFreq6 OBJECT-TYPE
        SYNTAX            INTEGER
        MAX-ACCESS        read-write
        STATUS            current
        DESCRIPTION
                "CMNT: - 
                 TYPE: - Number
                 PAGE: - AudSetup
                    Freq6  cmdID= 42606
                    min= 1  max= 160  step= 1  format= %d  div_scale= 1  preset= 24
                    Min = 0  Max = 0  Step = 0  Preset = 0  "
        ::= { iqupc00CmdEntry 42606 }


    iqupc00AudSetupTonesFreq7 OBJECT-TYPE
        SYNTAX            INTEGER
        MAX-ACCESS        read-write
        STATUS            current
        DESCRIPTION
                "CMNT: - 
                 TYPE: - Number
                 PAGE: - AudSetup
                    Freq7  cmdID= 42607
                    min= 1  max= 160  step= 1  format= %d  div_scale= 1  preset= 48
                    Min = 0  Max = 0  Step = 0  Preset = 0  "
        ::= { iqupc00CmdEntry 42607 }


    iqupc00AudSetupTonesIdent0 OBJECT-TYPE
        SYNTAX            INTEGER { disable(0), enable(1)  }
        MAX-ACCESS        read-write
        STATUS            current
        DESCRIPTION
                "CMNT: - 
                 TYPE: - Checkbox
                 PAGE: - AudSetup
                    Ident0  cmdID= 42610  "
        ::= { iqupc00CmdEntry 42610 }


    iqupc00AudSetupTonesIdent1 OBJECT-TYPE
        SYNTAX            INTEGER { disable(0), enable(1)  }
        MAX-ACCESS        read-write
        STATUS            current
        DESCRIPTION
                "CMNT: - 
                 TYPE: - Checkbox
                 PAGE: - AudSetup
                    Ident1  cmdID= 42611  "
        ::= { iqupc00CmdEntry 42611 }


    iqupc00AudSetupTonesIdent2 OBJECT-TYPE
        SYNTAX            INTEGER { disable(0), enable(1)  }
        MAX-ACCESS        read-write
        STATUS            current
        DESCRIPTION
                "CMNT: - 
                 TYPE: - Checkbox
                 PAGE: - AudSetup
                    Ident2  cmdID= 42612  "
        ::= { iqupc00CmdEntry 42612 }


    iqupc00AudSetupTonesIdent3 OBJECT-TYPE
        SYNTAX            INTEGER { disable(0), enable(1)  }
        MAX-ACCESS        read-write
        STATUS            current
        DESCRIPTION
                "CMNT: - 
                 TYPE: - Checkbox
                 PAGE: - AudSetup
                    Ident3  cmdID= 42613  "
        ::= { iqupc00CmdEntry 42613 }


    iqupc00AudSetupTonesIdent4 OBJECT-TYPE
        SYNTAX            INTEGER { disable(0), enable(1)  }
        MAX-ACCESS        read-write
        STATUS            current
        DESCRIPTION
                "CMNT: - 
                 TYPE: - Checkbox
                 PAGE: - AudSetup
                    Ident4  cmdID= 42614  "
        ::= { iqupc00CmdEntry 42614 }


    iqupc00AudSetupTonesIdent5 OBJECT-TYPE
        SYNTAX            INTEGER { disable(0), enable(1)  }
        MAX-ACCESS        read-write
        STATUS            current
        DESCRIPTION
                "CMNT: - 
                 TYPE: - Checkbox
                 PAGE: - AudSetup
                    Ident5  cmdID= 42615  "
        ::= { iqupc00CmdEntry 42615 }


    iqupc00AudSetupTonesIdent6 OBJECT-TYPE
        SYNTAX            INTEGER { disable(0), enable(1)  }
        MAX-ACCESS        read-write
        STATUS            current
        DESCRIPTION
                "CMNT: - 
                 TYPE: - Checkbox
                 PAGE: - AudSetup
                    Ident6  cmdID= 42616  "
        ::= { iqupc00CmdEntry 42616 }


    iqupc00AudSetupTonesIdent7 OBJECT-TYPE
        SYNTAX            INTEGER { disable(0), enable(1)  }
        MAX-ACCESS        read-write
        STATUS            current
        DESCRIPTION
                "CMNT: - 
                 TYPE: - Checkbox
                 PAGE: - AudSetup
                    Ident7  cmdID= 42617  "
        ::= { iqupc00CmdEntry 42617 }


    iqupc00AudioAudSetupNeg1Frame OBJECT-TYPE
        SYNTAX            INTEGER { noAction(0),valNeg1Frame(1) }
        MAX-ACCESS        read-write
        STATUS            current
        DESCRIPTION
                "CMNT: - 
                 TYPE: - Button
                 PAGE: - Audio
                    Neg1Frame  cmdID= 40626
                    value= 1  "
        ::= { iqupc00CmdEntry 40626 }


    iqupc00AudioAudSetupNeg1ms OBJECT-TYPE
        SYNTAX            INTEGER { noAction(0),valNeg1ms(1) }
        MAX-ACCESS        read-write
        STATUS            current
        DESCRIPTION
                "CMNT: - 
                 TYPE: - Button
                 PAGE: - Audio
                    Neg1ms  cmdID= 40627
                    value= 1  "
        ::= { iqupc00CmdEntry 40627 }


    iqupc00AudioAudSetupNeg4samp OBJECT-TYPE
        SYNTAX            INTEGER { noAction(0),valNeg4samp(1) }
        MAX-ACCESS        read-write
        STATUS            current
        DESCRIPTION
                "CMNT: - 
                 TYPE: - Button
                 PAGE: - Audio
                    Neg4samp  cmdID= 40628
                    value= 1  "
        ::= { iqupc00CmdEntry 40628 }


    iqupc00AudioAudSetupPos4samp OBJECT-TYPE
        SYNTAX            INTEGER { noAction(0),valPos4samp(1) }
        MAX-ACCESS        read-write
        STATUS            current
        DESCRIPTION
                "CMNT: - 
                 TYPE: - Button
                 PAGE: - Audio
                    Pos4samp  cmdID= 40629
                    value= 1  "
        ::= { iqupc00CmdEntry 40629 }


    iqupc00AudioAudSetupPos1ms OBJECT-TYPE
        SYNTAX            INTEGER { noAction(0),valPos1ms(1) }
        MAX-ACCESS        read-write
        STATUS            current
        DESCRIPTION
                "CMNT: - 
                 TYPE: - Button
                 PAGE: - Audio
                    Pos1ms  cmdID= 40630
                    value= 1  "
        ::= { iqupc00CmdEntry 40630 }


    iqupc00AudioAudSetupPos1Frame OBJECT-TYPE
        SYNTAX            INTEGER { noAction(0),valPos1Frame(1) }
        MAX-ACCESS        read-write
        STATUS            current
        DESCRIPTION
                "CMNT: - 
                 TYPE: - Button
                 PAGE: - Audio
                    Pos1Frame  cmdID= 40631
                    value= 1  "
        ::= { iqupc00CmdEntry 40631 }


    iqupc00AudioAudSetupSilentLevel OBJECT-TYPE
        SYNTAX            INTEGER
        MAX-ACCESS        read-write
        STATUS            current
        DESCRIPTION
                "CMNT: - Set Audio Silent level
                 TYPE: - Number
                 PAGE: - Audio
                    SilentLevel  cmdID= 3061
                    min= -100  max= -2  step= 1  format= %0.0f dBFS  div_scale= 1  preset= -70
                    Min = -100 dBFS  Max = -2 dBFS  Step = 1 dBFS  Preset = -70 dBFS  "
        ::= { iqupc00CmdEntry 3061 }


    iqupc00AudioAudSetupOverloadLevel OBJECT-TYPE
        SYNTAX            INTEGER
        MAX-ACCESS        read-write
        STATUS            current
        DESCRIPTION
                "CMNT: - Set Audio Overload level
                 TYPE: - Number
                 PAGE: - Audio
                    OverloadLevel  cmdID= 3064
                    min= -99  max= -1  step= 1  format= %0.0f dBFS  div_scale= 1  preset= -1
                    Min = -99 dBFS  Max = -1 dBFS  Step = 1 dBFS  Preset = -1 dBFS  "
        ::= { iqupc00CmdEntry 3064 }


    iqupc00AudioAudSetupLevelTimeout OBJECT-TYPE
        SYNTAX            INTEGER
        MAX-ACCESS        read-write
        STATUS            current
        DESCRIPTION
                "CMNT: - Set Audio level timeout
                 TYPE: - Number
                 PAGE: - Audio
                    LevelTimeout  cmdID= 3065
                    min= 1  max= 20  step= 1  format= %d  div_scale= 1  preset= 10
                    Min = 0  Max = 0  Step = 0  Preset = 0  "
        ::= { iqupc00CmdEntry 3065 }


    iqupc00AudioAudSetupLevelUpdateEnb OBJECT-TYPE
        SYNTAX            INTEGER { disable(0), enable(1)  }
        MAX-ACCESS        read-write
        STATUS            current
        DESCRIPTION
                "CMNT: - Enable Audio level updates to rollmap
                 TYPE: - Checkbox
                 PAGE: - Audio
                    LevelUpdateEnb  cmdID= 38275  "
        ::= { iqupc00CmdEntry 38275 }


    iqupc00AudioAudSetupAudLevel OBJECT-TYPE
        SYNTAX            RollCallString
        MAX-ACCESS        read-only
        STATUS            current
        DESCRIPTION
                "CMNT: - Audio level updates to rollmap
                 TYPE: - Display
                 PAGE: - Audio
                    AudLevel  cmdID= 38276  "
        ::= { iqupc00CmdEntry 38276 }


    iqupc00AudioRoutingInputRouteDest1 OBJECT-TYPE
        SYNTAX            INTEGER
        MAX-ACCESS        read-write
        STATUS            current
        DESCRIPTION
                "CMNT: - 
                 TYPE: - Number
                 PAGE: - Audio
                    Input Route Dest 1  cmdID= 40223
                    min= 0  max= 22  step= 1  format= 0  div_scale= 1  preset= 0
                    Min = 0  Max = 0  Step = 0  Preset = 0  "
        ::= { iqupc00CmdEntry 40223 }


    iqupc00AudioRoutingInputRouteDest2 OBJECT-TYPE
        SYNTAX            INTEGER
        MAX-ACCESS        read-write
        STATUS            current
        DESCRIPTION
                "CMNT: - 
                 TYPE: - Number
                 PAGE: - Audio
                    Input Route Dest 2  cmdID= 40224
                    min= 0  max= 22  step= 1  format= 0  div_scale= 1  preset= 1
                    Min = 0  Max = 0  Step = 0  Preset = 0  "
        ::= { iqupc00CmdEntry 40224 }


    iqupc00AudioRoutingInputRouteDest3 OBJECT-TYPE
        SYNTAX            INTEGER
        MAX-ACCESS        read-write
        STATUS            current
        DESCRIPTION
                "CMNT: - 
                 TYPE: - Number
                 PAGE: - Audio
                    Input Route Dest 3  cmdID= 40225
                    min= 0  max= 22  step= 1  format= 0  div_scale= 1  preset= 2
                    Min = 0  Max = 0  Step = 0  Preset = 0  "
        ::= { iqupc00CmdEntry 40225 }


    iqupc00AudioRoutingInputRouteDest4 OBJECT-TYPE
        SYNTAX            INTEGER
        MAX-ACCESS        read-write
        STATUS            current
        DESCRIPTION
                "CMNT: - 
                 TYPE: - Number
                 PAGE: - Audio
                    Input Route Dest 4  cmdID= 40226
                    min= 0  max= 22  step= 1  format= 0  div_scale= 1  preset= 3
                    Min = 0  Max = 0  Step = 0  Preset = 0  "
        ::= { iqupc00CmdEntry 40226 }


    iqupc00AudioRoutingInputRouteDest5 OBJECT-TYPE
        SYNTAX            INTEGER
        MAX-ACCESS        read-write
        STATUS            current
        DESCRIPTION
                "CMNT: - 
                 TYPE: - Number
                 PAGE: - Audio
                    Input Route Dest 5  cmdID= 40227
                    min= 0  max= 22  step= 1  format= 0  div_scale= 1  preset= 4
                    Min = 0  Max = 0  Step = 0  Preset = 0  "
        ::= { iqupc00CmdEntry 40227 }


    iqupc00AudioRoutingInputRouteDest6 OBJECT-TYPE
        SYNTAX            INTEGER
        MAX-ACCESS        read-write
        STATUS            current
        DESCRIPTION
                "CMNT: - 
                 TYPE: - Number
                 PAGE: - Audio
                    Input Route Dest 6  cmdID= 40228
                    min= 0  max= 22  step= 1  format= 0  div_scale= 1  preset= 5
                    Min = 0  Max = 0  Step = 0  Preset = 0  "
        ::= { iqupc00CmdEntry 40228 }


    iqupc00AudioRoutingInputRouteDest7 OBJECT-TYPE
        SYNTAX            INTEGER
        MAX-ACCESS        read-write
        STATUS            current
        DESCRIPTION
                "CMNT: - 
                 TYPE: - Number
                 PAGE: - Audio
                    Input Route Dest 7  cmdID= 40229
                    min= 0  max= 22  step= 1  format= 0  div_scale= 1  preset= 6
                    Min = 0  Max = 0  Step = 0  Preset = 0  "
        ::= { iqupc00CmdEntry 40229 }


    iqupc00AudioRoutingInputRouteDest8 OBJECT-TYPE
        SYNTAX            INTEGER
        MAX-ACCESS        read-write
        STATUS            current
        DESCRIPTION
                "CMNT: - 
                 TYPE: - Number
                 PAGE: - Audio
                    Input Route Dest 8  cmdID= 40230
                    min= 0  max= 22  step= 1  format= 0  div_scale= 1  preset= 7
                    Min = 0  Max = 0  Step = 0  Preset = 0  "
        ::= { iqupc00CmdEntry 40230 }


    iqupc00AudioRoutingInputNameAnalog OBJECT-TYPE
        SYNTAX            RollCallString
        MAX-ACCESS        read-only
        STATUS            current
        DESCRIPTION
                "CMNT: - 
                 TYPE: - Display
                 PAGE: - Audio
                    Input Name Analog  cmdID= 40216  "
        ::= { iqupc00CmdEntry 40216 }


    iqupc00AudioRoutingInputNameDlby1 OBJECT-TYPE
        SYNTAX            RollCallString
        MAX-ACCESS        read-only
        STATUS            current
        DESCRIPTION
                "CMNT: - 
                 TYPE: - Display
                 PAGE: - Audio
                    Input Name Dlby 1  cmdID= 40218  "
        ::= { iqupc00CmdEntry 40218 }


    iqupc00AudioRoutingInputNameDlby2 OBJECT-TYPE
        SYNTAX            RollCallString
        MAX-ACCESS        read-only
        STATUS            current
        DESCRIPTION
                "CMNT: - 
                 TYPE: - Display
                 PAGE: - Audio
                    Input Name Dlby 2  cmdID= 40219  "
        ::= { iqupc00CmdEntry 40219 }


    iqupc00AudioRoutingInputNameDlby3 OBJECT-TYPE
        SYNTAX            RollCallString
        MAX-ACCESS        read-only
        STATUS            current
        DESCRIPTION
                "CMNT: - 
                 TYPE: - Display
                 PAGE: - Audio
                    Input Name Dlby 3  cmdID= 40220  "
        ::= { iqupc00CmdEntry 40220 }


    iqupc00AudioRoutingInputNameDlby4 OBJECT-TYPE
        SYNTAX            RollCallString
        MAX-ACCESS        read-only
        STATUS            current
        DESCRIPTION
                "CMNT: - 
                 TYPE: - Display
                 PAGE: - Audio
                    Input Name Dlby 4  cmdID= 40221  "
        ::= { iqupc00CmdEntry 40221 }


    iqupc00AudioRoutingInputNameDlby5 OBJECT-TYPE
        SYNTAX            RollCallString
        MAX-ACCESS        read-only
        STATUS            current
        DESCRIPTION
                "CMNT: - 
                 TYPE: - Display
                 PAGE: - Audio
                    Input Name Dlby 5  cmdID= 40222  "
        ::= { iqupc00CmdEntry 40222 }


    iqupc00AudioRoutingInputHideAES1 OBJECT-TYPE
        SYNTAX            RollCallString
        MAX-ACCESS        read-only
        STATUS            current
        DESCRIPTION
                "CMNT: - 
                 TYPE: - Display
                 PAGE: - Audio
                    Input Hide AES 1  cmdID= 40233  "
        ::= { iqupc00CmdEntry 40233 }


    iqupc00AudioRoutingInputHideAES2 OBJECT-TYPE
        SYNTAX            RollCallString
        MAX-ACCESS        read-only
        STATUS            current
        DESCRIPTION
                "CMNT: - 
                 TYPE: - Display
                 PAGE: - Audio
                    Input Hide AES 2  cmdID= 40234  "
        ::= { iqupc00CmdEntry 40234 }


    iqupc00AudioRoutingInputHideAES3 OBJECT-TYPE
        SYNTAX            RollCallString
        MAX-ACCESS        read-only
        STATUS            current
        DESCRIPTION
                "CMNT: - 
                 TYPE: - Display
                 PAGE: - Audio
                    Input Hide AES 3  cmdID= 40235  "
        ::= { iqupc00CmdEntry 40235 }


    iqupc00AudioRoutingInputHideAES4 OBJECT-TYPE
        SYNTAX            RollCallString
        MAX-ACCESS        read-only
        STATUS            current
        DESCRIPTION
                "CMNT: - 
                 TYPE: - Display
                 PAGE: - Audio
                    Input Hide AES 4  cmdID= 40236  "
        ::= { iqupc00CmdEntry 40236 }


    iqupc00AudioRoutingInputHideAES5 OBJECT-TYPE
        SYNTAX            RollCallString
        MAX-ACCESS        read-only
        STATUS            current
        DESCRIPTION
                "CMNT: - 
                 TYPE: - Display
                 PAGE: - Audio
                    Input Hide AES 5  cmdID= 40237  "
        ::= { iqupc00CmdEntry 40237 }


    iqupc00AudioRoutingInputHideAES6 OBJECT-TYPE
        SYNTAX            RollCallString
        MAX-ACCESS        read-only
        STATUS            current
        DESCRIPTION
                "CMNT: - 
                 TYPE: - Display
                 PAGE: - Audio
                    Input Hide AES 6  cmdID= 40238  "
        ::= { iqupc00CmdEntry 40238 }


    iqupc00AudioRoutingInputHideAES7 OBJECT-TYPE
        SYNTAX            RollCallString
        MAX-ACCESS        read-only
        STATUS            current
        DESCRIPTION
                "CMNT: - 
                 TYPE: - Display
                 PAGE: - Audio
                    Input Hide AES 7  cmdID= 40239  "
        ::= { iqupc00CmdEntry 40239 }


    iqupc00AudioRoutingInputHideAES8 OBJECT-TYPE
        SYNTAX            RollCallString
        MAX-ACCESS        read-only
        STATUS            current
        DESCRIPTION
                "CMNT: - 
                 TYPE: - Display
                 PAGE: - Audio
                    Input Hide AES 8  cmdID= 40240  "
        ::= { iqupc00CmdEntry 40240 }


    iqupc00AudioRoutingOutputHideAES1 OBJECT-TYPE
        SYNTAX            RollCallString
        MAX-ACCESS        read-only
        STATUS            current
        DESCRIPTION
                "CMNT: - 
                 TYPE: - Display
                 PAGE: - Audio
                    Output Hide AES 1  cmdID= 40250  "
        ::= { iqupc00CmdEntry 40250 }


    iqupc00AudioRoutingOutputHideAES2 OBJECT-TYPE
        SYNTAX            RollCallString
        MAX-ACCESS        read-only
        STATUS            current
        DESCRIPTION
                "CMNT: - 
                 TYPE: - Display
                 PAGE: - Audio
                    Output Hide AES 2  cmdID= 40251  "
        ::= { iqupc00CmdEntry 40251 }


    iqupc00AudioRoutingOutputHideAES3 OBJECT-TYPE
        SYNTAX            RollCallString
        MAX-ACCESS        read-only
        STATUS            current
        DESCRIPTION
                "CMNT: - 
                 TYPE: - Display
                 PAGE: - Audio
                    Output Hide AES 3  cmdID= 40252  "
        ::= { iqupc00CmdEntry 40252 }


    iqupc00AudioRoutingOutputHideAES4 OBJECT-TYPE
        SYNTAX            RollCallString
        MAX-ACCESS        read-only
        STATUS            current
        DESCRIPTION
                "CMNT: - 
                 TYPE: - Display
                 PAGE: - Audio
                    Output Hide AES 4  cmdID= 40253  "
        ::= { iqupc00CmdEntry 40253 }


    iqupc00AudioRoutingOutputHideAES5 OBJECT-TYPE
        SYNTAX            RollCallString
        MAX-ACCESS        read-only
        STATUS            current
        DESCRIPTION
                "CMNT: - 
                 TYPE: - Display
                 PAGE: - Audio
                    Output Hide AES 5  cmdID= 40254  "
        ::= { iqupc00CmdEntry 40254 }


    iqupc00AudioRoutingOutputHideAES6 OBJECT-TYPE
        SYNTAX            RollCallString
        MAX-ACCESS        read-only
        STATUS            current
        DESCRIPTION
                "CMNT: - 
                 TYPE: - Display
                 PAGE: - Audio
                    Output Hide AES 6  cmdID= 40255  "
        ::= { iqupc00CmdEntry 40255 }


    iqupc00AudioRoutingOutputHideAES7 OBJECT-TYPE
        SYNTAX            RollCallString
        MAX-ACCESS        read-only
        STATUS            current
        DESCRIPTION
                "CMNT: - 
                 TYPE: - Display
                 PAGE: - Audio
                    Output Hide AES 7  cmdID= 40256  "
        ::= { iqupc00CmdEntry 40256 }


    iqupc00AudioRoutingOutputHideAES8 OBJECT-TYPE
        SYNTAX            RollCallString
        MAX-ACCESS        read-only
        STATUS            current
        DESCRIPTION
                "CMNT: - 
                 TYPE: - Display
                 PAGE: - Audio
                    Output Hide AES 8  cmdID= 40257  "
        ::= { iqupc00CmdEntry 40257 }


    iqupc00AudioRoutingDolbyDecodeSource OBJECT-TYPE
        SYNTAX            INTEGER {
                            valDisembed1(0),
                            valDisembed2(1),
                            valDisembed3(2),
                            valDisembed4(3),
                            valDisembed5(4),
                            valDisembed6(5),
                            valDisembed7(6),
                            valDisembed8(7),
                            valAes1(8),
                            valAes2(9),
                            valAes3(10),
                            valAes4(11),
                            valAes5(12),
                            valAes6(13),
                            valAes7(14),
                            valAes8(15)
                            }
        MAX-ACCESS        read-write
        STATUS            current
        DESCRIPTION
                "CMNT: - 
                 TYPE: - RadiobuttonList
                 PAGE: - Audio
                    DolbyDecode Source  cmdID= 40241
                    Disembed 1  value= 0
                    Disembed 2  value= 1
                    Disembed 3  value= 2
                    Disembed 4  value= 3
                    Disembed 5  value= 4
                    Disembed 6  value= 5
                    Disembed 7  value= 6
                    Disembed 8  value= 7
                    Aes 1  value= 8
                    Aes 2  value= 9
                    Aes 3  value= 10
                    Aes 4  value= 11
                    Aes 5  value= 12
                    Aes 6  value= 13
                    Aes 7  value= 14
                    Aes 8  value= 15  "
        ::= { iqupc00CmdEntry 40241 }


    iqupc00AudioRoutingDolbyDecodeNum OBJECT-TYPE
        SYNTAX            INTEGER
        MAX-ACCESS        read-write
        STATUS            current
        DESCRIPTION
                "CMNT: - 
                 TYPE: - Number
                 PAGE: - Audio
                    DolbyDecodeNum  cmdID= 40242
                    min= 0  max= 1  step= 1  format= 0  div_scale= 1  preset= 0
                    Min = 0  Max = 0  Step = 0  Preset = 0  "
        ::= { iqupc00CmdEntry 40242 }


    iqupc00AudioOutputRoutingOutDest1 OBJECT-TYPE
        SYNTAX            INTEGER
        MAX-ACCESS        read-write
        STATUS            current
        DESCRIPTION
                "CMNT: - 
                 TYPE: - Number
                 PAGE: - Audio
                    OutDest1  cmdID= 40293
                    min= 0  max= 47  step= 1  format= %d  div_scale= 1  preset= 0
                    Min = 0  Max = 0  Step = 0  Preset = 0  "
        ::= { iqupc00CmdEntry 40293 }


    iqupc00AudioOutputRoutingOutDest2 OBJECT-TYPE
        SYNTAX            INTEGER
        MAX-ACCESS        read-write
        STATUS            current
        DESCRIPTION
                "CMNT: - 
                 TYPE: - Number
                 PAGE: - Audio
                    OutDest2  cmdID= 40294
                    min= 0  max= 47  step= 1  format= %d  div_scale= 1  preset= 1
                    Min = 0  Max = 0  Step = 0  Preset = 0  "
        ::= { iqupc00CmdEntry 40294 }


    iqupc00AudioOutputRoutingOutDest3 OBJECT-TYPE
        SYNTAX            INTEGER
        MAX-ACCESS        read-write
        STATUS            current
        DESCRIPTION
                "CMNT: - 
                 TYPE: - Number
                 PAGE: - Audio
                    OutDest3  cmdID= 40295
                    min= 0  max= 47  step= 1  format= %d  div_scale= 1  preset= 2
                    Min = 0  Max = 0  Step = 0  Preset = 0  "
        ::= { iqupc00CmdEntry 40295 }


    iqupc00AudioOutputRoutingOutDest4 OBJECT-TYPE
        SYNTAX            INTEGER
        MAX-ACCESS        read-write
        STATUS            current
        DESCRIPTION
                "CMNT: - 
                 TYPE: - Number
                 PAGE: - Audio
                    OutDest4  cmdID= 40296
                    min= 0  max= 47  step= 1  format= %d  div_scale= 1  preset= 3
                    Min = 0  Max = 0  Step = 0  Preset = 0  "
        ::= { iqupc00CmdEntry 40296 }


    iqupc00AudioOutputRoutingOutDest5 OBJECT-TYPE
        SYNTAX            INTEGER
        MAX-ACCESS        read-write
        STATUS            current
        DESCRIPTION
                "CMNT: - 
                 TYPE: - Number
                 PAGE: - Audio
                    OutDest5  cmdID= 40297
                    min= 0  max= 47  step= 1  format= %d  div_scale= 1  preset= 4
                    Min = 0  Max = 0  Step = 0  Preset = 0  "
        ::= { iqupc00CmdEntry 40297 }


    iqupc00AudioOutputRoutingOutDest6 OBJECT-TYPE
        SYNTAX            INTEGER
        MAX-ACCESS        read-write
        STATUS            current
        DESCRIPTION
                "CMNT: - 
                 TYPE: - Number
                 PAGE: - Audio
                    OutDest6  cmdID= 40298
                    min= 0  max= 47  step= 1  format= %d  div_scale= 1  preset= 5
                    Min = 0  Max = 0  Step = 0  Preset = 0  "
        ::= { iqupc00CmdEntry 40298 }


    iqupc00AudioOutputRoutingOutDest7 OBJECT-TYPE
        SYNTAX            INTEGER
        MAX-ACCESS        read-write
        STATUS            current
        DESCRIPTION
                "CMNT: - 
                 TYPE: - Number
                 PAGE: - Audio
                    OutDest7  cmdID= 40299
                    min= 0  max= 47  step= 1  format= %d  div_scale= 1  preset= 6
                    Min = 0  Max = 0  Step = 0  Preset = 0  "
        ::= { iqupc00CmdEntry 40299 }


    iqupc00AudioOutputRoutingOutDest8 OBJECT-TYPE
        SYNTAX            INTEGER
        MAX-ACCESS        read-write
        STATUS            current
        DESCRIPTION
                "CMNT: - 
                 TYPE: - Number
                 PAGE: - Audio
                    OutDest8  cmdID= 40300
                    min= 0  max= 47  step= 1  format= %d  div_scale= 1  preset= 7
                    Min = 0  Max = 0  Step = 0  Preset = 0  "
        ::= { iqupc00CmdEntry 40300 }


    iqupc00AudioOutputRoutingOutDest9 OBJECT-TYPE
        SYNTAX            INTEGER
        MAX-ACCESS        read-write
        STATUS            current
        DESCRIPTION
                "CMNT: - 
                 TYPE: - Number
                 PAGE: - Audio
                    OutDest9  cmdID= 40301
                    min= 0  max= 47  step= 1  format= %d  div_scale= 1  preset= 8
                    Min = 0  Max = 0  Step = 0  Preset = 0  "
        ::= { iqupc00CmdEntry 40301 }


    iqupc00AudioOutputRoutingOutDest10 OBJECT-TYPE
        SYNTAX            INTEGER
        MAX-ACCESS        read-write
        STATUS            current
        DESCRIPTION
                "CMNT: - 
                 TYPE: - Number
                 PAGE: - Audio
                    OutDest10  cmdID= 40302
                    min= 0  max= 47  step= 1  format= %d  div_scale= 1  preset= 9
                    Min = 0  Max = 0  Step = 0  Preset = 0  "
        ::= { iqupc00CmdEntry 40302 }


    iqupc00AudioOutputRoutingOutDest11 OBJECT-TYPE
        SYNTAX            INTEGER
        MAX-ACCESS        read-write
        STATUS            current
        DESCRIPTION
                "CMNT: - 
                 TYPE: - Number
                 PAGE: - Audio
                    OutDest11  cmdID= 40303
                    min= 0  max= 47  step= 1  format= %d  div_scale= 1  preset= 10
                    Min = 0  Max = 0  Step = 0  Preset = 0  "
        ::= { iqupc00CmdEntry 40303 }


    iqupc00AudioOutputRoutingOutDest12 OBJECT-TYPE
        SYNTAX            INTEGER
        MAX-ACCESS        read-write
        STATUS            current
        DESCRIPTION
                "CMNT: - 
                 TYPE: - Number
                 PAGE: - Audio
                    OutDest12  cmdID= 40304
                    min= 0  max= 47  step= 1  format= %d  div_scale= 1  preset= 11
                    Min = 0  Max = 0  Step = 0  Preset = 0  "
        ::= { iqupc00CmdEntry 40304 }


    iqupc00AudioOutputRoutingOutDest13 OBJECT-TYPE
        SYNTAX            INTEGER
        MAX-ACCESS        read-write
        STATUS            current
        DESCRIPTION
                "CMNT: - 
                 TYPE: - Number
                 PAGE: - Audio
                    OutDest13  cmdID= 40305
                    min= 0  max= 47  step= 1  format= %d  div_scale= 1  preset= 12
                    Min = 0  Max = 0  Step = 0  Preset = 0  "
        ::= { iqupc00CmdEntry 40305 }


    iqupc00AudioOutputRoutingOutDest14 OBJECT-TYPE
        SYNTAX            INTEGER
        MAX-ACCESS        read-write
        STATUS            current
        DESCRIPTION
                "CMNT: - 
                 TYPE: - Number
                 PAGE: - Audio
                    OutDest14  cmdID= 40306
                    min= 0  max= 47  step= 1  format= %d  div_scale= 1  preset= 13
                    Min = 0  Max = 0  Step = 0  Preset = 0  "
        ::= { iqupc00CmdEntry 40306 }


    iqupc00AudioOutputRoutingOutDest15 OBJECT-TYPE
        SYNTAX            INTEGER
        MAX-ACCESS        read-write
        STATUS            current
        DESCRIPTION
                "CMNT: - 
                 TYPE: - Number
                 PAGE: - Audio
                    OutDest15  cmdID= 40307
                    min= 0  max= 47  step= 1  format= %d  div_scale= 1  preset= 14
                    Min = 0  Max = 0  Step = 0  Preset = 0  "
        ::= { iqupc00CmdEntry 40307 }


    iqupc00AudioOutputRoutingOutDest16 OBJECT-TYPE
        SYNTAX            INTEGER
        MAX-ACCESS        read-write
        STATUS            current
        DESCRIPTION
                "CMNT: - 
                 TYPE: - Number
                 PAGE: - Audio
                    OutDest16  cmdID= 40308
                    min= 0  max= 47  step= 1  format= %d  div_scale= 1  preset= 15
                    Min = 0  Max = 0  Step = 0  Preset = 0  "
        ::= { iqupc00CmdEntry 40308 }


    iqupc00AudioOutputRoutingDolbyEncEnb OBJECT-TYPE
        SYNTAX            RollCallString
        MAX-ACCESS        read-only
        STATUS            current
        DESCRIPTION
                "CMNT: - 
                 TYPE: - Display
                 PAGE: - Audio
                    DolbyEncEnb  cmdID= 40214  "
        ::= { iqupc00CmdEntry 40214 }


    iqupc00AudioOutputRoutingUpmixEnb OBJECT-TYPE
        SYNTAX            RollCallString
        MAX-ACCESS        read-only
        STATUS            current
        DESCRIPTION
                "CMNT: - 
                 TYPE: - Display
                 PAGE: - Audio
                    UpmixEnb  cmdID= 40213  "
        ::= { iqupc00CmdEntry 40213 }


    iqupc00AudioProcDefaultEmbed OBJECT-TYPE
        SYNTAX            INTEGER {
                            valCustom(3),
                            valRampp2dB(0),
                            valRampn2dB(1),
                            valLevel0dB(2)
                            }
        MAX-ACCESS        read-write
        STATUS            current
        DESCRIPTION
                "CMNT: - Procamp default
                 TYPE: - RadiobuttonList
                 PAGE: - Audio
                    Embed  cmdID= 43105
                    Custom  value= 3
                    Ramp +2dB  value= 0
                    Ramp -2dB  value= 1
                    Level 0dB  value= 2  "
        ::= { iqupc00CmdEntry 43105 }


    iqupc00AudioRoutingMatrixBus1audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 1 aud sel  cmdID= 40200
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40200 }


    iqupc00AudioRoutingMatrixBus2audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 2 aud sel  cmdID= 40201
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40201 }


    iqupc00AudioRoutingMatrixBus3audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 3 aud sel  cmdID= 40202
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40202 }


    iqupc00AudioRoutingMatrixBus4audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 4 aud sel  cmdID= 40203
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40203 }


    iqupc00AudioRoutingMatrixBus5audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 5 aud sel  cmdID= 40204
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40204 }


    iqupc00AudioRoutingMatrixBus6audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 6 aud sel  cmdID= 40205
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40205 }


    iqupc00AudioRoutingMatrixBus7audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 7 aud sel  cmdID= 40206
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40206 }


    iqupc00AudioRoutingMatrixBus8audsel OBJECT-TYPE
        SYNTAX            INTEGER {
                            valDisemb1(0),
                            valDisemb2(1),
                            valDisemb3(2),
                            valDisemb4(3),
                            valDisemb5(4),
                            valDisemb6(5),
                            valDisemb7(6),
                            valDisemb8(7),
                            valDolbyDec1(18),
                            valDolbyDec2(19),
                            valDolbyDec3(20),
                            valDolbyDec4(21),
                            valDolbyDec5(22)
                            }
        MAX-ACCESS        read-write
        STATUS            current
        DESCRIPTION
                "CMNT: - 
                 TYPE: - RadiobuttonList
                 PAGE: - Audio Routing Matrix
                    Bus 8 aud sel  cmdID= 40207
                    Disemb1  value= 0
                    Disemb2  value= 1
                    Disemb3  value= 2
                    Disemb4  value= 3
                    Disemb5  value= 4
                    Disemb6  value= 5
                    Disemb7  value= 6
                    Disemb8  value= 7
                    DolbyDec1  value= 18
                    DolbyDec2  value= 19
                    DolbyDec3  value= 20
                    DolbyDec4  value= 21
                    DolbyDec5  value= 22  "
        ::= { iqupc00CmdEntry 40207 }


    iqupc00AudioOutRouteMatrixEmbed12MatrixEmbed11audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed1_1 aud sel  cmdID= 40329
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40329 }


    iqupc00AudioOutRouteMatrixEmbed12MatrixEmbed12audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed1_2 aud sel  cmdID= 40330
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40330 }


    iqupc00AudioOutRouteMatrixEmbed12MatrixEmbed21audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed2_1 aud sel  cmdID= 40331
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40331 }


    iqupc00AudioOutRouteMatrixEmbed12MatrixEmbed22audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed2_2 aud sel  cmdID= 40332
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40332 }


    iqupc00AudioOutRouteMatrixEmbed34MatrixEmbed31audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed3_1 aud sel  cmdID= 40333
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40333 }


    iqupc00AudioOutRouteMatrixEmbed34MatrixEmbed32audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed3_2 aud sel  cmdID= 40334
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40334 }


    iqupc00AudioOutRouteMatrixEmbed34MatrixEmbed41audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed4_1 aud sel  cmdID= 40335
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40335 }


    iqupc00AudioOutRouteMatrixEmbed34MatrixEmbed42audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed4_2 aud sel  cmdID= 40336
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40336 }


    iqupc00AudioOutRouteMatrixEmbed56MatrixEmbed51audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed5_1 aud sel  cmdID= 40337
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40337 }


    iqupc00AudioOutRouteMatrixEmbed56MatrixEmbed52audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed5_2 aud sel  cmdID= 40338
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40338 }


    iqupc00AudioOutRouteMatrixEmbed56MatrixEmbed61audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed6_1 aud sel  cmdID= 40339
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40339 }


    iqupc00AudioOutRouteMatrixEmbed56MatrixEmbed62audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed6_2 aud sel  cmdID= 40340
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40340 }


    iqupc00AudioOutRouteMatrixEmbed78MatrixEmbed71audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed7_1 aud sel  cmdID= 40341
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40341 }


    iqupc00AudioOutRouteMatrixEmbed78MatrixEmbed72audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed7_2 aud sel  cmdID= 40342
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40342 }


    iqupc00AudioOutRouteMatrixEmbed78MatrixEmbed81audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed8_1 aud sel  cmdID= 40343
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40343 }


    iqupc00AudioOutRouteMatrixEmbed78MatrixEmbed82audsel OBJECT-TYPE
        SYNTAX            INTEGER {
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valSilence(34),
                            valMixer1(35),
                            valMixer2(36),
                            valMixer3(37),
                            valMixer4(38),
                            valDownmix11(39),
                            valDownmix12(40),
                            valDownmix21(41),
                            valDownmix22(42),
                            valUpmixL(24),
                            valUpmixR(25),
                            valUpmixC(26),
                            valUpmixLFE(27),
                            valUpmixLs(28),
                            valUpmixRs(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - 
                 TYPE: - RadiobuttonList
                 PAGE: - AudioOut RouteMatrix
                    Embed8_2 aud sel  cmdID= 40344
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Silence  value= 34
                    Mixer1  value= 35
                    Mixer2  value= 36
                    Mixer3  value= 37
                    Mixer4  value= 38
                    Downmix1_1  value= 39
                    Downmix1_2  value= 40
                    Downmix2_1  value= 41
                    Downmix2_2  value= 42
                    UpmixL  value= 24
                    UpmixR  value= 25
                    UpmixC  value= 26
                    UpmixLFE  value= 27
                    UpmixLs  value= 28
                    UpmixRs  value= 29
                    Tone 1  value= 16
                    Tone 2  value= 17
                    Tone 3  value= 18
                    Tone 4  value= 19
                    Tone 5  value= 20
                    Tone 6  value= 21
                    Tone 7  value= 22
                    Tone 8  value= 23  "
        ::= { iqupc00CmdEntry 40344 }


    iqupc00AudioOutRouteMatrixDefaultsEmbOut OBJECT-TYPE
        SYNTAX            INTEGER {
                            valCustom(10),
                            valEmbedPassthrough(0),
                            valAESPassthrough(1),
                            valDisEm1n4(2),
                            valDisEm1n4AESin1n4(3),
                            valDisEm1n4AESin5n8(4),
                            valAESin1n4(5),
                            valAESin5n8(6),
                            valAnlgin1n2(7),
                            valTone1n2(8),
                            valSilent(9)
                            }
        MAX-ACCESS        read-write
        STATUS            current
        DESCRIPTION
                "CMNT: - 
                 TYPE: - RadiobuttonList
                 PAGE: - AudioOut RouteMatrix
                    Emb Out  cmdID= 40365
                    Custom  value= 10
                    Embed Passthrough  value= 0
                    AES Passthrough  value= 1
                    DisEm1-4  value= 2
                    DisEm1-4 & AESin1-4  value= 3
                    DisEm1-4 & AESin5-8  value= 4
                    AESin1-4  value= 5
                    AESin5-8  value= 6
                    Anlg in 1-2  value= 7
                    Tone 1-2  value= 8
                    Silent  value= 9  "
        ::= { iqupc00CmdEntry 40365 }


    iqupc00UpMixerLoud14Source1ProcGain OBJECT-TYPE
        SYNTAX            INTEGER
        MAX-ACCESS        read-write
        STATUS            current
        DESCRIPTION
                "CMNT: - Mix_1 Proc Amp Gain
                 TYPE: - Number
                 PAGE: - UpMixerLoud1_4
                    ProcGain  cmdID= 40834
                    min= -801  max= 120  step= 1  format= %0.1f dB  div_scale= 10  preset= 0
                    Min = -80.1 dB  Max = 12.0 dB  Step = 0.1 dB  Preset = 0.0 dB  "
        ::= { iqupc00CmdEntry 40834 }


    iqupc00UpMixerLoud14Source1Mute OBJECT-TYPE
        SYNTAX            INTEGER { disable(0), enable(1)  }
        MAX-ACCESS        read-write
        STATUS            current
        DESCRIPTION
                "CMNT: - Mix_1 Mute
                 TYPE: - Checkbox
                 PAGE: - UpMixerLoud1_4
                    Mute  cmdID= 40840  "
        ::= { iqupc00CmdEntry 40840 }


    iqupc00UpMixerLoud14Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_1 source
                 TYPE: - RadiobuttonList
                 PAGE: - UpMixerLoud1_4
                    Src  cmdID= 40846
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40846 }


    iqupc00UpMixerLoud14Source2ProcGain OBJECT-TYPE
        SYNTAX            INTEGER
        MAX-ACCESS        read-write
        STATUS            current
        DESCRIPTION
                "CMNT: - Mix_2 Proc Amp Gain
                 TYPE: - Number
                 PAGE: - UpMixerLoud1_4
                    ProcGain  cmdID= 40835
                    min= -801  max= 120  step= 1  format= %0.1f dB  div_scale= 10  preset= 0
                    Min = -80.1 dB  Max = 12.0 dB  Step = 0.1 dB  Preset = 0.0 dB  "
        ::= { iqupc00CmdEntry 40835 }


    iqupc00UpMixerLoud14Source2Mute OBJECT-TYPE
        SYNTAX            INTEGER { disable(0), enable(1)  }
        MAX-ACCESS        read-write
        STATUS            current
        DESCRIPTION
                "CMNT: - Mix_2 Mute
                 TYPE: - Checkbox
                 PAGE: - UpMixerLoud1_4
                    Mute  cmdID= 40841  "
        ::= { iqupc00CmdEntry 40841 }


    iqupc00UpMixerLoud14Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_2 source
                 TYPE: - RadiobuttonList
                 PAGE: - UpMixerLoud1_4
                    Src  cmdID= 40847
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40847 }


    iqupc00UpMixerLoud14Source3ProcGain OBJECT-TYPE
        SYNTAX            INTEGER
        MAX-ACCESS        read-write
        STATUS            current
        DESCRIPTION
                "CMNT: - Mix_3 Proc Amp Gain
                 TYPE: - Number
                 PAGE: - UpMixerLoud1_4
                    ProcGain  cmdID= 40836
                    min= -801  max= 120  step= 1  format= %0.1f dB  div_scale= 10  preset= 0
                    Min = -80.1 dB  Max = 12.0 dB  Step = 0.1 dB  Preset = 0.0 dB  "
        ::= { iqupc00CmdEntry 40836 }


    iqupc00UpMixerLoud14Source3Mute OBJECT-TYPE
        SYNTAX            INTEGER { disable(0), enable(1)  }
        MAX-ACCESS        read-write
        STATUS            current
        DESCRIPTION
                "CMNT: - Mix_3 Mute
                 TYPE: - Checkbox
                 PAGE: - UpMixerLoud1_4
                    Mute  cmdID= 40842  "
        ::= { iqupc00CmdEntry 40842 }


    iqupc00UpMixerLoud14Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_3 source
                 TYPE: - RadiobuttonList
                 PAGE: - UpMixerLoud1_4
                    Src  cmdID= 40848
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40848 }


    iqupc00UpMixerLoud14Source4ProcGain OBJECT-TYPE
        SYNTAX            INTEGER
        MAX-ACCESS        read-write
        STATUS            current
        DESCRIPTION
                "CMNT: - Mix_4 Proc Amp Gain
                 TYPE: - Number
                 PAGE: - UpMixerLoud1_4
                    ProcGain  cmdID= 40837
                    min= -801  max= 120  step= 1  format= %0.1f dB  div_scale= 10  preset= 0
                    Min = -80.1 dB  Max = 12.0 dB  Step = 0.1 dB  Preset = 0.0 dB  "
        ::= { iqupc00CmdEntry 40837 }


    iqupc00UpMixerLoud14Source4Mute OBJECT-TYPE
        SYNTAX            INTEGER { disable(0), enable(1)  }
        MAX-ACCESS        read-write
        STATUS            current
        DESCRIPTION
                "CMNT: - Mix_4 Mute
                 TYPE: - Checkbox
                 PAGE: - UpMixerLoud1_4
                    Mute  cmdID= 40843  "
        ::= { iqupc00CmdEntry 40843 }


    iqupc00UpMixerLoud14Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_4 source
                 TYPE: - RadiobuttonList
                 PAGE: - UpMixerLoud1_4
                    Src  cmdID= 40849
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40849 }


    iqupc00UpMixerLoud14Mode OBJECT-TYPE
        SYNTAX            INTEGER {
                            valAuto(0),
                            valAlwaysUpmix(1),
                            valBypass(2)
                            }
        MAX-ACCESS        read-write
        STATUS            current
        DESCRIPTION
                "CMNT: - UpMixer mode
                 TYPE: - RadiobuttonList
                 PAGE: - UpMixerLoud1_4
                    Mode  cmdID= 40854
                    Auto  value= 0
                    Always Upmix  value= 1
                    Bypass  value= 2  "
        ::= { iqupc00CmdEntry 40854 }


    iqupc00UpMixerLoud14Status OBJECT-TYPE
        SYNTAX            RollCallString
        MAX-ACCESS        read-only
        STATUS            current
        DESCRIPTION
                "CMNT: - UpMixer status
                 TYPE: - Display
                 PAGE: - UpMixerLoud1_4
                    Status  cmdID= 40855  "
        ::= { iqupc00CmdEntry 40855 }


    iqupc00UpMixerLoud14XfadeBypass OBJECT-TYPE
        SYNTAX            INTEGER {
                            valVerySlow(0),
                            valSlow(1),
                            valMedium(2),
                            valFast(3),
                            valVeryFast(4),
                            valInstant(5)
                            }
        MAX-ACCESS        read-write
        STATUS            current
        DESCRIPTION
                "CMNT: - UpMixer Xfade to bypass
                 TYPE: - RadiobuttonList
                 PAGE: - UpMixerLoud1_4
                    XfadeBypass  cmdID= 40856
                    Very Slow  value= 0
                    Slow  value= 1
                    Medium  value= 2
                    Fast  value= 3
                    Very Fast  value= 4
                    Instant  value= 5  "
        ::= { iqupc00CmdEntry 40856 }


    iqupc00UpMixerLoud14XfadeUpmix OBJECT-TYPE
        SYNTAX            INTEGER {
                            valVerySlow(0),
                            valSlow(1),
                            valMedium(2),
                            valFast(3),
                            valVeryFast(4),
                            valInstant(5)
                            }
        MAX-ACCESS        read-write
        STATUS            current
        DESCRIPTION
                "CMNT: - UpMixer Xfade to upmix
                 TYPE: - RadiobuttonList
                 PAGE: - UpMixerLoud1_4
                    XfadeUpmix  cmdID= 40857
                    Very Slow  value= 0
                    Slow  value= 1
                    Medium  value= 2
                    Fast  value= 3
                    Very Fast  value= 4
                    Instant  value= 5  "
        ::= { iqupc00CmdEntry 40857 }


    iqupc00UpMixerLoud14Detect OBJECT-TYPE
        SYNTAX            INTEGER
        MAX-ACCESS        read-write
        STATUS            current
        DESCRIPTION
                "CMNT: - UpMixer Detection threshold
                 TYPE: - Number
                 PAGE: - UpMixerLoud1_4
                    Detect  cmdID= 40858
                    min= -1500  max= 0  step= 1  format= %0.1f dB  div_scale= 10  preset= -600
                    Min = -150.0 dB  Max = 0.0 dB  Step = 0.1 dB  Preset = -60.0 dB  "
        ::= { iqupc00CmdEntry 40858 }


    iqupc00UpMixerLoud14CenterWidth OBJECT-TYPE
        SYNTAX            INTEGER
        MAX-ACCESS        read-write
        STATUS            current
        DESCRIPTION
                "CMNT: - UpMixer Center width
                 TYPE: - Number
                 PAGE: - UpMixerLoud1_4
                    CenterWidth  cmdID= 40859
                    min= 0  max= 1000  step= 1  format= %0.1f%%  div_scale= 10  preset= 0
                    Min = 0.0%  Max = 100.0%  Step = 0.1%  Preset = 0.0%  "
        ::= { iqupc00CmdEntry 40859 }


    iqupc00UpMixerLoud14Surround OBJECT-TYPE
        SYNTAX            INTEGER
        MAX-ACCESS        read-write
        STATUS            current
        DESCRIPTION
                "CMNT: - UpMixer Surround Depth
                 TYPE: - Number
                 PAGE: - UpMixerLoud1_4
                    Surround  cmdID= 40860
                    min= 0  max= 1000  step= 1  format= %0.1f%%  div_scale= 10  preset= 1000
                    Min = 0.0%  Max = 100.0%  Step = 0.1%  Preset = 100.0%  "
        ::= { iqupc00CmdEntry 40860 }


    iqupc00UpMixerLoud14AlgorithmType OBJECT-TYPE
        SYNTAX            INTEGER {
                            valUpmix(0),
                            valLoudness51(1),
                            valLoudness1p2(2),
                            valLoudness1(3),
                            valUpmixLoudA(5)
                            }
        MAX-ACCESS        read-write
        STATUS            current
        DESCRIPTION
                "CMNT: - Linear Acoustic Algorithm Type
                 TYPE: - RadiobuttonList
                 PAGE: - UpMixerLoud1_4
                    Algorithm Type  cmdID= 36148
                    Upmix  value= 0
                    Loudness5.1  value= 1
                    Loudness1+2  value= 2
                    Loudness1  value= 3
                    UpmixLoudA  value= 5  "
        ::= { iqupc00CmdEntry 36148 }


    iqupc00UpMixerLoud58LoudnessPreset1 OBJECT-TYPE
        SYNTAX            INTEGER {
                            valGeneral(0),
                            valLight(1),
                            valHeavy(2),
                            valLoud(3),
                            valLoudLimit(4),
                            valProtectionLimit(5),
                            valCustom1(6),
                            valCustom2(7)
                            }
        MAX-ACCESS        read-write
        STATUS            current
        DESCRIPTION
                "CMNT: - Linear Acoustic Preset 1
                 TYPE: - RadiobuttonList
                 PAGE: - UpMixerLoud5_8
                    Preset1  cmdID= 36151
                    General  value= 0
                    Light  value= 1
                    Heavy  value= 2
                    Loud  value= 3
                    Loud Limit  value= 4
                    Protection Limit  value= 5
                    Custom 1  value= 6
                    Custom 2  value= 7  "
        ::= { iqupc00CmdEntry 36151 }


    iqupc00UpMixerLoud58LoudnessMasterLevel1 OBJECT-TYPE
        SYNTAX            INTEGER
        MAX-ACCESS        read-write
        STATUS            current
        DESCRIPTION
                "CMNT: - Linear Acoustic Master level 1
                 TYPE: - Number
                 PAGE: - UpMixerLoud5_8
                    MasterLevel1  cmdID= 36149
                    min= -310  max= 0  step= 1  format= %0.1f dB  div_scale= 10  preset= -110
                    Min = -31.0 dB  Max = 0.0 dB  Step = 0.1 dB  Preset = -11.0 dB  "
        ::= { iqupc00CmdEntry 36149 }


    iqupc00UpMixerLoud58LoudnessName1 OBJECT-TYPE
        SYNTAX            RollCallString
        MAX-ACCESS        read-only
        STATUS            current
        DESCRIPTION
                "CMNT: - Linear Acoustic Name 1
                 TYPE: - Display
                 PAGE: - UpMixerLoud5_8
                    Name1  cmdID= 36153  "
        ::= { iqupc00CmdEntry 36153 }


    iqupc00UpMixerLoud58LoudnessBypass1 OBJECT-TYPE
        SYNTAX            INTEGER { disable(0), enable(1)  }
        MAX-ACCESS        read-write
        STATUS            current
        DESCRIPTION
                "CMNT: - Linear Acoustic Bypass 1
                 TYPE: - Checkbox
                 PAGE: - UpMixerLoud5_8
                    Bypass 1  cmdID= 36173  "
        ::= { iqupc00CmdEntry 36173 }


    iqupc00UpMixerLoud58LoudnessPreset2 OBJECT-TYPE
        SYNTAX            INTEGER {
                            valGeneral(0),
                            valLight(1),
                            valHeavy(2),
                            valLoud(3),
                            valLoudLimit(4),
                            valProtectionLimit(5),
                            valCustom1(6),
                            valCustom2(7)
                            }
        MAX-ACCESS        read-write
        STATUS            current
        DESCRIPTION
                "CMNT: - Linear Acoustic Preset 2
                 TYPE: - RadiobuttonList
                 PAGE: - UpMixerLoud5_8
                    Preset2  cmdID= 36152
                    General  value= 0
                    Light  value= 1
                    Heavy  value= 2
                    Loud  value= 3
                    Loud Limit  value= 4
                    Protection Limit  value= 5
                    Custom 1  value= 6
                    Custom 2  value= 7  "
        ::= { iqupc00CmdEntry 36152 }


    iqupc00UpMixerLoud58LoudnessMasterLevel2 OBJECT-TYPE
        SYNTAX            INTEGER
        MAX-ACCESS        read-write
        STATUS            current
        DESCRIPTION
                "CMNT: - Linear Acoustic Master level 2
                 TYPE: - Number
                 PAGE: - UpMixerLoud5_8
                    MasterLevel2  cmdID= 36150
                    min= -310  max= 0  step= 1  format= %0.1f dB  div_scale= 10  preset= -110
                    Min = -31.0 dB  Max = 0.0 dB  Step = 0.1 dB  Preset = -11.0 dB  "
        ::= { iqupc00CmdEntry 36150 }


    iqupc00UpMixerLoud58LoudnessName2 OBJECT-TYPE
        SYNTAX            RollCallString
        MAX-ACCESS        read-only
        STATUS            current
        DESCRIPTION
                "CMNT: - Linear Acoustic Name 2
                 TYPE: - Display
                 PAGE: - UpMixerLoud5_8
                    Name2  cmdID= 36154  "
        ::= { iqupc00CmdEntry 36154 }


    iqupc00UpMixerLoud58LoudnessBypass2 OBJECT-TYPE
        SYNTAX            INTEGER { disable(0), enable(1)  }
        MAX-ACCESS        read-write
        STATUS            current
        DESCRIPTION
                "CMNT: - Linear Acoustic Bypass 2
                 TYPE: - Checkbox
                 PAGE: - UpMixerLoud5_8
                    Bypass 2  cmdID= 36174  "
        ::= { iqupc00CmdEntry 36174 }


    iqupc00UpMixerLoud58Source5ProcGain OBJECT-TYPE
        SYNTAX            INTEGER
        MAX-ACCESS        read-write
        STATUS            current
        DESCRIPTION
                "CMNT: - Mix_5 Proc Amp Gain
                 TYPE: - Number
                 PAGE: - UpMixerLoud5_8
                    ProcGain  cmdID= 40838
                    min= -801  max= 120  step= 1  format= %0.1f dB  div_scale= 10  preset= 0
                    Min = -80.1 dB  Max = 12.0 dB  Step = 0.1 dB  Preset = 0.0 dB  "
        ::= { iqupc00CmdEntry 40838 }


    iqupc00UpMixerLoud58Source5Mute OBJECT-TYPE
        SYNTAX            INTEGER { disable(0), enable(1)  }
        MAX-ACCESS        read-write
        STATUS            current
        DESCRIPTION
                "CMNT: - Mix_5 Mute
                 TYPE: - Checkbox
                 PAGE: - UpMixerLoud5_8
                    Mute  cmdID= 40844  "
        ::= { iqupc00CmdEntry 40844 }


    iqupc00UpMixerLoud58Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_5 source
                 TYPE: - RadiobuttonList
                 PAGE: - UpMixerLoud5_8
                    Src  cmdID= 40850
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40850 }


    iqupc00UpMixerLoud58Source6ProcGain OBJECT-TYPE
        SYNTAX            INTEGER
        MAX-ACCESS        read-write
        STATUS            current
        DESCRIPTION
                "CMNT: - Mix_6 Proc Amp Gain
                 TYPE: - Number
                 PAGE: - UpMixerLoud5_8
                    ProcGain  cmdID= 40839
                    min= -801  max= 120  step= 1  format= %0.1f dB  div_scale= 10  preset= 0
                    Min = -80.1 dB  Max = 12.0 dB  Step = 0.1 dB  Preset = 0.0 dB  "
        ::= { iqupc00CmdEntry 40839 }


    iqupc00UpMixerLoud58Source6Mute OBJECT-TYPE
        SYNTAX            INTEGER { disable(0), enable(1)  }
        MAX-ACCESS        read-write
        STATUS            current
        DESCRIPTION
                "CMNT: - Mix_6 Mute
                 TYPE: - Checkbox
                 PAGE: - UpMixerLoud5_8
                    Mute  cmdID= 40845  "
        ::= { iqupc00CmdEntry 40845 }


    iqupc00UpMixerLoud58Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_6 source
                 TYPE: - RadiobuttonList
                 PAGE: - UpMixerLoud5_8
                    Src  cmdID= 40851
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40851 }


    iqupc00UpMixerLoud58Source7ProcGain OBJECT-TYPE
        SYNTAX            INTEGER
        MAX-ACCESS        read-write
        STATUS            current
        DESCRIPTION
                "CMNT: - Mix_7 Proc Amp Gain
                 TYPE: - Number
                 PAGE: - UpMixerLoud5_8
                    ProcGain  cmdID= 40873
                    min= -801  max= 120  step= 1  format= %0.1f dB  div_scale= 10  preset= 0
                    Min = -80.1 dB  Max = 12.0 dB  Step = 0.1 dB  Preset = 0.0 dB  "
        ::= { iqupc00CmdEntry 40873 }


    iqupc00UpMixerLoud58Source7Mute OBJECT-TYPE
        SYNTAX            INTEGER { disable(0), enable(1)  }
        MAX-ACCESS        read-write
        STATUS            current
        DESCRIPTION
                "CMNT: - Mix_7 Mute
                 TYPE: - Checkbox
                 PAGE: - UpMixerLoud5_8
                    Mute  cmdID= 40875  "
        ::= { iqupc00CmdEntry 40875 }


    iqupc00UpMixerLoud58Source7Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_7 source
                 TYPE: - RadiobuttonList
                 PAGE: - UpMixerLoud5_8
                    Src  cmdID= 40877
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40877 }


    iqupc00UpMixerLoud58Source8ProcGain OBJECT-TYPE
        SYNTAX            INTEGER
        MAX-ACCESS        read-write
        STATUS            current
        DESCRIPTION
                "CMNT: - Mix_8 Proc Amp Gain
                 TYPE: - Number
                 PAGE: - UpMixerLoud5_8
                    ProcGain  cmdID= 40874
                    min= -801  max= 120  step= 1  format= %0.1f dB  div_scale= 10  preset= 0
                    Min = -80.1 dB  Max = 12.0 dB  Step = 0.1 dB  Preset = 0.0 dB  "
        ::= { iqupc00CmdEntry 40874 }


    iqupc00UpMixerLoud58Source8Mute OBJECT-TYPE
        SYNTAX            INTEGER { disable(0), enable(1)  }
        MAX-ACCESS        read-write
        STATUS            current
        DESCRIPTION
                "CMNT: - Mix_8 Mute
                 TYPE: - Checkbox
                 PAGE: - UpMixerLoud5_8
                    Mute  cmdID= 40876  "
        ::= { iqupc00CmdEntry 40876 }


    iqupc00UpMixerLoud58Source8Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valMixer1(35),
                            valMixer2(36),
                            valMixer3(37),
                            valMixer4(38),
                            valDownmix11(39),
                            valDownmix12(40),
                            valDownmix21(41),
                            valDownmix22(42),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_8 source
                 TYPE: - RadiobuttonList
                 PAGE: - UpMixerLoud5_8
                    Src  cmdID= 40878
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    Mixer1  value= 35
                    Mixer2  value= 36
                    Mixer3  value= 37
                    Mixer4  value= 38
                    Downmix1_1  value= 39
                    Downmix1_2  value= 40
                    Downmix2_1  value= 41
                    Downmix2_2  value= 42
                    Tone1  value= 16
                    Tone2  value= 17
                    Tone3  value= 18
                    Tone4  value= 19
                    Tone5  value= 20
                    Tone6  value= 21
                    Tone7  value= 22
                    Tone8  value= 23  "
        ::= { iqupc00CmdEntry 40878 }


    iqupc00UpMixerLoud58UpmixHide OBJECT-TYPE
        SYNTAX            RollCallString
        MAX-ACCESS        read-only
        STATUS            current
        DESCRIPTION
                "CMNT: - Hide Upmix
                 TYPE: - Display
                 PAGE: - UpMixerLoud5_8
                    UpmixHide  cmdID= 36155  "
        ::= { iqupc00CmdEntry 36155 }


    iqupc00UpMixerLoud58Chan1Name OBJECT-TYPE
        SYNTAX            RollCallString
        MAX-ACCESS        read-only
        STATUS            current
        DESCRIPTION
                "CMNT: - Linear Acoustic Chan Name 1
                 TYPE: - Display
                 PAGE: - UpMixerLoud5_8
                    Chan1Name  cmdID= 36158  "
        ::= { iqupc00CmdEntry 36158 }


    iqupc00UpMixerLoud58Chan2Name OBJECT-TYPE
        SYNTAX            RollCallString
        MAX-ACCESS        read-only
        STATUS            current
        DESCRIPTION
                "CMNT: - Linear Acoustic Chan Name 2
                 TYPE: - Display
                 PAGE: - UpMixerLoud5_8
                    Chan2Name  cmdID= 36159  "
        ::= { iqupc00CmdEntry 36159 }


    iqupc00UpMixerLoud58Chan3Name OBJECT-TYPE
        SYNTAX            RollCallString
        MAX-ACCESS        read-only
        STATUS            current
        DESCRIPTION
                "CMNT: - Linear Acoustic Chan Name 3
                 TYPE: - Display
                 PAGE: - UpMixerLoud5_8
                    Chan3Name  cmdID= 36160  "
        ::= { iqupc00CmdEntry 36160 }


    iqupc00UpMixerLoud58Chan4Name OBJECT-TYPE
        SYNTAX            RollCallString
        MAX-ACCESS        read-only
        STATUS            current
        DESCRIPTION
                "CMNT: - Linear Acoustic Chan Name 4
                 TYPE: - Display
                 PAGE: - UpMixerLoud5_8
                    Chan4Name  cmdID= 36161  "
        ::= { iqupc00CmdEntry 36161 }


    iqupc00UpMixerLoud58Chan5Name OBJECT-TYPE
        SYNTAX            RollCallString
        MAX-ACCESS        read-only
        STATUS            current
        DESCRIPTION
                "CMNT: - Linear Acoustic Chan Name 5
                 TYPE: - Display
                 PAGE: - UpMixerLoud5_8
                    Chan5Name  cmdID= 36162  "
        ::= { iqupc00CmdEntry 36162 }


    iqupc00UpMixerLoud58Chan6Name OBJECT-TYPE
        SYNTAX            RollCallString
        MAX-ACCESS        read-only
        STATUS            current
        DESCRIPTION
                "CMNT: - Linear Acoustic Chan Name 6
                 TYPE: - Display
                 PAGE: - UpMixerLoud5_8
                    Chan6Name  cmdID= 36163  "
        ::= { iqupc00CmdEntry 36163 }


    iqupc00UpMixerLoud58Chan7Name OBJECT-TYPE
        SYNTAX            RollCallString
        MAX-ACCESS        read-only
        STATUS            current
        DESCRIPTION
                "CMNT: - Linear Acoustic Chan Name 7
                 TYPE: - Display
                 PAGE: - UpMixerLoud5_8
                    Chan7Name  cmdID= 36183  "
        ::= { iqupc00CmdEntry 36183 }


    iqupc00UpMixerLoud58Chan8Name OBJECT-TYPE
        SYNTAX            RollCallString
        MAX-ACCESS        read-only
        STATUS            current
        DESCRIPTION
                "CMNT: - Linear Acoustic Chan Name 8
                 TYPE: - Display
                 PAGE: - UpMixerLoud5_8
                    Chan8Name  cmdID= 36184  "
        ::= { iqupc00CmdEntry 36184 }


    iqupc00UpMixerLoud58Chan1NameIn OBJECT-TYPE
        SYNTAX            RollCallString
        MAX-ACCESS        read-only
        STATUS            current
        DESCRIPTION
                "CMNT: - Linear Acoustic Chan Name 1
                 TYPE: - Display
                 PAGE: - UpMixerLoud5_8
                    Chan1NameIn  cmdID= 36175  "
        ::= { iqupc00CmdEntry 36175 }


    iqupc00UpMixerLoud58Chan2NameIn OBJECT-TYPE
        SYNTAX            RollCallString
        MAX-ACCESS        read-only
        STATUS            current
        DESCRIPTION
                "CMNT: - Linear Acoustic Chan Name 2
                 TYPE: - Display
                 PAGE: - UpMixerLoud5_8
                    Chan2NameIn  cmdID= 36176  "
        ::= { iqupc00CmdEntry 36176 }


    iqupc00UpMixerLoud58Chan3NameIn OBJECT-TYPE
        SYNTAX            RollCallString
        MAX-ACCESS        read-only
        STATUS            current
        DESCRIPTION
                "CMNT: - Linear Acoustic Chan Name 3
                 TYPE: - Display
                 PAGE: - UpMixerLoud5_8
                    Chan3NameIn  cmdID= 36177  "
        ::= { iqupc00CmdEntry 36177 }


    iqupc00UpMixerLoud58Chan4NameIn OBJECT-TYPE
        SYNTAX            RollCallString
        MAX-ACCESS        read-only
        STATUS            current
        DESCRIPTION
                "CMNT: - Linear Acoustic Chan Name 4
                 TYPE: - Display
                 PAGE: - UpMixerLoud5_8
                    Chan4NameIn  cmdID= 36178  "
        ::= { iqupc00CmdEntry 36178 }


    iqupc00UpMixerLoud58Chan5NameIn OBJECT-TYPE
        SYNTAX            RollCallString
        MAX-ACCESS        read-only
        STATUS            current
        DESCRIPTION
                "CMNT: - Linear Acoustic Chan Name 5
                 TYPE: - Display
                 PAGE: - UpMixerLoud5_8
                    Chan5NameIn  cmdID= 36179  "
        ::= { iqupc00CmdEntry 36179 }


    iqupc00UpMixerLoud58Chan6NameIn OBJECT-TYPE
        SYNTAX            RollCallString
        MAX-ACCESS        read-only
        STATUS            current
        DESCRIPTION
                "CMNT: - Linear Acoustic Chan Name 6
                 TYPE: - Display
                 PAGE: - UpMixerLoud5_8
                    Chan6NameIn  cmdID= 36180  "
        ::= { iqupc00CmdEntry 36180 }


    iqupc00UpMixerLoud58Chan7NameIn OBJECT-TYPE
        SYNTAX            RollCallString
        MAX-ACCESS        read-only
        STATUS            current
        DESCRIPTION
                "CMNT: - Linear Acoustic Chan Name 7
                 TYPE: - Display
                 PAGE: - UpMixerLoud5_8
                    Chan7NameIn  cmdID= 36181  "
        ::= { iqupc00CmdEntry 36181 }


    iqupc00UpMixerLoud58Chan8NameIn OBJECT-TYPE
        SYNTAX            RollCallString
        MAX-ACCESS        read-only
        STATUS            current
        DESCRIPTION
                "CMNT: - Linear Acoustic Chan Name 8
                 TYPE: - Display
                 PAGE: - UpMixerLoud5_8
                    Chan8NameIn  cmdID= 36182  "
        ::= { iqupc00CmdEntry 36182 }


    iqupc00UpMixerLoud58DialogHide OBJECT-TYPE
        SYNTAX            RollCallString
        MAX-ACCESS        read-only
        STATUS            current
        DESCRIPTION
                "CMNT: - Hide Upmix DIALOG
                 TYPE: - Display
                 PAGE: - UpMixerLoud5_8
                    DialogHide  cmdID= 36164  "
        ::= { iqupc00CmdEntry 36164 }


    iqupc00LoudCustomBlock1Name OBJECT-TYPE
        SYNTAX            RollCallString
        MAX-ACCESS        read-write
        STATUS            current
        DESCRIPTION
                "CMNT: - Linear Acoustic MB Block1 Name
                 TYPE: - Editstring
                 PAGE: - LoudCustom
                    Name  cmdID= 36304
                    preset= Custom Block 1"
        ::= { iqupc00CmdEntry 36304 }


    iqupc00LoudCustomBlock1inagcfreeze OBJECT-TYPE
        SYNTAX            INTEGER
        MAX-ACCESS        read-write
        STATUS            current
        DESCRIPTION
                "CMNT: - Linear Acoustic InAGC Block1 Freeze Threshold
                 TYPE: - Number
                 PAGE: - LoudCustom
                    inagc freeze  cmdID= 36200
                    min= -180  max= 0  step= 1  format= %0.1f dBFS  div_scale= 2  preset= -62
                    Min = -90.0 dBFS  Max = 0.0 dBFS  Step = 0.5 dBFS  Preset = -31.0 dBFS  "
        ::= { iqupc00CmdEntry 36200 }


    iqupc00LoudCustomBlock1inagcgate OBJECT-TYPE
        SYNTAX            INTEGER
        MAX-ACCESS        read-write
        STATUS            current
        DESCRIPTION
                "CMNT: - Linear Acoustic InAGC Block1 Gate Threshold
                 TYPE: - Number
                 PAGE: - LoudCustom
                    inagc gate  cmdID= 36202
                    min= -180  max= 0  step= 1  format= %0.1f dBFS  div_scale= 2  preset= -42
                    Min = -90.0 dBFS  Max = 0.0 dBFS  Step = 0.5 dBFS  Preset = -21.0 dBFS  "
        ::= { iqupc00CmdEntry 36202 }


    iqupc00LoudCustomBlock1inagcratio OBJECT-TYPE
        SYNTAX            INTEGER
        MAX-ACCESS        read-write
        STATUS            current
        DESCRIPTION
                "CMNT: - Linear Acoustic InAGC Block1 Ratio
                 TYPE: - Number
                 PAGE: - LoudCustom
                    inagc ratio  cmdID= 36208
                    min= 0  max= 100  step= 1  format= %0.0f  div_scale= 1  preset= 91
                    Min = 0  Max = 100  Step = 1  Preset = 91  "
        ::= { iqupc00CmdEntry 36208 }


    iqupc00LoudCustomBlock1inagcrange OBJECT-TYPE
        SYNTAX            INTEGER
        MAX-ACCESS        read-write
        STATUS            current
        DESCRIPTION
                "CMNT: - Linear Acoustic InAGC Block1 Range
                 TYPE: - Number
                 PAGE: - LoudCustom
                    inagc range  cmdID= 36206
                    min= 0  max= 180  step= 1  format= %0.1f dB  div_scale= 5  preset= 125
                    Min = 0.0 dB  Max = 36.0 dB  Step = 0.2 dB  Preset = 25.0 dB  "
        ::= { iqupc00CmdEntry 36206 }


    iqupc00LoudCustomBlock1inagcthresh OBJECT-TYPE
        SYNTAX            INTEGER
        MAX-ACCESS        read-write
        STATUS            current
        DESCRIPTION
                "CMNT: - Linear Acoustic InAGC Block1 Threshold
                 TYPE: - Number
                 PAGE: - LoudCustom
                    inagc thresh  cmdID= 36204
                    min= -180  max= 0  step= 1  format= %0.1f dBFS  div_scale= 10  preset= -140
                    Min = -18.0 dBFS  Max = 0.0 dBFS  Step = 0.1 dBFS  Preset = -14.0 dBFS  "
        ::= { iqupc00CmdEntry 36204 }


    iqupc00LoudCustomBlock1inagcattack OBJECT-TYPE
        SYNTAX            INTEGER
        MAX-ACCESS        read-write
        STATUS            current
        DESCRIPTION
                "CMNT: - Linear Acoustic InAGC Block1 Attack
                 TYPE: - Number
                 PAGE: - LoudCustom
                    inagc attack  cmdID= 36210
                    min= 1  max= 100  step= 1  format= %0.0f  div_scale= 1  preset= 24
                    Min = 1  Max = 100  Step = 1  Preset = 24  "
        ::= { iqupc00CmdEntry 36210 }


    iqupc00LoudCustomBlock1inagcrelease OBJECT-TYPE
        SYNTAX            INTEGER
        MAX-ACCESS        read-write
        STATUS            current
        DESCRIPTION
                "CMNT: - Linear Acoustic InAGC Block1 Release
                 TYPE: - Number
                 PAGE: - LoudCustom
                    inagc release  cmdID= 36212
                    min= 1  max= 100  step= 1  format= %0.0f  div_scale= 1  preset= 42
                    Min = 1  Max = 100  Step = 1  Preset = 42  "
        ::= { iqupc00CmdEntry 36212 }


    iqupc00LoudCustomBlock1peqfreq1 OBJECT-TYPE
        SYNTAX            INTEGER
        MAX-ACCESS        read-write
        STATUS            current
        DESCRIPTION
                "CMNT: - Linear Acoustic PEQ Block1 Index 1 Frequency
                 TYPE: - Number
                 PAGE: - LoudCustom
                    peq freq 1  cmdID= 36276
                    min= 20  max= 20000  step= 1  format= %0.0f Hz  div_scale= 1  preset= 1000
                    Min = 20 Hz  Max = 20000 Hz  Step = 1 Hz  Preset = 1000 Hz  "
        ::= { iqupc00CmdEntry 36276 }


    iqupc00LoudCustomBlock1peqq1 OBJECT-TYPE
        SYNTAX            INTEGER
        MAX-ACCESS        read-write
        STATUS            current
        DESCRIPTION
                "CMNT: - Linear Acoustic PEQ Block1 Index 1 Q
                 TYPE: - Number
                 PAGE: - LoudCustom
                    peq q 1  cmdID= 36282
                    min= 1  max= 200  step= 1  format= %0.2f  div_scale= 20  preset= 20
                    Min = 0.05  Max = 10.00  Step = 0.05  Preset = 1.00  "
        ::= { iqupc00CmdEntry 36282 }


    iqupc00LoudCustomBlock1peqlevel1 OBJECT-TYPE
        SYNTAX            INTEGER
        MAX-ACCESS        read-write
        STATUS            current
        DESCRIPTION
                "CMNT: - Linear Acoustic PEQ Block1 Index 1 Level
                 TYPE: - Number
                 PAGE: - LoudCustom
                    peq level 1  cmdID= 36288
                    min= -90  max= 90  step= 1  format= %0.1f dB  div_scale= 5  preset= 0
                    Min = -18.0 dB  Max = 18.0 dB  Step = 0.2 dB  Preset = 0.0 dB  "
        ::= { iqupc00CmdEntry 36288 }


    iqupc00LoudCustomBlock1peqfreq2 OBJECT-TYPE
        SYNTAX            INTEGER
        MAX-ACCESS        read-write
        STATUS            current
        DESCRIPTION
                "CMNT: - Linear Acoustic PEQ Block1 Index 2 Frequency
                 TYPE: - Number
                 PAGE: - LoudCustom
                    peq freq 2  cmdID= 36277
                    min= 20  max= 20000  step= 1  format= %0.0f Hz  div_scale= 1  preset= 1000
                    Min = 20 Hz  Max = 20000 Hz  Step = 1 Hz  Preset = 1000 Hz  "
        ::= { iqupc00CmdEntry 36277 }


    iqupc00LoudCustomBlock1peqq2 OBJECT-TYPE
        SYNTAX            INTEGER
        MAX-ACCESS        read-write
        STATUS            current
        DESCRIPTION
                "CMNT: - Linear Acoustic PEQ Block1 Index 2 Q
                 TYPE: - Number
                 PAGE: - LoudCustom
                    peq q 2  cmdID= 36283
                    min= 1  max= 200  step= 1  format= %0.2f  div_scale= 20  preset= 20
                    Min = 0.05  Max = 10.00  Step = 0.05  Preset = 1.00  "
        ::= { iqupc00CmdEntry 36283 }


    iqupc00LoudCustomBlock1peqlevel2 OBJECT-TYPE
        SYNTAX            INTEGER
        MAX-ACCESS        read-write
        STATUS            current
        DESCRIPTION
                "CMNT: - Linear Acoustic PEQ Block1 Index 2 Level
                 TYPE: - Number
                 PAGE: - LoudCustom
                    peq level 2  cmdID= 36289
                    min= -90  max= 90  step= 1  format= %0.1f dB  div_scale= 5  preset= 0
                    Min = -18.0 dB  Max = 18.0 dB  Step = 0.2 dB  Preset = 0.0 dB  "
        ::= { iqupc00CmdEntry 36289 }


    iqupc00LoudCustomBlock1peqfreq3 OBJECT-TYPE
        SYNTAX            INTEGER
        MAX-ACCESS        read-write
        STATUS            current
        DESCRIPTION
                "CMNT: - Linear Acoustic PEQ Block1 Index 3 Frequency
                 TYPE: - Number
                 PAGE: - LoudCustom
                    peq freq 3  cmdID= 36278
                    min= 20  max= 20000  step= 1  format= %0.0f Hz  div_scale= 1  preset= 1000
                    Min = 20 Hz  Max = 20000 Hz  Step = 1 Hz  Preset = 1000 Hz  "
        ::= { iqupc00CmdEntry 36278 }


    iqupc00LoudCustomBlock1peqq3 OBJECT-TYPE
        SYNTAX            INTEGER
        MAX-ACCESS        read-write
        STATUS            current
        DESCRIPTION
                "CMNT: - Linear Acoustic PEQ Block1 Index 3 Q
                 TYPE: - Number
                 PAGE: - LoudCustom
                    peq q 3  cmdID= 36284
                    min= 1  max= 200  step= 1  format= %0.2f  div_scale= 20  preset= 20
                    Min = 0.05  Max = 10.00  Step = 0.05  Preset = 1.00  "
        ::= { iqupc00CmdEntry 36284 }


    iqupc00LoudCustomBlock1peqlevel3 OBJECT-TYPE
        SYNTAX            INTEGER
        MAX-ACCESS        read-write
        STATUS            current
        DESCRIPTION
                "CMNT: - Linear Acoustic PEQ Block1 Index 3 Level
                 TYPE: - Number
                 PAGE: - LoudCustom
                    peq level 3  cmdID= 36290
                    min= -90  max= 90  step= 1  format= %0.1f dB  div_scale= 5  preset= 0
                    Min = -18.0 dB  Max = 18.0 dB  Step = 0.2 dB  Preset = 0.0 dB  "
        ::= { iqupc00CmdEntry 36290 }


    iqupc00LoudCustomBlock1mbagcatk1 OBJECT-TYPE
        SYNTAX            INTEGER
        MAX-ACCESS        read-write
        STATUS            current
        DESCRIPTION
                "CMNT: - Linear Acoustic MBAGC Block1 Index 1 Attack
                 TYPE: - Number
                 PAGE: - LoudCustom
                    mbagc atk 1  cmdID= 36236
                    min= 0  max= 100  step= 1  format= %0.0f  div_scale= 1  preset= 24
                    Min = 0  Max = 100  Step = 1  Preset = 24  "
        ::= { iqupc00CmdEntry 36236 }


    iqupc00LoudCustomBlock1mbagcrel1 OBJECT-TYPE
        SYNTAX            INTEGER
        MAX-ACCESS        read-write
        STATUS            current
        DESCRIPTION
                "CMNT: - Linear Acoustic MBAGC Block1 Index 1 Release
                 TYPE: - Number
                 PAGE: - LoudCustom
                    mbagc rel 1  cmdID= 36226
                    min= 0  max= 100  step= 1  format= %0.0f  div_scale= 1  preset= 42
                    Min = 0  Max = 100  Step = 1  Preset = 42  "
        ::= { iqupc00CmdEntry 36226 }


    iqupc00LoudCustomBlock1mbagcthresh1 OBJECT-TYPE
        SYNTAX            INTEGER
        MAX-ACCESS        read-write
        STATUS            current
        DESCRIPTION
                "CMNT: - Linear Acoustic MBAGC Block1 Index 1 Threshold
                 TYPE: - Number
                 PAGE: - LoudCustom
                    mbagc thresh 1  cmdID= 36246
                    min= -120  max= 120  step= 1  format= %0.1f dB  div_scale= 10  preset= 0
                    Min = -12.0 dB  Max = 12.0 dB  Step = 0.1 dB  Preset = 0.0 dB  "
        ::= { iqupc00CmdEntry 36246 }


    iqupc00LoudCustomBlock1mbagcoutlev1 OBJECT-TYPE
        SYNTAX            INTEGER
        MAX-ACCESS        read-write
        STATUS            current
        DESCRIPTION
                "CMNT: - Linear Acoustic MBAGC Block1 Index 1 OutLevel
                 TYPE: - Number
                 PAGE: - LoudCustom
                    mbagc outlev 1  cmdID= 36266
                    min= -120  max= 120  step= 1  format= %0.1f dB  div_scale= 10  preset= 0
                    Min = -12.0 dB  Max = 12.0 dB  Step = 0.1 dB  Preset = 0.0 dB  "
        ::= { iqupc00CmdEntry 36266 }


    iqupc00LoudCustomBlock1mbagclimthresh1 OBJECT-TYPE
        SYNTAX            INTEGER
        MAX-ACCESS        read-write
        STATUS            current
        DESCRIPTION
                "CMNT: - Linear Acoustic MBAGC Block1 Index 1 Limit Threshold
                 TYPE: - Number
                 PAGE: - LoudCustom
                    mbagc limthresh 1  cmdID= 36256
                    min= 0  max= 180  step= 1  format= %0.1f dB  div_scale= 10  preset= 0
                    Min = 0.0 dB  Max = 18.0 dB  Step = 0.1 dB  Preset = 0.0 dB  "
        ::= { iqupc00CmdEntry 36256 }


    iqupc00LoudCustomBlock1mbagcinfthr1 OBJECT-TYPE
        SYNTAX            INTEGER { disable(0), enable(1)  }
        MAX-ACCESS        read-write
        STATUS            current
        DESCRIPTION
                "CMNT: - Linear Acoustic MBAGC Block1 Index 1 InfThr
                 TYPE: - Checkbox
                 PAGE: - LoudCustom
                    mbagc infthr 1  cmdID= 36294  "
        ::= { iqupc00CmdEntry 36294 }


    iqupc00LoudCustomBlock1mbagcatk2 OBJECT-TYPE
        SYNTAX            INTEGER
        MAX-ACCESS        read-write
        STATUS            current
        DESCRIPTION
                "CMNT: - Linear Acoustic MBAGC Block1 Index 2 Attack
                 TYPE: - Number
                 PAGE: - LoudCustom
                    mbagc atk 2  cmdID= 36237
                    min= 0  max= 100  step= 1  format= %0.0f  div_scale= 1  preset= 24
                    Min = 0  Max = 100  Step = 1  Preset = 24  "
        ::= { iqupc00CmdEntry 36237 }


    iqupc00LoudCustomBlock1mbagcrel2 OBJECT-TYPE
        SYNTAX            INTEGER
        MAX-ACCESS        read-write
        STATUS            current
        DESCRIPTION
                "CMNT: - Linear Acoustic MBAGC Block1 Index 2 Release
                 TYPE: - Number
                 PAGE: - LoudCustom
                    mbagc rel 2  cmdID= 36227
                    min= 0  max= 100  step= 1  format= %0.0f  div_scale= 1  preset= 42
                    Min = 0  Max = 100  Step = 1  Preset = 42  "
        ::= { iqupc00CmdEntry 36227 }


    iqupc00LoudCustomBlock1mbagcthresh2 OBJECT-TYPE
        SYNTAX            INTEGER
        MAX-ACCESS        read-write
        STATUS            current
        DESCRIPTION
                "CMNT: - Linear Acoustic MBAGC Block1 Index 2 Threshold
                 TYPE: - Number
                 PAGE: - LoudCustom
                    mbagc thresh 2  cmdID= 36247
                    min= -120  max= 120  step= 1  format= %0.1f dB  div_scale= 10  preset= 0
                    Min = -12.0 dB  Max = 12.0 dB  Step = 0.1 dB  Preset = 0.0 dB  "
        ::= { iqupc00CmdEntry 36247 }


    iqupc00LoudCustomBlock1mbagcoutlev2 OBJECT-TYPE
        SYNTAX            INTEGER
        MAX-ACCESS        read-write
        STATUS            current
        DESCRIPTION
                "CMNT: - Linear Acoustic MBAGC Block1 Index 2 OutLevel
                 TYPE: - Number
                 PAGE: - LoudCustom
                    mbagc outlev 2  cmdID= 36267
                    min= -120  max= 120  step= 1  format= %0.1f dB  div_scale= 10  preset= 0
                    Min = -12.0 dB  Max = 12.0 dB  Step = 0.1 dB  Preset = 0.0 dB  "
        ::= { iqupc00CmdEntry 36267 }


    iqupc00LoudCustomBlock1mbagclimthresh2 OBJECT-TYPE
        SYNTAX            INTEGER
        MAX-ACCESS        read-write
        STATUS            current
        DESCRIPTION
                "CMNT: - Linear Acoustic MBAGC Block1 Index 2 Limit Threshold
                 TYPE: - Number
                 PAGE: - LoudCustom
                    mbagc limthresh 2  cmdID= 36257
                    min= 0  max= 180  step= 1  format= %0.1f dB  div_scale= 10  preset= 0
                    Min = 0.0 dB  Max = 18.0 dB  Step = 0.1 dB  Preset = 0.0 dB  "
        ::= { iqupc00CmdEntry 36257 }


    iqupc00LoudCustomBlock1mbagcinfthr2 OBJECT-TYPE
        SYNTAX            INTEGER { disable(0), enable(1)  }
        MAX-ACCESS        read-write
        STATUS            current
        DESCRIPTION
                "CMNT: - Linear Acoustic MBAGC Block1 Index 2 InfThr
                 TYPE: - Checkbox
                 PAGE: - LoudCustom
                    mbagc infthr 2  cmdID= 36295  "
        ::= { iqupc00CmdEntry 36295 }


    iqupc00LoudCustomBlock1mbagcatk3 OBJECT-TYPE
        SYNTAX            INTEGER
        MAX-ACCESS        read-write
        STATUS            current
        DESCRIPTION
                "CMNT: - Linear Acoustic MBAGC Block1 Index 3 Attack
                 TYPE: - Number
                 PAGE: - LoudCustom
                    mbagc atk 3  cmdID= 36238
                    min= 0  max= 100  step= 1  format= %0.0f  div_scale= 1  preset= 24
                    Min = 0  Max = 100  Step = 1  Preset = 24  "
        ::= { iqupc00CmdEntry 36238 }


    iqupc00LoudCustomBlock1mbagcrel3 OBJECT-TYPE
        SYNTAX            INTEGER
        MAX-ACCESS        read-write
        STATUS            current
        DESCRIPTION
                "CMNT: - Linear Acoustic MBAGC Block1 Index 3 Release
                 TYPE: - Number
                 PAGE: - LoudCustom
                    mbagc rel 3  cmdID= 36228
                    min= 0  max= 100  step= 1  format= %0.0f  div_scale= 1  preset= 42
                    Min = 0  Max = 100  Step = 1  Preset = 42  "
        ::= { iqupc00CmdEntry 36228 }


    iqupc00LoudCustomBlock1mbagcthresh3 OBJECT-TYPE
        SYNTAX            INTEGER
        MAX-ACCESS        read-write
        STATUS            current
        DESCRIPTION
                "CMNT: - Linear Acoustic MBAGC Block1 Index 3 Threshold
                 TYPE: - Number
                 PAGE: - LoudCustom
                    mbagc thresh 3  cmdID= 36248
                    min= -120  max= 120  step= 1  format= %0.1f dB  div_scale= 10  preset= 0
                    Min = -12.0 dB  Max = 12.0 dB  Step = 0.1 dB  Preset = 0.0 dB  "
        ::= { iqupc00CmdEntry 36248 }


    iqupc00LoudCustomBlock1mbagcoutlev3 OBJECT-TYPE
        SYNTAX            INTEGER
        MAX-ACCESS        read-write
        STATUS            current
        DESCRIPTION
                "CMNT: - Linear Acoustic MBAGC Block1 Index 3 OutLevel
                 TYPE: - Number
                 PAGE: - LoudCustom
                    mbagc outlev 3  cmdID= 36268
                    min= -120  max= 120  step= 1  format= %0.1f dB  div_scale= 10  preset= 0
                    Min = -12.0 dB  Max = 12.0 dB  Step = 0.1 dB  Preset = 0.0 dB  "
        ::= { iqupc00CmdEntry 36268 }


    iqupc00LoudCustomBlock1mbagclimthresh3 OBJECT-TYPE
        SYNTAX            INTEGER
        MAX-ACCESS        read-write
        STATUS            current
        DESCRIPTION
                "CMNT: - Linear Acoustic MBAGC Block1 Index 3 Limit Threshold
                 TYPE: - Number
                 PAGE: - LoudCustom
                    mbagc limthresh 3  cmdID= 36258
                    min= 0  max= 180  step= 1  format= %0.1f dB  div_scale= 10  preset= 0
                    Min = 0.0 dB  Max = 18.0 dB  Step = 0.1 dB  Preset = 0.0 dB  "
        ::= { iqupc00CmdEntry 36258 }


    iqupc00LoudCustomBlock1mbagcinfthr3 OBJECT-TYPE
        SYNTAX            INTEGER { disable(0), enable(1)  }
        MAX-ACCESS        read-write
        STATUS            current
        DESCRIPTION
                "CMNT: - Linear Acoustic MBAGC Block1 Index 3 InfThr
                 TYPE: - Checkbox
                 PAGE: - LoudCustom
                    mbagc infthr 3  cmdID= 36296  "
        ::= { iqupc00CmdEntry 36296 }


    iqupc00LoudCustomBlock1mbagcatk4 OBJECT-TYPE
        SYNTAX            INTEGER
        MAX-ACCESS        read-write
        STATUS            current
        DESCRIPTION
                "CMNT: - Linear Acoustic MBAGC Block1 Index 4 Attack
                 TYPE: - Number
                 PAGE: - LoudCustom
                    mbagc atk 4  cmdID= 36239
                    min= 0  max= 100  step= 1  format= %0.0f  div_scale= 1  preset= 24
                    Min = 0  Max = 100  Step = 1  Preset = 24  "
        ::= { iqupc00CmdEntry 36239 }


    iqupc00LoudCustomBlock1mbagcrel4 OBJECT-TYPE
        SYNTAX            INTEGER
        MAX-ACCESS        read-write
        STATUS            current
        DESCRIPTION
                "CMNT: - Linear Acoustic MBAGC Block1 Index 4 Release
                 TYPE: - Number
                 PAGE: - LoudCustom
                    mbagc rel 4  cmdID= 36229
                    min= 0  max= 100  step= 1  format= %0.0f  div_scale= 1  preset= 42
                    Min = 0  Max = 100  Step = 1  Preset = 42  "
        ::= { iqupc00CmdEntry 36229 }


    iqupc00LoudCustomBlock1mbagcthresh4 OBJECT-TYPE
        SYNTAX            INTEGER
        MAX-ACCESS        read-write
        STATUS            current
        DESCRIPTION
                "CMNT: - Linear Acoustic MBAGC Block1 Index 4 Threshold
                 TYPE: - Number
                 PAGE: - LoudCustom
                    mbagc thresh 4  cmdID= 36249
                    min= -120  max= 120  step= 1  format= %0.1f dB  div_scale= 10  preset= 0
                    Min = -12.0 dB  Max = 12.0 dB  Step = 0.1 dB  Preset = 0.0 dB  "
        ::= { iqupc00CmdEntry 36249 }


    iqupc00LoudCustomBlock1mbagcoutlev4 OBJECT-TYPE
        SYNTAX            INTEGER
        MAX-ACCESS        read-write
        STATUS            current
        DESCRIPTION
                "CMNT: - Linear Acoustic MBAGC Block1 Index 4 OutLevel
                 TYPE: - Number
                 PAGE: - LoudCustom
                    mbagc outlev 4  cmdID= 36269
                    min= -120  max= 120  step= 1  format= %0.1f dB  div_scale= 10  preset= 0
                    Min = -12.0 dB  Max = 12.0 dB  Step = 0.1 dB  Preset = 0.0 dB  "
        ::= { iqupc00CmdEntry 36269 }


    iqupc00LoudCustomBlock1mbagclimthresh4 OBJECT-TYPE
        SYNTAX            INTEGER
        MAX-ACCESS        read-write
        STATUS            current
        DESCRIPTION
                "CMNT: - Linear Acoustic MBAGC Block1 Index 4 Limit Threshold
                 TYPE: - Number
                 PAGE: - LoudCustom
                    mbagc limthresh 4  cmdID= 36259
                    min= 0  max= 180  step= 1  format= %0.1f dB  div_scale= 10  preset= 0
                    Min = 0.0 dB  Max = 18.0 dB  Step = 0.1 dB  Preset = 0.0 dB  "
        ::= { iqupc00CmdEntry 36259 }


    iqupc00LoudCustomBlock1mbagcinfthr4 OBJECT-TYPE
        SYNTAX            INTEGER { disable(0), enable(1)  }
        MAX-ACCESS        read-write
        STATUS            current
        DESCRIPTION
                "CMNT: - Linear Acoustic MBAGC Block1 Index 4 InfThr
                 TYPE: - Checkbox
                 PAGE: - LoudCustom
                    mbagc infthr 4  cmdID= 36297  "
        ::= { iqupc00CmdEntry 36297 }


    iqupc00LoudCustomBlock1mbagcatk5 OBJECT-TYPE
        SYNTAX            INTEGER
        MAX-ACCESS        read-write
        STATUS            current
        DESCRIPTION
                "CMNT: - Linear Acoustic MBAGC Block1 Index 5 Attack
                 TYPE: - Number
                 PAGE: - LoudCustom
                    mbagc atk 5  cmdID= 36240
                    min= 0  max= 100  step= 1  format= %0.0f  div_scale= 1  preset= 24
                    Min = 0  Max = 100  Step = 1  Preset = 24  "
        ::= { iqupc00CmdEntry 36240 }


    iqupc00LoudCustomBlock1mbagcrel5 OBJECT-TYPE
        SYNTAX            INTEGER
        MAX-ACCESS        read-write
        STATUS            current
        DESCRIPTION
                "CMNT: - Linear Acoustic MBAGC Block1 Index 5 Release
                 TYPE: - Number
                 PAGE: - LoudCustom
                    mbagc rel 5  cmdID= 36230
                    min= 0  max= 100  step= 1  format= %0.0f  div_scale= 1  preset= 42
                    Min = 0  Max = 100  Step = 1  Preset = 42  "
        ::= { iqupc00CmdEntry 36230 }


    iqupc00LoudCustomBlock1mbagcthresh5 OBJECT-TYPE
        SYNTAX            INTEGER
        MAX-ACCESS        read-write
        STATUS            current
        DESCRIPTION
                "CMNT: - Linear Acoustic MBAGC Block1 Index 5 Threshold
                 TYPE: - Number
                 PAGE: - LoudCustom
                    mbagc thresh 5  cmdID= 36250
                    min= -120  max= 120  step= 1  format= %0.1f dB  div_scale= 10  preset= 0
                    Min = -12.0 dB  Max = 12.0 dB  Step = 0.1 dB  Preset = 0.0 dB  "
        ::= { iqupc00CmdEntry 36250 }


    iqupc00LoudCustomBlock1mbagcoutlev5 OBJECT-TYPE
        SYNTAX            INTEGER
        MAX-ACCESS        read-write
        STATUS            current
        DESCRIPTION
                "CMNT: - Linear Acoustic MBAGC Block1 Index 5 OutLevel
                 TYPE: - Number
                 PAGE: - LoudCustom
                    mbagc outlev 5  cmdID= 36270
                    min= -120  max= 120  step= 1  format= %0.1f dB  div_scale= 10  preset= 0
                    Min = -12.0 dB  Max = 12.0 dB  Step = 0.1 dB  Preset = 0.0 dB  "
        ::= { iqupc00CmdEntry 36270 }


    iqupc00LoudCustomBlock1mbagclimthresh5 OBJECT-TYPE
        SYNTAX            INTEGER
        MAX-ACCESS        read-write
        STATUS            current
        DESCRIPTION
                "CMNT: - Linear Acoustic MBAGC Block1 Index 5 Limit Threshold
                 TYPE: - Number
                 PAGE: - LoudCustom
                    mbagc limthresh 5  cmdID= 36260
                    min= 0  max= 180  step= 1  format= %0.1f dB  div_scale= 10  preset= 0
                    Min = 0.0 dB  Max = 18.0 dB  Step = 0.1 dB  Preset = 0.0 dB  "
        ::= { iqupc00CmdEntry 36260 }


    iqupc00LoudCustomBlock1mbagcinfthr5 OBJECT-TYPE
        SYNTAX            INTEGER { disable(0), enable(1)  }
        MAX-ACCESS        read-write
        STATUS            current
        DESCRIPTION
                "CMNT: - Linear Acoustic MBAGC Block1 Index 5 InfThr
                 TYPE: - Checkbox
                 PAGE: - LoudCustom
                    mbagc infthr 5  cmdID= 36298  "
        ::= { iqupc00CmdEntry 36298 }


    iqupc00LoudCustomBlock1mbrange OBJECT-TYPE
        SYNTAX            INTEGER
        MAX-ACCESS        read-write
        STATUS            current
        DESCRIPTION
                "CMNT: - Linear Acoustic MB Block1 Range
                 TYPE: - Number
                 PAGE: - LoudCustom
                    mb range  cmdID= 36216
                    min= 0  max= 180  step= 1  format= %0.1f dB  div_scale= 5  preset= 90
                    Min = 0.0 dB  Max = 36.0 dB  Step = 0.2 dB  Preset = 18.0 dB  "
        ::= { iqupc00CmdEntry 36216 }


    iqupc00LoudCustomBlock1mbprogrise OBJECT-TYPE
        SYNTAX            INTEGER
        MAX-ACCESS        read-write
        STATUS            current
        DESCRIPTION
                "CMNT: - Linear Acoustic MB Block1 Progressive Rise
                 TYPE: - Number
                 PAGE: - LoudCustom
                    mb progrise  cmdID= 36214
                    min= 0  max= 100  step= 1  format= %0.0f  div_scale= 1  preset= 1
                    Min = 0  Max = 100  Step = 1  Preset = 1  "
        ::= { iqupc00CmdEntry 36214 }


    iqupc00LoudCustomBlock1mbsoftclip1 OBJECT-TYPE
        SYNTAX            INTEGER
        MAX-ACCESS        read-write
        STATUS            current
        DESCRIPTION
                "CMNT: - Linear Acoustic MB Block1 SoftClip1
                 TYPE: - Number
                 PAGE: - LoudCustom
                    mb softclip1  cmdID= 36218
                    min= 0  max= 180  step= 1  format= %0.1f dB  div_scale= 10  preset= 180
                    Min = 0.0 dB  Max = 18.0 dB  Step = 0.1 dB  Preset = 18.0 dB  "
        ::= { iqupc00CmdEntry 36218 }


    iqupc00LoudCustomBlock1mbsoftclip2 OBJECT-TYPE
        SYNTAX            INTEGER
        MAX-ACCESS        read-write
        STATUS            current
        DESCRIPTION
                "CMNT: - Linear Acoustic MB Block1 SoftClip2
                 TYPE: - Number
                 PAGE: - LoudCustom
                    mb softclip2  cmdID= 36220
                    min= 0  max= 180  step= 1  format= %0.1f dB  div_scale= 10  preset= 180
                    Min = 0.0 dB  Max = 18.0 dB  Step = 0.1 dB  Preset = 18.0 dB  "
        ::= { iqupc00CmdEntry 36220 }


    iqupc00LoudCustomBlock1mbratio OBJECT-TYPE
        SYNTAX            INTEGER
        MAX-ACCESS        read-write
        STATUS            current
        DESCRIPTION
                "CMNT: - Linear Acoustic MB Block1 Ratio
                 TYPE: - Number
                 PAGE: - LoudCustom
                    mb ratio  cmdID= 36222
                    min= 0  max= 100  step= 1  format= %0.0f  div_scale= 1  preset= 63
                    Min = 0  Max = 100  Step = 1  Preset = 63  "
        ::= { iqupc00CmdEntry 36222 }


    iqupc00LoudCustomBlock1mblimdrive OBJECT-TYPE
        SYNTAX            INTEGER
        MAX-ACCESS        read-write
        STATUS            current
        DESCRIPTION
                "CMNT: - Linear Acoustic MB Block1 OutLimDrive
                 TYPE: - Number
                 PAGE: - LoudCustom
                    mb lim drive  cmdID= 36224
                    min= -60  max= 60  step= 1  format= %0.1f dB  div_scale= 10  preset= -50
                    Min = -6.0 dB  Max = 6.0 dB  Step = 0.1 dB  Preset = -5.0 dB  "
        ::= { iqupc00CmdEntry 36224 }


    iqupc00LoudCustomBlock1CustomPreset OBJECT-TYPE
        SYNTAX            INTEGER {
                            valGeneral(0),
                            valLight(1),
                            valHeavy(2),
                            valLoud(3),
                            valLoudLimit(4),
                            valProtectionLimit(5),
                            valDefaults(6),
                            valCustom(7)
                            }
        MAX-ACCESS        read-write
        STATUS            current
        DESCRIPTION
                "CMNT: - Linear Acoustic Cust Preset 1
                 TYPE: - RadiobuttonList
                 PAGE: - LoudCustom
                    CustomPreset  cmdID= 36306
                    General  value= 0
                    Light  value= 1
                    Heavy  value= 2
                    Loud  value= 3
                    LoudLimit  value= 4
                    ProtectionLimit  value= 5
                    Defaults  value= 6
                    Custom  value= 7  "
        ::= { iqupc00CmdEntry 36306 }


    iqupc00LoudCustomBlock1Copyto2 OBJECT-TYPE
        SYNTAX            INTEGER { noAction(0),valCopyto2(1) }
        MAX-ACCESS        read-write
        STATUS            current
        DESCRIPTION
                "CMNT: - Linear Acoustic Cust Preset COPY 1 to 2
                 TYPE: - Button
                 PAGE: - LoudCustom
                    Copy to 2  cmdID= 36309
                    value= 1  "
        ::= { iqupc00CmdEntry 36309 }


    iqupc00LoudCustomBlock2Name OBJECT-TYPE
        SYNTAX            RollCallString
        MAX-ACCESS        read-write
        STATUS            current
        DESCRIPTION
                "CMNT: - Linear Acoustic MB Block2 Name
                 TYPE: - Editstring
                 PAGE: - LoudCustom
                    Name  cmdID= 36305
                    preset= Custom Block 2"
        ::= { iqupc00CmdEntry 36305 }


    iqupc00LoudCustomBlock2inagcfreeze OBJECT-TYPE
        SYNTAX            INTEGER
        MAX-ACCESS        read-write
        STATUS            current
        DESCRIPTION
                "CMNT: - Linear Acoustic InAGC Block2 Freeze Threshold
                 TYPE: - Number
                 PAGE: - LoudCustom
                    inagc freeze  cmdID= 36201
                    min= -180  max= 0  step= 1  format= %0.1f dBFS  div_scale= 2  preset= -62
                    Min = -90.0 dBFS  Max = 0.0 dBFS  Step = 0.5 dBFS  Preset = -31.0 dBFS  "
        ::= { iqupc00CmdEntry 36201 }


    iqupc00LoudCustomBlock2inagcgate OBJECT-TYPE
        SYNTAX            INTEGER
        MAX-ACCESS        read-write
        STATUS            current
        DESCRIPTION
                "CMNT: - Linear Acoustic InAGC Block2 Gate Threshold
                 TYPE: - Number
                 PAGE: - LoudCustom
                    inagc gate  cmdID= 36203
                    min= -180  max= 0  step= 1  format= %0.1f dBFS  div_scale= 2  preset= -42
                    Min = -90.0 dBFS  Max = 0.0 dBFS  Step = 0.5 dBFS  Preset = -21.0 dBFS  "
        ::= { iqupc00CmdEntry 36203 }


    iqupc00LoudCustomBlock2inagcratio OBJECT-TYPE
        SYNTAX            INTEGER
        MAX-ACCESS        read-write
        STATUS            current
        DESCRIPTION
                "CMNT: - Linear Acoustic InAGC Block2 Ratio
                 TYPE: - Number
                 PAGE: - LoudCustom
                    inagc ratio  cmdID= 36209
                    min= 0  max= 100  step= 1  format= %0.0f  div_scale= 1  preset= 91
                    Min = 0  Max = 100  Step = 1  Preset = 91  "
        ::= { iqupc00CmdEntry 36209 }


    iqupc00LoudCustomBlock2inagcrange OBJECT-TYPE
        SYNTAX            INTEGER
        MAX-ACCESS        read-write
        STATUS            current
        DESCRIPTION
                "CMNT: - Linear Acoustic InAGC Block2 Range
                 TYPE: - Number
                 PAGE: - LoudCustom
                    inagc range  cmdID= 36207
                    min= 0  max= 180  step= 1  format= %0.1f dB  div_scale= 5  preset= 125
                    Min = 0.0 dB  Max = 36.0 dB  Step = 0.2 dB  Preset = 25.0 dB  "
        ::= { iqupc00CmdEntry 36207 }


    iqupc00LoudCustomBlock2inagcthresh OBJECT-TYPE
        SYNTAX            INTEGER
        MAX-ACCESS        read-write
        STATUS            current
        DESCRIPTION
                "CMNT: - Linear Acoustic InAGC Block2 Threshold
                 TYPE: - Number
                 PAGE: - LoudCustom
                    inagc thresh  cmdID= 36205
                    min= -180  max= 0  step= 1  format= %0.1f dBFS  div_scale= 10  preset= -140
                    Min = -18.0 dBFS  Max = 0.0 dBFS  Step = 0.1 dBFS  Preset = -14.0 dBFS  "
        ::= { iqupc00CmdEntry 36205 }


    iqupc00LoudCustomBlock2inagcattack OBJECT-TYPE
        SYNTAX            INTEGER
        MAX-ACCESS        read-write
        STATUS            current
        DESCRIPTION
                "CMNT: - Linear Acoustic InAGC Block2 Attack
                 TYPE: - Number
                 PAGE: - LoudCustom
                    inagc attack  cmdID= 36211
                    min= 1  max= 100  step= 1  format= %0.0f  div_scale= 1  preset= 24
                    Min = 1  Max = 100  Step = 1  Preset = 24  "
        ::= { iqupc00CmdEntry 36211 }


    iqupc00LoudCustomBlock2inagcrelease OBJECT-TYPE
        SYNTAX            INTEGER
        MAX-ACCESS        read-write
        STATUS            current
        DESCRIPTION
                "CMNT: - Linear Acoustic InAGC Block2 Release
                 TYPE: - Number
                 PAGE: - LoudCustom
                    inagc release  cmdID= 36213
                    min= 1  max= 100  step= 1  format= %0.0f  div_scale= 1  preset= 42
                    Min = 1  Max = 100  Step = 1  Preset = 42  "
        ::= { iqupc00CmdEntry 36213 }


    iqupc00LoudCustomBlock2peqfreq1 OBJECT-TYPE
        SYNTAX            INTEGER
        MAX-ACCESS        read-write
        STATUS            current
        DESCRIPTION
                "CMNT: - Linear Acoustic PEQ Block2 Index 1 Frequency
                 TYPE: - Number
                 PAGE: - LoudCustom
                    peq freq 1  cmdID= 36279
                    min= 20  max= 20000  step= 1  format= %0.0f Hz  div_scale= 1  preset= 1000
                    Min = 20 Hz  Max = 20000 Hz  Step = 1 Hz  Preset = 1000 Hz  "
        ::= { iqupc00CmdEntry 36279 }


    iqupc00LoudCustomBlock2peqq1 OBJECT-TYPE
        SYNTAX            INTEGER
        MAX-ACCESS        read-write
        STATUS            current
        DESCRIPTION
                "CMNT: - Linear Acoustic PEQ Block2 Index 1 Q
                 TYPE: - Number
                 PAGE: - LoudCustom
                    peq q 1  cmdID= 36285
                    min= 1  max= 200  step= 1  format= %0.2f  div_scale= 20  preset= 20
                    Min = 0.05  Max = 10.00  Step = 0.05  Preset = 1.00  "
        ::= { iqupc00CmdEntry 36285 }


    iqupc00LoudCustomBlock2peqlevel1 OBJECT-TYPE
        SYNTAX            INTEGER
        MAX-ACCESS        read-write
        STATUS            current
        DESCRIPTION
                "CMNT: - Linear Acoustic PEQ Block2 Index 1 Level
                 TYPE: - Number
                 PAGE: - LoudCustom
                    peq level 1  cmdID= 36291
                    min= -90  max= 90  step= 1  format= %0.1f dB  div_scale= 5  preset= 0
                    Min = -18.0 dB  Max = 18.0 dB  Step = 0.2 dB  Preset = 0.0 dB  "
        ::= { iqupc00CmdEntry 36291 }


    iqupc00LoudCustomBlock2peqfreq2 OBJECT-TYPE
        SYNTAX            INTEGER
        MAX-ACCESS        read-write
        STATUS            current
        DESCRIPTION
                "CMNT: - Linear Acoustic PEQ Block2 Index 2 Frequency
                 TYPE: - Number
                 PAGE: - LoudCustom
                    peq freq 2  cmdID= 36280
                    min= 20  max= 20000  step= 1  format= %0.0f Hz  div_scale= 1  preset= 1000
                    Min = 20 Hz  Max = 20000 Hz  Step = 1 Hz  Preset = 1000 Hz  "
        ::= { iqupc00CmdEntry 36280 }


    iqupc00LoudCustomBlock2peqq2 OBJECT-TYPE
        SYNTAX            INTEGER
        MAX-ACCESS        read-write
        STATUS            current
        DESCRIPTION
                "CMNT: - Linear Acoustic PEQ Block2 Index 2 Q
                 TYPE: - Number
                 PAGE: - LoudCustom
                    peq q 2  cmdID= 36286
                    min= 1  max= 200  step= 1  format= %0.2f  div_scale= 20  preset= 20
                    Min = 0.05  Max = 10.00  Step = 0.05  Preset = 1.00  "
        ::= { iqupc00CmdEntry 36286 }


    iqupc00LoudCustomBlock2peqlevel2 OBJECT-TYPE
        SYNTAX            INTEGER
        MAX-ACCESS        read-write
        STATUS            current
        DESCRIPTION
                "CMNT: - Linear Acoustic PEQ Block2 Index 2 Level
                 TYPE: - Number
                 PAGE: - LoudCustom
                    peq level 2  cmdID= 36292
                    min= -90  max= 90  step= 1  format= %0.1f dB  div_scale= 5  preset= 0
                    Min = -18.0 dB  Max = 18.0 dB  Step = 0.2 dB  Preset = 0.0 dB  "
        ::= { iqupc00CmdEntry 36292 }


    iqupc00LoudCustomBlock2peqfreq3 OBJECT-TYPE
        SYNTAX            INTEGER
        MAX-ACCESS        read-write
        STATUS            current
        DESCRIPTION
                "CMNT: - Linear Acoustic PEQ Block2 Index 3 Frequency
                 TYPE: - Number
                 PAGE: - LoudCustom
                    peq freq 3  cmdID= 36281
                    min= 20  max= 20000  step= 1  format= %0.0f Hz  div_scale= 1  preset= 1000
                    Min = 20 Hz  Max = 20000 Hz  Step = 1 Hz  Preset = 1000 Hz  "
        ::= { iqupc00CmdEntry 36281 }


    iqupc00LoudCustomBlock2peqq3 OBJECT-TYPE
        SYNTAX            INTEGER
        MAX-ACCESS        read-write
        STATUS            current
        DESCRIPTION
                "CMNT: - Linear Acoustic PEQ Block2 Index 3 Q
                 TYPE: - Number
                 PAGE: - LoudCustom
                    peq q 3  cmdID= 36287
                    min= 1  max= 200  step= 1  format= %0.2f  div_scale= 20  preset= 20
                    Min = 0.05  Max = 10.00  Step = 0.05  Preset = 1.00  "
        ::= { iqupc00CmdEntry 36287 }


    iqupc00LoudCustomBlock2peqlevel3 OBJECT-TYPE
        SYNTAX            INTEGER
        MAX-ACCESS        read-write
        STATUS            current
        DESCRIPTION
                "CMNT: - Linear Acoustic PEQ Block2 Index 3 Level
                 TYPE: - Number
                 PAGE: - LoudCustom
                    peq level 3  cmdID= 36293
                    min= -90  max= 90  step= 1  format= %0.1f dB  div_scale= 5  preset= 0
                    Min = -18.0 dB  Max = 18.0 dB  Step = 0.2 dB  Preset = 0.0 dB  "
        ::= { iqupc00CmdEntry 36293 }


    iqupc00LoudCustomBlock2mbagcatk1 OBJECT-TYPE
        SYNTAX            INTEGER
        MAX-ACCESS        read-write
        STATUS            current
        DESCRIPTION
                "CMNT: - Linear Acoustic MBAGC Block2 Index 1 Attack
                 TYPE: - Number
                 PAGE: - LoudCustom
                    mbagc atk 1  cmdID= 36241
                    min= 0  max= 100  step= 1  format= %0.0f  div_scale= 1  preset= 24
                    Min = 0  Max = 100  Step = 1  Preset = 24  "
        ::= { iqupc00CmdEntry 36241 }


    iqupc00LoudCustomBlock2mbagcrel1 OBJECT-TYPE
        SYNTAX            INTEGER
        MAX-ACCESS        read-write
        STATUS            current
        DESCRIPTION
                "CMNT: - Linear Acoustic MBAGC Block2 Index 1 Release
                 TYPE: - Number
                 PAGE: - LoudCustom
                    mbagc rel 1  cmdID= 36231
                    min= 0  max= 100  step= 1  format= %0.0f  div_scale= 1  preset= 42
                    Min = 0  Max = 100  Step = 1  Preset = 42  "
        ::= { iqupc00CmdEntry 36231 }


    iqupc00LoudCustomBlock2mbagcthresh1 OBJECT-TYPE
        SYNTAX            INTEGER
        MAX-ACCESS        read-write
        STATUS            current
        DESCRIPTION
                "CMNT: - Linear Acoustic MBAGC Block2 Index 1 Threshold
                 TYPE: - Number
                 PAGE: - LoudCustom
                    mbagc thresh 1  cmdID= 36251
                    min= -120  max= 120  step= 1  format= %0.1f dB  div_scale= 10  preset= 0
                    Min = -12.0 dB  Max = 12.0 dB  Step = 0.1 dB  Preset = 0.0 dB  "
        ::= { iqupc00CmdEntry 36251 }


    iqupc00LoudCustomBlock2mbagcoutlev1 OBJECT-TYPE
        SYNTAX            INTEGER
        MAX-ACCESS        read-write
        STATUS            current
        DESCRIPTION
                "CMNT: - Linear Acoustic MBAGC Block2 Index 1 OutLevel
                 TYPE: - Number
                 PAGE: - LoudCustom
                    mbagc outlev 1  cmdID= 36271
                    min= -120  max= 120  step= 1  format= %0.1f dB  div_scale= 10  preset= 0
                    Min = -12.0 dB  Max = 12.0 dB  Step = 0.1 dB  Preset = 0.0 dB  "
        ::= { iqupc00CmdEntry 36271 }


    iqupc00LoudCustomBlock2mbagclimthresh1 OBJECT-TYPE
        SYNTAX            INTEGER
        MAX-ACCESS        read-write
        STATUS            current
        DESCRIPTION
                "CMNT: - Linear Acoustic MBAGC Block2 Index 1 Limit Threshold
                 TYPE: - Number
                 PAGE: - LoudCustom
                    mbagc limthresh 1  cmdID= 36261
                    min= 0  max= 180  step= 1  format= %0.1f dB  div_scale= 10  preset= 0
                    Min = 0.0 dB  Max = 18.0 dB  Step = 0.1 dB  Preset = 0.0 dB  "
        ::= { iqupc00CmdEntry 36261 }


    iqupc00LoudCustomBlock2mbagcinfthr1 OBJECT-TYPE
        SYNTAX            INTEGER { disable(0), enable(1)  }
        MAX-ACCESS        read-write
        STATUS            current
        DESCRIPTION
                "CMNT: - Linear Acoustic MBAGC Block2 Index 1 InfThr
                 TYPE: - Checkbox
                 PAGE: - LoudCustom
                    mbagc infthr 1  cmdID= 36299  "
        ::= { iqupc00CmdEntry 36299 }


    iqupc00LoudCustomBlock2mbagcatk2 OBJECT-TYPE
        SYNTAX            INTEGER
        MAX-ACCESS        read-write
        STATUS            current
        DESCRIPTION
                "CMNT: - Linear Acoustic MBAGC Block2 Index 2 Attack
                 TYPE: - Number
                 PAGE: - LoudCustom
                    mbagc atk 2  cmdID= 36242
                    min= 0  max= 100  step= 1  format= %0.0f  div_scale= 1  preset= 24
                    Min = 0  Max = 100  Step = 1  Preset = 24  "
        ::= { iqupc00CmdEntry 36242 }


    iqupc00LoudCustomBlock2mbagcrel2 OBJECT-TYPE
        SYNTAX            INTEGER
        MAX-ACCESS        read-write
        STATUS            current
        DESCRIPTION
                "CMNT: - Linear Acoustic MBAGC Block2 Index 2 Release
                 TYPE: - Number
                 PAGE: - LoudCustom
                    mbagc rel 2  cmdID= 36232
                    min= 0  max= 100  step= 1  format= %0.0f  div_scale= 1  preset= 42
                    Min = 0  Max = 100  Step = 1  Preset = 42  "
        ::= { iqupc00CmdEntry 36232 }


    iqupc00LoudCustomBlock2mbagcthresh2 OBJECT-TYPE
        SYNTAX            INTEGER
        MAX-ACCESS        read-write
        STATUS            current
        DESCRIPTION
                "CMNT: - Linear Acoustic MBAGC Block2 Index 2 Threshold
                 TYPE: - Number
                 PAGE: - LoudCustom
                    mbagc thresh 2  cmdID= 36252
                    min= -120  max= 120  step= 1  format= %0.1f dB  div_scale= 10  preset= 0
                    Min = -12.0 dB  Max = 12.0 dB  Step = 0.1 dB  Preset = 0.0 dB  "
        ::= { iqupc00CmdEntry 36252 }


    iqupc00LoudCustomBlock2mbagcoutlev2 OBJECT-TYPE
        SYNTAX            INTEGER
        MAX-ACCESS        read-write
        STATUS            current
        DESCRIPTION
                "CMNT: - Linear Acoustic MBAGC Block2 Index 2 OutLevel
                 TYPE: - Number
                 PAGE: - LoudCustom
                    mbagc outlev 2  cmdID= 36272
                    min= -120  max= 120  step= 1  format= %0.1f dB  div_scale= 10  preset= 0
                    Min = -12.0 dB  Max = 12.0 dB  Step = 0.1 dB  Preset = 0.0 dB  "
        ::= { iqupc00CmdEntry 36272 }


    iqupc00LoudCustomBlock2mbagclimthresh2 OBJECT-TYPE
        SYNTAX            INTEGER
        MAX-ACCESS        read-write
        STATUS            current
        DESCRIPTION
                "CMNT: - Linear Acoustic MBAGC Block2 Index 2 Limit Threshold
                 TYPE: - Number
                 PAGE: - LoudCustom
                    mbagc limthresh 2  cmdID= 36262
                    min= 0  max= 180  step= 1  format= %0.1f dB  div_scale= 10  preset= 0
                    Min = 0.0 dB  Max = 18.0 dB  Step = 0.1 dB  Preset = 0.0 dB  "
        ::= { iqupc00CmdEntry 36262 }


    iqupc00LoudCustomBlock2mbagcinfthr2 OBJECT-TYPE
        SYNTAX            INTEGER { disable(0), enable(1)  }
        MAX-ACCESS        read-write
        STATUS            current
        DESCRIPTION
                "CMNT: - Linear Acoustic MBAGC Block2 Index 2 InfThr
                 TYPE: - Checkbox
                 PAGE: - LoudCustom
                    mbagc infthr 2  cmdID= 36300  "
        ::= { iqupc00CmdEntry 36300 }


    iqupc00LoudCustomBlock2mbagcatk3 OBJECT-TYPE
        SYNTAX            INTEGER
        MAX-ACCESS        read-write
        STATUS            current
        DESCRIPTION
                "CMNT: - Linear Acoustic MBAGC Block2 Index 3 Attack
                 TYPE: - Number
                 PAGE: - LoudCustom
                    mbagc atk 3  cmdID= 36243
                    min= 0  max= 100  step= 1  format= %0.0f  div_scale= 1  preset= 24
                    Min = 0  Max = 100  Step = 1  Preset = 24  "
        ::= { iqupc00CmdEntry 36243 }


    iqupc00LoudCustomBlock2mbagcrel3 OBJECT-TYPE
        SYNTAX            INTEGER
        MAX-ACCESS        read-write
        STATUS            current
        DESCRIPTION
                "CMNT: - Linear Acoustic MBAGC Block2 Index 3 Release
                 TYPE: - Number
                 PAGE: - LoudCustom
                    mbagc rel 3  cmdID= 36233
                    min= 0  max= 100  step= 1  format= %0.0f  div_scale= 1  preset= 42
                    Min = 0  Max = 100  Step = 1  Preset = 42  "
        ::= { iqupc00CmdEntry 36233 }


    iqupc00LoudCustomBlock2mbagcthresh3 OBJECT-TYPE
        SYNTAX            INTEGER
        MAX-ACCESS        read-write
        STATUS            current
        DESCRIPTION
                "CMNT: - Linear Acoustic MBAGC Block2 Index 3 Threshold
                 TYPE: - Number
                 PAGE: - LoudCustom
                    mbagc thresh 3  cmdID= 36253
                    min= -120  max= 120  step= 1  format= %0.1f dB  div_scale= 10  preset= 0
                    Min = -12.0 dB  Max = 12.0 dB  Step = 0.1 dB  Preset = 0.0 dB  "
        ::= { iqupc00CmdEntry 36253 }


    iqupc00LoudCustomBlock2mbagcoutlev3 OBJECT-TYPE
        SYNTAX            INTEGER
        MAX-ACCESS        read-write
        STATUS            current
        DESCRIPTION
                "CMNT: - Linear Acoustic MBAGC Block2 Index 3 OutLevel
                 TYPE: - Number
                 PAGE: - LoudCustom
                    mbagc outlev 3  cmdID= 36273
                    min= -120  max= 120  step= 1  format= %0.1f dB  div_scale= 10  preset= 0
                    Min = -12.0 dB  Max = 12.0 dB  Step = 0.1 dB  Preset = 0.0 dB  "
        ::= { iqupc00CmdEntry 36273 }


    iqupc00LoudCustomBlock2mbagclimthresh3 OBJECT-TYPE
        SYNTAX            INTEGER
        MAX-ACCESS        read-write
        STATUS            current
        DESCRIPTION
                "CMNT: - Linear Acoustic MBAGC Block2 Index 3 Limit Threshold
                 TYPE: - Number
                 PAGE: - LoudCustom
                    mbagc limthresh 3  cmdID= 36263
                    min= 0  max= 180  step= 1  format= %0.1f dB  div_scale= 10  preset= 0
                    Min = 0.0 dB  Max = 18.0 dB  Step = 0.1 dB  Preset = 0.0 dB  "
        ::= { iqupc00CmdEntry 36263 }


    iqupc00LoudCustomBlock2mbagcinfthr3 OBJECT-TYPE
        SYNTAX            INTEGER { disable(0), enable(1)  }
        MAX-ACCESS        read-write
        STATUS            current
        DESCRIPTION
                "CMNT: - Linear Acoustic MBAGC Block2 Index 3 InfThr
                 TYPE: - Checkbox
                 PAGE: - LoudCustom
                    mbagc infthr 3  cmdID= 36301  "
        ::= { iqupc00CmdEntry 36301 }


    iqupc00LoudCustomBlock2mbagcatk4 OBJECT-TYPE
        SYNTAX            INTEGER
        MAX-ACCESS        read-write
        STATUS            current
        DESCRIPTION
                "CMNT: - Linear Acoustic MBAGC Block2 Index 4 Attack
                 TYPE: - Number
                 PAGE: - LoudCustom
                    mbagc atk 4  cmdID= 36244
                    min= 0  max= 100  step= 1  format= %0.0f  div_scale= 1  preset= 24
                    Min = 0  Max = 100  Step = 1  Preset = 24  "
        ::= { iqupc00CmdEntry 36244 }


    iqupc00LoudCustomBlock2mbagcrel4 OBJECT-TYPE
        SYNTAX            INTEGER
        MAX-ACCESS        read-write
        STATUS            current
        DESCRIPTION
                "CMNT: - Linear Acoustic MBAGC Block2 Index 4 Release
                 TYPE: - Number
                 PAGE: - LoudCustom
                    mbagc rel 4  cmdID= 36234
                    min= 0  max= 100  step= 1  format= %0.0f  div_scale= 1  preset= 42
                    Min = 0  Max = 100  Step = 1  Preset = 42  "
        ::= { iqupc00CmdEntry 36234 }


    iqupc00LoudCustomBlock2mbagcthresh4 OBJECT-TYPE
        SYNTAX            INTEGER
        MAX-ACCESS        read-write
        STATUS            current
        DESCRIPTION
                "CMNT: - Linear Acoustic MBAGC Block2 Index 4 Threshold
                 TYPE: - Number
                 PAGE: - LoudCustom
                    mbagc thresh 4  cmdID= 36254
                    min= -120  max= 120  step= 1  format= %0.1f dB  div_scale= 10  preset= 0
                    Min = -12.0 dB  Max = 12.0 dB  Step = 0.1 dB  Preset = 0.0 dB  "
        ::= { iqupc00CmdEntry 36254 }


    iqupc00LoudCustomBlock2mbagcoutlev4 OBJECT-TYPE
        SYNTAX            INTEGER
        MAX-ACCESS        read-write
        STATUS            current
        DESCRIPTION
                "CMNT: - Linear Acoustic MBAGC Block2 Index 4 OutLevel
                 TYPE: - Number
                 PAGE: - LoudCustom
                    mbagc outlev 4  cmdID= 36274
                    min= -120  max= 120  step= 1  format= %0.1f dB  div_scale= 10  preset= 0
                    Min = -12.0 dB  Max = 12.0 dB  Step = 0.1 dB  Preset = 0.0 dB  "
        ::= { iqupc00CmdEntry 36274 }


    iqupc00LoudCustomBlock2mbagclimthresh4 OBJECT-TYPE
        SYNTAX            INTEGER
        MAX-ACCESS        read-write
        STATUS            current
        DESCRIPTION
                "CMNT: - Linear Acoustic MBAGC Block2 Index 4 Limit Threshold
                 TYPE: - Number
                 PAGE: - LoudCustom
                    mbagc limthresh 4  cmdID= 36264
                    min= 0  max= 180  step= 1  format= %0.1f dB  div_scale= 10  preset= 0
                    Min = 0.0 dB  Max = 18.0 dB  Step = 0.1 dB  Preset = 0.0 dB  "
        ::= { iqupc00CmdEntry 36264 }


    iqupc00LoudCustomBlock2mbagcinfthr4 OBJECT-TYPE
        SYNTAX            INTEGER { disable(0), enable(1)  }
        MAX-ACCESS        read-write
        STATUS            current
        DESCRIPTION
                "CMNT: - Linear Acoustic MBAGC Block2 Index 4 InfThr
                 TYPE: - Checkbox
                 PAGE: - LoudCustom
                    mbagc infthr 4  cmdID= 36302  "
        ::= { iqupc00CmdEntry 36302 }


    iqupc00LoudCustomBlock2mbagcatk5 OBJECT-TYPE
        SYNTAX            INTEGER
        MAX-ACCESS        read-write
        STATUS            current
        DESCRIPTION
                "CMNT: - Linear Acoustic MBAGC Block2 Index 5 Attack
                 TYPE: - Number
                 PAGE: - LoudCustom
                    mbagc atk 5  cmdID= 36245
                    min= 0  max= 100  step= 1  format= %0.0f  div_scale= 1  preset= 24
                    Min = 0  Max = 100  Step = 1  Preset = 24  "
        ::= { iqupc00CmdEntry 36245 }


    iqupc00LoudCustomBlock2mbagcrel5 OBJECT-TYPE
        SYNTAX            INTEGER
        MAX-ACCESS        read-write
        STATUS            current
        DESCRIPTION
                "CMNT: - Linear Acoustic MBAGC Block2 Index 5 Release
                 TYPE: - Number
                 PAGE: - LoudCustom
                    mbagc rel 5  cmdID= 36235
                    min= 0  max= 100  step= 1  format= %0.0f  div_scale= 1  preset= 42
                    Min = 0  Max = 100  Step = 1  Preset = 42  "
        ::= { iqupc00CmdEntry 36235 }


    iqupc00LoudCustomBlock2mbagcthresh5 OBJECT-TYPE
        SYNTAX            INTEGER
        MAX-ACCESS        read-write
        STATUS            current
        DESCRIPTION
                "CMNT: - Linear Acoustic MBAGC Block2 Index 5 Threshold
                 TYPE: - Number
                 PAGE: - LoudCustom
                    mbagc thresh 5  cmdID= 36255
                    min= -120  max= 120  step= 1  format= %0.1f dB  div_scale= 10  preset= 0
                    Min = -12.0 dB  Max = 12.0 dB  Step = 0.1 dB  Preset = 0.0 dB  "
        ::= { iqupc00CmdEntry 36255 }


    iqupc00LoudCustomBlock2mbagcoutlev5 OBJECT-TYPE
        SYNTAX            INTEGER
        MAX-ACCESS        read-write
        STATUS            current
        DESCRIPTION
                "CMNT: - Linear Acoustic MBAGC Block2 Index 5 OutLevel
                 TYPE: - Number
                 PAGE: - LoudCustom
                    mbagc outlev 5  cmdID= 36275
                    min= -120  max= 120  step= 1  format= %0.1f dB  div_scale= 10  preset= 0
                    Min = -12.0 dB  Max = 12.0 dB  Step = 0.1 dB  Preset = 0.0 dB  "
        ::= { iqupc00CmdEntry 36275 }


    iqupc00LoudCustomBlock2mbagclimthresh5 OBJECT-TYPE
        SYNTAX            INTEGER
        MAX-ACCESS        read-write
        STATUS            current
        DESCRIPTION
                "CMNT: - Linear Acoustic MBAGC Block2 Index 5 Limit Threshold
                 TYPE: - Number
                 PAGE: - LoudCustom
                    mbagc limthresh 5  cmdID= 36265
                    min= 0  max= 180  step= 1  format= %0.1f dB  div_scale= 10  preset= 0
                    Min = 0.0 dB  Max = 18.0 dB  Step = 0.1 dB  Preset = 0.0 dB  "
        ::= { iqupc00CmdEntry 36265 }


    iqupc00LoudCustomBlock2mbagcinfthr5 OBJECT-TYPE
        SYNTAX            INTEGER { disable(0), enable(1)  }
        MAX-ACCESS        read-write
        STATUS            current
        DESCRIPTION
                "CMNT: - Linear Acoustic MBAGC Block2 Index 5 InfThr
                 TYPE: - Checkbox
                 PAGE: - LoudCustom
                    mbagc infthr 5  cmdID= 36303  "
        ::= { iqupc00CmdEntry 36303 }


    iqupc00LoudCustomBlock2mbrange OBJECT-TYPE
        SYNTAX            INTEGER
        MAX-ACCESS        read-write
        STATUS            current
        DESCRIPTION
                "CMNT: - Linear Acoustic MB Block2 Range
                 TYPE: - Number
                 PAGE: - LoudCustom
                    mb range  cmdID= 36217
                    min= 0  max= 180  step= 1  format= %0.1f dB  div_scale= 5  preset= 90
                    Min = 0.0 dB  Max = 36.0 dB  Step = 0.2 dB  Preset = 18.0 dB  "
        ::= { iqupc00CmdEntry 36217 }


    iqupc00LoudCustomBlock2mbprogrise OBJECT-TYPE
        SYNTAX            INTEGER
        MAX-ACCESS        read-write
        STATUS            current
        DESCRIPTION
                "CMNT: - Linear Acoustic MB Block2 Progressive Rise
                 TYPE: - Number
                 PAGE: - LoudCustom
                    mb progrise  cmdID= 36215
                    min= 0  max= 100  step= 1  format= %0.0f  div_scale= 1  preset= 1
                    Min = 0  Max = 100  Step = 1  Preset = 1  "
        ::= { iqupc00CmdEntry 36215 }


    iqupc00LoudCustomBlock2mbsoftclip1 OBJECT-TYPE
        SYNTAX            INTEGER
        MAX-ACCESS        read-write
        STATUS            current
        DESCRIPTION
                "CMNT: - Linear Acoustic MB Block2 SoftClip1
                 TYPE: - Number
                 PAGE: - LoudCustom
                    mb softclip1  cmdID= 36219
                    min= 0  max= 180  step= 1  format= %0.1f dB  div_scale= 10  preset= 180
                    Min = 0.0 dB  Max = 18.0 dB  Step = 0.1 dB  Preset = 18.0 dB  "
        ::= { iqupc00CmdEntry 36219 }


    iqupc00LoudCustomBlock2mbsoftclip2 OBJECT-TYPE
        SYNTAX            INTEGER
        MAX-ACCESS        read-write
        STATUS            current
        DESCRIPTION
                "CMNT: - Linear Acoustic MB Block2 SoftClip2
                 TYPE: - Number
                 PAGE: - LoudCustom
                    mb softclip2  cmdID= 36221
                    min= 0  max= 180  step= 1  format= %0.1f dB  div_scale= 10  preset= 180
                    Min = 0.0 dB  Max = 18.0 dB  Step = 0.1 dB  Preset = 18.0 dB  "
        ::= { iqupc00CmdEntry 36221 }


    iqupc00LoudCustomBlock2mbratio OBJECT-TYPE
        SYNTAX            INTEGER
        MAX-ACCESS        read-write
        STATUS            current
        DESCRIPTION
                "CMNT: - Linear Acoustic MB Block2 Ratio
                 TYPE: - Number
                 PAGE: - LoudCustom
                    mb ratio  cmdID= 36223
                    min= 0  max= 100  step= 1  format= %0.0f  div_scale= 1  preset= 63
                    Min = 0  Max = 100  Step = 1  Preset = 63  "
        ::= { iqupc00CmdEntry 36223 }


    iqupc00LoudCustomBlock2mblimdrive OBJECT-TYPE
        SYNTAX            INTEGER
        MAX-ACCESS        read-write
        STATUS            current
        DESCRIPTION
                "CMNT: - Linear Acoustic MB Block2 OutLimDrive
                 TYPE: - Number
                 PAGE: - LoudCustom
                    mb lim drive  cmdID= 36225
                    min= -60  max= 60  step= 1  format= %0.1f dB  div_scale= 10  preset= -50
                    Min = -6.0 dB  Max = 6.0 dB  Step = 0.1 dB  Preset = -5.0 dB  "
        ::= { iqupc00CmdEntry 36225 }


    iqupc00LoudCustomBlock2CustomPreset OBJECT-TYPE
        SYNTAX            INTEGER {
                            valGeneral(0),
                            valLight(1),
                            valHeavy(2),
                            valLoud(3),
                            valLoudLimit(4),
                            valProtectionLimit(5),
                            valDefaults(6),
                            valCustom(7)
                            }
        MAX-ACCESS        read-write
        STATUS            current
        DESCRIPTION
                "CMNT: - Linear Acoustic Cust Preset 2
                 TYPE: - RadiobuttonList
                 PAGE: - LoudCustom
                    CustomPreset  cmdID= 36307
                    General  value= 0
                    Light  value= 1
                    Heavy  value= 2
                    Loud  value= 3
                    LoudLimit  value= 4
                    ProtectionLimit  value= 5
                    Defaults  value= 6
                    Custom  value= 7  "
        ::= { iqupc00CmdEntry 36307 }


    iqupc00LoudCustomBlock2Copyto1 OBJECT-TYPE
        SYNTAX            INTEGER { noAction(0),valCopyto1(1) }
        MAX-ACCESS        read-write
        STATUS            current
        DESCRIPTION
                "CMNT: - Linear Acoustic Cust Preset COPY 2 to 1
                 TYPE: - Button
                 PAGE: - LoudCustom
                    Copy to 1  cmdID= 36308
                    value= 1  "
        ::= { iqupc00CmdEntry 36308 }


    iqupc00LoudCustomMasterLevelCustom1 OBJECT-TYPE
        SYNTAX            INTEGER
        MAX-ACCESS        read-write
        STATUS            current
        DESCRIPTION
                "CMNT: - Linear Acoustic CUSTOM1 Master Level 
                 TYPE: - Number
                 PAGE: - LoudCustom
                    Custom1  cmdID= 36328
                    min= -310  max= 0  step= 1  format= %0.1f dB  div_scale= 10  preset= -110
                    Min = -31.0 dB  Max = 0.0 dB  Step = 0.1 dB  Preset = -11.0 dB  "
        ::= { iqupc00CmdEntry 36328 }


    iqupc00LoudCustomMasterLevelCustom2 OBJECT-TYPE
        SYNTAX            INTEGER
        MAX-ACCESS        read-write
        STATUS            current
        DESCRIPTION
                "CMNT: - Linear Acoustic CUSTOM2 Master Level 
                 TYPE: - Number
                 PAGE: - LoudCustom
                    Custom2  cmdID= 36329
                    min= -310  max= 0  step= 1  format= %0.1f dB  div_scale= 10  preset= -110
                    Min = -31.0 dB  Max = 0.0 dB  Step = 0.1 dB  Preset = -11.0 dB  "
        ::= { iqupc00CmdEntry 36329 }


    iqupc00LoudCustomMasterLevelGen51 OBJECT-TYPE
        SYNTAX            INTEGER
        MAX-ACCESS        read-write
        STATUS            current
        DESCRIPTION
                "CMNT: - Linear Acoustic 5.1 Master Level General
                 TYPE: - Number
                 PAGE: - LoudCustom
                    Gen_51  cmdID= 36310
                    min= -310  max= 0  step= 1  format= %0.1f dB  div_scale= 10  preset= -110
                    Min = -31.0 dB  Max = 0.0 dB  Step = 0.1 dB  Preset = -11.0 dB  "
        ::= { iqupc00CmdEntry 36310 }


    iqupc00LoudCustomMasterLevelLight51 OBJECT-TYPE
        SYNTAX            INTEGER
        MAX-ACCESS        read-write
        STATUS            current
        DESCRIPTION
                "CMNT: - Linear Acoustic 5.1 Master Level Light
                 TYPE: - Number
                 PAGE: - LoudCustom
                    Light_51  cmdID= 36311
                    min= -310  max= 0  step= 1  format= %0.1f dB  div_scale= 10  preset= -110
                    Min = -31.0 dB  Max = 0.0 dB  Step = 0.1 dB  Preset = -11.0 dB  "
        ::= { iqupc00CmdEntry 36311 }


    iqupc00LoudCustomMasterLevelHeavy51 OBJECT-TYPE
        SYNTAX            INTEGER
        MAX-ACCESS        read-write
        STATUS            current
        DESCRIPTION
                "CMNT: - Linear Acoustic 5.1 Master Level Heavy
                 TYPE: - Number
                 PAGE: - LoudCustom
                    Heavy_51  cmdID= 36312
                    min= -310  max= 0  step= 1  format= %0.1f dB  div_scale= 10  preset= -110
                    Min = -31.0 dB  Max = 0.0 dB  Step = 0.1 dB  Preset = -11.0 dB  "
        ::= { iqupc00CmdEntry 36312 }


    iqupc00LoudCustomMasterLevelLoud51 OBJECT-TYPE
        SYNTAX            INTEGER
        MAX-ACCESS        read-write
        STATUS            current
        DESCRIPTION
                "CMNT: - Linear Acoustic 5.1 Master Level Loud
                 TYPE: - Number
                 PAGE: - LoudCustom
                    Loud_51  cmdID= 36313
                    min= -310  max= 0  step= 1  format= %0.1f dB  div_scale= 10  preset= -110
                    Min = -31.0 dB  Max = 0.0 dB  Step = 0.1 dB  Preset = -11.0 dB  "
        ::= { iqupc00CmdEntry 36313 }


    iqupc00LoudCustomMasterLevelLoudLimit51 OBJECT-TYPE
        SYNTAX            INTEGER
        MAX-ACCESS        read-write
        STATUS            current
        DESCRIPTION
                "CMNT: - Linear Acoustic 5.1 Master Level LoudLimit
                 TYPE: - Number
                 PAGE: - LoudCustom
                    LoudLimit_51  cmdID= 36314
                    min= -310  max= 0  step= 1  format= %0.1f dB  div_scale= 10  preset= -60
                    Min = -31.0 dB  Max = 0.0 dB  Step = 0.1 dB  Preset = -6.0 dB  "
        ::= { iqupc00CmdEntry 36314 }


    iqupc00LoudCustomMasterLevelProtect51 OBJECT-TYPE
        SYNTAX            INTEGER
        MAX-ACCESS        read-write
        STATUS            current
        DESCRIPTION
                "CMNT: - Linear Acoustic 5.1 Master Level Protection
                 TYPE: - Number
                 PAGE: - LoudCustom
                    Protect_51  cmdID= 36315
                    min= -310  max= 0  step= 1  format= %0.1f dB  div_scale= 10  preset= -30
                    Min = -31.0 dB  Max = 0.0 dB  Step = 0.1 dB  Preset = -3.0 dB  "
        ::= { iqupc00CmdEntry 36315 }


    iqupc00LoudCustomMasterLevelGenSterA OBJECT-TYPE
        SYNTAX            INTEGER
        MAX-ACCESS        read-write
        STATUS            current
        DESCRIPTION
                "CMNT: - Linear Acoustic StereoA Master Level General
                 TYPE: - Number
                 PAGE: - LoudCustom
                    Gen_SterA  cmdID= 36316
                    min= -310  max= 0  step= 1  format= %0.1f dB  div_scale= 10  preset= -110
                    Min = -31.0 dB  Max = 0.0 dB  Step = 0.1 dB  Preset = -11.0 dB  "
        ::= { iqupc00CmdEntry 36316 }


    iqupc00LoudCustomMasterLevelLightSterA OBJECT-TYPE
        SYNTAX            INTEGER
        MAX-ACCESS        read-write
        STATUS            current
        DESCRIPTION
                "CMNT: - Linear Acoustic StereoA Master Level Light
                 TYPE: - Number
                 PAGE: - LoudCustom
                    Light_SterA  cmdID= 36317
                    min= -310  max= 0  step= 1  format= %0.1f dB  div_scale= 10  preset= -110
                    Min = -31.0 dB  Max = 0.0 dB  Step = 0.1 dB  Preset = -11.0 dB  "
        ::= { iqupc00CmdEntry 36317 }


    iqupc00LoudCustomMasterLevelHeavySterA OBJECT-TYPE
        SYNTAX            INTEGER
        MAX-ACCESS        read-write
        STATUS            current
        DESCRIPTION
                "CMNT: - Linear Acoustic StereoA Master Level Heavy
                 TYPE: - Number
                 PAGE: - LoudCustom
                    Heavy_SterA  cmdID= 36318
                    min= -310  max= 0  step= 1  format= %0.1f dB  div_scale= 10  preset= -110
                    Min = -31.0 dB  Max = 0.0 dB  Step = 0.1 dB  Preset = -11.0 dB  "
        ::= { iqupc00CmdEntry 36318 }


    iqupc00LoudCustomMasterLevelLoudSterA OBJECT-TYPE
        SYNTAX            INTEGER
        MAX-ACCESS        read-write
        STATUS            current
        DESCRIPTION
                "CMNT: - Linear Acoustic StereoA Master Level Loud
                 TYPE: - Number
                 PAGE: - LoudCustom
                    Loud_SterA  cmdID= 36319
                    min= -310  max= 0  step= 1  format= %0.1f dB  div_scale= 10  preset= -110
                    Min = -31.0 dB  Max = 0.0 dB  Step = 0.1 dB  Preset = -11.0 dB  "
        ::= { iqupc00CmdEntry 36319 }


    iqupc00LoudCustomMasterLevelLoudLimitSterA OBJECT-TYPE
        SYNTAX            INTEGER
        MAX-ACCESS        read-write
        STATUS            current
        DESCRIPTION
                "CMNT: - Linear Acoustic StereoA Master Level LoudLimit
                 TYPE: - Number
                 PAGE: - LoudCustom
                    LoudLimit_SterA  cmdID= 36320
                    min= -310  max= 0  step= 1  format= %0.1f dB  div_scale= 10  preset= -60
                    Min = -31.0 dB  Max = 0.0 dB  Step = 0.1 dB  Preset = -6.0 dB  "
        ::= { iqupc00CmdEntry 36320 }


    iqupc00LoudCustomMasterLevelProtectSterA OBJECT-TYPE
        SYNTAX            INTEGER
        MAX-ACCESS        read-write
        STATUS            current
        DESCRIPTION
                "CMNT: - Linear Acoustic StereoA Master Level Protection
                 TYPE: - Number
                 PAGE: - LoudCustom
                    Protect_SterA  cmdID= 36321
                    min= -310  max= 0  step= 1  format= %0.1f dB  div_scale= 10  preset= -30
                    Min = -31.0 dB  Max = 0.0 dB  Step = 0.1 dB  Preset = -3.0 dB  "
        ::= { iqupc00CmdEntry 36321 }


    iqupc00LoudCustomMasterLevelGenSterB OBJECT-TYPE
        SYNTAX            INTEGER
        MAX-ACCESS        read-write
        STATUS            current
        DESCRIPTION
                "CMNT: - Linear Acoustic StereoB Master Level General
                 TYPE: - Number
                 PAGE: - LoudCustom
                    Gen_SterB  cmdID= 36322
                    min= -310  max= 0  step= 1  format= %0.1f dB  div_scale= 10  preset= -110
                    Min = -31.0 dB  Max = 0.0 dB  Step = 0.1 dB  Preset = -11.0 dB  "
        ::= { iqupc00CmdEntry 36322 }


    iqupc00LoudCustomMasterLevelLightSterB OBJECT-TYPE
        SYNTAX            INTEGER
        MAX-ACCESS        read-write
        STATUS            current
        DESCRIPTION
                "CMNT: - Linear Acoustic StereoB Master Level Light
                 TYPE: - Number
                 PAGE: - LoudCustom
                    Light_SterB  cmdID= 36323
                    min= -310  max= 0  step= 1  format= %0.1f dB  div_scale= 10  preset= -110
                    Min = -31.0 dB  Max = 0.0 dB  Step = 0.1 dB  Preset = -11.0 dB  "
        ::= { iqupc00CmdEntry 36323 }


    iqupc00LoudCustomMasterLevelHeavySterB OBJECT-TYPE
        SYNTAX            INTEGER
        MAX-ACCESS        read-write
        STATUS            current
        DESCRIPTION
                "CMNT: - Linear Acoustic StereoB Master Level Heavy
                 TYPE: - Number
                 PAGE: - LoudCustom
                    Heavy_SterB  cmdID= 36324
                    min= -310  max= 0  step= 1  format= %0.1f dB  div_scale= 10  preset= -110
                    Min = -31.0 dB  Max = 0.0 dB  Step = 0.1 dB  Preset = -11.0 dB  "
        ::= { iqupc00CmdEntry 36324 }


    iqupc00LoudCustomMasterLevelLoudSterB OBJECT-TYPE
        SYNTAX            INTEGER
        MAX-ACCESS        read-write
        STATUS            current
        DESCRIPTION
                "CMNT: - Linear Acoustic StereoB Master Level Loud
                 TYPE: - Number
                 PAGE: - LoudCustom
                    Loud_SterB  cmdID= 36325
                    min= -310  max= 0  step= 1  format= %0.1f dB  div_scale= 10  preset= -110
                    Min = -31.0 dB  Max = 0.0 dB  Step = 0.1 dB  Preset = -11.0 dB  "
        ::= { iqupc00CmdEntry 36325 }


    iqupc00LoudCustomMasterLevelLoudLimitSterB OBJECT-TYPE
        SYNTAX            INTEGER
        MAX-ACCESS        read-write
        STATUS            current
        DESCRIPTION
                "CMNT: - Linear Acoustic StereoB Master Level LoudLimit
                 TYPE: - Number
                 PAGE: - LoudCustom
                    LoudLimit_SterB  cmdID= 36326
                    min= -310  max= 0  step= 1  format= %0.1f dB  div_scale= 10  preset= -60
                    Min = -31.0 dB  Max = 0.0 dB  Step = 0.1 dB  Preset = -6.0 dB  "
        ::= { iqupc00CmdEntry 36326 }


    iqupc00LoudCustomMasterLevelProtectSterB OBJECT-TYPE
        SYNTAX            INTEGER
        MAX-ACCESS        read-write
        STATUS            current
        DESCRIPTION
                "CMNT: - Linear Acoustic StereoB Master Level Protection
                 TYPE: - Number
                 PAGE: - LoudCustom
                    Protect_SterB  cmdID= 36327
                    min= -310  max= 0  step= 1  format= %0.1f dB  div_scale= 10  preset= -30
                    Min = -31.0 dB  Max = 0.0 dB  Step = 0.1 dB  Preset = -3.0 dB  "
        ::= { iqupc00CmdEntry 36327 }


    iqupc00Mixers13Select OBJECT-TYPE
        SYNTAX            INTEGER {
                            valMixer1(0),
                            valMixer2(1),
                            valMixer3(2),
                            valMixer4(3),
                            valDownmix1n1(4),
                            valDownmix1n2(5)
                            }
        MAX-ACCESS        read-write
        STATUS            current
        DESCRIPTION
                "CMNT: - Mixer select
                 TYPE: - RadiobuttonList
                 PAGE: - Mixers1_3
                    Select  cmdID= 40825
                    Mixer1  value= 0
                    Mixer2  value= 1
                    Mixer3  value= 2
                    Mixer4  value= 3
                    Downmix1-1  value= 4
                    Downmix1-2  value= 5  "
        ::= { iqupc00CmdEntry 40825 }


    iqupc00Mixers13Source1ProcGain OBJECT-TYPE
        SYNTAX            INTEGER
        MAX-ACCESS        read-write
        STATUS            current
        DESCRIPTION
                "CMNT: - Mix_1 Proc Amp Gain
                 TYPE: - Number
                 PAGE: - Mixers1_3
                    ProcGain  cmdID= 40800
                    min= -801  max= 120  step= 1  format= %0.1f dB  div_scale= 10  preset= 0
                    Min = -80.1 dB  Max = 12.0 dB  Step = 0.1 dB  Preset = 0.0 dB  "
        ::= { iqupc00CmdEntry 40800 }


    iqupc00Mixers13Source1Invert OBJECT-TYPE
        SYNTAX            INTEGER { disable(0), enable(1)  }
        MAX-ACCESS        read-write
        STATUS            current
        DESCRIPTION
                "CMNT: - Mix_1 Invert
                 TYPE: - Checkbox
                 PAGE: - Mixers1_3
                    Invert  cmdID= 40806  "
        ::= { iqupc00CmdEntry 40806 }


    iqupc00Mixers13Source1Mute OBJECT-TYPE
        SYNTAX            INTEGER { disable(0), enable(1)  }
        MAX-ACCESS        read-write
        STATUS            current
        DESCRIPTION
                "CMNT: - Mix_1 Mute
                 TYPE: - Checkbox
                 PAGE: - Mixers1_3
                    Mute  cmdID= 40812  "
        ::= { iqupc00CmdEntry 40812 }


    iqupc00Mixers13Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_1 source
                 TYPE: - RadiobuttonList
                 PAGE: - Mixers1_3
                    Src  cmdID= 40818
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 40818 }


    iqupc00Mixers13Source1Name OBJECT-TYPE
        SYNTAX            RollCallString
        MAX-ACCESS        read-only
        STATUS            current
        DESCRIPTION
                "CMNT: - Mix_1 name
                 TYPE: - Display
                 PAGE: - Mixers1_3
                    Name  cmdID= 40826  "
        ::= { iqupc00CmdEntry 40826 }


    iqupc00Mixers13Source2ProcGain OBJECT-TYPE
        SYNTAX            INTEGER
        MAX-ACCESS        read-write
        STATUS            current
        DESCRIPTION
                "CMNT: - Mix_2 Proc Amp Gain
                 TYPE: - Number
                 PAGE: - Mixers1_3
                    ProcGain  cmdID= 40801
                    min= -801  max= 120  step= 1  format= %0.1f dB  div_scale= 10  preset= 0
                    Min = -80.1 dB  Max = 12.0 dB  Step = 0.1 dB  Preset = 0.0 dB  "
        ::= { iqupc00CmdEntry 40801 }


    iqupc00Mixers13Source2Invert OBJECT-TYPE
        SYNTAX            INTEGER { disable(0), enable(1)  }
        MAX-ACCESS        read-write
        STATUS            current
        DESCRIPTION
                "CMNT: - Mix_2 Invert
                 TYPE: - Checkbox
                 PAGE: - Mixers1_3
                    Invert  cmdID= 40807  "
        ::= { iqupc00CmdEntry 40807 }


    iqupc00Mixers13Source2Mute OBJECT-TYPE
        SYNTAX            INTEGER { disable(0), enable(1)  }
        MAX-ACCESS        read-write
        STATUS            current
        DESCRIPTION
                "CMNT: - Mix_2 Mute
                 TYPE: - Checkbox
                 PAGE: - Mixers1_3
                    Mute  cmdID= 40813  "
        ::= { iqupc00CmdEntry 40813 }


    iqupc00Mixers13Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_2 source
                 TYPE: - RadiobuttonList
                 PAGE: - Mixers1_3
                    Src  cmdID= 40819
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 40819 }


    iqupc00Mixers13Source2Name OBJECT-TYPE
        SYNTAX            RollCallString
        MAX-ACCESS        read-only
        STATUS            current
        DESCRIPTION
                "CMNT: - Mix_2 name
                 TYPE: - Display
                 PAGE: - Mixers1_3
                    Name  cmdID= 40827  "
        ::= { iqupc00CmdEntry 40827 }


    iqupc00Mixers13Source3ProcGain OBJECT-TYPE
        SYNTAX            INTEGER
        MAX-ACCESS        read-write
        STATUS            current
        DESCRIPTION
                "CMNT: - Mix_3 Proc Amp Gain
                 TYPE: - Number
                 PAGE: - Mixers1_3
                    ProcGain  cmdID= 40802
                    min= -801  max= 120  step= 1  format= %0.1f dB  div_scale= 10  preset= 0
                    Min = -80.1 dB  Max = 12.0 dB  Step = 0.1 dB  Preset = 0.0 dB  "
        ::= { iqupc00CmdEntry 40802 }


    iqupc00Mixers13Source3Invert OBJECT-TYPE
        SYNTAX            INTEGER { disable(0), enable(1)  }
        MAX-ACCESS        read-write
        STATUS            current
        DESCRIPTION
                "CMNT: - Mix_3 Invert
                 TYPE: - Checkbox
                 PAGE: - Mixers1_3
                    Invert  cmdID= 40808  "
        ::= { iqupc00CmdEntry 40808 }


    iqupc00Mixers13Source3Mute OBJECT-TYPE
        SYNTAX            INTEGER { disable(0), enable(1)  }
        MAX-ACCESS        read-write
        STATUS            current
        DESCRIPTION
                "CMNT: - Mix_3 Mute
                 TYPE: - Checkbox
                 PAGE: - Mixers1_3
                    Mute  cmdID= 40814  "
        ::= { iqupc00CmdEntry 40814 }


    iqupc00Mixers13Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_3 source
                 TYPE: - RadiobuttonList
                 PAGE: - Mixers1_3
                    Src  cmdID= 40820
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 40820 }


    iqupc00Mixers13Source3Name OBJECT-TYPE
        SYNTAX            RollCallString
        MAX-ACCESS        read-only
        STATUS            current
        DESCRIPTION
                "CMNT: - Mix_3 name
                 TYPE: - Display
                 PAGE: - Mixers1_3
                    Name  cmdID= 40828  "
        ::= { iqupc00CmdEntry 40828 }


    iqupc00Mixers13MixerLoRo OBJECT-TYPE
        SYNTAX            INTEGER {
                            valCustom(0),
                            valn3dBCpLsRs(1),
                            valn3dBCn3dBLsRs(2),
                            valn3dBCn6dBLsRs(3),
                            valn3dBCn9dBLsRs(4)
                            }
        MAX-ACCESS        read-write
        STATUS            current
        DESCRIPTION
                "CMNT: - DownMixLoRo
                 TYPE: - RadiobuttonList
                 PAGE: - Mixers1_3
                    MixerLoRo  cmdID= 40832
                    Custom  value= 0
                    -3dB C + Ls/Rs  value= 1
                    -3dB C -3dB Ls/Rs  value= 2
                    -3dB C -6dB Ls/Rs  value= 3
                    -3dB C -9dB Ls/Rs  value= 4  "
        ::= { iqupc00CmdEntry 40832 }


    iqupc00Mixers46Source4ProcGain OBJECT-TYPE
        SYNTAX            INTEGER
        MAX-ACCESS        read-write
        STATUS            current
        DESCRIPTION
                "CMNT: - Mix_4 Proc Amp Gain
                 TYPE: - Number
                 PAGE: - Mixers4_6
                    ProcGain  cmdID= 40803
                    min= -801  max= 120  step= 1  format= %0.1f dB  div_scale= 10  preset= 0
                    Min = -80.1 dB  Max = 12.0 dB  Step = 0.1 dB  Preset = 0.0 dB  "
        ::= { iqupc00CmdEntry 40803 }


    iqupc00Mixers46Source4Invert OBJECT-TYPE
        SYNTAX            INTEGER { disable(0), enable(1)  }
        MAX-ACCESS        read-write
        STATUS            current
        DESCRIPTION
                "CMNT: - Mix_4 Invert
                 TYPE: - Checkbox
                 PAGE: - Mixers4_6
                    Invert  cmdID= 40809  "
        ::= { iqupc00CmdEntry 40809 }


    iqupc00Mixers46Source4Mute OBJECT-TYPE
        SYNTAX            INTEGER { disable(0), enable(1)  }
        MAX-ACCESS        read-write
        STATUS            current
        DESCRIPTION
                "CMNT: - Mix_4 Mute
                 TYPE: - Checkbox
                 PAGE: - Mixers4_6
                    Mute  cmdID= 40815  "
        ::= { iqupc00CmdEntry 40815 }


    iqupc00Mixers46Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_4 source
                 TYPE: - RadiobuttonList
                 PAGE: - Mixers4_6
                    Src  cmdID= 40821
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 40821 }


    iqupc00Mixers46Source4Name OBJECT-TYPE
        SYNTAX            RollCallString
        MAX-ACCESS        read-only
        STATUS            current
        DESCRIPTION
                "CMNT: - Mix_4 name
                 TYPE: - Display
                 PAGE: - Mixers4_6
                    Name  cmdID= 40829  "
        ::= { iqupc00CmdEntry 40829 }


    iqupc00Mixers46Source5ProcGain OBJECT-TYPE
        SYNTAX            INTEGER
        MAX-ACCESS        read-write
        STATUS            current
        DESCRIPTION
                "CMNT: - Mix_5 Proc Amp Gain
                 TYPE: - Number
                 PAGE: - Mixers4_6
                    ProcGain  cmdID= 40804
                    min= -801  max= 120  step= 1  format= %0.1f dB  div_scale= 10  preset= 0
                    Min = -80.1 dB  Max = 12.0 dB  Step = 0.1 dB  Preset = 0.0 dB  "
        ::= { iqupc00CmdEntry 40804 }


    iqupc00Mixers46Source5Invert OBJECT-TYPE
        SYNTAX            INTEGER { disable(0), enable(1)  }
        MAX-ACCESS        read-write
        STATUS            current
        DESCRIPTION
                "CMNT: - Mix_5 Invert
                 TYPE: - Checkbox
                 PAGE: - Mixers4_6
                    Invert  cmdID= 40810  "
        ::= { iqupc00CmdEntry 40810 }


    iqupc00Mixers46Source5Mute OBJECT-TYPE
        SYNTAX            INTEGER { disable(0), enable(1)  }
        MAX-ACCESS        read-write
        STATUS            current
        DESCRIPTION
                "CMNT: - Mix_5 Mute
                 TYPE: - Checkbox
                 PAGE: - Mixers4_6
                    Mute  cmdID= 40816  "
        ::= { iqupc00CmdEntry 40816 }


    iqupc00Mixers46Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_5 source
                 TYPE: - RadiobuttonList
                 PAGE: - Mixers4_6
                    Src  cmdID= 40822
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 40822 }


    iqupc00Mixers46Source5Name OBJECT-TYPE
        SYNTAX            RollCallString
        MAX-ACCESS        read-only
        STATUS            current
        DESCRIPTION
                "CMNT: - Mix_5 name
                 TYPE: - Display
                 PAGE: - Mixers4_6
                    Name  cmdID= 40830  "
        ::= { iqupc00CmdEntry 40830 }


    iqupc00Mixers46Source6ProcGain OBJECT-TYPE
        SYNTAX            INTEGER
        MAX-ACCESS        read-write
        STATUS            current
        DESCRIPTION
                "CMNT: - Mix_6 Proc Amp Gain
                 TYPE: - Number
                 PAGE: - Mixers4_6
                    ProcGain  cmdID= 40805
                    min= -801  max= 120  step= 1  format= %0.1f dB  div_scale= 10  preset= 0
                    Min = -80.1 dB  Max = 12.0 dB  Step = 0.1 dB  Preset = 0.0 dB  "
        ::= { iqupc00CmdEntry 40805 }


    iqupc00Mixers46Source6Invert OBJECT-TYPE
        SYNTAX            INTEGER { disable(0), enable(1)  }
        MAX-ACCESS        read-write
        STATUS            current
        DESCRIPTION
                "CMNT: - Mix_6 Invert
                 TYPE: - Checkbox
                 PAGE: - Mixers4_6
                    Invert  cmdID= 40811  "
        ::= { iqupc00CmdEntry 40811 }


    iqupc00Mixers46Source6Mute OBJECT-TYPE
        SYNTAX            INTEGER { disable(0), enable(1)  }
        MAX-ACCESS        read-write
        STATUS            current
        DESCRIPTION
                "CMNT: - Mix_6 Mute
                 TYPE: - Checkbox
                 PAGE: - Mixers4_6
                    Mute  cmdID= 40817  "
        ::= { iqupc00CmdEntry 40817 }


    iqupc00Mixers46Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - Mix_6 source
                 TYPE: - RadiobuttonList
                 PAGE: - Mixers4_6
                    Src  cmdID= 40823
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 40823 }


    iqupc00Mixers46Source6Name OBJECT-TYPE
        SYNTAX            RollCallString
        MAX-ACCESS        read-only
        STATUS            current
        DESCRIPTION
                "CMNT: - Mix_6 name
                 TYPE: - Display
                 PAGE: - Mixers4_6
                    Name  cmdID= 40831  "
        ::= { iqupc00CmdEntry 40831 }


    iqupc00DolbyDecodeDolbyDecoderDetectMode OBJECT-TYPE
        SYNTAX            INTEGER {
                            valAuto(0),
                            valDolbyEorMute(1),
                            valDolbyDigitalorMute(2),
                            valMute(3)
                            }
        MAX-ACCESS        read-write
        STATUS            current
        DESCRIPTION
                "CMNT: - Dolby decoder detect mode
                 TYPE: - RadiobuttonList
                 PAGE: - DolbyDecode
                    Detect Mode  cmdID= 42401
                    Auto  value= 0
                    Dolby E or Mute  value= 1
                    Dolby Digital or Mute  value= 2
                    Mute  value= 3  "
        ::= { iqupc00CmdEntry 42401 }


    iqupc00DolbyDecodeDolbyDecoderAESChannelSelect OBJECT-TYPE
        SYNTAX            INTEGER {
                            valChannel1(0),
                            valChannel2(1)
                            }
        MAX-ACCESS        read-write
        STATUS            current
        DESCRIPTION
                "CMNT: - Dolby Digital Pro 16 AES channel select
                 TYPE: - RadiobuttonList
                 PAGE: - DolbyDecode
                    AES Channel Select  cmdID= 42402
                    Channel 1  value= 0
                    Channel 2  value= 1  "
        ::= { iqupc00CmdEntry 42402 }


    iqupc00DolbyDecodeDolbyDecoderPCMLatency OBJECT-TYPE
        SYNTAX            INTEGER {
                            valSingleVideoFrame(0),
                            valMinimum(1)
                            }
        MAX-ACCESS        read-write
        STATUS            current
        DESCRIPTION
                "CMNT: - Dolby decoder PCM latency
                 TYPE: - RadiobuttonList
                 PAGE: - DolbyDecode
                    PCM Latency  cmdID= 42403
                    Single Video Frame  value= 0
                    Minimum  value= 1  "
        ::= { iqupc00CmdEntry 42403 }


    iqupc00DolbyDecodeDolbyDecoderListeningModeDolbyD OBJECT-TYPE
        SYNTAX            INTEGER {
                            valFull(0),
                            valEX(1),
                            val3Stereo(2),
                            valPhantom(3),
                            valStereo(4),
                            valMono(5)
                            }
        MAX-ACCESS        read-write
        STATUS            current
        DESCRIPTION
                "CMNT: - Dolby decoder listening mode
                 TYPE: - RadiobuttonList
                 PAGE: - DolbyDecode
                    Listening Mode Dolby D  cmdID= 42404
                    Full  value= 0
                    EX  value= 1
                    3 Stereo  value= 2
                    Phantom  value= 3
                    Stereo  value= 4
                    Mono  value= 5  "
        ::= { iqupc00CmdEntry 42404 }


    iqupc00DolbyDecodeDolbyDecoderDynamicRange OBJECT-TYPE
        SYNTAX            INTEGER {
                            valLineMode(0),
                            valRFMode(1),
                            valBypassMode(3)
                            }
        MAX-ACCESS        read-write
        STATUS            current
        DESCRIPTION
                "CMNT: - Dolby decoder dynamic range
                 TYPE: - RadiobuttonList
                 PAGE: - DolbyDecode
                    Dynamic Range   cmdID= 42405
                    Line Mode  value= 0
                    RF Mode  value= 1
                    Bypass Mode  value= 3  "
        ::= { iqupc00CmdEntry 42405 }


    iqupc00DolbyDecoderAuxChannelProgramSelect OBJECT-TYPE
        SYNTAX            INTEGER {
                            valProgram1(0),
                            valProgram2(1),
                            valProgram3(2),
                            valProgram4(3),
                            valProgram5(4),
                            valProgram6(5),
                            valProgram7(6),
                            valProgram8(7)
                            }
        MAX-ACCESS        read-write
        STATUS            current
        DESCRIPTION
                "CMNT: - Dolby decoder auxiliary channel program select
                 TYPE: - RadiobuttonList
                 PAGE: - Dolby Decoder
                    Program Select  cmdID= 42406
                    Program 1  value= 0
                    Program 2  value= 1
                    Program 3  value= 2
                    Program 4  value= 3
                    Program 5  value= 4
                    Program 6  value= 5
                    Program 7  value= 6
                    Program 8  value= 7  "
        ::= { iqupc00CmdEntry 42406 }


    iqupc00DolbyDecoderAuxChannelDynamicRange OBJECT-TYPE
        SYNTAX            INTEGER {
                            valLineMode(0),
                            valRFMode(1)
                            }
        MAX-ACCESS        read-write
        STATUS            current
        DESCRIPTION
                "CMNT: - Dolby decoder auxiliary channel dynamic range
                 TYPE: - RadiobuttonList
                 PAGE: - Dolby Decoder
                    Dynamic Range  cmdID= 42407
                    Line Mode  value= 0
                    RF Mode  value= 1  "
        ::= { iqupc00CmdEntry 42407 }


    iqupc00DolbyDecoderAuxChannelOutputMode OBJECT-TYPE
        SYNTAX            INTEGER {
                            valLtRt(0),
                            valLoRo(1),
                            valMono(2),
                            valMute(3)
                            }
        MAX-ACCESS        read-write
        STATUS            current
        DESCRIPTION
                "CMNT: - Dolby decoder auxiliary channel output mode
                 TYPE: - RadiobuttonList
                 PAGE: - Dolby Decoder
                    Output Mode  cmdID= 42408
                    Lt/Rt  value= 0
                    Lo/Ro  value= 1
                    Mono  value= 2
                    Mute  value= 3  "
        ::= { iqupc00CmdEntry 42408 }


    iqupc00DolbyDecoderDecoderStatusBitstreamFormat OBJECT-TYPE
        SYNTAX            RollCallString
        MAX-ACCESS        read-only
        STATUS            current
        DESCRIPTION
                "CMNT: - Dolby decoder I/P bitstream format
                 TYPE: - Display
                 PAGE: - Dolby Decoder
                    Bitstream Format  cmdID= 42409  "
        ::= { iqupc00CmdEntry 42409 }


    iqupc00DolbyDecoderDecoderStatusBitstreamStatus OBJECT-TYPE
        SYNTAX            RollCallString
        MAX-ACCESS        read-only
        STATUS            current
        DESCRIPTION
                "CMNT: - Dolby decoder I/P bitstream status
                 TYPE: - Display
                 PAGE: - Dolby Decoder
                    Bitstream Status  cmdID= 42410  "
        ::= { iqupc00CmdEntry 42410 }


    iqupc00DolbyDecoderDecoderStatusDCRCErrorCount OBJECT-TYPE
        SYNTAX            RollCallString
        MAX-ACCESS        read-only
        STATUS            current
        DESCRIPTION
                "CMNT: - Dolby D decoder CRC error count
                 TYPE: - Display
                 PAGE: - Dolby Decoder
                    D CRC Error Count  cmdID= 42505  "
        ::= { iqupc00CmdEntry 42505 }


    iqupc00DolbyDecoderDecoderStatusDCRCErrorTime OBJECT-TYPE
        SYNTAX            RollCallString
        MAX-ACCESS        read-only
        STATUS            current
        DESCRIPTION
                "CMNT: - Dolby D decoder CRC error time
                 TYPE: - Display
                 PAGE: - Dolby Decoder
                    D CRC Error Time  cmdID= 42504  "
        ::= { iqupc00CmdEntry 42504 }


    iqupc00DolbyDecoderDecoderStatusECRCErrorCount OBJECT-TYPE
        SYNTAX            RollCallString
        MAX-ACCESS        read-only
        STATUS            current
        DESCRIPTION
                "CMNT: - Dolby E decoder CRC error count
                 TYPE: - Display
                 PAGE: - Dolby Decoder
                    E CRC Error Count  cmdID= 42507  "
        ::= { iqupc00CmdEntry 42507 }


    iqupc00DolbyDecoderDecoderStatusECRCErrorTime OBJECT-TYPE
        SYNTAX            RollCallString
        MAX-ACCESS        read-only
        STATUS            current
        DESCRIPTION
                "CMNT: - Dolby E decoder CRC error time
                 TYPE: - Display
                 PAGE: - Dolby Decoder
                    E CRC Error Time  cmdID= 42506  "
        ::= { iqupc00CmdEntry 42506 }


    iqupc00DolbyDecoderDecoderStatusResetErrors OBJECT-TYPE
        SYNTAX            INTEGER { noAction(0),valResetErrors(1) }
        MAX-ACCESS        read-write
        STATUS            current
        DESCRIPTION
                "CMNT: - Dolby decoder CRC error reset
                 TYPE: - Button
                 PAGE: - Dolby Decoder
                    Reset Errors  cmdID= 42502
                    value= 1  "
        ::= { iqupc00CmdEntry 42502 }


    iqupc00DolbyDecoderDecoderStatusResetTime OBJECT-TYPE
        SYNTAX            RollCallString
        MAX-ACCESS        read-only
        STATUS            current
        DESCRIPTION
                "CMNT: - Dolby decoder CRC error reset time
                 TYPE: - Display
                 PAGE: - Dolby Decoder
                    Reset Time  cmdID= 42503  "
        ::= { iqupc00CmdEntry 42503 }


    iqupc00DolbyDecoderOutputsA1A2A1Gain OBJECT-TYPE
        SYNTAX            INTEGER
        MAX-ACCESS        read-write
        STATUS            current
        DESCRIPTION
                "CMNT: - Dolby decoder O/P A1 gain
                 TYPE: - Number
                 PAGE: - Dolby Decoder Outputs
                    A1 Gain  cmdID= 42558
                    min= -801  max= 120  step= 1  format= %0.1f dB  div_scale= 10  preset= 0
                    Min = -80.1 dB  Max = 12.0 dB  Step = 0.1 dB  Preset = 0.0 dB  "
        ::= { iqupc00CmdEntry 42558 }


    iqupc00DolbyDecoderOutputsA1A2A2Gain OBJECT-TYPE
        SYNTAX            INTEGER
        MAX-ACCESS        read-write
        STATUS            current
        DESCRIPTION
                "CMNT: - Dolby decoder O/P A2 gain
                 TYPE: - Number
                 PAGE: - Dolby Decoder Outputs
                    A2 Gain  cmdID= 42559
                    min= -801  max= 120  step= 1  format= %0.1f dB  div_scale= 10  preset= 0
                    Min = -80.1 dB  Max = 12.0 dB  Step = 0.1 dB  Preset = 0.0 dB  "
        ::= { iqupc00CmdEntry 42559 }


    iqupc00DolbyDecoderOutputsA1A2MuteA1 OBJECT-TYPE
        SYNTAX            INTEGER { disable(0), enable(1)  }
        MAX-ACCESS        read-write
        STATUS            current
        DESCRIPTION
                "CMNT: - Dolby decoder O/P A1 mute
                 TYPE: - Checkbox
                 PAGE: - Dolby Decoder Outputs
                    Mute A1  cmdID= 42568  "
        ::= { iqupc00CmdEntry 42568 }


    iqupc00DolbyDecoderOutputsA1A2MuteA2 OBJECT-TYPE
        SYNTAX            INTEGER { disable(0), enable(1)  }
        MAX-ACCESS        read-write
        STATUS            current
        DESCRIPTION
                "CMNT: - Dolby decoder O/P A2 mute
                 TYPE: - Checkbox
                 PAGE: - Dolby Decoder Outputs
                    Mute A2  cmdID= 42569  "
        ::= { iqupc00CmdEntry 42569 }


    iqupc00DolbyDecoderOutputsA1A2StereoA OBJECT-TYPE
        SYNTAX            INTEGER { disable(0), enable(1)  }
        MAX-ACCESS        read-write
        STATUS            current
        DESCRIPTION
                "CMNT: - Dolby decoder O/P A stereo
                 TYPE: - Checkbox
                 PAGE: - Dolby Decoder Outputs
                    Stereo A  cmdID= 42578  "
        ::= { iqupc00CmdEntry 42578 }


    iqupc00DolbyDecoderOutputsB3B4B3Gain OBJECT-TYPE
        SYNTAX            INTEGER
        MAX-ACCESS        read-write
        STATUS            current
        DESCRIPTION
                "CMNT: - Dolby decoder O/P B3 gain
                 TYPE: - Number
                 PAGE: - Dolby Decoder Outputs
                    B3 Gain  cmdID= 42560
                    min= -801  max= 120  step= 1  format= %0.1f dB  div_scale= 10  preset= 0
                    Min = -80.1 dB  Max = 12.0 dB  Step = 0.1 dB  Preset = 0.0 dB  "
        ::= { iqupc00CmdEntry 42560 }


    iqupc00DolbyDecoderOutputsB3B4B4Gain OBJECT-TYPE
        SYNTAX            INTEGER
        MAX-ACCESS        read-write
        STATUS            current
        DESCRIPTION
                "CMNT: - Dolby decoder O/P B4 gain
                 TYPE: - Number
                 PAGE: - Dolby Decoder Outputs
                    B4 Gain  cmdID= 42561
                    min= -801  max= 120  step= 1  format= %0.1f dB  div_scale= 10  preset= 0
                    Min = -80.1 dB  Max = 12.0 dB  Step = 0.1 dB  Preset = 0.0 dB  "
        ::= { iqupc00CmdEntry 42561 }


    iqupc00DolbyDecoderOutputsB3B4MuteB3 OBJECT-TYPE
        SYNTAX            INTEGER { disable(0), enable(1)  }
        MAX-ACCESS        read-write
        STATUS            current
        DESCRIPTION
                "CMNT: - Dolby decoder O/P B3 mute
                 TYPE: - Checkbox
                 PAGE: - Dolby Decoder Outputs
                    Mute B3  cmdID= 42570  "
        ::= { iqupc00CmdEntry 42570 }


    iqupc00DolbyDecoderOutputsB3B4MuteB4 OBJECT-TYPE
        SYNTAX            INTEGER { disable(0), enable(1)  }
        MAX-ACCESS        read-write
        STATUS            current
        DESCRIPTION
                "CMNT: - Dolby decoder O/P B4 mute
                 TYPE: - Checkbox
                 PAGE: - Dolby Decoder Outputs
                    Mute B4  cmdID= 42571  "
        ::= { iqupc00CmdEntry 42571 }


    iqupc00DolbyDecoderOutputsB3B4StereoB OBJECT-TYPE
        SYNTAX            INTEGER { disable(0), enable(1)  }
        MAX-ACCESS        read-write
        STATUS            current
        DESCRIPTION
                "CMNT: - Dolby decoder O/P B stereo
                 TYPE: - Checkbox
                 PAGE: - Dolby Decoder Outputs
                    Stereo B  cmdID= 42579  "
        ::= { iqupc00CmdEntry 42579 }


    iqupc00DolbyDecoderOutputsC5C6C5Gain OBJECT-TYPE
        SYNTAX            INTEGER
        MAX-ACCESS        read-write
        STATUS            current
        DESCRIPTION
                "CMNT: - Dolby decoder O/P C5 gain
                 TYPE: - Number
                 PAGE: - Dolby Decoder Outputs
                    C5 Gain  cmdID= 42562
                    min= -801  max= 120  step= 1  format= %0.1f dB  div_scale= 10  preset= 0
                    Min = -80.1 dB  Max = 12.0 dB  Step = 0.1 dB  Preset = 0.0 dB  "
        ::= { iqupc00CmdEntry 42562 }


    iqupc00DolbyDecoderOutputsC5C6C6Gain OBJECT-TYPE
        SYNTAX            INTEGER
        MAX-ACCESS        read-write
        STATUS            current
        DESCRIPTION
                "CMNT: - Dolby decoder O/P C6 gain
                 TYPE: - Number
                 PAGE: - Dolby Decoder Outputs
                    C6 Gain  cmdID= 42563
                    min= -801  max= 120  step= 1  format= %0.1f dB  div_scale= 10  preset= 0
                    Min = -80.1 dB  Max = 12.0 dB  Step = 0.1 dB  Preset = 0.0 dB  "
        ::= { iqupc00CmdEntry 42563 }


    iqupc00DolbyDecoderOutputsC5C6MuteC5 OBJECT-TYPE
        SYNTAX            INTEGER { disable(0), enable(1)  }
        MAX-ACCESS        read-write
        STATUS            current
        DESCRIPTION
                "CMNT: - Dolby decoder O/P C5 mute
                 TYPE: - Checkbox
                 PAGE: - Dolby Decoder Outputs
                    Mute C5  cmdID= 42572  "
        ::= { iqupc00CmdEntry 42572 }


    iqupc00DolbyDecoderOutputsC5C6MuteC6 OBJECT-TYPE
        SYNTAX            INTEGER { disable(0), enable(1)  }
        MAX-ACCESS        read-write
        STATUS            current
        DESCRIPTION
                "CMNT: - Dolby decoder O/P C6 mute
                 TYPE: - Checkbox
                 PAGE: - Dolby Decoder Outputs
                    Mute C6  cmdID= 42573  "
        ::= { iqupc00CmdEntry 42573 }


    iqupc00DolbyDecoderOutputsC5C6StereoC OBJECT-TYPE
        SYNTAX            INTEGER { disable(0), enable(1)  }
        MAX-ACCESS        read-write
        STATUS            current
        DESCRIPTION
                "CMNT: - Dolby decoder O/P C stereo
                 TYPE: - Checkbox
                 PAGE: - Dolby Decoder Outputs
                    Stereo C  cmdID= 42580  "
        ::= { iqupc00CmdEntry 42580 }


    iqupc00DolbyDecoderOutputsD7D8D7Gain OBJECT-TYPE
        SYNTAX            INTEGER
        MAX-ACCESS        read-write
        STATUS            current
        DESCRIPTION
                "CMNT: - Dolby decoder O/P D7 gain
                 TYPE: - Number
                 PAGE: - Dolby Decoder Outputs
                    D7 Gain  cmdID= 42564
                    min= -801  max= 120  step= 1  format= %0.1f dB  div_scale= 10  preset= 0
                    Min = -80.1 dB  Max = 12.0 dB  Step = 0.1 dB  Preset = 0.0 dB  "
        ::= { iqupc00CmdEntry 42564 }


    iqupc00DolbyDecoderOutputsD7D8D8Gain OBJECT-TYPE
        SYNTAX            INTEGER
        MAX-ACCESS        read-write
        STATUS            current
        DESCRIPTION
                "CMNT: - Dolby decoder O/P D8 gain
                 TYPE: - Number
                 PAGE: - Dolby Decoder Outputs
                    D8 Gain  cmdID= 42565
                    min= -801  max= 120  step= 1  format= %0.1f dB  div_scale= 10  preset= 0
                    Min = -80.1 dB  Max = 12.0 dB  Step = 0.1 dB  Preset = 0.0 dB  "
        ::= { iqupc00CmdEntry 42565 }


    iqupc00DolbyDecoderOutputsD7D8MuteD7 OBJECT-TYPE
        SYNTAX            INTEGER { disable(0), enable(1)  }
        MAX-ACCESS        read-write
        STATUS            current
        DESCRIPTION
                "CMNT: - Dolby decoder O/P D7 mute
                 TYPE: - Checkbox
                 PAGE: - Dolby Decoder Outputs
                    Mute D7  cmdID= 42574  "
        ::= { iqupc00CmdEntry 42574 }


    iqupc00DolbyDecoderOutputsD7D8MuteD8 OBJECT-TYPE
        SYNTAX            INTEGER { disable(0), enable(1)  }
        MAX-ACCESS        read-write
        STATUS            current
        DESCRIPTION
                "CMNT: - Dolby decoder O/P D8 mute
                 TYPE: - Checkbox
                 PAGE: - Dolby Decoder Outputs
                    Mute D8  cmdID= 42575  "
        ::= { iqupc00CmdEntry 42575 }


    iqupc00DolbyDecoderOutputsD7D8StereoD OBJECT-TYPE
        SYNTAX            INTEGER { disable(0), enable(1)  }
        MAX-ACCESS        read-write
        STATUS            current
        DESCRIPTION
                "CMNT: - Dolby decoder O/P D stereo
                 TYPE: - Checkbox
                 PAGE: - Dolby Decoder Outputs
                    Stereo D  cmdID= 42581  "
        ::= { iqupc00CmdEntry 42581 }


    iqupc00DolbyDecoderOutputsMLMRMLGain OBJECT-TYPE
        SYNTAX            INTEGER
        MAX-ACCESS        read-write
        STATUS            current
        DESCRIPTION
                "CMNT: - Dolby decoder downmix O/P L gain
                 TYPE: - Number
                 PAGE: - Dolby Decoder Outputs
                    ML Gain  cmdID= 42566
                    min= -801  max= 120  step= 1  format= %0.1f dB  div_scale= 10  preset= 0
                    Min = -80.1 dB  Max = 12.0 dB  Step = 0.1 dB  Preset = 0.0 dB  "
        ::= { iqupc00CmdEntry 42566 }


    iqupc00DolbyDecoderOutputsMLMRMRGain OBJECT-TYPE
        SYNTAX            INTEGER
        MAX-ACCESS        read-write
        STATUS            current
        DESCRIPTION
                "CMNT: - Dolby decoder downmix O/P R gain
                 TYPE: - Number
                 PAGE: - Dolby Decoder Outputs
                    MR Gain  cmdID= 42567
                    min= -801  max= 120  step= 1  format= %0.1f dB  div_scale= 10  preset= 0
                    Min = -80.1 dB  Max = 12.0 dB  Step = 0.1 dB  Preset = 0.0 dB  "
        ::= { iqupc00CmdEntry 42567 }


    iqupc00DolbyDecoderOutputsMLMRMuteML OBJECT-TYPE
        SYNTAX            INTEGER { disable(0), enable(1)  }
        MAX-ACCESS        read-write
        STATUS            current
        DESCRIPTION
                "CMNT: - Dolby decoder downmix O/P L mute
                 TYPE: - Checkbox
                 PAGE: - Dolby Decoder Outputs
                    Mute ML  cmdID= 42576  "
        ::= { iqupc00CmdEntry 42576 }


    iqupc00DolbyDecoderOutputsMLMRMuteMR OBJECT-TYPE
        SYNTAX            INTEGER { disable(0), enable(1)  }
        MAX-ACCESS        read-write
        STATUS            current
        DESCRIPTION
                "CMNT: - Dolby decoder downmix O/P R mute
                 TYPE: - Checkbox
                 PAGE: - Dolby Decoder Outputs
                    Mute MR  cmdID= 42577  "
        ::= { iqupc00CmdEntry 42577 }


    iqupc00DolbyDecoderOutputsMLMRStereoM OBJECT-TYPE
        SYNTAX            INTEGER { disable(0), enable(1)  }
        MAX-ACCESS        read-write
        STATUS            current
        DESCRIPTION
                "CMNT: - Dolby decoder downmix O/P stereo
                 TYPE: - Checkbox
                 PAGE: - Dolby Decoder Outputs
                    Stereo M  cmdID= 42582  "
        ::= { iqupc00CmdEntry 42582 }


    iqupc00DolbyDecodeDolbyDecoderOutputsMasterGain OBJECT-TYPE
        SYNTAX            INTEGER
        MAX-ACCESS        read-write
        STATUS            current
        DESCRIPTION
                "CMNT: - Dolby decoder O/P master gain
                 TYPE: - Number
                 PAGE: - DolbyDecode
                    Master Gain  cmdID= 42556
                    min= -801  max= 120  step= 1  format= %0.1f dB  div_scale= 10  preset= 0
                    Min = -80.1 dB  Max = 12.0 dB  Step = 0.1 dB  Preset = 0.0 dB  "
        ::= { iqupc00CmdEntry 42556 }


    iqupc00DolbyDecodeDolbyDecoderOutputsMasterMute OBJECT-TYPE
        SYNTAX            INTEGER { disable(0), enable(1)  }
        MAX-ACCESS        read-write
        STATUS            current
        DESCRIPTION
                "CMNT: - Dolby decoder O/P master mute
                 TYPE: - Checkbox
                 PAGE: - DolbyDecode
                    Master Mute  cmdID= 42557  "
        ::= { iqupc00CmdEntry 42557 }


    iqupc00DolbyEncInp14Source1ProcGain OBJECT-TYPE
        SYNTAX            INTEGER
        MAX-ACCESS        read-write
        STATUS            current
        DESCRIPTION
                "CMNT: - Dolby encoder A1 input gain
                 TYPE: - Number
                 PAGE: - Dolby Enc Inp1_4
                    ProcGain  cmdID= 42520
                    min= -801  max= 120  step= 1  format= %0.1f dB  div_scale= 10  preset= 0
                    Min = -80.1 dB  Max = 12.0 dB  Step = 0.1 dB  Preset = 0.0 dB  "
        ::= { iqupc00CmdEntry 42520 }


    iqupc00DolbyEncInp14Source1Mute OBJECT-TYPE
        SYNTAX            INTEGER { disable(0), enable(1)  }
        MAX-ACCESS        read-write
        STATUS            current
        DESCRIPTION
                "CMNT: - Dolby encoder A1 input mute
                 TYPE: - Checkbox
                 PAGE: - Dolby Enc Inp1_4
                    Mute  cmdID= 42528  "
        ::= { iqupc00CmdEntry 42528 }


    iqupc00DolbyEncInp14Source1Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder A1 input source
                 TYPE: - RadiobuttonList
                 PAGE: - Dolby Enc Inp1_4
                    Src  cmdID= 42536
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42536 }


    iqupc00DolbyEncInp14Source2ProcGain OBJECT-TYPE
        SYNTAX            INTEGER
        MAX-ACCESS        read-write
        STATUS            current
        DESCRIPTION
                "CMNT: - Dolby encoder A2 input gain
                 TYPE: - Number
                 PAGE: - Dolby Enc Inp1_4
                    ProcGain  cmdID= 42521
                    min= -801  max= 120  step= 1  format= %0.1f dB  div_scale= 10  preset= 0
                    Min = -80.1 dB  Max = 12.0 dB  Step = 0.1 dB  Preset = 0.0 dB  "
        ::= { iqupc00CmdEntry 42521 }


    iqupc00DolbyEncInp14Source2Mute OBJECT-TYPE
        SYNTAX            INTEGER { disable(0), enable(1)  }
        MAX-ACCESS        read-write
        STATUS            current
        DESCRIPTION
                "CMNT: - Dolby encoder A2 input mute
                 TYPE: - Checkbox
                 PAGE: - Dolby Enc Inp1_4
                    Mute  cmdID= 42529  "
        ::= { iqupc00CmdEntry 42529 }


    iqupc00DolbyEncInp14Source2Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder A2 input source
                 TYPE: - RadiobuttonList
                 PAGE: - Dolby Enc Inp1_4
                    Src  cmdID= 42537
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42537 }


    iqupc00DolbyEncInp14Source3ProcGain OBJECT-TYPE
        SYNTAX            INTEGER
        MAX-ACCESS        read-write
        STATUS            current
        DESCRIPTION
                "CMNT: - Dolby encoder B3 input gain
                 TYPE: - Number
                 PAGE: - Dolby Enc Inp1_4
                    ProcGain  cmdID= 42522
                    min= -801  max= 120  step= 1  format= %0.1f dB  div_scale= 10  preset= 0
                    Min = -80.1 dB  Max = 12.0 dB  Step = 0.1 dB  Preset = 0.0 dB  "
        ::= { iqupc00CmdEntry 42522 }


    iqupc00DolbyEncInp14Source3Mute OBJECT-TYPE
        SYNTAX            INTEGER { disable(0), enable(1)  }
        MAX-ACCESS        read-write
        STATUS            current
        DESCRIPTION
                "CMNT: - Dolby encoder B3 input mute
                 TYPE: - Checkbox
                 PAGE: - Dolby Enc Inp1_4
                    Mute  cmdID= 42530  "
        ::= { iqupc00CmdEntry 42530 }


    iqupc00DolbyEncInp14Source3Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder B3 input source
                 TYPE: - RadiobuttonList
                 PAGE: - Dolby Enc Inp1_4
                    Src  cmdID= 42538
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42538 }


    iqupc00DolbyEncInp14Source4ProcGain OBJECT-TYPE
        SYNTAX            INTEGER
        MAX-ACCESS        read-write
        STATUS            current
        DESCRIPTION
                "CMNT: - Dolby encoder B4 input gain
                 TYPE: - Number
                 PAGE: - Dolby Enc Inp1_4
                    ProcGain  cmdID= 42523
                    min= -801  max= 120  step= 1  format= %0.1f dB  div_scale= 10  preset= 0
                    Min = -80.1 dB  Max = 12.0 dB  Step = 0.1 dB  Preset = 0.0 dB  "
        ::= { iqupc00CmdEntry 42523 }


    iqupc00DolbyEncInp14Source4Mute OBJECT-TYPE
        SYNTAX            INTEGER { disable(0), enable(1)  }
        MAX-ACCESS        read-write
        STATUS            current
        DESCRIPTION
                "CMNT: - Dolby encoder B4 input mute
                 TYPE: - Checkbox
                 PAGE: - Dolby Enc Inp1_4
                    Mute  cmdID= 42531  "
        ::= { iqupc00CmdEntry 42531 }


    iqupc00DolbyEncInp14Source4Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder B4 input source
                 TYPE: - RadiobuttonList
                 PAGE: - Dolby Enc Inp1_4
                    Src  cmdID= 42539
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42539 }


    iqupc00DolbyEncInp58Source5ProcGain OBJECT-TYPE
        SYNTAX            INTEGER
        MAX-ACCESS        read-write
        STATUS            current
        DESCRIPTION
                "CMNT: - Dolby encoder C5 input gain
                 TYPE: - Number
                 PAGE: - Dolby Enc Inp5_8
                    ProcGain  cmdID= 42524
                    min= -801  max= 120  step= 1  format= %0.1f dB  div_scale= 10  preset= 0
                    Min = -80.1 dB  Max = 12.0 dB  Step = 0.1 dB  Preset = 0.0 dB  "
        ::= { iqupc00CmdEntry 42524 }


    iqupc00DolbyEncInp58Source5Mute OBJECT-TYPE
        SYNTAX            INTEGER { disable(0), enable(1)  }
        MAX-ACCESS        read-write
        STATUS            current
        DESCRIPTION
                "CMNT: - Dolby encoder C5 input mute
                 TYPE: - Checkbox
                 PAGE: - Dolby Enc Inp5_8
                    Mute  cmdID= 42532  "
        ::= { iqupc00CmdEntry 42532 }


    iqupc00DolbyEncInp58Source5Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder C5 input source
                 TYPE: - RadiobuttonList
                 PAGE: - Dolby Enc Inp5_8
                    Src  cmdID= 42540
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42540 }


    iqupc00DolbyEncInp58Source6ProcGain OBJECT-TYPE
        SYNTAX            INTEGER
        MAX-ACCESS        read-write
        STATUS            current
        DESCRIPTION
                "CMNT: - Dolby encoder C6 input gain
                 TYPE: - Number
                 PAGE: - Dolby Enc Inp5_8
                    ProcGain  cmdID= 42525
                    min= -801  max= 120  step= 1  format= %0.1f dB  div_scale= 10  preset= 0
                    Min = -80.1 dB  Max = 12.0 dB  Step = 0.1 dB  Preset = 0.0 dB  "
        ::= { iqupc00CmdEntry 42525 }


    iqupc00DolbyEncInp58Source6Mute OBJECT-TYPE
        SYNTAX            INTEGER { disable(0), enable(1)  }
        MAX-ACCESS        read-write
        STATUS            current
        DESCRIPTION
                "CMNT: - Dolby encoder C6 input mute
                 TYPE: - Checkbox
                 PAGE: - Dolby Enc Inp5_8
                    Mute  cmdID= 42533  "
        ::= { iqupc00CmdEntry 42533 }


    iqupc00DolbyEncInp58Source6Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder C6 input source
                 TYPE: - RadiobuttonList
                 PAGE: - Dolby Enc Inp5_8
                    Src  cmdID= 42541
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42541 }


    iqupc00DolbyEncInp58Source7ProcGain OBJECT-TYPE
        SYNTAX            INTEGER
        MAX-ACCESS        read-write
        STATUS            current
        DESCRIPTION
                "CMNT: - Dolby encoder D7 input gain
                 TYPE: - Number
                 PAGE: - Dolby Enc Inp5_8
                    ProcGain  cmdID= 42526
                    min= -801  max= 120  step= 1  format= %0.1f dB  div_scale= 10  preset= 0
                    Min = -80.1 dB  Max = 12.0 dB  Step = 0.1 dB  Preset = 0.0 dB  "
        ::= { iqupc00CmdEntry 42526 }


    iqupc00DolbyEncInp58Source7Mute OBJECT-TYPE
        SYNTAX            INTEGER { disable(0), enable(1)  }
        MAX-ACCESS        read-write
        STATUS            current
        DESCRIPTION
                "CMNT: - Dolby encoder D7 input mute
                 TYPE: - Checkbox
                 PAGE: - Dolby Enc Inp5_8
                    Mute  cmdID= 42534  "
        ::= { iqupc00CmdEntry 42534 }


    iqupc00DolbyEncInp58Source7Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder D7 input source
                 TYPE: - RadiobuttonList
                 PAGE: - Dolby Enc Inp5_8
                    Src  cmdID= 42542
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42542 }


    iqupc00DolbyEncInp58Source8ProcGain OBJECT-TYPE
        SYNTAX            INTEGER
        MAX-ACCESS        read-write
        STATUS            current
        DESCRIPTION
                "CMNT: - Dolby encoder D8 input gain
                 TYPE: - Number
                 PAGE: - Dolby Enc Inp5_8
                    ProcGain  cmdID= 42527
                    min= -801  max= 120  step= 1  format= %0.1f dB  div_scale= 10  preset= 0
                    Min = -80.1 dB  Max = 12.0 dB  Step = 0.1 dB  Preset = 0.0 dB  "
        ::= { iqupc00CmdEntry 42527 }


    iqupc00DolbyEncInp58Source8Mute OBJECT-TYPE
        SYNTAX            INTEGER { disable(0), enable(1)  }
        MAX-ACCESS        read-write
        STATUS            current
        DESCRIPTION
                "CMNT: - Dolby encoder D8 input mute
                 TYPE: - Checkbox
                 PAGE: - Dolby Enc Inp5_8
                    Mute  cmdID= 42535  "
        ::= { iqupc00CmdEntry 42535 }


    iqupc00DolbyEncInp58Source8Src OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAcc11(24),
                            valLinAcc12(25),
                            valLinAcc21(26),
                            valLinAcc22(27),
                            valLinAcc31(28),
                            valLinAcc32(29)
                            }
        MAX-ACCESS        read-write
        STATUS            current
        DESCRIPTION
                "CMNT: - Dolby encoder D8 input source
                 TYPE: - RadiobuttonList
                 PAGE: - Dolby Enc Inp5_8
                    Src  cmdID= 42543
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAcc1_1  value= 24
                    LinAcc1_2  value= 25
                    LinAcc2_1  value= 26
                    LinAcc2_2  value= 27
                    LinAcc3_1  value= 28
                    LinAcc3_2  value= 29  "
        ::= { iqupc00CmdEntry 42543 }


    iqupc00DolbyControlDolbyEncoderControlSampleRateConversion OBJECT-TYPE
        SYNTAX            INTEGER {
                            valEnabled(0),
                            valDisabled(1)
                            }
        MAX-ACCESS        read-write
        STATUS            current
        DESCRIPTION
                "CMNT: - Dolby encoder sample rate converter
                 TYPE: - RadiobuttonList
                 PAGE: - DolbyControl
                    Sample Rate Conversion  cmdID= 42451
                    Enabled  value= 0
                    Disabled  value= 1  "
        ::= { iqupc00CmdEntry 42451 }


    iqupc00DolbyControlDolbyEncoderControlMetaRevertMode OBJECT-TYPE
        SYNTAX            INTEGER {
                            valLastused(0),
                            valInternal(1)
                            }
        MAX-ACCESS        read-write
        STATUS            current
        DESCRIPTION
                "CMNT: - Dolby encoder metadata revert mode
                 TYPE: - RadiobuttonList
                 PAGE: - DolbyControl
                    Meta Revert Mode  cmdID= 42452
                    Last used  value= 0
                    Internal  value= 1  "
        ::= { iqupc00CmdEntry 42452 }


    iqupc00DolbyControlDolbyEncoderControlEncodingMode OBJECT-TYPE
        SYNTAX            INTEGER {
                            valEncode(0),
                            valPassThrough(1)
                            }
        MAX-ACCESS        read-write
        STATUS            current
        DESCRIPTION
                "CMNT: - Dolby encoding mode
                 TYPE: - RadiobuttonList
                 PAGE: - DolbyControl
                    Encoding Mode  cmdID= 42450
                    Encode  value= 0
                    Pass Through  value= 1  "
        ::= { iqupc00CmdEntry 42450 }


    iqupc00DolbyControlDolbyEEncoderCntrlBitDepth OBJECT-TYPE
        SYNTAX            INTEGER {
                            val20bit(0),
                            val16bit(1)
                            }
        MAX-ACCESS        read-write
        STATUS            current
        DESCRIPTION
                "CMNT: - Dolby E encoder bit depth
                 TYPE: - RadiobuttonList
                 PAGE: - DolbyControl
                    Bit Depth  cmdID= 42453
                    20 bit  value= 0
                    16 bit  value= 1  "
        ::= { iqupc00CmdEntry 42453 }


    iqupc00DolbyControlDolbyEEncoderCntrlMetadataSource OBJECT-TYPE
        SYNTAX            INTEGER {
                            valExternal(0),
                            valInternal(1)
                            }
        MAX-ACCESS        read-write
        STATUS            current
        DESCRIPTION
                "CMNT: - Dolby E encoder metadata sample rate converter
                 TYPE: - RadiobuttonList
                 PAGE: - DolbyControl
                    Metadata Source  cmdID= 42456
                    External  value= 0
                    Internal  value= 1  "
        ::= { iqupc00CmdEntry 42456 }


    iqupc00DolbyControlDolbyEEncoderCntrlInternalConfig OBJECT-TYPE
        SYNTAX            INTEGER {
                            val51p2(0),
                            val51p2x1(1),
                            val4p4(2),
                            val4p2x2(3),
                            val4p2p2x1(4),
                            val4p4x1(5),
                            val4x2(6),
                            val3x2p2x1(7),
                            val2x2p4x1(8),
                            val2p6x1(9),
                            val8x1(10),
                            val51(11),
                            val4p2(12),
                            val4p2x1(13),
                            val3x2(14),
                            val2x2p2x1(15),
                            val2p4x1(16),
                            val6x1(17),
                            val4(18),
                            val2p2(19),
                            val2p2x1(20),
                            val4x1(21),
                            val71(22),
                            val71Screen(23)
                            }
        MAX-ACCESS        read-write
        STATUS            current
        DESCRIPTION
                "CMNT: - Dolby E encoder internal program configuration
                 TYPE: - RadiobuttonList
                 PAGE: - DolbyControl
                    Internal Config  cmdID= 42455
                    5.1+2  value= 0
                    5.1+2x1  value= 1
                    4+4  value= 2
                    4+2x2  value= 3
                    4+2+2x1  value= 4
                    4+4x1  value= 5
                    4x2  value= 6
                    3x2+2x1  value= 7
                    2x2+4x1  value= 8
                    2+6x1  value= 9
                    8x1  value= 10
                    5.1  value= 11
                    4+2  value= 12
                    4+2x1  value= 13
                    3x2  value= 14
                    2x2+2x1  value= 15
                    2+4x1  value= 16
                    6x1  value= 17
                    4  value= 18
                    2+2  value= 19
                    2+2x1  value= 20
                    4x1  value= 21
                    7.1  value= 22
                    7.1 Screen  value= 23  "
        ::= { iqupc00CmdEntry 42455 }


    iqupc00DolbyControlDolbyEEncoderCntrlDefaultAllMeta OBJECT-TYPE
        SYNTAX            INTEGER { noAction(0),valDefaultAllMeta(3) }
        MAX-ACCESS        read-write
        STATUS            current
        DESCRIPTION
                "CMNT: - Dolby encoder default all internal metadata
                 TYPE: - Button
                 PAGE: - DolbyControl
                    Default All Meta  cmdID= 42514
                    value= 3  "
        ::= { iqupc00CmdEntry 42514 }


    iqupc00DolbyControlDolbyIntMetaCntrlCopyExtMetadata OBJECT-TYPE
        SYNTAX            INTEGER { noAction(0),valCopyExtMetadata(1) }
        MAX-ACCESS        read-write
        STATUS            current
        DESCRIPTION
                "CMNT: - Dolby encoder copy external metadata to internal
                 TYPE: - Button
                 PAGE: - DolbyControl
                    Copy Ext Metadata  cmdID= 42512
                    value= 1  "
        ::= { iqupc00CmdEntry 42512 }


    iqupc00DolbyControlDolbyIntMetaCntrlDefaultProgramMeta OBJECT-TYPE
        SYNTAX            INTEGER { noAction(0),valDefaultProgramMeta(2) }
        MAX-ACCESS        read-write
        STATUS            current
        DESCRIPTION
                "CMNT: - Dolby encoder default internal metadata
                 TYPE: - Button
                 PAGE: - DolbyControl
                    Default Program Meta  cmdID= 42513
                    value= 2  "
        ::= { iqupc00CmdEntry 42513 }


    iqupc00DolbyControlDolbyIntMetaCntrlDialogueNorm OBJECT-TYPE
        SYNTAX            INTEGER
        MAX-ACCESS        read-write
        STATUS            current
        DESCRIPTION
                "CMNT: - Dolby encoder internal metadata AC-3 dialogue normalisation
                 TYPE: - Number
                 PAGE: - DolbyControl
                    Dialogue Norm  cmdID= 42468
                    min= 1  max= 31  step= 1  format= -%0.0f dBFS  div_scale= 1  preset= 27
                    Min = -1 dBFS  Max = -31 dBFS  Step = -1 dBFS  Preset = -27 dBFS  "
        ::= { iqupc00CmdEntry 42468 }


    iqupc00DolbyControlDolbyIntMetaCntrlChannelMode OBJECT-TYPE
        SYNTAX            INTEGER {
                            val10C(1),
                            val20LR(2),
                            val30LCR(3),
                            val21LRS(4),
                            val31LCRS(5),
                            val22LRSLSR(6),
                            val32LCRSLSR(7)
                            }
        MAX-ACCESS        read-write
        STATUS            current
        DESCRIPTION
                "CMNT: - Dolby encoder internal metadata AC-3 channel (coding) mode
                 TYPE: - RadiobuttonList
                 PAGE: - DolbyControl
                    Channel Mode  cmdID= 42461
                    1/0 (C)  value= 1
                    2/0 (L R)  value= 2
                    3/0 (L C R)  value= 3
                    2/1 (L R S)  value= 4
                    3/1 (L C R S)  value= 5
                    2/2 (L R SL SR)  value= 6
                    3/2 (L C R SL SR)  value= 7  "
        ::= { iqupc00CmdEntry 42461 }


    iqupc00DolbyControlDolbyIntMetaCntrlLFEChannel OBJECT-TYPE
        SYNTAX            INTEGER { disable(0), enable(1)  }
        MAX-ACCESS        read-write
        STATUS            current
        DESCRIPTION
                "CMNT: - Dolby encoder internal metadata AC-3 low frequency effect channel
                 TYPE: - Checkbox
                 PAGE: - DolbyControl
                    LFE Channel  cmdID= 42467  "
        ::= { iqupc00CmdEntry 42467 }


    iqupc00DolbyControlDolbyIntMetaCntrlBitstreamMode OBJECT-TYPE
        SYNTAX            INTEGER {
                            valCompleteMain(0),
                            valMusicEffects(1),
                            valVisuallyImpaired(2),
                            valHearingImpaired(3),
                            valDialogue(4),
                            valCommentary(5),
                            valEmergency(6),
                            valVoiceOverKaraoke(7)
                            }
        MAX-ACCESS        read-write
        STATUS            current
        DESCRIPTION
                "CMNT: - Dolby encoder internal metadata AC-3 bitstream mode
                 TYPE: - RadiobuttonList
                 PAGE: - DolbyControl
                    Bitstream Mode  cmdID= 42460
                    Complete Main  value= 0
                    Music & Effects  value= 1
                    Visually Impaired  value= 2
                    Hearing Impaired  value= 3
                    Dialogue  value= 4
                    Commentary  value= 5
                    Emergency  value= 6
                    Voice Over/Karaoke  value= 7  "
        ::= { iqupc00CmdEntry 42460 }


    iqupc00DolbyControlDolbyIntMetaCntrlRFMode OBJECT-TYPE
        SYNTAX            INTEGER {
                            valNone(0),
                            valFilmStandard(1),
                            valFilmLight(2),
                            valMusicStandard(3),
                            valMusicLight(4),
                            valSpeech(5)
                            }
        MAX-ACCESS        read-write
        STATUS            current
        DESCRIPTION
                "CMNT: - Dolby encoder internal metadata AC-3 RF mode
                 TYPE: - RadiobuttonList
                 PAGE: - DolbyControl
                    RF Mode  cmdID= 42463
                    None  value= 0
                    Film Standard  value= 1
                    Film Light  value= 2
                    Music Standard  value= 3
                    Music Light  value= 4
                    Speech  value= 5  "
        ::= { iqupc00CmdEntry 42463 }


    iqupc00DolbyControlDolbyIntMetaCntrlLineMode OBJECT-TYPE
        SYNTAX            INTEGER {
                            valNone(0),
                            valFilmStandard(1),
                            valFilmLight(2),
                            valMusicStandard(3),
                            valMusicLight(4),
                            valSpeech(5)
                            }
        MAX-ACCESS        read-write
        STATUS            current
        DESCRIPTION
                "CMNT: - Dolby encoder internal metadata AC-3 line mode
                 TYPE: - RadiobuttonList
                 PAGE: - DolbyControl
                    Line Mode  cmdID= 42462
                    None  value= 0
                    Film Standard  value= 1
                    Film Light  value= 2
                    Music Standard  value= 3
                    Music Light  value= 4
                    Speech  value= 5  "
        ::= { iqupc00CmdEntry 42462 }


    iqupc00DolbyIntMetaCntrlAudioProductionInfoExists OBJECT-TYPE
        SYNTAX            INTEGER { disable(0), enable(1)  }
        MAX-ACCESS        read-write
        STATUS            current
        DESCRIPTION
                "CMNT: - Dolby encoder internal metadata AC-3 audio production information exists
                 TYPE: - Checkbox
                 PAGE: - Dolby Int Meta Cntrl
                    Exists  cmdID= 42469  "
        ::= { iqupc00CmdEntry 42469 }


    iqupc00DolbyIntMetaCntrlAudioProductionInfoMixLevel OBJECT-TYPE
        SYNTAX            INTEGER
        MAX-ACCESS        read-write
        STATUS            current
        DESCRIPTION
                "CMNT: - Dolby encoder internal metadata AC-3 audio production mix level
                 TYPE: - Number
                 PAGE: - Dolby Int Meta Cntrl
                    Mix Level  cmdID= 42470
                    min= 80  max= 111  step= 1  format= %0.0f dB SPL  div_scale= 1  preset= 105
                    Min = 80 dB SPL  Max = 111 dB SPL  Step = 1 dB SPL  Preset = 105 dB SPL  "
        ::= { iqupc00CmdEntry 42470 }


    iqupc00DolbyIntMetaCntrlAudioProductionInfoRoomType OBJECT-TYPE
        SYNTAX            INTEGER {
                            valNotindicated(0),
                            valLarge(1),
                            valSmall(2)
                            }
        MAX-ACCESS        read-write
        STATUS            current
        DESCRIPTION
                "CMNT: - Dolby encoder internal metadata AC-3 audio production room type
                 TYPE: - RadiobuttonList
                 PAGE: - Dolby Int Meta Cntrl
                    Room Type  cmdID= 42471
                    Not indicated  value= 0
                    Large  value= 1
                    Small  value= 2  "
        ::= { iqupc00CmdEntry 42471 }


    iqupc00DolbyControlDolbyIntMetaCntrlCentreMixLevel OBJECT-TYPE
        SYNTAX            INTEGER {
                            valn30dB(0),
                            valn45dB(1),
                            valn60dB(2)
                            }
        MAX-ACCESS        read-write
        STATUS            current
        DESCRIPTION
                "CMNT: - Dolby encoder internal metadata AC-3 centre mix level
                 TYPE: - RadiobuttonList
                 PAGE: - DolbyControl
                    Centre Mix Level  cmdID= 42464
                    -3.0dB  value= 0
                    -4.5dB  value= 1
                    -6.0dB  value= 2  "
        ::= { iqupc00CmdEntry 42464 }


    iqupc00DolbyControlDolbyIntMetaCntrlSurroundMixLevel OBJECT-TYPE
        SYNTAX            INTEGER {
                            valn30dB(0),
                            valn60dB(1),
                            valOff(2)
                            }
        MAX-ACCESS        read-write
        STATUS            current
        DESCRIPTION
                "CMNT: - Dolby encoder internal metadata AC-3 surround mix level
                 TYPE: - RadiobuttonList
                 PAGE: - DolbyControl
                    Surround Mix Level  cmdID= 42465
                    -3.0dB  value= 0
                    -6.0dB  value= 1
                    Off  value= 2  "
        ::= { iqupc00CmdEntry 42465 }


    iqupc00DolbyControlDolbyIntMetaCntrlSurroundMode OBJECT-TYPE
        SYNTAX            INTEGER {
                            valNotindicated(0),
                            valOff(1),
                            valOn(2)
                            }
        MAX-ACCESS        read-write
        STATUS            current
        DESCRIPTION
                "CMNT: - Dolby encoder internal metadata AC-3 surround mode
                 TYPE: - RadiobuttonList
                 PAGE: - DolbyControl
                    Surround Mode  cmdID= 42466
                    Not indicated  value= 0
                    Off  value= 1
                    On  value= 2  "
        ::= { iqupc00CmdEntry 42466 }


    iqupc00DolbyControlDolbyIntMetaCntrlCopyright OBJECT-TYPE
        SYNTAX            INTEGER { disable(0), enable(1)  }
        MAX-ACCESS        read-write
        STATUS            current
        DESCRIPTION
                "CMNT: - Dolby encoder internal metadata AC-3 copyright
                 TYPE: - Checkbox
                 PAGE: - DolbyControl
                    Copyright  cmdID= 42384  "
        ::= { iqupc00CmdEntry 42384 }


    iqupc00DolbyIntMetaCntrlExtendedBSI1Exists OBJECT-TYPE
        SYNTAX            INTEGER { disable(0), enable(1)  }
        MAX-ACCESS        read-write
        STATUS            current
        DESCRIPTION
                "CMNT: - Dolby encoder internal metadata AC-3 BSI 1 exists
                 TYPE: - Checkbox
                 PAGE: - Dolby Int Meta Cntrl
                    Exists  cmdID= 42472  "
        ::= { iqupc00CmdEntry 42472 }


    iqupc00DolbyIntMetaCntrlExtendedBSI1StereoDownmixMode OBJECT-TYPE
        SYNTAX            INTEGER {
                            valNotindicated(0),
                            valLtRtPreferred(1),
                            valLoRoPreferred(2)
                            }
        MAX-ACCESS        read-write
        STATUS            current
        DESCRIPTION
                "CMNT: - Dolby encoder internal metadata AC-3 BSI 1 preferred stereo downmix mode
                 TYPE: - RadiobuttonList
                 PAGE: - Dolby Int Meta Cntrl
                    Stereo Downmix Mode  cmdID= 42473
                    Not indicated  value= 0
                    LtRt Preferred  value= 1
                    LoRo Preferred  value= 2  "
        ::= { iqupc00CmdEntry 42473 }


    iqupc00DolbyIntMetaCntrlExtendedBSI1LtRtCentreMixLevel OBJECT-TYPE
        SYNTAX            INTEGER {
                            valp30dB(0),
                            valp15dB(1),
                            valp00dB(2),
                            valn15dB(3),
                            valn30dB(4),
                            valn45dB(5),
                            valn60dB(6),
                            valOff(7)
                            }
        MAX-ACCESS        read-write
        STATUS            current
        DESCRIPTION
                "CMNT: - Dolby encoder internal metadata AC-3 BSI 1 LtRt centre mix level
                 TYPE: - RadiobuttonList
                 PAGE: - Dolby Int Meta Cntrl
                    Lt/Rt Centre Mix Level  cmdID= 42474
                    +3.0dB  value= 0
                    +1.5dB  value= 1
                    +0.0dB  value= 2
                    -1.5dB  value= 3
                    -3.0dB  value= 4
                    -4.5dB  value= 5
                    -6.0dB  value= 6
                    Off  value= 7  "
        ::= { iqupc00CmdEntry 42474 }


    iqupc00DolbyIntMetaCntrlExtendedBSI1LtRtSurrMixLevel OBJECT-TYPE
        SYNTAX            INTEGER {
                            valn15dB(3),
                            valn30dB(4),
                            valn45dB(5),
                            valn60dB(6),
                            valOff(7)
                            }
        MAX-ACCESS        read-write
        STATUS            current
        DESCRIPTION
                "CMNT: - Dolby encoder internal metadata AC-3 BSI 1 LtRt surround mix level
                 TYPE: - RadiobuttonList
                 PAGE: - Dolby Int Meta Cntrl
                    Lt/Rt Surr Mix Level  cmdID= 42475
                    -1.5dB  value= 3
                    -3.0dB  value= 4
                    -4.5dB  value= 5
                    -6.0dB  value= 6
                    Off  value= 7  "
        ::= { iqupc00CmdEntry 42475 }


    iqupc00DolbyIntMetaCntrlExtendedBSI1LoRoCentreMixLevel OBJECT-TYPE
        SYNTAX            INTEGER {
                            valp30dB(0),
                            valp15dB(1),
                            valp00dB(2),
                            valn15dB(3),
                            valn30dB(4),
                            valn45dB(5),
                            valn60dB(6),
                            valOff(7)
                            }
        MAX-ACCESS        read-write
        STATUS            current
        DESCRIPTION
                "CMNT: - Dolby encoder internal metadata AC-3 BSI 1 LoRo centre mix level
                 TYPE: - RadiobuttonList
                 PAGE: - Dolby Int Meta Cntrl
                    Lo/Ro Centre Mix Level  cmdID= 42476
                    +3.0dB  value= 0
                    +1.5dB  value= 1
                    +0.0dB  value= 2
                    -1.5dB  value= 3
                    -3.0dB  value= 4
                    -4.5dB  value= 5
                    -6.0dB  value= 6
                    Off  value= 7  "
        ::= { iqupc00CmdEntry 42476 }


    iqupc00DolbyIntMetaCntrlExtendedBSI1LoRoSurrMixLevel OBJECT-TYPE
        SYNTAX            INTEGER {
                            valn15dB(3),
                            valn30dB(4),
                            valn45dB(5),
                            valn60dB(6),
                            valOff(7)
                            }
        MAX-ACCESS        read-write
        STATUS            current
        DESCRIPTION
                "CMNT: - Dolby encoder internal metadata AC-3 BSI 1 LoRo surround mix level
                 TYPE: - RadiobuttonList
                 PAGE: - Dolby Int Meta Cntrl
                    Lo/Ro Surr Mix Level  cmdID= 42477
                    -1.5dB  value= 3
                    -3.0dB  value= 4
                    -4.5dB  value= 5
                    -6.0dB  value= 6
                    Off  value= 7  "
        ::= { iqupc00CmdEntry 42477 }


    iqupc00DolbyIntMetaCntrlExtendedBSI2Exists OBJECT-TYPE
        SYNTAX            INTEGER { disable(0), enable(1)  }
        MAX-ACCESS        read-write
        STATUS            current
        DESCRIPTION
                "CMNT: - Dolby encoder internal metadata AC-3 BSI 2 exists
                 TYPE: - Checkbox
                 PAGE: - Dolby Int Meta Cntrl
                    Exists  cmdID= 42478  "
        ::= { iqupc00CmdEntry 42478 }


    iqupc00DolbyIntMetaCntrlExtendedBSI2SurroundEXMode OBJECT-TYPE
        SYNTAX            INTEGER {
                            valNotindicated(0),
                            valOff(1),
                            valOn(2)
                            }
        MAX-ACCESS        read-write
        STATUS            current
        DESCRIPTION
                "CMNT: - Dolby encoder internal metadata AC-3 BSI 2 surround EX mode
                 TYPE: - RadiobuttonList
                 PAGE: - Dolby Int Meta Cntrl
                    Surround EX Mode  cmdID= 42479
                    Not indicated  value= 0
                    Off  value= 1
                    On  value= 2  "
        ::= { iqupc00CmdEntry 42479 }


    iqupc00DolbyIntMetaCntrlExtendedBSI2LowpassFilter OBJECT-TYPE
        SYNTAX            INTEGER { disable(0), enable(1)  }
        MAX-ACCESS        read-write
        STATUS            current
        DESCRIPTION
                "CMNT: - Dolby encoder internal metadata AC-3 BSI 2 lowpass filter
                 TYPE: - Checkbox
                 PAGE: - Dolby Int Meta Cntrl
                    Lowpass Filter  cmdID= 42480  "
        ::= { iqupc00CmdEntry 42480 }


    iqupc00DolbyIntMetaCntrlExtendedBSI2LFEFIlter OBJECT-TYPE
        SYNTAX            INTEGER { disable(0), enable(1)  }
        MAX-ACCESS        read-write
        STATUS            current
        DESCRIPTION
                "CMNT: - Dolby encoder internal metadata AC-3 BSI 2 LFE filter
                 TYPE: - Checkbox
                 PAGE: - Dolby Int Meta Cntrl
                    LFE FIlter  cmdID= 42481  "
        ::= { iqupc00CmdEntry 42481 }


    iqupc00DolbyIntMetaCntrlExtendedBSI2SurrPhaseShiftFltr OBJECT-TYPE
        SYNTAX            INTEGER { disable(0), enable(1)  }
        MAX-ACCESS        read-write
        STATUS            current
        DESCRIPTION
                "CMNT: - Dolby encoder internal metadata AC-3 BSI 2 surround 90deg phase shift filter
                 TYPE: - Checkbox
                 PAGE: - Dolby Int Meta Cntrl
                    Surr Phase Shift Fltr  cmdID= 42482  "
        ::= { iqupc00CmdEntry 42482 }


    iqupc00DolbyIntMetaCntrlExtendedBSI2Surr3dBAttenuator OBJECT-TYPE
        SYNTAX            INTEGER { disable(0), enable(1)  }
        MAX-ACCESS        read-write
        STATUS            current
        DESCRIPTION
                "CMNT: - Dolby encoder internal metadata AC-3 BSI 2 3dB surround channel attenuator
                 TYPE: - Checkbox
                 PAGE: - Dolby Int Meta Cntrl
                    Surr 3dB Attenuator  cmdID= 42483  "
        ::= { iqupc00CmdEntry 42483 }


    iqupc00DolbyControlDolbyIntMetaCntrlProgramDescriptionL OBJECT-TYPE
        SYNTAX            RollCallString
        MAX-ACCESS        read-write
        STATUS            current
        DESCRIPTION
                "CMNT: - Dolby encoder internal metadata text description (LH part)
                 TYPE: - Editstring
                 PAGE: - DolbyControl
                    Program Description L  cmdID= 42510
                    preset= Prog"
        ::= { iqupc00CmdEntry 42510 }


    iqupc00DolbyControlDolbyIntMetaCntrlProgramDescriptionR OBJECT-TYPE
        SYNTAX            RollCallString
        MAX-ACCESS        read-write
        STATUS            current
        DESCRIPTION
                "CMNT: - Dolby encoder internal metadata text description (RH part)
                 TYPE: - Editstring
                 PAGE: - DolbyControl
                    Program Description R  cmdID= 42511
                    preset= Prog"
        ::= { iqupc00CmdEntry 42511 }


    iqupc00DolbyControlDolbyIntMetaCntrlIntMetaSaveset OBJECT-TYPE
        SYNTAX            INTEGER
        MAX-ACCESS        read-write
        STATUS            current
        DESCRIPTION
                "CMNT: - Used to save 8 internal metadata programs through RollCall
                 TYPE: - Number
                 PAGE: - DolbyControl
                    Int Meta Saveset  cmdID= 42590
                    min= 0  max= 8  step= 1  format= %0.0f  div_scale= 1  preset= 0
                    Min = 0  Max = 8  Step = 1  Preset = 0  "
        ::= { iqupc00CmdEntry 42590 }


    iqupc00DolbyControlDolbyDEncoderCntrlInternalMode OBJECT-TYPE
        SYNTAX            INTEGER {
                            valFilmSurround(0),
                            valFilmStereo(1),
                            valMusicSurround(2),
                            valMusicStereo(3),
                            valManual(4)
                            }
        MAX-ACCESS        read-write
        STATUS            current
        DESCRIPTION
                "CMNT: - Dolby Digital encoder internal metadata mode
                 TYPE: - RadiobuttonList
                 PAGE: - DolbyControl
                    Internal Mode  cmdID= 42485
                    Film Surround  value= 0
                    Film Stereo  value= 1
                    Music Surround  value= 2
                    Music Stereo  value= 3
                    Manual  value= 4  "
        ::= { iqupc00CmdEntry 42485 }


    iqupc00DolbyControlDolbyDEncoderCntrlBitstreamFormat OBJECT-TYPE
        SYNTAX            INTEGER {
                            val32bit(0),
                            val16bitChl1(1),
                            val16bitChl2(2)
                            }
        MAX-ACCESS        read-write
        STATUS            current
        DESCRIPTION
                "CMNT: - Dolby D encoder bit depth
                 TYPE: - RadiobuttonList
                 PAGE: - DolbyControl
                    Bitstream Format  cmdID= 42454
                    32 bit  value= 0
                    16 bit Chl1  value= 1
                    16 bit Chl2  value= 2  "
        ::= { iqupc00CmdEntry 42454 }


    iqupc00DolbyControlDolbyDEncoderCntrlMetadataSource OBJECT-TYPE
        SYNTAX            INTEGER {
                            valProgram1(0),
                            valProgram2(1),
                            valProgram3(2),
                            valProgram4(3),
                            valProgram5(4),
                            valProgram6(5),
                            valProgram7(6),
                            valProgram8(7),
                            valInternal(8)
                            }
        MAX-ACCESS        read-write
        STATUS            current
        DESCRIPTION
                "CMNT: - Dolby D encoder metadata sample rate converter
                 TYPE: - RadiobuttonList
                 PAGE: - DolbyControl
                    Metadata Source  cmdID= 42498
                    Program 1  value= 0
                    Program 2  value= 1
                    Program 3  value= 2
                    Program 4  value= 3
                    Program 5  value= 4
                    Program 6  value= 5
                    Program 7  value= 6
                    Program 8  value= 7
                    Internal  value= 8  "
        ::= { iqupc00CmdEntry 42498 }


    iqupc00DolbyControlDolbyDEncoderCntrlIntMetaDataRate OBJECT-TYPE
        SYNTAX            INTEGER {
                            valAuto384(0),
                            valAuto448(1),
                            val56kbps(2),
                            val64kbps(3),
                            val80kbps(4),
                            val96kbps(5),
                            val112kbps(6),
                            val128kbps(7),
                            val160kbps(8),
                            val192kbps(9),
                            val224kbps(10),
                            val256kbps(11),
                            val320kbps(12),
                            val384kbps(13),
                            val448kbps(14),
                            val512kbps(15),
                            val576kbps(16),
                            val640kbps(17)
                            }
        MAX-ACCESS        read-write
        STATUS            current
        DESCRIPTION
                "CMNT: - Dolby D encoder internal metadata rate
                 TYPE: - RadiobuttonList
                 PAGE: - DolbyControl
                    Int Meta Data Rate  cmdID= 42499
                    Auto 384  value= 0
                    Auto 448  value= 1
                    56 kbps  value= 2
                    64 kbps  value= 3
                    80 kbps  value= 4
                    96 kbps  value= 5
                    112 kbps  value= 6
                    128 kbps  value= 7
                    160 kbps  value= 8
                    192 kbps  value= 9
                    224 kbps  value= 10
                    256 kbps  value= 11
                    320 kbps  value= 12
                    384 kbps  value= 13
                    448 kbps  value= 14
                    512 kbps  value= 15
                    576 kbps  value= 16
                    640 kbps  value= 17  "
        ::= { iqupc00CmdEntry 42499 }


    iqupc00DolbyControlDolbyDEncoderCntrlExtMetaDataRate OBJECT-TYPE
        SYNTAX            INTEGER {
                            valAuto384(0),
                            valAuto448(1),
                            val56kbps(2),
                            val64kbps(3),
                            val80kbps(4),
                            val96kbps(5),
                            val112kbps(6),
                            val128kbps(7),
                            val160kbps(8),
                            val192kbps(9),
                            val224kbps(10),
                            val256kbps(11),
                            val320kbps(12),
                            val384kbps(13),
                            val448kbps(14),
                            val512kbps(15),
                            val576kbps(16),
                            val640kbps(17)
                            }
        MAX-ACCESS        read-write
        STATUS            current
        DESCRIPTION
                "CMNT: - Dolby D encoder external metadata rate
                 TYPE: - RadiobuttonList
                 PAGE: - DolbyControl
                    Ext Meta Data Rate  cmdID= 42500
                    Auto 384  value= 0
                    Auto 448  value= 1
                    56 kbps  value= 2
                    64 kbps  value= 3
                    80 kbps  value= 4
                    96 kbps  value= 5
                    112 kbps  value= 6
                    128 kbps  value= 7
                    160 kbps  value= 8
                    192 kbps  value= 9
                    224 kbps  value= 10
                    256 kbps  value= 11
                    320 kbps  value= 12
                    384 kbps  value= 13
                    448 kbps  value= 14
                    512 kbps  value= 15
                    576 kbps  value= 16
                    640 kbps  value= 17  "
        ::= { iqupc00CmdEntry 42500 }


    iqupc00DolbyControlDolbyDEncoderCntrlStreamNumber OBJECT-TYPE
        SYNTAX            INTEGER {
                            valStream0(0),
                            valStream1(1),
                            valStream2(2),
                            valStream3(3),
                            valStream4(4),
                            valStream5(5),
                            valStream6(6)
                            }
        MAX-ACCESS        read-write
        STATUS            current
        DESCRIPTION
                "CMNT: - Dolby D encoder stream number
                 TYPE: - RadiobuttonList
                 PAGE: - DolbyControl
                    Stream Number  cmdID= 42357
                    Stream 0  value= 0
                    Stream 1  value= 1
                    Stream 2  value= 2
                    Stream 3  value= 3
                    Stream 4  value= 4
                    Stream 5  value= 5
                    Stream 6  value= 6  "
        ::= { iqupc00CmdEntry 42357 }


    iqupc00DolbyControlDolbyMetaProgSelMetaProgramSelect OBJECT-TYPE
        SYNTAX            INTEGER {
                            valProgram1(0),
                            valProgram2(1),
                            valProgram3(2),
                            valProgram4(3),
                            valProgram5(4),
                            valProgram6(5),
                            valProgram7(6),
                            valProgram8(7)
                            }
        MAX-ACCESS        read-write
        STATUS            current
        DESCRIPTION
                "CMNT: - Dolby metadata program select
                 TYPE: - RadiobuttonList
                 PAGE: - DolbyControl
                    Meta Program Select  cmdID= 42413
                    Program 1  value= 0
                    Program 2  value= 1
                    Program 3  value= 2
                    Program 4  value= 3
                    Program 5  value= 4
                    Program 6  value= 5
                    Program 7  value= 6
                    Program 8  value= 7  "
        ::= { iqupc00CmdEntry 42413 }


    iqupc00DolbyStatusDolbyCommonStatusVideoSync OBJECT-TYPE
        SYNTAX            RollCallString
        MAX-ACCESS        read-only
        STATUS            current
        DESCRIPTION
                "CMNT: - Dolby video sync status
                 TYPE: - Display
                 PAGE: - DolbyStatus
                    Video Sync  cmdID= 42381  "
        ::= { iqupc00CmdEntry 42381 }


    iqupc00DolbyStatusDolbyCommonStatusFrameRate OBJECT-TYPE
        SYNTAX            RollCallString
        MAX-ACCESS        read-only
        STATUS            current
        DESCRIPTION
                "CMNT: - Dolby video frame rate
                 TYPE: - Display
                 PAGE: - DolbyStatus
                    Frame Rate  cmdID= 42412  "
        ::= { iqupc00CmdEntry 42412 }


    iqupc00DolbyStatusDolbyCommonStatusProgramConfig OBJECT-TYPE
        SYNTAX            RollCallString
        MAX-ACCESS        read-only
        STATUS            current
        DESCRIPTION
                "CMNT: - Dolby external metadata program configuration
                 TYPE: - Display
                 PAGE: - DolbyStatus
                    Program Config  cmdID= 42439  "
        ::= { iqupc00CmdEntry 42439 }


    iqupc00DolbyStatusDolbyCommonStatusFWVersion OBJECT-TYPE
        SYNTAX            RollCallString
        MAX-ACCESS        read-only
        STATUS            current
        DESCRIPTION
                "CMNT: - Dolby firmware version
                 TYPE: - Display
                 PAGE: - DolbyStatus
                    F/W Version  cmdID= 42493  "
        ::= { iqupc00CmdEntry 42493 }


    iqupc00DolbyStatusDolbyCommonStatusDeviceName OBJECT-TYPE
        SYNTAX            RollCallString
        MAX-ACCESS        read-only
        STATUS            current
        DESCRIPTION
                "CMNT: - Dolby device name
                 TYPE: - Display
                 PAGE: - DolbyStatus
                    Device Name  cmdID= 42495  "
        ::= { iqupc00CmdEntry 42495 }


    iqupc00DolbyCommonStatusChannelAssignmentDolbyA1 OBJECT-TYPE
        SYNTAX            RollCallString
        MAX-ACCESS        read-only
        STATUS            current
        DESCRIPTION
                "CMNT: - Dolby encoder A1 input channel assignment
                 TYPE: - Display
                 PAGE: - Dolby Common Status
                    Dolby A1  cmdID= 42548  "
        ::= { iqupc00CmdEntry 42548 }


    iqupc00DolbyCommonStatusChannelAssignmentDolbyA2 OBJECT-TYPE
        SYNTAX            RollCallString
        MAX-ACCESS        read-only
        STATUS            current
        DESCRIPTION
                "CMNT: - Dolby encoder A2 input channel assignment
                 TYPE: - Display
                 PAGE: - Dolby Common Status
                    Dolby A2  cmdID= 42549  "
        ::= { iqupc00CmdEntry 42549 }


    iqupc00DolbyCommonStatusChannelAssignmentDolbyB3 OBJECT-TYPE
        SYNTAX            RollCallString
        MAX-ACCESS        read-only
        STATUS            current
        DESCRIPTION
                "CMNT: - Dolby encoder B3 input channel assignment
                 TYPE: - Display
                 PAGE: - Dolby Common Status
                    Dolby B3  cmdID= 42550  "
        ::= { iqupc00CmdEntry 42550 }


    iqupc00DolbyCommonStatusChannelAssignmentDolbyB4 OBJECT-TYPE
        SYNTAX            RollCallString
        MAX-ACCESS        read-only
        STATUS            current
        DESCRIPTION
                "CMNT: - Dolby encoder B4 input channel assignment
                 TYPE: - Display
                 PAGE: - Dolby Common Status
                    Dolby B4  cmdID= 42551  "
        ::= { iqupc00CmdEntry 42551 }


    iqupc00DolbyCommonStatusChannelAssignmentDolbyC5 OBJECT-TYPE
        SYNTAX            RollCallString
        MAX-ACCESS        read-only
        STATUS            current
        DESCRIPTION
                "CMNT: - Dolby encoder C5 input channel assignment
                 TYPE: - Display
                 PAGE: - Dolby Common Status
                    Dolby C5  cmdID= 42552  "
        ::= { iqupc00CmdEntry 42552 }


    iqupc00DolbyCommonStatusChannelAssignmentDolbyC6 OBJECT-TYPE
        SYNTAX            RollCallString
        MAX-ACCESS        read-only
        STATUS            current
        DESCRIPTION
                "CMNT: - Dolby encoder C6 input channel assignment
                 TYPE: - Display
                 PAGE: - Dolby Common Status
                    Dolby C6  cmdID= 42553  "
        ::= { iqupc00CmdEntry 42553 }


    iqupc00DolbyCommonStatusChannelAssignmentDolbyD7 OBJECT-TYPE
        SYNTAX            RollCallString
        MAX-ACCESS        read-only
        STATUS            current
        DESCRIPTION
                "CMNT: - Dolby encoder D7 input channel assignment
                 TYPE: - Display
                 PAGE: - Dolby Common Status
                    Dolby D7  cmdID= 42554  "
        ::= { iqupc00CmdEntry 42554 }


    iqupc00DolbyCommonStatusChannelAssignmentDolbyD8 OBJECT-TYPE
        SYNTAX            RollCallString
        MAX-ACCESS        read-only
        STATUS            current
        DESCRIPTION
                "CMNT: - Dolby encoder D8 input channel assignment
                 TYPE: - Display
                 PAGE: - Dolby Common Status
                    Dolby D8  cmdID= 42555  "
        ::= { iqupc00CmdEntry 42555 }


    iqupc00DolbyCommonStatusChnlPairAssignmentDolby12 OBJECT-TYPE
        SYNTAX            RollCallString
        MAX-ACCESS        read-only
        STATUS            current
        DESCRIPTION
                "CMNT: - Dolby encoder A1/A2 output channel assignment
                 TYPE: - Display
                 PAGE: - Dolby Common Status
                    Dolby 1/2  cmdID= 42544  "
        ::= { iqupc00CmdEntry 42544 }


    iqupc00DolbyCommonStatusChnlPairAssignmentDolby34 OBJECT-TYPE
        SYNTAX            RollCallString
        MAX-ACCESS        read-only
        STATUS            current
        DESCRIPTION
                "CMNT: - Dolby encoder B3/B4 output channel assignment
                 TYPE: - Display
                 PAGE: - Dolby Common Status
                    Dolby 3/4  cmdID= 42545  "
        ::= { iqupc00CmdEntry 42545 }


    iqupc00DolbyCommonStatusChnlPairAssignmentDolby56 OBJECT-TYPE
        SYNTAX            RollCallString
        MAX-ACCESS        read-only
        STATUS            current
        DESCRIPTION
                "CMNT: - Dolby encoder C5/C6 output channel assignment
                 TYPE: - Display
                 PAGE: - Dolby Common Status
                    Dolby 5/6  cmdID= 42546  "
        ::= { iqupc00CmdEntry 42546 }


    iqupc00DolbyCommonStatusChnlPairAssignmentDolby78 OBJECT-TYPE
        SYNTAX            RollCallString
        MAX-ACCESS        read-only
        STATUS            current
        DESCRIPTION
                "CMNT: - Dolby encoder D7/D8 output channel assignment
                 TYPE: - Display
                 PAGE: - Dolby Common Status
                    Dolby 7/8  cmdID= 42547  "
        ::= { iqupc00CmdEntry 42547 }


    iqupc00DolbyStatusDolbyExtProgStatusP1Status OBJECT-TYPE
        SYNTAX            RollCallString
        MAX-ACCESS        read-only
        STATUS            current
        DESCRIPTION
                "CMNT: - Dolby external metadata program 1 status
                 TYPE: - Display
                 PAGE: - DolbyStatus
                    P1 Status  cmdID= 42441  "
        ::= { iqupc00CmdEntry 42441 }


    iqupc00DolbyStatusDolbyExtProgStatusP2Status OBJECT-TYPE
        SYNTAX            RollCallString
        MAX-ACCESS        read-only
        STATUS            current
        DESCRIPTION
                "CMNT: - Dolby external metadata program 2 status
                 TYPE: - Display
                 PAGE: - DolbyStatus
                    P2 Status  cmdID= 42442  "
        ::= { iqupc00CmdEntry 42442 }


    iqupc00DolbyStatusDolbyExtProgStatusP3Status OBJECT-TYPE
        SYNTAX            RollCallString
        MAX-ACCESS        read-only
        STATUS            current
        DESCRIPTION
                "CMNT: - Dolby external metadata program 3 status
                 TYPE: - Display
                 PAGE: - DolbyStatus
                    P3 Status  cmdID= 42443  "
        ::= { iqupc00CmdEntry 42443 }


    iqupc00DolbyStatusDolbyExtProgStatusP4Status OBJECT-TYPE
        SYNTAX            RollCallString
        MAX-ACCESS        read-only
        STATUS            current
        DESCRIPTION
                "CMNT: - Dolby external metadata program 4 status
                 TYPE: - Display
                 PAGE: - DolbyStatus
                    P4 Status  cmdID= 42444  "
        ::= { iqupc00CmdEntry 42444 }


    iqupc00DolbyStatusDolbyExtProgStatusP5Status OBJECT-TYPE
        SYNTAX            RollCallString
        MAX-ACCESS        read-only
        STATUS            current
        DESCRIPTION
                "CMNT: - Dolby external metadata program 5 status
                 TYPE: - Display
                 PAGE: - DolbyStatus
                    P5 Status  cmdID= 42445  "
        ::= { iqupc00CmdEntry 42445 }


    iqupc00DolbyStatusDolbyExtProgStatusP6Status OBJECT-TYPE
        SYNTAX            RollCallString
        MAX-ACCESS        read-only
        STATUS            current
        DESCRIPTION
                "CMNT: - Dolby external metadata program 6 status
                 TYPE: - Display
                 PAGE: - DolbyStatus
                    P6 Status  cmdID= 42446  "
        ::= { iqupc00CmdEntry 42446 }


    iqupc00DolbyStatusDolbyExtProgStatusP7Status OBJECT-TYPE
        SYNTAX            RollCallString
        MAX-ACCESS        read-only
        STATUS            current
        DESCRIPTION
                "CMNT: - Dolby external metadata program 7 status
                 TYPE: - Display
                 PAGE: - DolbyStatus
                    P7 Status  cmdID= 42447  "
        ::= { iqupc00CmdEntry 42447 }


    iqupc00DolbyStatusDolbyExtProgStatusP8Status OBJECT-TYPE
        SYNTAX            RollCallString
        MAX-ACCESS        read-only
        STATUS            current
        DESCRIPTION
                "CMNT: - Dolby external metadata program 8 status
                 TYPE: - Display
                 PAGE: - DolbyStatus
                    P8 Status  cmdID= 42448  "
        ::= { iqupc00CmdEntry 42448 }


    iqupc00DolbyStatusDolbyMetadataStatusProgramDescriptionL OBJECT-TYPE
        SYNTAX            RollCallString
        MAX-ACCESS        read-only
        STATUS            current
        DESCRIPTION
                "CMNT: - Dolby metadata AC-3 status text description (LH part)
                 TYPE: - Display
                 PAGE: - DolbyStatus
                    Program Description L  cmdID= 42508  "
        ::= { iqupc00CmdEntry 42508 }


    iqupc00DolbyStatusDolbyMetadataStatusProgramDescriptionR OBJECT-TYPE
        SYNTAX            RollCallString
        MAX-ACCESS        read-only
        STATUS            current
        DESCRIPTION
                "CMNT: - Dolby metadata AC-3 status text description (RH part)
                 TYPE: - Display
                 PAGE: - DolbyStatus
                    Program Description R  cmdID= 42509  "
        ::= { iqupc00CmdEntry 42509 }


    iqupc00DolbyStatusDolbyMetadataStatusDialogueNorm OBJECT-TYPE
        SYNTAX            RollCallString
        MAX-ACCESS        read-only
        STATUS            current
        DESCRIPTION
                "CMNT: - Dolby metadata AC-3 status dialogue normalisation
                 TYPE: - Display
                 PAGE: - DolbyStatus
                    Dialogue Norm  cmdID= 42422  "
        ::= { iqupc00CmdEntry 42422 }


    iqupc00DolbyStatusDolbyMetadataStatusChannelMode OBJECT-TYPE
        SYNTAX            RollCallString
        MAX-ACCESS        read-only
        STATUS            current
        DESCRIPTION
                "CMNT: - Dolby metadata AC-3 status channel (coding) mode
                 TYPE: - Display
                 PAGE: - DolbyStatus
                    Channel Mode  cmdID= 42415  "
        ::= { iqupc00CmdEntry 42415 }


    iqupc00DolbyStatusDolbyMetadataStatusLFE OBJECT-TYPE
        SYNTAX            RollCallString
        MAX-ACCESS        read-only
        STATUS            current
        DESCRIPTION
                "CMNT: - Dolby metadata AC-3 status low frequency effects channel
                 TYPE: - Display
                 PAGE: - DolbyStatus
                    LFE  cmdID= 42421  "
        ::= { iqupc00CmdEntry 42421 }


    iqupc00DolbyStatusDolbyMetadataStatusBitstreamMode OBJECT-TYPE
        SYNTAX            RollCallString
        MAX-ACCESS        read-only
        STATUS            current
        DESCRIPTION
                "CMNT: - Dolby metadata AC-3 status bitstream mode
                 TYPE: - Display
                 PAGE: - DolbyStatus
                    Bitstream Mode  cmdID= 42414  "
        ::= { iqupc00CmdEntry 42414 }


    iqupc00DolbyStatusDolbyMetadataStatusRFMode OBJECT-TYPE
        SYNTAX            RollCallString
        MAX-ACCESS        read-only
        STATUS            current
        DESCRIPTION
                "CMNT: - Dolby metadata AC-3 status RF mode
                 TYPE: - Display
                 PAGE: - DolbyStatus
                    RF Mode  cmdID= 42417  "
        ::= { iqupc00CmdEntry 42417 }


    iqupc00DolbyStatusDolbyMetadataStatusLineMode OBJECT-TYPE
        SYNTAX            RollCallString
        MAX-ACCESS        read-only
        STATUS            current
        DESCRIPTION
                "CMNT: - Dolby metadata AC-3 status line mode
                 TYPE: - Display
                 PAGE: - DolbyStatus
                    Line Mode  cmdID= 42416  "
        ::= { iqupc00CmdEntry 42416 }


    iqupc00DolbyStatusDolbyMetadataStatusCentreMixLevel OBJECT-TYPE
        SYNTAX            RollCallString
        MAX-ACCESS        read-only
        STATUS            current
        DESCRIPTION
                "CMNT: - Dolby metadata AC-3 status centre mix level
                 TYPE: - Display
                 PAGE: - DolbyStatus
                    Centre Mix Level  cmdID= 42418  "
        ::= { iqupc00CmdEntry 42418 }


    iqupc00DolbyStatusDolbyMetadataStatusSurroundMixLevel OBJECT-TYPE
        SYNTAX            RollCallString
        MAX-ACCESS        read-only
        STATUS            current
        DESCRIPTION
                "CMNT: - Dolby metadata AC-3 status surround mix level
                 TYPE: - Display
                 PAGE: - DolbyStatus
                    Surround Mix Level  cmdID= 42419  "
        ::= { iqupc00CmdEntry 42419 }


    iqupc00DolbyStatusDolbyMetadataStatusSurroundMode OBJECT-TYPE
        SYNTAX            RollCallString
        MAX-ACCESS        read-only
        STATUS            current
        DESCRIPTION
                "CMNT: - Dolby metadata AC-3 status surround mode
                 TYPE: - Display
                 PAGE: - DolbyStatus
                    Surround Mode  cmdID= 42420  "
        ::= { iqupc00CmdEntry 42420 }


    iqupc00DolbyStatusDolbyMetadataStatusCopyright OBJECT-TYPE
        SYNTAX            RollCallString
        MAX-ACCESS        read-only
        STATUS            current
        DESCRIPTION
                "CMNT: - Dolby metadata AC-3 status copyright
                 TYPE: - Display
                 PAGE: - DolbyStatus
                    Copyright  cmdID= 42438  "
        ::= { iqupc00CmdEntry 42438 }


    iqupc00DolbyMetadataStatusAudioProductionInfoAudioProdInfoExists OBJECT-TYPE
        SYNTAX            RollCallString
        MAX-ACCESS        read-only
        STATUS            current
        DESCRIPTION
                "CMNT: - Dolby metadata AC-3 status audio production information exists
                 TYPE: - Display
                 PAGE: - Dolby Metadata Status
                    Audio Prod Info Exists  cmdID= 42423  "
        ::= { iqupc00CmdEntry 42423 }


    iqupc00DolbyMetadataStatusAudioProductionInfoMixLevel OBJECT-TYPE
        SYNTAX            RollCallString
        MAX-ACCESS        read-only
        STATUS            current
        DESCRIPTION
                "CMNT: - Dolby metadata AC-3 status audio production mix level
                 TYPE: - Display
                 PAGE: - Dolby Metadata Status
                    Mix Level  cmdID= 42424  "
        ::= { iqupc00CmdEntry 42424 }


    iqupc00DolbyMetadataStatusAudioProductionInfoRoomType OBJECT-TYPE
        SYNTAX            RollCallString
        MAX-ACCESS        read-only
        STATUS            current
        DESCRIPTION
                "CMNT: - Dolby metadata AC-3 status audio production room type
                 TYPE: - Display
                 PAGE: - Dolby Metadata Status
                    Room Type  cmdID= 42425  "
        ::= { iqupc00CmdEntry 42425 }


    iqupc00DolbyStatusDolbyMetadataStatusExtendedBSI1Exists OBJECT-TYPE
        SYNTAX            RollCallString
        MAX-ACCESS        read-only
        STATUS            current
        DESCRIPTION
                "CMNT: - Dolby metadata AC-3 status BSI 1 exists
                 TYPE: - Display
                 PAGE: - DolbyStatus
                    Extended BSI1 Exists  cmdID= 42426  "
        ::= { iqupc00CmdEntry 42426 }


    iqupc00DolbyMetadataStatusExtendedBSI1StereoDownmixMode OBJECT-TYPE
        SYNTAX            RollCallString
        MAX-ACCESS        read-only
        STATUS            current
        DESCRIPTION
                "CMNT: - Dolby metadata AC-3 status BSI 1 preferred stereo downmix mode
                 TYPE: - Display
                 PAGE: - Dolby Metadata Status
                    Stereo Downmix Mode  cmdID= 42427  "
        ::= { iqupc00CmdEntry 42427 }


    iqupc00DolbyMetadataStatusExtendedBSI1LtRtCentreMixLevel OBJECT-TYPE
        SYNTAX            RollCallString
        MAX-ACCESS        read-only
        STATUS            current
        DESCRIPTION
                "CMNT: - Dolby metadata AC-3 status BSI 1 LtRt center mix level
                 TYPE: - Display
                 PAGE: - Dolby Metadata Status
                    Lt/Rt Centre Mix Level  cmdID= 42428  "
        ::= { iqupc00CmdEntry 42428 }


    iqupc00DolbyMetadataStatusExtendedBSI1LtRtSurrMixLevel OBJECT-TYPE
        SYNTAX            RollCallString
        MAX-ACCESS        read-only
        STATUS            current
        DESCRIPTION
                "CMNT: - Dolby metadata AC-3 status BSI 1 LtRt surround mix level
                 TYPE: - Display
                 PAGE: - Dolby Metadata Status
                    Lt/Rt Surr Mix Level  cmdID= 42429  "
        ::= { iqupc00CmdEntry 42429 }


    iqupc00DolbyMetadataStatusExtendedBSI1LoRoCentreMixLevel OBJECT-TYPE
        SYNTAX            RollCallString
        MAX-ACCESS        read-only
        STATUS            current
        DESCRIPTION
                "CMNT: - Dolby metadata AC-3 status BSI 1 LoRo center mix level
                 TYPE: - Display
                 PAGE: - Dolby Metadata Status
                    Lo/Ro Centre Mix Level  cmdID= 42430  "
        ::= { iqupc00CmdEntry 42430 }


    iqupc00DolbyMetadataStatusExtendedBSI1LoRoSurrMixLevel OBJECT-TYPE
        SYNTAX            RollCallString
        MAX-ACCESS        read-only
        STATUS            current
        DESCRIPTION
                "CMNT: - Dolby metadata AC-3 status BSI 1 LoRo surround mix level
                 TYPE: - Display
                 PAGE: - Dolby Metadata Status
                    Lo/Ro Surr Mix Level  cmdID= 42431  "
        ::= { iqupc00CmdEntry 42431 }


    iqupc00DolbyStatusDolbyMetadataStatusExtendedBSI2Exists OBJECT-TYPE
        SYNTAX            RollCallString
        MAX-ACCESS        read-only
        STATUS            current
        DESCRIPTION
                "CMNT: - Dolby metadata AC-3 status BSI 2 exists
                 TYPE: - Display
                 PAGE: - DolbyStatus
                    Extended BSI2 Exists  cmdID= 42432  "
        ::= { iqupc00CmdEntry 42432 }


    iqupc00DolbyMetadataStatusExtendedBSI2SurroundEXMode OBJECT-TYPE
        SYNTAX            RollCallString
        MAX-ACCESS        read-only
        STATUS            current
        DESCRIPTION
                "CMNT: - Dolby metadata AC-3 status BSI 2 surround EX mode
                 TYPE: - Display
                 PAGE: - Dolby Metadata Status
                    Surround EX Mode  cmdID= 42433  "
        ::= { iqupc00CmdEntry 42433 }


    iqupc00DolbyMetadataStatusExtendedBSI2LowpassFilter OBJECT-TYPE
        SYNTAX            RollCallString
        MAX-ACCESS        read-only
        STATUS            current
        DESCRIPTION
                "CMNT: - Dolby metadata AC-3 status BSI 2 lowpass filter
                 TYPE: - Display
                 PAGE: - Dolby Metadata Status
                    Lowpass Filter  cmdID= 42434  "
        ::= { iqupc00CmdEntry 42434 }


    iqupc00DolbyMetadataStatusExtendedBSI2LFEFilter OBJECT-TYPE
        SYNTAX            RollCallString
        MAX-ACCESS        read-only
        STATUS            current
        DESCRIPTION
                "CMNT: - Dolby metadata AC-3 status BSI 2 LFE filter
                 TYPE: - Display
                 PAGE: - Dolby Metadata Status
                    LFE Filter  cmdID= 42435  "
        ::= { iqupc00CmdEntry 42435 }


    iqupc00DolbyMetadataStatusExtendedBSI2SurrPhaseShiftFltr OBJECT-TYPE
        SYNTAX            RollCallString
        MAX-ACCESS        read-only
        STATUS            current
        DESCRIPTION
                "CMNT: - Dolby metadata AC-3 status BSI 2 surround 90deg phase shift filter
                 TYPE: - Display
                 PAGE: - Dolby Metadata Status
                    Surr Phase Shift Fltr  cmdID= 42436  "
        ::= { iqupc00CmdEntry 42436 }


    iqupc00DolbyMetadataStatusExtendedBSI2Surr3dBAtten OBJECT-TYPE
        SYNTAX            RollCallString
        MAX-ACCESS        read-only
        STATUS            current
        DESCRIPTION
                "CMNT: - Dolby metadata AC-3 status BSI 2 3dB surround channel attenuator
                 TYPE: - Display
                 PAGE: - Dolby Metadata Status
                    Surr 3dB Atten  cmdID= 42437  "
        ::= { iqupc00CmdEntry 42437 }


    iqupc00DolbyStatusDolbyEncoderStatusStatus OBJECT-TYPE
        SYNTAX            RollCallString
        MAX-ACCESS        read-only
        STATUS            current
        DESCRIPTION
                "CMNT: - Dolby encoder status
                 TYPE: - Display
                 PAGE: - DolbyStatus
                    Status  cmdID= 42491  "
        ::= { iqupc00CmdEntry 42491 }


    iqupc00DolbyStatusDolbyEncoderStatusBitstreamStatus OBJECT-TYPE
        SYNTAX            RollCallString
        MAX-ACCESS        read-only
        STATUS            current
        DESCRIPTION
                "CMNT: - Dolby encoder external metadata bitstream status
                 TYPE: - Display
                 PAGE: - DolbyStatus
                    Bitstream Status  cmdID= 42496  "
        ::= { iqupc00CmdEntry 42496 }


    iqupc00DolbyStatusDolbyEncoderStatusReversionStatus OBJECT-TYPE
        SYNTAX            RollCallString
        MAX-ACCESS        read-only
        STATUS            current
        DESCRIPTION
                "CMNT: - Dolby encoder external metadata reversion status
                 TYPE: - Display
                 PAGE: - DolbyStatus
                    Reversion Status  cmdID= 42497  "
        ::= { iqupc00CmdEntry 42497 }


    iqupc00DolbyStatusDolbyEncoderStatusHWVersion OBJECT-TYPE
        SYNTAX            RollCallString
        MAX-ACCESS        read-only
        STATUS            current
        DESCRIPTION
                "CMNT: - Dolby encoder hardware version
                 TYPE: - Display
                 PAGE: - DolbyStatus
                    H/W Version  cmdID= 42494  "
        ::= { iqupc00CmdEntry 42494 }


    iqupc00DolbyStatusDolbyEncoderStatusOPProgramConfig OBJECT-TYPE
        SYNTAX            RollCallString
        MAX-ACCESS        read-only
        STATUS            current
        DESCRIPTION
                "CMNT: - Dolby encoder output program configuration
                 TYPE: - Display
                 PAGE: - DolbyStatus
                    O/P Program Config  cmdID= 42392  "
        ::= { iqupc00CmdEntry 42392 }


    iqupc00RollCallMemoriesMemoriesABCRecallMemory OBJECT-TYPE
        SYNTAX            INTEGER {
                            valNoneSelected(0),
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - RollCall/Memories
                    Recall Memory  cmdID= 37100
                    None Selected  value= 0
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqupc00CmdEntry 37100 }


    iqupc00RollCallMemoriesMemoriesABCSelMemory OBJECT-TYPE
        SYNTAX            INTEGER {
                            valUserMemory1(1),
                            valUserMemory2(2),
                            valUserMemory3(3),
                            valUserMemory4(4),
                            valUserMemory5(5),
                            valUserMemory6(6),
                            valUserMemory7(7),
                            valUserMemory8(8),
                            valUserMemory9(9),
                            valUserMemory10(10),
                            valUserMemory11(11),
                            valUserMemory12(12),
                            valUserMemory13(13),
                            valUserMemory14(14),
                            valUserMemory15(15),
                            valUserMemory16(16)
                            }
        MAX-ACCESS        read-write
        STATUS            current
        DESCRIPTION
                "CMNT: - 
                 TYPE: - RadiobuttonList
                 PAGE: - RollCall/Memories
                    Sel Memory  cmdID= 37101
                    User Memory 1  value= 1
                    User Memory 2  value= 2
                    User Memory 3  value= 3
                    User Memory 4  value= 4
                    User Memory 5  value= 5
                    User Memory 6  value= 6
                    User Memory 7  value= 7
                    User Memory 8  value= 8
                    User Memory 9  value= 9
                    User Memory 10  value= 10
                    User Memory 11  value= 11
                    User Memory 12  value= 12
                    User Memory 13  value= 13
                    User Memory 14  value= 14
                    User Memory 15  value= 15
                    User Memory 16  value= 16  "
        ::= { iqupc00CmdEntry 37101 }


    iqupc00RollCallMemoriesMemoriesABCSaveMemory OBJECT-TYPE
        SYNTAX            INTEGER { noAction(0),valSaveMemory(1) }
        MAX-ACCESS        read-write
        STATUS            current
        DESCRIPTION
                "CMNT: - 
                 TYPE: - Button
                 PAGE: - RollCall/Memories
                    Save Memory  cmdID= 37102
                    value= 1  "
        ::= { iqupc00CmdEntry 37102 }


    iqupc00RollCallMemoriesMemoriesABCClearMemory OBJECT-TYPE
        SYNTAX            INTEGER { noAction(0),valClearMemory(1) }
        MAX-ACCESS        read-write
        STATUS            current
        DESCRIPTION
                "CMNT: - Delete User Memory
                 TYPE: - Button
                 PAGE: - RollCall/Memories
                    Clear Memory  cmdID= 37105
                    value= 1  "
        ::= { iqupc00CmdEntry 37105 }


    iqupc00MemoriesABCMemoryNameChangeName OBJECT-TYPE
        SYNTAX            RollCallString
        MAX-ACCESS        read-write
        STATUS            current
        DESCRIPTION
                "CMNT: - 
                 TYPE: - Editstring
                 PAGE: - MemoriesABC
                    Change Name  cmdID= 37103
                    preset= Display Memory"
        ::= { iqupc00CmdEntry 37103 }


    iqupc00MemoriesABCMemoryNameLastUserMemory OBJECT-TYPE
        SYNTAX            RollCallString
        MAX-ACCESS        read-only
        STATUS            current
        DESCRIPTION
                "CMNT: - 
                 TYPE: - Display
                 PAGE: - MemoriesABC
                    Last User Memory  cmdID= 37104  "
        ::= { iqupc00CmdEntry 37104 }


    iqupc00RollCallMemoriesMemoriesABCMemoryName1 OBJECT-TYPE
        SYNTAX            RollCallString
        MAX-ACCESS        read-only
        STATUS            current
        DESCRIPTION
                "CMNT: - 
                 TYPE: - Display
                 PAGE: - RollCall/Memories
                    Memory Name1  cmdID= 37106  "
        ::= { iqupc00CmdEntry 37106 }


    iqupc00RollCallMemoriesMemoriesABCMemoryName2 OBJECT-TYPE
        SYNTAX            RollCallString
        MAX-ACCESS        read-only
        STATUS            current
        DESCRIPTION
                "CMNT: - 
                 TYPE: - Display
                 PAGE: - RollCall/Memories
                    Memory Name2  cmdID= 37107  "
        ::= { iqupc00CmdEntry 37107 }


    iqupc00RollCallMemoriesMemoriesABCMemoryName3 OBJECT-TYPE
        SYNTAX            RollCallString
        MAX-ACCESS        read-only
        STATUS            current
        DESCRIPTION
                "CMNT: - 
                 TYPE: - Display
                 PAGE: - RollCall/Memories
                    Memory Name3  cmdID= 37108  "
        ::= { iqupc00CmdEntry 37108 }


    iqupc00RollCallMemoriesMemoriesABCMemoryName4 OBJECT-TYPE
        SYNTAX            RollCallString
        MAX-ACCESS        read-only
        STATUS            current
        DESCRIPTION
                "CMNT: - 
                 TYPE: - Display
                 PAGE: - RollCall/Memories
                    Memory Name4  cmdID= 37109  "
        ::= { iqupc00CmdEntry 37109 }


    iqupc00RollCallMemoriesMemoriesABCMemoryName5 OBJECT-TYPE
        SYNTAX            RollCallString
        MAX-ACCESS        read-only
        STATUS            current
        DESCRIPTION
                "CMNT: - 
                 TYPE: - Display
                 PAGE: - RollCall/Memories
                    Memory Name5  cmdID= 37110  "
        ::= { iqupc00CmdEntry 37110 }


    iqupc00RollCallMemoriesMemoriesABCMemoryName6 OBJECT-TYPE
        SYNTAX            RollCallString
        MAX-ACCESS        read-only
        STATUS            current
        DESCRIPTION
                "CMNT: - 
                 TYPE: - Display
                 PAGE: - RollCall/Memories
                    Memory Name6  cmdID= 37111  "
        ::= { iqupc00CmdEntry 37111 }


    iqupc00RollCallMemoriesMemoriesABCMemoryName7 OBJECT-TYPE
        SYNTAX            RollCallString
        MAX-ACCESS        read-only
        STATUS            current
        DESCRIPTION
                "CMNT: - 
                 TYPE: - Display
                 PAGE: - RollCall/Memories
                    Memory Name7  cmdID= 37112  "
        ::= { iqupc00CmdEntry 37112 }


    iqupc00RollCallMemoriesMemoriesABCMemoryName8 OBJECT-TYPE
        SYNTAX            RollCallString
        MAX-ACCESS        read-only
        STATUS            current
        DESCRIPTION
                "CMNT: - 
                 TYPE: - Display
                 PAGE: - RollCall/Memories
                    Memory Name8  cmdID= 37113  "
        ::= { iqupc00CmdEntry 37113 }


    iqupc00RollCallMemoriesMemoriesABCMemoryName9 OBJECT-TYPE
        SYNTAX            RollCallString
        MAX-ACCESS        read-only
        STATUS            current
        DESCRIPTION
                "CMNT: - 
                 TYPE: - Display
                 PAGE: - RollCall/Memories
                    Memory Name9  cmdID= 37114  "
        ::= { iqupc00CmdEntry 37114 }


    iqupc00RollCallMemoriesMemoriesABCMemoryName10 OBJECT-TYPE
        SYNTAX            RollCallString
        MAX-ACCESS        read-only
        STATUS            current
        DESCRIPTION
                "CMNT: - 
                 TYPE: - Display
                 PAGE: - RollCall/Memories
                    Memory Name10  cmdID= 37115  "
        ::= { iqupc00CmdEntry 37115 }


    iqupc00RollCallMemoriesMemoriesABCMemoryName11 OBJECT-TYPE
        SYNTAX            RollCallString
        MAX-ACCESS        read-only
        STATUS            current
        DESCRIPTION
                "CMNT: - 
                 TYPE: - Display
                 PAGE: - RollCall/Memories
                    Memory Name11  cmdID= 37116  "
        ::= { iqupc00CmdEntry 37116 }


    iqupc00RollCallMemoriesMemoriesABCMemoryName12 OBJECT-TYPE
        SYNTAX            RollCallString
        MAX-ACCESS        read-only
        STATUS            current
        DESCRIPTION
                "CMNT: - 
                 TYPE: - Display
                 PAGE: - RollCall/Memories
                    Memory Name12  cmdID= 37117  "
        ::= { iqupc00CmdEntry 37117 }


    iqupc00RollCallMemoriesMemoriesABCMemoryName13 OBJECT-TYPE
        SYNTAX            RollCallString
        MAX-ACCESS        read-only
        STATUS            current
        DESCRIPTION
                "CMNT: - 
                 TYPE: - Display
                 PAGE: - RollCall/Memories
                    Memory Name13  cmdID= 37118  "
        ::= { iqupc00CmdEntry 37118 }


    iqupc00RollCallMemoriesMemoriesABCMemoryName14 OBJECT-TYPE
        SYNTAX            RollCallString
        MAX-ACCESS        read-only
        STATUS            current
        DESCRIPTION
                "CMNT: - 
                 TYPE: - Display
                 PAGE: - RollCall/Memories
                    Memory Name14  cmdID= 37119  "
        ::= { iqupc00CmdEntry 37119 }


    iqupc00RollCallMemoriesMemoriesABCMemoryName15 OBJECT-TYPE
        SYNTAX            RollCallString
        MAX-ACCESS        read-only
        STATUS            current
        DESCRIPTION
                "CMNT: - 
                 TYPE: - Display
                 PAGE: - RollCall/Memories
                    Memory Name15  cmdID= 37120  "
        ::= { iqupc00CmdEntry 37120 }


    iqupc00RollCallMemoriesMemoriesABCMemoryName16 OBJECT-TYPE
        SYNTAX            RollCallString
        MAX-ACCESS        read-only
        STATUS            current
        DESCRIPTION
                "CMNT: - 
                 TYPE: - Display
                 PAGE: - RollCall/Memories
                    Memory Name16  cmdID= 37121  "
        ::= { iqupc00CmdEntry 37121 }


    iqupc00Logging1OutEmbAudLoggingLogOutEmb11state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.11 state  cmdID= 42024  "
        ::= { iqupc00CmdEntry 42024 }


    iqupc00Logging1OutEmbAudLoggingOutEmb11state OBJECT-TYPE
        SYNTAX            RollCallString
        MAX-ACCESS        read-only
        STATUS            current
        DESCRIPTION
                "CMNT: - Logging state for Inp 1, Emb Pair 1 state
                 TYPE: - Display
                 PAGE: - Logging1
                    Out Emb.11 state=  cmdID= 42224  "
        ::= { iqupc00CmdEntry 42224 }


    iqupc00Logging1OutEmbAudLoggingLogOutEmb12state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.12 state  cmdID= 42025  "
        ::= { iqupc00CmdEntry 42025 }


    iqupc00Logging1OutEmbAudLoggingOutEmb12state OBJECT-TYPE
        SYNTAX            RollCallString
        MAX-ACCESS        read-only
        STATUS            current
        DESCRIPTION
                "CMNT: - Logging state for Inp 1, Emb Pair 1 state
                 TYPE: - Display
                 PAGE: - Logging1
                    Out Emb.12 state=  cmdID= 42225  "
        ::= { iqupc00CmdEntry 42225 }


    iqupc00Logging1OutEmbAudLoggingLogOutEmb21state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.21 state  cmdID= 42026  "
        ::= { iqupc00CmdEntry 42026 }


    iqupc00Logging1OutEmbAudLoggingOutEmb21state OBJECT-TYPE
        SYNTAX            RollCallString
        MAX-ACCESS        read-only
        STATUS            current
        DESCRIPTION
                "CMNT: - Logging state for Inp 1, Emb Pair 1 state
                 TYPE: - Display
                 PAGE: - Logging1
                    Out Emb.21 state=  cmdID= 42226  "
        ::= { iqupc00CmdEntry 42226 }


    iqupc00Logging1OutEmbAudLoggingLogOutEmb22state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.22 state  cmdID= 42027  "
        ::= { iqupc00CmdEntry 42027 }


    iqupc00Logging1OutEmbAudLoggingOutEmb22state OBJECT-TYPE
        SYNTAX            RollCallString
        MAX-ACCESS        read-only
        STATUS            current
        DESCRIPTION
                "CMNT: - Logging state for Inp 1, Emb Pair 1 state
                 TYPE: - Display
                 PAGE: - Logging1
                    Out Emb.22 state=  cmdID= 42227  "
        ::= { iqupc00CmdEntry 42227 }


    iqupc00Logging1OutEmbAudLoggingLogOutEmb31state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.31 state  cmdID= 42028  "
        ::= { iqupc00CmdEntry 42028 }


    iqupc00Logging1OutEmbAudLoggingOutEmb31state OBJECT-TYPE
        SYNTAX            RollCallString
        MAX-ACCESS        read-only
        STATUS            current
        DESCRIPTION
                "CMNT: - Logging state for Inp 1, Emb Pair 1 state
                 TYPE: - Display
                 PAGE: - Logging1
                    Out Emb.31 state=  cmdID= 42228  "
        ::= { iqupc00CmdEntry 42228 }


    iqupc00Logging1OutEmbAudLoggingLogOutEmb32state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.32 state  cmdID= 42029  "
        ::= { iqupc00CmdEntry 42029 }


    iqupc00Logging1OutEmbAudLoggingOutEmb32state OBJECT-TYPE
        SYNTAX            RollCallString
        MAX-ACCESS        read-only
        STATUS            current
        DESCRIPTION
                "CMNT: - Logging state for Inp 1, Emb Pair 1 state
                 TYPE: - Display
                 PAGE: - Logging1
                    Out Emb.32 state=  cmdID= 42229  "
        ::= { iqupc00CmdEntry 42229 }


    iqupc00Logging1OutEmbAudLoggingLogOutEmb41state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.41 state  cmdID= 42030  "
        ::= { iqupc00CmdEntry 42030 }


    iqupc00Logging1OutEmbAudLoggingOutEmb41state OBJECT-TYPE
        SYNTAX            RollCallString
        MAX-ACCESS        read-only
        STATUS            current
        DESCRIPTION
                "CMNT: - Logging state for Inp 1, Emb Pair 1 state
                 TYPE: - Display
                 PAGE: - Logging1
                    Out Emb.41 state=  cmdID= 42230  "
        ::= { iqupc00CmdEntry 42230 }


    iqupc00Logging1OutEmbAudLoggingLogOutEmb42state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.42 state  cmdID= 42031  "
        ::= { iqupc00CmdEntry 42031 }


    iqupc00Logging1OutEmbAudLoggingOutEmb42state OBJECT-TYPE
        SYNTAX            RollCallString
        MAX-ACCESS        read-only
        STATUS            current
        DESCRIPTION
                "CMNT: - Logging state for Inp 1, Emb Pair 1 state
                 TYPE: - Display
                 PAGE: - Logging1
                    Out Emb.42 state=  cmdID= 42231  "
        ::= { iqupc00CmdEntry 42231 }


    iqupc00Logging1OutEmbAudLoggingLogOutEmb51state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.51 state  cmdID= 42032  "
        ::= { iqupc00CmdEntry 42032 }


    iqupc00Logging1OutEmbAudLoggingOutEmb51state OBJECT-TYPE
        SYNTAX            RollCallString
        MAX-ACCESS        read-only
        STATUS            current
        DESCRIPTION
                "CMNT: - Logging state for Inp 1, Emb Pair 1 state
                 TYPE: - Display
                 PAGE: - Logging1
                    Out Emb.51 state=  cmdID= 42232  "
        ::= { iqupc00CmdEntry 42232 }


    iqupc00Logging1OutEmbAudLoggingLogOutEmb52state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.52 state  cmdID= 42033  "
        ::= { iqupc00CmdEntry 42033 }


    iqupc00Logging1OutEmbAudLoggingOutEmb52state OBJECT-TYPE
        SYNTAX            RollCallString
        MAX-ACCESS        read-only
        STATUS            current
        DESCRIPTION
                "CMNT: - Logging state for Inp 1, Emb Pair 1 state
                 TYPE: - Display
                 PAGE: - Logging1
                    Out Emb.52 state=  cmdID= 42233  "
        ::= { iqupc00CmdEntry 42233 }


    iqupc00Logging1OutEmbAudLoggingLogOutEmb61state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.61 state  cmdID= 42034  "
        ::= { iqupc00CmdEntry 42034 }


    iqupc00Logging1OutEmbAudLoggingOutEmb61state OBJECT-TYPE
        SYNTAX            RollCallString
        MAX-ACCESS        read-only
        STATUS            current
        DESCRIPTION
                "CMNT: - Logging state for Inp 1, Emb Pair 1 state
                 TYPE: - Display
                 PAGE: - Logging1
                    Out Emb.61 state=  cmdID= 42234  "
        ::= { iqupc00CmdEntry 42234 }


    iqupc00Logging1OutEmbAudLoggingLogOutEmb62state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.62 state  cmdID= 42035  "
        ::= { iqupc00CmdEntry 42035 }


    iqupc00Logging1OutEmbAudLoggingOutEmb62state OBJECT-TYPE
        SYNTAX            RollCallString
        MAX-ACCESS        read-only
        STATUS            current
        DESCRIPTION
                "CMNT: - Logging state for Inp 1, Emb Pair 1 state
                 TYPE: - Display
                 PAGE: - Logging1
                    Out Emb.62 state=  cmdID= 42235  "
        ::= { iqupc00CmdEntry 42235 }


    iqupc00Logging1OutEmbAudLoggingLogOutEmb71state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.71 state  cmdID= 42036  "
        ::= { iqupc00CmdEntry 42036 }


    iqupc00Logging1OutEmbAudLoggingOutEmb71state OBJECT-TYPE
        SYNTAX            RollCallString
        MAX-ACCESS        read-only
        STATUS            current
        DESCRIPTION
                "CMNT: - Logging state for Inp 1, Emb Pair 1 state
                 TYPE: - Display
                 PAGE: - Logging1
                    Out Emb.71 state=  cmdID= 42236  "
        ::= { iqupc00CmdEntry 42236 }


    iqupc00Logging1OutEmbAudLoggingLogOutEmb72state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.72 state  cmdID= 42037  "
        ::= { iqupc00CmdEntry 42037 }


    iqupc00Logging1OutEmbAudLoggingOutEmb72state OBJECT-TYPE
        SYNTAX            RollCallString
        MAX-ACCESS        read-only
        STATUS            current
        DESCRIPTION
                "CMNT: - Logging state for Inp 1, Emb Pair 1 state
                 TYPE: - Display
                 PAGE: - Logging1
                    Out Emb.72 state=  cmdID= 42237  "
        ::= { iqupc00CmdEntry 42237 }


    iqupc00Logging1OutEmbAudLoggingLogOutEmb81state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.81 state  cmdID= 42038  "
        ::= { iqupc00CmdEntry 42038 }


    iqupc00Logging1OutEmbAudLoggingOutEmb81state OBJECT-TYPE
        SYNTAX            RollCallString
        MAX-ACCESS        read-only
        STATUS            current
        DESCRIPTION
                "CMNT: - Logging state for Inp 1, Emb Pair 1 state
                 TYPE: - Display
                 PAGE: - Logging1
                    Out Emb.81 state=  cmdID= 42238  "
        ::= { iqupc00CmdEntry 42238 }


    iqupc00Logging1OutEmbAudLoggingLogOutEmb82state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging1
                    Log Out Emb.82 state  cmdID= 42039  "
        ::= { iqupc00CmdEntry 42039 }


    iqupc00Logging1OutEmbAudLoggingOutEmb82state OBJECT-TYPE
        SYNTAX            RollCallString
        MAX-ACCESS        read-only
        STATUS            current
        DESCRIPTION
                "CMNT: - Logging state for Inp 1, Emb Pair 1 state
                 TYPE: - Display
                 PAGE: - Logging1
                    Out Emb.82 state=  cmdID= 42239  "
        ::= { iqupc00CmdEntry 42239 }


    iqupc00Logging1DolbyDecoderLoggingLogBitstreamFormat OBJECT-TYPE
        SYNTAX            INTEGER { disable(0), enable(1)  }
        MAX-ACCESS        read-write
        STATUS            current
        DESCRIPTION
                "CMNT: - Enable/Disable logging for Dolby Decoder bitstream format
                 TYPE: - Checkbox
                 PAGE: - Logging1
                    Log Bitstream Format  cmdID= 42100  "
        ::= { iqupc00CmdEntry 42100 }


    iqupc00Logging1DolbyDecoderLoggingBitstreamFormat OBJECT-TYPE
        SYNTAX            RollCallString
        MAX-ACCESS        read-only
        STATUS            current
        DESCRIPTION
                "CMNT: - Logging state for Dolby Decoder bitstream format
                 TYPE: - Display
                 PAGE: - Logging1
                    Bitstream Format=  cmdID= 42300  "
        ::= { iqupc00CmdEntry 42300 }


    iqupc00Logging1DolbyDecoderLoggingLogBitstreamStatus OBJECT-TYPE
        SYNTAX            INTEGER { disable(0), enable(1)  }
        MAX-ACCESS        read-write
        STATUS            current
        DESCRIPTION
                "CMNT: - Enable/Disable logging for Dolby Decoder bitstream status
                 TYPE: - Checkbox
                 PAGE: - Logging1
                    Log Bitstream Status  cmdID= 42101  "
        ::= { iqupc00CmdEntry 42101 }


    iqupc00Logging1DolbyDecoderLoggingBitstreamStatus OBJECT-TYPE
        SYNTAX            RollCallString
        MAX-ACCESS        read-only
        STATUS            current
        DESCRIPTION
                "CMNT: - Logging state for Dolby Decoder bitstream status
                 TYPE: - Display
                 PAGE: - Logging1
                    Bitstream Status=  cmdID= 42301  "
        ::= { iqupc00CmdEntry 42301 }


    iqupc00Logging1DolbyDecoderLoggingLogDCRCErrors OBJECT-TYPE
        SYNTAX            INTEGER { disable(0), enable(1)  }
        MAX-ACCESS        read-write
        STATUS            current
        DESCRIPTION
                "CMNT: - Enable/Disable logging for Dolby DecoderD CRC error count
                 TYPE: - Checkbox
                 PAGE: - Logging1
                    Log D CRC Errors  cmdID= 42102  "
        ::= { iqupc00CmdEntry 42102 }


    iqupc00Logging1DolbyDecoderLoggingDCRCErrorCount OBJECT-TYPE
        SYNTAX            RollCallString
        MAX-ACCESS        read-only
        STATUS            current
        DESCRIPTION
                "CMNT: - Logging state for Dolby Decoder D CRC error count
                 TYPE: - Display
                 PAGE: - Logging1
                    D CRC Error Count=  cmdID= 42302  "
        ::= { iqupc00CmdEntry 42302 }


    iqupc00Logging1DolbyDecoderLoggingLogECRCErrors OBJECT-TYPE
        SYNTAX            INTEGER { disable(0), enable(1)  }
        MAX-ACCESS        read-write
        STATUS            current
        DESCRIPTION
                "CMNT: - Enable/Disable logging for Dolby Decoder E CRC error count
                 TYPE: - Checkbox
                 PAGE: - Logging1
                    Log E CRC Errors  cmdID= 42103  "
        ::= { iqupc00CmdEntry 42103 }


    iqupc00Logging1DolbyDecoderLoggingECRCErrorCount OBJECT-TYPE
        SYNTAX            RollCallString
        MAX-ACCESS        read-only
        STATUS            current
        DESCRIPTION
                "CMNT: - Logging state for Dolby Decoder E CRC error count
                 TYPE: - Display
                 PAGE: - Logging1
                    E CRC Error Count=  cmdID= 42303  "
        ::= { iqupc00CmdEntry 42303 }


    iqupc00Logging1DolbyEncoderLoggingLogEncoderStatus OBJECT-TYPE
        SYNTAX            INTEGER { disable(0), enable(1)  }
        MAX-ACCESS        read-write
        STATUS            current
        DESCRIPTION
                "CMNT: - Enable/Disable logging for Dolby Encoder status
                 TYPE: - Checkbox
                 PAGE: - Logging1
                    Log Encoder Status  cmdID= 42112  "
        ::= { iqupc00CmdEntry 42112 }


    iqupc00Logging1DolbyEncoderLoggingEncoderStatus OBJECT-TYPE
        SYNTAX            RollCallString
        MAX-ACCESS        read-only
        STATUS            current
        DESCRIPTION
                "CMNT: - Logging state for Dolby Encoder status
                 TYPE: - Display
                 PAGE: - Logging1
                    Encoder Status=  cmdID= 42312  "
        ::= { iqupc00CmdEntry 42312 }


    iqupc00Logging1DolbyEncoderLoggingLogBitstreamStatus OBJECT-TYPE
        SYNTAX            INTEGER { disable(0), enable(1)  }
        MAX-ACCESS        read-write
        STATUS            current
        DESCRIPTION
                "CMNT: - Enable/Disable logging for Dolby Encoder bitstream status
                 TYPE: - Checkbox
                 PAGE: - Logging1
                    Log Bitstream Status  cmdID= 42113  "
        ::= { iqupc00CmdEntry 42113 }


    iqupc00Logging1DolbyEncoderLoggingBitstreamStatus OBJECT-TYPE
        SYNTAX            RollCallString
        MAX-ACCESS        read-only
        STATUS            current
        DESCRIPTION
                "CMNT: - Logging state for Dolby Encoder bitstream status
                 TYPE: - Display
                 PAGE: - Logging1
                    Bitstream Status=  cmdID= 42313  "
        ::= { iqupc00CmdEntry 42313 }


    iqupc00Logging1DolbyEncoderLoggingLogReversionStatus OBJECT-TYPE
        SYNTAX            INTEGER { disable(0), enable(1)  }
        MAX-ACCESS        read-write
        STATUS            current
        DESCRIPTION
                "CMNT: - Enable/Disable logging for Dolby Encoder reversion status
                 TYPE: - Checkbox
                 PAGE: - Logging1
                    Log Reversion Status  cmdID= 42114  "
        ::= { iqupc00CmdEntry 42114 }


    iqupc00Logging1DolbyEncoderLoggingReversionStatus OBJECT-TYPE
        SYNTAX            RollCallString
        MAX-ACCESS        read-only
        STATUS            current
        DESCRIPTION
                "CMNT: - Logging state for Dolby Encoder reversion status
                 TYPE: - Display
                 PAGE: - Logging1
                    Reversion Status=  cmdID= 42314  "
        ::= { iqupc00CmdEntry 42314 }


    iqupc00Logging1DolbyLoggingLogVideoSync OBJECT-TYPE
        SYNTAX            INTEGER { disable(0), enable(1)  }
        MAX-ACCESS        read-write
        STATUS            current
        DESCRIPTION
                "CMNT: - Enable/Disable logging for Dolby video sync
                 TYPE: - Checkbox
                 PAGE: - Logging1
                    Log Video Sync  cmdID= 42104  "
        ::= { iqupc00CmdEntry 42104 }


    iqupc00Logging1DolbyLoggingVideoSync OBJECT-TYPE
        SYNTAX            RollCallString
        MAX-ACCESS        read-only
        STATUS            current
        DESCRIPTION
                "CMNT: - Logging state for Dolby video sync
                 TYPE: - Display
                 PAGE: - Logging1
                    Video Sync=  cmdID= 42304  "
        ::= { iqupc00CmdEntry 42304 }


    iqupc00Logging1DolbyLoggingLogFrameRate OBJECT-TYPE
        SYNTAX            INTEGER { disable(0), enable(1)  }
        MAX-ACCESS        read-write
        STATUS            current
        DESCRIPTION
                "CMNT: - Enable/Disable logging for Dolby frame rate
                 TYPE: - Checkbox
                 PAGE: - Logging1
                    Log Frame Rate  cmdID= 42105  "
        ::= { iqupc00CmdEntry 42105 }


    iqupc00Logging1DolbyLoggingFrameRate OBJECT-TYPE
        SYNTAX            RollCallString
        MAX-ACCESS        read-only
        STATUS            current
        DESCRIPTION
                "CMNT: - Logging state for Dolby frame rate
                 TYPE: - Display
                 PAGE: - Logging1
                    Frame Rate=  cmdID= 42305  "
        ::= { iqupc00CmdEntry 42305 }


    iqupc00Logging1DolbyLoggingLogProgramConfig OBJECT-TYPE
        SYNTAX            INTEGER { disable(0), enable(1)  }
        MAX-ACCESS        read-write
        STATUS            current
        DESCRIPTION
                "CMNT: - Enable/Disable logging for Dolby program config
                 TYPE: - Checkbox
                 PAGE: - Logging1
                    Log Program Config  cmdID= 42106  "
        ::= { iqupc00CmdEntry 42106 }


    iqupc00Logging1DolbyLoggingProgramConfig OBJECT-TYPE
        SYNTAX            RollCallString
        MAX-ACCESS        read-only
        STATUS            current
        DESCRIPTION
                "CMNT: - Logging state for Dolby program config
                 TYPE: - Display
                 PAGE: - Logging1
                    Program Config=  cmdID= 42306  "
        ::= { iqupc00CmdEntry 42306 }


    iqupc00Logging1DolbyMetadataLoggingLogSelectedProgram OBJECT-TYPE
        SYNTAX            INTEGER { disable(0), enable(1)  }
        MAX-ACCESS        read-write
        STATUS            current
        DESCRIPTION
                "CMNT: - Enable/Disable logging for Dolby selected program
                 TYPE: - Checkbox
                 PAGE: - Logging1
                    Log Selected Program  cmdID= 42107  "
        ::= { iqupc00CmdEntry 42107 }


    iqupc00Logging1DolbyMetadataLoggingSelectedProgram OBJECT-TYPE
        SYNTAX            RollCallString
        MAX-ACCESS        read-only
        STATUS            current
        DESCRIPTION
                "CMNT: - Logging state for Dolby selected program
                 TYPE: - Display
                 PAGE: - Logging1
                    Selected Program=  cmdID= 42307  "
        ::= { iqupc00CmdEntry 42307 }


    iqupc00Logging1DolbyMetadataLoggingLogProgramDescriptor OBJECT-TYPE
        SYNTAX            INTEGER { disable(0), enable(1)  }
        MAX-ACCESS        read-write
        STATUS            current
        DESCRIPTION
                "CMNT: - Enable/Disable logging for Dolby program descriptor
                 TYPE: - Checkbox
                 PAGE: - Logging1
                    Log Program Descriptor  cmdID= 42108  "
        ::= { iqupc00CmdEntry 42108 }


    iqupc00Logging1DolbyMetadataLoggingProgramDescriptor OBJECT-TYPE
        SYNTAX            RollCallString
        MAX-ACCESS        read-only
        STATUS            current
        DESCRIPTION
                "CMNT: - Logging state for Dolby program descriptor
                 TYPE: - Display
                 PAGE: - Logging1
                    Program Descriptor=  cmdID= 42308  "
        ::= { iqupc00CmdEntry 42308 }


    iqupc00Logging1DolbyMetadataLoggingProgramDescPt2 OBJECT-TYPE
        SYNTAX            RollCallString
        MAX-ACCESS        read-only
        STATUS            current
        DESCRIPTION
                "CMNT: - Used for displaying 2nd half of program descriptor on logging page
                 TYPE: - Display
                 PAGE: - Logging1
                    Program Desc Pt2  cmdID= 42400  "
        ::= { iqupc00CmdEntry 42400 }


    iqupc00Logging1DolbyMetadataLoggingLogChannelMode OBJECT-TYPE
        SYNTAX            INTEGER { disable(0), enable(1)  }
        MAX-ACCESS        read-write
        STATUS            current
        DESCRIPTION
                "CMNT: - Enable/Disable logging for Dolby channel mode
                 TYPE: - Checkbox
                 PAGE: - Logging1
                    Log Channel Mode  cmdID= 42109  "
        ::= { iqupc00CmdEntry 42109 }


    iqupc00Logging1DolbyMetadataLoggingChannelMode OBJECT-TYPE
        SYNTAX            RollCallString
        MAX-ACCESS        read-only
        STATUS            current
        DESCRIPTION
                "CMNT: - Logging state for Dolby channel mode
                 TYPE: - Display
                 PAGE: - Logging1
                    Channel Mode=  cmdID= 42309  "
        ::= { iqupc00CmdEntry 42309 }


    iqupc00Logging1DolbyMetadataLoggingLogLFEChannel OBJECT-TYPE
        SYNTAX            INTEGER { disable(0), enable(1)  }
        MAX-ACCESS        read-write
        STATUS            current
        DESCRIPTION
                "CMNT: - Enable/Disable logging for Dolby lfe channel
                 TYPE: - Checkbox
                 PAGE: - Logging1
                    Log LFE Channel  cmdID= 42110  "
        ::= { iqupc00CmdEntry 42110 }


    iqupc00Logging1DolbyMetadataLoggingLFEChannel OBJECT-TYPE
        SYNTAX            RollCallString
        MAX-ACCESS        read-only
        STATUS            current
        DESCRIPTION
                "CMNT: - Logging state for Dolby lfe channel
                 TYPE: - Display
                 PAGE: - Logging1
                    LFE Channel=  cmdID= 42310  "
        ::= { iqupc00CmdEntry 42310 }


    iqupc00Logging1DolbyMetadataLoggingLogDialogueNorm OBJECT-TYPE
        SYNTAX            INTEGER { disable(0), enable(1)  }
        MAX-ACCESS        read-write
        STATUS            current
        DESCRIPTION
                "CMNT: - Enable/Disable logging for Dolby dialogue norm
                 TYPE: - Checkbox
                 PAGE: - Logging1
                    Log Dialogue Norm  cmdID= 42111  "
        ::= { iqupc00CmdEntry 42111 }


    iqupc00Logging1DolbyMetadataLoggingDialogueNorm OBJECT-TYPE
        SYNTAX            RollCallString
        MAX-ACCESS        read-only
        STATUS            current
        DESCRIPTION
                "CMNT: - Logging state for Dolby dialogue norm
                 TYPE: - Display
                 PAGE: - Logging1
                    Dialogue Norm=  cmdID= 42311  "
        ::= { iqupc00CmdEntry 42311 }


    iqupc00Logging1AncillaryDataLoggingLogVIInp1 OBJECT-TYPE
        SYNTAX            INTEGER { disable(0), enable(1)  }
        MAX-ACCESS        read-write
        STATUS            current
        DESCRIPTION
                "CMNT: - Enable/Disable logging for ancillary data VI status
                 TYPE: - Checkbox
                 PAGE: - Logging1
                    Log VI Inp1  cmdID= 42120  "
        ::= { iqupc00CmdEntry 42120 }


    iqupc00Logging1AncillaryDataLoggingVIInp1 OBJECT-TYPE
        SYNTAX            RollCallString
        MAX-ACCESS        read-only
        STATUS            current
        DESCRIPTION
                "CMNT: - Logging state for VI ancillary data on input
                 TYPE: - Display
                 PAGE: - Logging1
                    VI Inp1=  cmdID= 42320  "
        ::= { iqupc00CmdEntry 42320 }


    iqupc00Logging1AncillaryDataLoggingLogWSSInp1 OBJECT-TYPE
        SYNTAX            INTEGER { disable(0), enable(1)  }
        MAX-ACCESS        read-write
        STATUS            current
        DESCRIPTION
                "CMNT: - Enable/Disable logging for ancillary data WSS status
                 TYPE: - Checkbox
                 PAGE: - Logging1
                    Log WSS Inp1  cmdID= 42121  "
        ::= { iqupc00CmdEntry 42121 }


    iqupc00Logging1AncillaryDataLoggingWSSInp1 OBJECT-TYPE
        SYNTAX            RollCallString
        MAX-ACCESS        read-only
        STATUS            current
        DESCRIPTION
                "CMNT: - Logging state for WSS ancillary data on input
                 TYPE: - Display
                 PAGE: - Logging1
                    WSS Inp1=  cmdID= 42321  "
        ::= { iqupc00CmdEntry 42321 }


    iqupc00Logging1AncillaryDataLoggingLogVITCInp1 OBJECT-TYPE
        SYNTAX            INTEGER { disable(0), enable(1)  }
        MAX-ACCESS        read-write
        STATUS            current
        DESCRIPTION
                "CMNT: - Enable/Disable logging for ancillary data VITC status
                 TYPE: - Checkbox
                 PAGE: - Logging1
                    Log VITC Inp1  cmdID= 42122  "
        ::= { iqupc00CmdEntry 42122 }


    iqupc00Logging1AncillaryDataLoggingVITCInp1 OBJECT-TYPE
        SYNTAX            RollCallString
        MAX-ACCESS        read-only
        STATUS            current
        DESCRIPTION
                "CMNT: - Logging state for VITC ancillary data on input
                 TYPE: - Display
                 PAGE: - Logging1
                    VITC Inp1=  cmdID= 42322  "
        ::= { iqupc00CmdEntry 42322 }


    iqupc00Logging1AncillaryDataLoggingLogWSTInp1 OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log WST Inp1  cmdID= 42123  "
        ::= { iqupc00CmdEntry 42123 }


    iqupc00Logging1AncillaryDataLoggingWSTInp1 OBJECT-TYPE
        SYNTAX            RollCallString
        MAX-ACCESS        read-only
        STATUS            current
        DESCRIPTION
                "CMNT: - Logging state for WST ancillary data on input
                 TYPE: - Display
                 PAGE: - Logging1
                    WST Inp1=  cmdID= 42323  "
        ::= { iqupc00CmdEntry 42323 }


    iqupc00Logging1AncillaryDataLoggingLogCC608Inp1 OBJECT-TYPE
        SYNTAX            INTEGER { disable(0), enable(1)  }
        MAX-ACCESS        read-write
        STATUS            current
        DESCRIPTION
                "CMNT: - Enable/Disable logging for ancillary data CC608 status
                 TYPE: - Checkbox
                 PAGE: - Logging1
                    Log CC608 Inp1  cmdID= 42124  "
        ::= { iqupc00CmdEntry 42124 }


    iqupc00Logging1AncillaryDataLoggingCC608Inp1 OBJECT-TYPE
        SYNTAX            RollCallString
        MAX-ACCESS        read-only
        STATUS            current
        DESCRIPTION
                "CMNT: - Logging state for CC608 ancillary data on input
                 TYPE: - Display
                 PAGE: - Logging1
                    CC608 Inp1=  cmdID= 42324  "
        ::= { iqupc00CmdEntry 42324 }


    iqupc00Logging1AncillaryDataLoggingLog2016Inp1 OBJECT-TYPE
        SYNTAX            INTEGER { disable(0), enable(1)  }
        MAX-ACCESS        read-write
        STATUS            current
        DESCRIPTION
                "CMNT: - Enable/Disable logging for ancillary data SMPTE2016 status
                 TYPE: - Checkbox
                 PAGE: - Logging1
                    Log 2016 Inp1  cmdID= 42125  "
        ::= { iqupc00CmdEntry 42125 }


    iqupc00Logging1AncillaryDataLogging2016Inp1 OBJECT-TYPE
        SYNTAX            RollCallString
        MAX-ACCESS        read-only
        STATUS            current
        DESCRIPTION
                "CMNT: - Logging state for SMPTE2016 ancillary data on input
                 TYPE: - Display
                 PAGE: - Logging1
                    2016 Inp1=  cmdID= 42325  "
        ::= { iqupc00CmdEntry 42325 }


    iqupc00Logging1AncillaryDataLoggingLogATCInp1 OBJECT-TYPE
        SYNTAX            INTEGER { disable(0), enable(1)  }
        MAX-ACCESS        read-write
        STATUS            current
        DESCRIPTION
                "CMNT: - Enable/Disable logging for ancillary data ATC status
                 TYPE: - Checkbox
                 PAGE: - Logging1
                    Log ATC Inp1  cmdID= 42126  "
        ::= { iqupc00CmdEntry 42126 }


    iqupc00Logging1AncillaryDataLoggingATCInp1 OBJECT-TYPE
        SYNTAX            RollCallString
        MAX-ACCESS        read-only
        STATUS            current
        DESCRIPTION
                "CMNT: - Logging state for ATC/VITC ancillary data on input
                 TYPE: - Display
                 PAGE: - Logging1
                    ATC Inp1=  cmdID= 42326  "
        ::= { iqupc00CmdEntry 42326 }


    iqupc00Logging1AncillaryDataLoggingLogCC708Inp1 OBJECT-TYPE
        SYNTAX            INTEGER { disable(0), enable(1)  }
        MAX-ACCESS        read-write
        STATUS            current
        DESCRIPTION
                "CMNT: - Enable/Disable logging for ancillary data CC708 status
                 TYPE: - Checkbox
                 PAGE: - Logging1
                    Log CC708 Inp1  cmdID= 42127  "
        ::= { iqupc00CmdEntry 42127 }


    iqupc00Logging1AncillaryDataLoggingCC708Inp1 OBJECT-TYPE
        SYNTAX            RollCallString
        MAX-ACCESS        read-only
        STATUS            current
        DESCRIPTION
                "CMNT: - Logging state for CC708/OP47 ancillary data on input
                 TYPE: - Display
                 PAGE: - Logging1
                    CC708 Inp1=  cmdID= 42327  "
        ::= { iqupc00CmdEntry 42327 }


    iqupc00Logging1AncillaryDataLoggingLogARInp1 OBJECT-TYPE
        SYNTAX            INTEGER { disable(0), enable(1)  }
        MAX-ACCESS        read-write
        STATUS            current
        DESCRIPTION
                "CMNT: - Enable/Disable logging for ancillary data I/P aspect ratio
                 TYPE: - Checkbox
                 PAGE: - Logging1
                    Log AR Inp1  cmdID= 42176  "
        ::= { iqupc00CmdEntry 42176 }


    iqupc00Logging1AncillaryDataLoggingARInp1 OBJECT-TYPE
        SYNTAX            RollCallString
        MAX-ACCESS        read-only
        STATUS            current
        DESCRIPTION
                "CMNT: - Logging state for aspect ratio on input
                 TYPE: - Display
                 PAGE: - Logging1
                    AR Inp1  cmdID= 42376  "
        ::= { iqupc00CmdEntry 42376 }


    iqupc00Logging1AncillaryDataLoggingLogAFDInp1 OBJECT-TYPE
        SYNTAX            INTEGER { disable(0), enable(1)  }
        MAX-ACCESS        read-write
        STATUS            current
        DESCRIPTION
                "CMNT: - Enable/Disable logging for ancillary data I/P AFD
                 TYPE: - Checkbox
                 PAGE: - Logging1
                    Log AFD Inp1  cmdID= 42177  "
        ::= { iqupc00CmdEntry 42177 }


    iqupc00Logging1AncillaryDataLoggingAFDInp1 OBJECT-TYPE
        SYNTAX            RollCallString
        MAX-ACCESS        read-only
        STATUS            current
        DESCRIPTION
                "CMNT: - Logging state for AFD on input
                 TYPE: - Display
                 PAGE: - Logging1
                    AFD Inp1=  cmdID= 42377  "
        ::= { iqupc00CmdEntry 42377 }


    iqupc00Logging1AncillaryDataLoggingLogVIInp2 OBJECT-TYPE
        SYNTAX            INTEGER { disable(0), enable(1)  }
        MAX-ACCESS        read-write
        STATUS            current
        DESCRIPTION
                "CMNT: - Enable/Disable logging for ancillary data VI status
                 TYPE: - Checkbox
                 PAGE: - Logging1
                    Log VI Inp2  cmdID= 42180  "
        ::= { iqupc00CmdEntry 42180 }


    iqupc00Logging1AncillaryDataLoggingVIInp2 OBJECT-TYPE
        SYNTAX            RollCallString
        MAX-ACCESS        read-only
        STATUS            current
        DESCRIPTION
                "CMNT: - Logging state for VI ancillary data on input
                 TYPE: - Display
                 PAGE: - Logging1
                    VI Inp2=  cmdID= 42290  "
        ::= { iqupc00CmdEntry 42290 }


    iqupc00Logging1AncillaryDataLoggingLogWSSInp2 OBJECT-TYPE
        SYNTAX            INTEGER { disable(0), enable(1)  }
        MAX-ACCESS        read-write
        STATUS            current
        DESCRIPTION
                "CMNT: - Enable/Disable logging for ancillary data WSS status
                 TYPE: - Checkbox
                 PAGE: - Logging1
                    Log WSS Inp2  cmdID= 42181  "
        ::= { iqupc00CmdEntry 42181 }


    iqupc00Logging1AncillaryDataLoggingWSSInp2 OBJECT-TYPE
        SYNTAX            RollCallString
        MAX-ACCESS        read-only
        STATUS            current
        DESCRIPTION
                "CMNT: - Logging state for WSS ancillary data on input
                 TYPE: - Display
                 PAGE: - Logging1
                    WSS Inp2=  cmdID= 42291  "
        ::= { iqupc00CmdEntry 42291 }


    iqupc00Logging1AncillaryDataLoggingLogVITCInp2 OBJECT-TYPE
        SYNTAX            INTEGER { disable(0), enable(1)  }
        MAX-ACCESS        read-write
        STATUS            current
        DESCRIPTION
                "CMNT: - Enable/Disable logging for ancillary data VITC status
                 TYPE: - Checkbox
                 PAGE: - Logging1
                    Log VITC Inp2  cmdID= 42182  "
        ::= { iqupc00CmdEntry 42182 }


    iqupc00Logging1AncillaryDataLoggingVITCInp2 OBJECT-TYPE
        SYNTAX            RollCallString
        MAX-ACCESS        read-only
        STATUS            current
        DESCRIPTION
                "CMNT: - Logging state for VITC ancillary data on input
                 TYPE: - Display
                 PAGE: - Logging1
                    VITC Inp2=  cmdID= 42292  "
        ::= { iqupc00CmdEntry 42292 }


    iqupc00Logging1AncillaryDataLoggingLogWSTInp2 OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log WST Inp2  cmdID= 42183  "
        ::= { iqupc00CmdEntry 42183 }


    iqupc00Logging1AncillaryDataLoggingWSTInp2 OBJECT-TYPE
        SYNTAX            RollCallString
        MAX-ACCESS        read-only
        STATUS            current
        DESCRIPTION
                "CMNT: - Logging state for WST ancillary data on input
                 TYPE: - Display
                 PAGE: - Logging1
                    WST Inp2=  cmdID= 42293  "
        ::= { iqupc00CmdEntry 42293 }


    iqupc00Logging1AncillaryDataLoggingLogCC608Inp2 OBJECT-TYPE
        SYNTAX            INTEGER { disable(0), enable(1)  }
        MAX-ACCESS        read-write
        STATUS            current
        DESCRIPTION
                "CMNT: - Enable/Disable logging for ancillary data CC608 status
                 TYPE: - Checkbox
                 PAGE: - Logging1
                    Log CC608 Inp2  cmdID= 42184  "
        ::= { iqupc00CmdEntry 42184 }


    iqupc00Logging1AncillaryDataLoggingCC608Inp2 OBJECT-TYPE
        SYNTAX            RollCallString
        MAX-ACCESS        read-only
        STATUS            current
        DESCRIPTION
                "CMNT: - Logging state for CC608 ancillary data on input
                 TYPE: - Display
                 PAGE: - Logging1
                    CC608 Inp2=  cmdID= 42294  "
        ::= { iqupc00CmdEntry 42294 }


    iqupc00Logging1AncillaryDataLoggingLog2016Inp2 OBJECT-TYPE
        SYNTAX            INTEGER { disable(0), enable(1)  }
        MAX-ACCESS        read-write
        STATUS            current
        DESCRIPTION
                "CMNT: - Enable/Disable logging for ancillary data SMPTE2016 status
                 TYPE: - Checkbox
                 PAGE: - Logging1
                    Log 2016 Inp2  cmdID= 42185  "
        ::= { iqupc00CmdEntry 42185 }


    iqupc00Logging1AncillaryDataLogging2016Inp2 OBJECT-TYPE
        SYNTAX            RollCallString
        MAX-ACCESS        read-only
        STATUS            current
        DESCRIPTION
                "CMNT: - Logging state for SMPTE2016 ancillary data on input
                 TYPE: - Display
                 PAGE: - Logging1
                    2016 Inp2=  cmdID= 42295  "
        ::= { iqupc00CmdEntry 42295 }


    iqupc00Logging1AncillaryDataLoggingLogATCInp2 OBJECT-TYPE
        SYNTAX            INTEGER { disable(0), enable(1)  }
        MAX-ACCESS        read-write
        STATUS            current
        DESCRIPTION
                "CMNT: - Enable/Disable logging for ancillary data ATC status
                 TYPE: - Checkbox
                 PAGE: - Logging1
                    Log ATC Inp2  cmdID= 42186  "
        ::= { iqupc00CmdEntry 42186 }


    iqupc00Logging1AncillaryDataLoggingATCInp2 OBJECT-TYPE
        SYNTAX            RollCallString
        MAX-ACCESS        read-only
        STATUS            current
        DESCRIPTION
                "CMNT: - Logging state for ATC/VITC ancillary data on input
                 TYPE: - Display
                 PAGE: - Logging1
                    ATC Inp2=  cmdID= 42296  "
        ::= { iqupc00CmdEntry 42296 }


    iqupc00Logging1AncillaryDataLoggingLogCC708Inp2 OBJECT-TYPE
        SYNTAX            INTEGER { disable(0), enable(1)  }
        MAX-ACCESS        read-write
        STATUS            current
        DESCRIPTION
                "CMNT: - Enable/Disable logging for ancillary data CC708 status
                 TYPE: - Checkbox
                 PAGE: - Logging1
                    Log CC708 Inp2  cmdID= 42187  "
        ::= { iqupc00CmdEntry 42187 }


    iqupc00Logging1AncillaryDataLoggingCC708Inp2 OBJECT-TYPE
        SYNTAX            RollCallString
        MAX-ACCESS        read-only
        STATUS            current
        DESCRIPTION
                "CMNT: - Logging state for CC708/OP47 ancillary data on input
                 TYPE: - Display
                 PAGE: - Logging1
                    CC708 Inp2=  cmdID= 42297  "
        ::= { iqupc00CmdEntry 42297 }


    iqupc00Logging1AncillaryDataLoggingLogARInp2 OBJECT-TYPE
        SYNTAX            INTEGER { disable(0), enable(1)  }
        MAX-ACCESS        read-write
        STATUS            current
        DESCRIPTION
                "CMNT: - Enable/Disable logging for ancillary data I/P aspect ratio
                 TYPE: - Checkbox
                 PAGE: - Logging1
                    Log AR Inp2  cmdID= 42188  "
        ::= { iqupc00CmdEntry 42188 }


    iqupc00Logging1AncillaryDataLoggingARInp2 OBJECT-TYPE
        SYNTAX            RollCallString
        MAX-ACCESS        read-only
        STATUS            current
        DESCRIPTION
                "CMNT: - Logging state for aspect ratio on input
                 TYPE: - Display
                 PAGE: - Logging1
                    AR Inp2  cmdID= 42298  "
        ::= { iqupc00CmdEntry 42298 }


    iqupc00Logging1AncillaryDataLoggingLogAFDInp2 OBJECT-TYPE
        SYNTAX            INTEGER { disable(0), enable(1)  }
        MAX-ACCESS        read-write
        STATUS            current
        DESCRIPTION
                "CMNT: - Enable/Disable logging for ancillary data I/P AFD
                 TYPE: - Checkbox
                 PAGE: - Logging1
                    Log AFD Inp2  cmdID= 42199  "
        ::= { iqupc00CmdEntry 42199 }


    iqupc00Logging1AncillaryDataLoggingAFDInp2 OBJECT-TYPE
        SYNTAX            RollCallString
        MAX-ACCESS        read-only
        STATUS            current
        DESCRIPTION
                "CMNT: - Logging state for AFD on input
                 TYPE: - Display
                 PAGE: - Logging1
                    AFD Inp2=  cmdID= 42299  "
        ::= { iqupc00CmdEntry 42299 }


    iqupc00Logging1AncillaryDataLoggingLogOutput OBJECT-TYPE
        SYNTAX            INTEGER { disable(0), enable(1)  }
        MAX-ACCESS        read-write
        STATUS            current
        DESCRIPTION
                "CMNT: - Enable/Disable logging for ancillary data WST status
                 TYPE: - Checkbox
                 PAGE: - Logging1
                    Log Output  cmdID= 42128  "
        ::= { iqupc00CmdEntry 42128 }


    iqupc00Logging1AncillaryDataLoggingOutput OBJECT-TYPE
        SYNTAX            RollCallString
        MAX-ACCESS        read-only
        STATUS            current
        DESCRIPTION
                "CMNT: - Logging state for ancillary data on output
                 TYPE: - Display
                 PAGE: - Logging1
                    Output=  cmdID= 42328  "
        ::= { iqupc00CmdEntry 42328 }


    iqupc00Logging1AncillaryDataLoggingLogOPAR OBJECT-TYPE
        SYNTAX            INTEGER { disable(0), enable(1)  }
        MAX-ACCESS        read-write
        STATUS            current
        DESCRIPTION
                "CMNT: - Enable/Disable logging for ancillary data O/P aspect ratio
                 TYPE: - Checkbox
                 PAGE: - Logging1
                    Log O/P AR  cmdID= 42178  "
        ::= { iqupc00CmdEntry 42178 }


    iqupc00Logging1AncillaryDataLoggingOPAR OBJECT-TYPE
        SYNTAX            RollCallString
        MAX-ACCESS        read-only
        STATUS            current
        DESCRIPTION
                "CMNT: - Logging state for aspect ratio on output
                 TYPE: - Display
                 PAGE: - Logging1
                    O/P AR  cmdID= 42378  "
        ::= { iqupc00CmdEntry 42378 }


    iqupc00Logging1AncillaryDataLoggingLogOPAFD OBJECT-TYPE
        SYNTAX            INTEGER { disable(0), enable(1)  }
        MAX-ACCESS        read-write
        STATUS            current
        DESCRIPTION
                "CMNT: - Enable/Disable logging for ancillary dataO/P AFD
                 TYPE: - Checkbox
                 PAGE: - Logging1
                    Log O/P AFD  cmdID= 42179  "
        ::= { iqupc00CmdEntry 42179 }


    iqupc00Logging1AncillaryDataLoggingOPAFD OBJECT-TYPE
        SYNTAX            RollCallString
        MAX-ACCESS        read-only
        STATUS            current
        DESCRIPTION
                "CMNT: - Logging state for AFD on output
                 TYPE: - Display
                 PAGE: - Logging1
                    O/P AFD=  cmdID= 42379  "
        ::= { iqupc00CmdEntry 42379 }


    iqupc00Logging2VideoRefLogInp1Type OBJECT-TYPE
        SYNTAX            INTEGER { disable(0), enable(1)  }
        MAX-ACCESS        read-write
        STATUS            current
        DESCRIPTION
                "CMNT: - Enable/Disable logging for Inp 1, Type
                 TYPE: - Checkbox
                 PAGE: - Logging2
                    Log Inp1 Type  cmdID= 42060  "
        ::= { iqupc00CmdEntry 42060 }


    iqupc00Logging2VideoRefInp1Type OBJECT-TYPE
        SYNTAX            RollCallString
        MAX-ACCESS        read-only
        STATUS            current
        DESCRIPTION
                "CMNT: - Logging state for Inp 1 Type
                 TYPE: - Display
                 PAGE: - Logging2
                    Inp1 Type=  cmdID= 42260  "
        ::= { iqupc00CmdEntry 42260 }


    iqupc00Logging2VideoRefLogInp1State OBJECT-TYPE
        SYNTAX            INTEGER { disable(0), enable(1)  }
        MAX-ACCESS        read-write
        STATUS            current
        DESCRIPTION
                "CMNT: - Enable/Disable logging for Inp 1, State
                 TYPE: - Checkbox
                 PAGE: - Logging2
                    Log Inp1 State  cmdID= 42063  "
        ::= { iqupc00CmdEntry 42063 }


    iqupc00Logging2VideoRefInp1State OBJECT-TYPE
        SYNTAX            RollCallString
        MAX-ACCESS        read-only
        STATUS            current
        DESCRIPTION
                "CMNT: - Logging state for Inp 1 State
                 TYPE: - Display
                 PAGE: - Logging2
                    Inp1 State=  cmdID= 42263  "
        ::= { iqupc00CmdEntry 42263 }


    iqupc00Logging2VideoRefLogInp1Std OBJECT-TYPE
        SYNTAX            INTEGER { disable(0), enable(1)  }
        MAX-ACCESS        read-write
        STATUS            current
        DESCRIPTION
                "CMNT: - Enable/Disable logging for Inp 1, Standard
                 TYPE: - Checkbox
                 PAGE: - Logging2
                    Log Inp1 Std  cmdID= 42066  "
        ::= { iqupc00CmdEntry 42066 }


    iqupc00Logging2VideoRefInp1Std OBJECT-TYPE
        SYNTAX            RollCallString
        MAX-ACCESS        read-only
        STATUS            current
        DESCRIPTION
                "CMNT: - Logging state for Inp 1 Standard
                 TYPE: - Display
                 PAGE: - Logging2
                    Inp1 Std=  cmdID= 42266  "
        ::= { iqupc00CmdEntry 42266 }


    iqupc00Logging2VideoRefLogInp1SDIErrs OBJECT-TYPE
        SYNTAX            INTEGER { disable(0), enable(1)  }
        MAX-ACCESS        read-write
        STATUS            current
        DESCRIPTION
                "CMNT: - Enable/Disable logging for Inp 1, Sdi Errs
                 TYPE: - Checkbox
                 PAGE: - Logging2
                    Log Inp1 SDIErrs  cmdID= 42069  "
        ::= { iqupc00CmdEntry 42069 }


    iqupc00Logging2VideoRefInp1SDIErrs OBJECT-TYPE
        SYNTAX            RollCallString
        MAX-ACCESS        read-only
        STATUS            current
        DESCRIPTION
                "CMNT: - Logging state for Inp 1 Sdi Errs
                 TYPE: - Display
                 PAGE: - Logging2
                    Inp1 SDIErrs=  cmdID= 42269  "
        ::= { iqupc00CmdEntry 42269 }


    iqupc00Logging2VideoRefLogInp1SDIErrSec OBJECT-TYPE
        SYNTAX            INTEGER { disable(0), enable(1)  }
        MAX-ACCESS        read-write
        STATUS            current
        DESCRIPTION
                "CMNT: - Enable/Disable logging for Inp 1, Sdi Errs
                 TYPE: - Checkbox
                 PAGE: - Logging2
                    Log Inp1 SDIErrSec  cmdID= 42071  "
        ::= { iqupc00CmdEntry 42071 }


    iqupc00Logging2VideoRefInp1SDIErrSec OBJECT-TYPE
        SYNTAX            RollCallString
        MAX-ACCESS        read-only
        STATUS            current
        DESCRIPTION
                "CMNT: - Logging state for Inp 1 Sdi Errs
                 TYPE: - Display
                 PAGE: - Logging2
                    Inp1 SDIErrSec=  cmdID= 42271  "
        ::= { iqupc00CmdEntry 42271 }


    iqupc00Logging2VideoRefLogInp1ANCerrs OBJECT-TYPE
        SYNTAX            INTEGER { disable(0), enable(1)  }
        MAX-ACCESS        read-write
        STATUS            current
        DESCRIPTION
                "CMNT: - Enable/Disable logging for Inp 1, Sdi Anc Errs
                 TYPE: - Checkbox
                 PAGE: - Logging2
                    Log Inp1 ANCerrs  cmdID= 42073  "
        ::= { iqupc00CmdEntry 42073 }


    iqupc00Logging2VideoRefInp1ANCerrs OBJECT-TYPE
        SYNTAX            RollCallString
        MAX-ACCESS        read-only
        STATUS            current
        DESCRIPTION
                "CMNT: - Logging state for Inp 1 Sdi Anc Errs
                 TYPE: - Display
                 PAGE: - Logging2
                    Inp1 ANCerrs=  cmdID= 42273  "
        ::= { iqupc00CmdEntry 42273 }


    iqupc00Logging2VideoRefLogInp1ANCerrSec OBJECT-TYPE
        SYNTAX            INTEGER { disable(0), enable(1)  }
        MAX-ACCESS        read-write
        STATUS            current
        DESCRIPTION
                "CMNT: - Enable/Disable logging for Inp 1, Sdi Anc Errs
                 TYPE: - Checkbox
                 PAGE: - Logging2
                    Log Inp1 ANCerrSec  cmdID= 42075  "
        ::= { iqupc00CmdEntry 42075 }


    iqupc00Logging2VideoRefInp1ANCerrSec OBJECT-TYPE
        SYNTAX            RollCallString
        MAX-ACCESS        read-only
        STATUS            current
        DESCRIPTION
                "CMNT: - Logging state for Inp 1 Sdi Anc Errs
                 TYPE: - Display
                 PAGE: - Logging2
                    Inp1 ANCerrSec=  cmdID= 42275  "
        ::= { iqupc00CmdEntry 42275 }


    iqupc00Logging2VideoRefLogInp2Type OBJECT-TYPE
        SYNTAX            INTEGER { disable(0), enable(1)  }
        MAX-ACCESS        read-write
        STATUS            current
        DESCRIPTION
                "CMNT: - Enable/Disable logging for Inp 2, Type
                 TYPE: - Checkbox
                 PAGE: - Logging2
                    Log Inp2 Type  cmdID= 42061  "
        ::= { iqupc00CmdEntry 42061 }


    iqupc00Logging2VideoRefInp2Type OBJECT-TYPE
        SYNTAX            RollCallString
        MAX-ACCESS        read-only
        STATUS            current
        DESCRIPTION
                "CMNT: - Logging state for Inp 2 Type
                 TYPE: - Display
                 PAGE: - Logging2
                    Inp2 Type=  cmdID= 42261  "
        ::= { iqupc00CmdEntry 42261 }


    iqupc00Logging2VideoRefLogInp2State OBJECT-TYPE
        SYNTAX            INTEGER { disable(0), enable(1)  }
        MAX-ACCESS        read-write
        STATUS            current
        DESCRIPTION
                "CMNT: - Enable/Disable logging for Inp 2, State
                 TYPE: - Checkbox
                 PAGE: - Logging2
                    Log Inp2 State  cmdID= 42064  "
        ::= { iqupc00CmdEntry 42064 }


    iqupc00Logging2VideoRefInp2State OBJECT-TYPE
        SYNTAX            RollCallString
        MAX-ACCESS        read-only
        STATUS            current
        DESCRIPTION
                "CMNT: - Logging state for Inp 2 State
                 TYPE: - Display
                 PAGE: - Logging2
                    Inp2 State=  cmdID= 42264  "
        ::= { iqupc00CmdEntry 42264 }


    iqupc00Logging2VideoRefLogInp2Std OBJECT-TYPE
        SYNTAX            INTEGER { disable(0), enable(1)  }
        MAX-ACCESS        read-write
        STATUS            current
        DESCRIPTION
                "CMNT: - Enable/Disable logging for Inp 2, Standard
                 TYPE: - Checkbox
                 PAGE: - Logging2
                    Log Inp2 Std  cmdID= 42067  "
        ::= { iqupc00CmdEntry 42067 }


    iqupc00Logging2VideoRefInp2Std OBJECT-TYPE
        SYNTAX            RollCallString
        MAX-ACCESS        read-only
        STATUS            current
        DESCRIPTION
                "CMNT: - Logging state for Inp 2 Standard
                 TYPE: - Display
                 PAGE: - Logging2
                    Inp2 Std=  cmdID= 42267  "
        ::= { iqupc00CmdEntry 42267 }


    iqupc00Logging2VideoRefLogInp2SDIErrs OBJECT-TYPE
        SYNTAX            INTEGER { disable(0), enable(1)  }
        MAX-ACCESS        read-write
        STATUS            current
        DESCRIPTION
                "CMNT: - Enable/Disable logging for Inp 2, Sdi Errs
                 TYPE: - Checkbox
                 PAGE: - Logging2
                    Log Inp2 SDIErrs  cmdID= 42070  "
        ::= { iqupc00CmdEntry 42070 }


    iqupc00Logging2VideoRefInp2SDIErrs OBJECT-TYPE
        SYNTAX            RollCallString
        MAX-ACCESS        read-only
        STATUS            current
        DESCRIPTION
                "CMNT: - Logging state for Inp 2 Sdi Errs
                 TYPE: - Display
                 PAGE: - Logging2
                    Inp2 SDIErrs=  cmdID= 42270  "
        ::= { iqupc00CmdEntry 42270 }


    iqupc00Logging2VideoRefLogInp2SDIErrSec OBJECT-TYPE
        SYNTAX            INTEGER { disable(0), enable(1)  }
        MAX-ACCESS        read-write
        STATUS            current
        DESCRIPTION
                "CMNT: - Enable/Disable logging for Inp 2, Sdi Errs
                 TYPE: - Checkbox
                 PAGE: - Logging2
                    Log Inp2 SDIErrSec  cmdID= 42072  "
        ::= { iqupc00CmdEntry 42072 }


    iqupc00Logging2VideoRefInp2SDIErrSec OBJECT-TYPE
        SYNTAX            RollCallString
        MAX-ACCESS        read-only
        STATUS            current
        DESCRIPTION
                "CMNT: - Logging state for Inp 2 Sdi Errs
                 TYPE: - Display
                 PAGE: - Logging2
                    Inp2 SDIErrSec=  cmdID= 42272  "
        ::= { iqupc00CmdEntry 42272 }


    iqupc00Logging2VideoRefLogInp2ANCerrs OBJECT-TYPE
        SYNTAX            INTEGER { disable(0), enable(1)  }
        MAX-ACCESS        read-write
        STATUS            current
        DESCRIPTION
                "CMNT: - Enable/Disable logging for Inp 2, Sdi Anc Errs
                 TYPE: - Checkbox
                 PAGE: - Logging2
                    Log Inp2 ANCerrs  cmdID= 42074  "
        ::= { iqupc00CmdEntry 42074 }


    iqupc00Logging2VideoRefInp2ANCerrs OBJECT-TYPE
        SYNTAX            RollCallString
        MAX-ACCESS        read-only
        STATUS            current
        DESCRIPTION
                "CMNT: - Logging state for Inp 2 Sdi Anc Errs
                 TYPE: - Display
                 PAGE: - Logging2
                    Inp2 ANCerrs=  cmdID= 42274  "
        ::= { iqupc00CmdEntry 42274 }


    iqupc00Logging2VideoRefLogInp2ANCerrSec OBJECT-TYPE
        SYNTAX            INTEGER { disable(0), enable(1)  }
        MAX-ACCESS        read-write
        STATUS            current
        DESCRIPTION
                "CMNT: - Enable/Disable logging for Inp 2, Sdi Anc Errs
                 TYPE: - Checkbox
                 PAGE: - Logging2
                    Log Inp2 ANCerrSec  cmdID= 42076  "
        ::= { iqupc00CmdEntry 42076 }


    iqupc00Logging2VideoRefInp2ANCerrSec OBJECT-TYPE
        SYNTAX            RollCallString
        MAX-ACCESS        read-only
        STATUS            current
        DESCRIPTION
                "CMNT: - Logging state for Inp 2 Sdi Anc Errs
                 TYPE: - Display
                 PAGE: - Logging2
                    Inp2 ANCerrSec=  cmdID= 42276  "
        ::= { iqupc00CmdEntry 42276 }


    iqupc00Logging2VideoRefLogOutp1Type OBJECT-TYPE
        SYNTAX            INTEGER { disable(0), enable(1)  }
        MAX-ACCESS        read-write
        STATUS            current
        DESCRIPTION
                "CMNT: - Enable/Disable logging for Out 1, Type
                 TYPE: - Checkbox
                 PAGE: - Logging2
                    Log Outp1 Type  cmdID= 42077  "
        ::= { iqupc00CmdEntry 42077 }


    iqupc00Logging2VideoRefOutp1Type OBJECT-TYPE
        SYNTAX            RollCallString
        MAX-ACCESS        read-only
        STATUS            current
        DESCRIPTION
                "CMNT: - Logging state for Out 1 Type
                 TYPE: - Display
                 PAGE: - Logging2
                    Outp1 Type=  cmdID= 42277  "
        ::= { iqupc00CmdEntry 42277 }


    iqupc00Logging2VideoRefLogOutp1State OBJECT-TYPE
        SYNTAX            INTEGER { disable(0), enable(1)  }
        MAX-ACCESS        read-write
        STATUS            current
        DESCRIPTION
                "CMNT: - Enable/Disable logging for Out 1, State
                 TYPE: - Checkbox
                 PAGE: - Logging2
                    Log Outp1 State  cmdID= 42078  "
        ::= { iqupc00CmdEntry 42078 }


    iqupc00Logging2VideoRefOutp1State OBJECT-TYPE
        SYNTAX            RollCallString
        MAX-ACCESS        read-only
        STATUS            current
        DESCRIPTION
                "CMNT: - Logging state for Out 1 State
                 TYPE: - Display
                 PAGE: - Logging2
                    Outp1 State=  cmdID= 42278  "
        ::= { iqupc00CmdEntry 42278 }


    iqupc00Logging2VideoRefLogOutp1Std OBJECT-TYPE
        SYNTAX            INTEGER { disable(0), enable(1)  }
        MAX-ACCESS        read-write
        STATUS            current
        DESCRIPTION
                "CMNT: - Enable/Disable logging for Out 1, Standard
                 TYPE: - Checkbox
                 PAGE: - Logging2
                    Log Outp1 Std  cmdID= 42079  "
        ::= { iqupc00CmdEntry 42079 }


    iqupc00Logging2VideoRefOutp1Std OBJECT-TYPE
        SYNTAX            RollCallString
        MAX-ACCESS        read-only
        STATUS            current
        DESCRIPTION
                "CMNT: - Logging state for Out 1 Standard
                 TYPE: - Display
                 PAGE: - Logging2
                    Outp1 Std=  cmdID= 42279  "
        ::= { iqupc00CmdEntry 42279 }


    iqupc00Logging2VideoRefLogOutp2State OBJECT-TYPE
        SYNTAX            INTEGER { disable(0), enable(1)  }
        MAX-ACCESS        read-write
        STATUS            current
        DESCRIPTION
                "CMNT: - Enable/Disable logging for Out 1, State
                 TYPE: - Checkbox
                 PAGE: - Logging2
                    Log Outp2 State  cmdID= 42086  "
        ::= { iqupc00CmdEntry 42086 }


    iqupc00Logging2VideoRefOutp2State OBJECT-TYPE
        SYNTAX            RollCallString
        MAX-ACCESS        read-only
        STATUS            current
        DESCRIPTION
                "CMNT: - Logging state for Out 1 State
                 TYPE: - Display
                 PAGE: - Logging2
                    Outp2 State=  cmdID= 42286  "
        ::= { iqupc00CmdEntry 42286 }


    iqupc00Logging2VideoRefLogOutp2Std OBJECT-TYPE
        SYNTAX            INTEGER { disable(0), enable(1)  }
        MAX-ACCESS        read-write
        STATUS            current
        DESCRIPTION
                "CMNT: - Enable/Disable logging for Out 1, Standard
                 TYPE: - Checkbox
                 PAGE: - Logging2
                    Log Outp2 Std  cmdID= 42087  "
        ::= { iqupc00CmdEntry 42087 }


    iqupc00Logging2VideoRefOutp2Std OBJECT-TYPE
        SYNTAX            RollCallString
        MAX-ACCESS        read-only
        STATUS            current
        DESCRIPTION
                "CMNT: - Logging state for Out 1 Standard
                 TYPE: - Display
                 PAGE: - Logging2
                    Outp2 Std=  cmdID= 42287  "
        ::= { iqupc00CmdEntry 42287 }


    iqupc00Logging2VideoRefLogOutp1 OBJECT-TYPE
        SYNTAX            INTEGER { disable(0), enable(1)  }
        MAX-ACCESS        read-write
        STATUS            current
        DESCRIPTION
                "CMNT: - Enable/Disable logging for Out 1, 
                 TYPE: - Checkbox
                 PAGE: - Logging2
                    Log Outp1  cmdID= 42080  "
        ::= { iqupc00CmdEntry 42080 }


    iqupc00Logging2VideoRefOutp1 OBJECT-TYPE
        SYNTAX            RollCallString
        MAX-ACCESS        read-only
        STATUS            current
        DESCRIPTION
                "CMNT: - Logging state for Out 1 
                 TYPE: - Display
                 PAGE: - Logging2
                    Outp1=  cmdID= 42280  "
        ::= { iqupc00CmdEntry 42280 }


    iqupc00Logging2VideoRefLogOutp1Capt OBJECT-TYPE
        SYNTAX            INTEGER { disable(0), enable(1)  }
        MAX-ACCESS        read-write
        STATUS            current
        DESCRIPTION
                "CMNT: - Enable/Disable logging for Out 1 CAPTION 
                 TYPE: - Checkbox
                 PAGE: - Logging2
                    Log Outp1 Capt  cmdID= 42081  "
        ::= { iqupc00CmdEntry 42081 }


    iqupc00Logging2VideoRefOutp1Capt OBJECT-TYPE
        SYNTAX            RollCallString
        MAX-ACCESS        read-only
        STATUS            current
        DESCRIPTION
                "CMNT: - Logging state for Out 1 CAPTION
                 TYPE: - Display
                 PAGE: - Logging2
                    Outp1 Capt=  cmdID= 42281  "
        ::= { iqupc00CmdEntry 42281 }


    iqupc00Logging2VideoRefLogRefType OBJECT-TYPE
        SYNTAX            INTEGER { disable(0), enable(1)  }
        MAX-ACCESS        read-write
        STATUS            current
        DESCRIPTION
                "CMNT: - Enable/Disable logging for REFERENCE 1, Type
                 TYPE: - Checkbox
                 PAGE: - Logging2
                    Log Ref Type  cmdID= 42083  "
        ::= { iqupc00CmdEntry 42083 }


    iqupc00Logging2VideoRefRefType OBJECT-TYPE
        SYNTAX            RollCallString
        MAX-ACCESS        read-only
        STATUS            current
        DESCRIPTION
                "CMNT: - Logging state for REFERENCE 1 Type
                 TYPE: - Display
                 PAGE: - Logging2
                    Ref Type=  cmdID= 42283  "
        ::= { iqupc00CmdEntry 42283 }


    iqupc00Logging2VideoRefLogRefState OBJECT-TYPE
        SYNTAX            INTEGER { disable(0), enable(1)  }
        MAX-ACCESS        read-write
        STATUS            current
        DESCRIPTION
                "CMNT: - Enable/Disable logging for REFERENCE 1 STATE
                 TYPE: - Checkbox
                 PAGE: - Logging2
                    Log Ref State  cmdID= 42084  "
        ::= { iqupc00CmdEntry 42084 }


    iqupc00Logging2VideoRefRefState OBJECT-TYPE
        SYNTAX            RollCallString
        MAX-ACCESS        read-only
        STATUS            current
        DESCRIPTION
                "CMNT: - Logging state for REFERENCE 1 STATE
                 TYPE: - Display
                 PAGE: - Logging2
                    Ref State=  cmdID= 42284  "
        ::= { iqupc00CmdEntry 42284 }


    iqupc00Logging2VideoRefLogRefStd OBJECT-TYPE
        SYNTAX            INTEGER { disable(0), enable(1)  }
        MAX-ACCESS        read-write
        STATUS            current
        DESCRIPTION
                "CMNT: - Enable/Disable logging for REFERENCE 1 STANDARD
                 TYPE: - Checkbox
                 PAGE: - Logging2
                    Log Ref Std  cmdID= 42085  "
        ::= { iqupc00CmdEntry 42085 }


    iqupc00Logging2VideoRefRefStd OBJECT-TYPE
        SYNTAX            RollCallString
        MAX-ACCESS        read-only
        STATUS            current
        DESCRIPTION
                "CMNT: - Logging state for REFERENCE 1 STANDARD
                 TYPE: - Display
                 PAGE: - Logging2
                    Ref Std=  cmdID= 42285  "
        ::= { iqupc00CmdEntry 42285 }


    iqupc00Logging2VideoRefLogGenlockState OBJECT-TYPE
        SYNTAX            INTEGER { disable(0), enable(1)  }
        MAX-ACCESS        read-write
        STATUS            current
        DESCRIPTION
                "CMNT: - Enable/Disable logging for GENLOCK 1, State
                 TYPE: - Checkbox
                 PAGE: - Logging2
                    Log Genlock State  cmdID= 42082  "
        ::= { iqupc00CmdEntry 42082 }


    iqupc00Logging2VideoRefGenlocState OBJECT-TYPE
        SYNTAX            RollCallString
        MAX-ACCESS        read-only
        STATUS            current
        DESCRIPTION
                "CMNT: - Logging state for GENLOCK 1 State
                 TYPE: - Display
                 PAGE: - Logging2
                    Genloc State=  cmdID= 42282  "
        ::= { iqupc00CmdEntry 42282 }


    iqupc00Logging2VideoRefLogInp1Ident OBJECT-TYPE
        SYNTAX            INTEGER { disable(0), enable(1)  }
        MAX-ACCESS        read-write
        STATUS            current
        DESCRIPTION
                "CMNT: - Enable/Disable logging for Inp 1, Ident
                 TYPE: - Checkbox
                 PAGE: - Logging2
                    Log Inp1 Ident  cmdID= 42130  "
        ::= { iqupc00CmdEntry 42130 }


    iqupc00Logging2VideoRefInp1Ident OBJECT-TYPE
        SYNTAX            RollCallString
        MAX-ACCESS        read-only
        STATUS            current
        DESCRIPTION
                "CMNT: - Logging state for Inp 1 Ident
                 TYPE: - Display
                 PAGE: - Logging2
                    Inp1 Ident=  cmdID= 42330  "
        ::= { iqupc00CmdEntry 42330 }


    iqupc00Logging2VideoRefLogInp1Name OBJECT-TYPE
        SYNTAX            INTEGER { disable(0), enable(1)  }
        MAX-ACCESS        read-write
        STATUS            current
        DESCRIPTION
                "CMNT: - Enable/Disable logging for Inp 1, Name
                 TYPE: - Checkbox
                 PAGE: - Logging2
                    Log Inp1 Name  cmdID= 42133  "
        ::= { iqupc00CmdEntry 42133 }


    iqupc00Logging2VideoRefInp1Name OBJECT-TYPE
        SYNTAX            RollCallString
        MAX-ACCESS        read-only
        STATUS            current
        DESCRIPTION
                "CMNT: - Logging state for Inp 1 Name
                 TYPE: - Display
                 PAGE: - Logging2
                    Inp1 Name=  cmdID= 42333  "
        ::= { iqupc00CmdEntry 42333 }


    iqupc00Logging2VideoRefLogInp2Ident OBJECT-TYPE
        SYNTAX            INTEGER { disable(0), enable(1)  }
        MAX-ACCESS        read-write
        STATUS            current
        DESCRIPTION
                "CMNT: - Enable/Disable logging for Inp 2, Ident
                 TYPE: - Checkbox
                 PAGE: - Logging2
                    Log Inp2 Ident  cmdID= 42131  "
        ::= { iqupc00CmdEntry 42131 }


    iqupc00Logging2VideoRefInp2Ident OBJECT-TYPE
        SYNTAX            RollCallString
        MAX-ACCESS        read-only
        STATUS            current
        DESCRIPTION
                "CMNT: - Logging state for Inp 2 Ident
                 TYPE: - Display
                 PAGE: - Logging2
                    Inp2 Ident=  cmdID= 42331  "
        ::= { iqupc00CmdEntry 42331 }


    iqupc00Logging2VideoRefLogInp2Name OBJECT-TYPE
        SYNTAX            INTEGER { disable(0), enable(1)  }
        MAX-ACCESS        read-write
        STATUS            current
        DESCRIPTION
                "CMNT: - Enable/Disable logging for Inp 2, Name
                 TYPE: - Checkbox
                 PAGE: - Logging2
                    Log Inp2 Name  cmdID= 42134  "
        ::= { iqupc00CmdEntry 42134 }


    iqupc00Logging2VideoRefInp2Name OBJECT-TYPE
        SYNTAX            RollCallString
        MAX-ACCESS        read-only
        STATUS            current
        DESCRIPTION
                "CMNT: - Logging state for Inp 2 Name
                 TYPE: - Display
                 PAGE: - Logging2
                    Inp2 Name=  cmdID= 42334  "
        ::= { iqupc00CmdEntry 42334 }


    iqupc00Logging2VideoRefLogOutp2Type OBJECT-TYPE
        SYNTAX            INTEGER { disable(0), enable(1)  }
        MAX-ACCESS        read-write
        STATUS            current
        DESCRIPTION
                "CMNT: - Enable/Disable logging for Out 2, Type
                 TYPE: - Checkbox
                 PAGE: - Logging2
                    Log Outp2 Type  cmdID= 42620  "
        ::= { iqupc00CmdEntry 42620 }


    iqupc00Logging2VideoRefOutp2Type OBJECT-TYPE
        SYNTAX            RollCallString
        MAX-ACCESS        read-only
        STATUS            current
        DESCRIPTION
                "CMNT: - Logging state for Out 2 Type
                 TYPE: - Display
                 PAGE: - Logging2
                    Outp2 Type=  cmdID= 42820  "
        ::= { iqupc00CmdEntry 42820 }


    iqupc00Logging2VideoRefLogOutp2 OBJECT-TYPE
        SYNTAX            INTEGER { disable(0), enable(1)  }
        MAX-ACCESS        read-write
        STATUS            current
        DESCRIPTION
                "CMNT: - Enable/Disable logging for Out 2
                 TYPE: - Checkbox
                 PAGE: - Logging2
                    Log Outp2  cmdID= 42622  "
        ::= { iqupc00CmdEntry 42622 }


    iqupc00Logging2VideoRefOutp2 OBJECT-TYPE
        SYNTAX            RollCallString
        MAX-ACCESS        read-only
        STATUS            current
        DESCRIPTION
                "CMNT: - Logging state for Out 2
                 TYPE: - Display
                 PAGE: - Logging2
                    Outp2=  cmdID= 42822  "
        ::= { iqupc00CmdEntry 42822 }


    iqupc00Logging2VideoRefLogOutp2Capt OBJECT-TYPE
        SYNTAX            INTEGER { disable(0), enable(1)  }
        MAX-ACCESS        read-write
        STATUS            current
        DESCRIPTION
                "CMNT: - Enable/Disable logging for Out 2, Type
                 TYPE: - Checkbox
                 PAGE: - Logging2
                    Log Outp2 Capt  cmdID= 42624  "
        ::= { iqupc00CmdEntry 42624 }


    iqupc00Logging2VideoRefOutp2Capt OBJECT-TYPE
        SYNTAX            RollCallString
        MAX-ACCESS        read-only
        STATUS            current
        DESCRIPTION
                "CMNT: - Logging state for Out 2 Type
                 TYPE: - Display
                 PAGE: - Logging2
                    Outp2 Capt=  cmdID= 42824  "
        ::= { iqupc00CmdEntry 42824 }


    iqupc00Logging2InEmbAudLoggingInpEmb1state OBJECT-TYPE
        SYNTAX            RollCallString
        MAX-ACCESS        read-only
        STATUS            current
        DESCRIPTION
                "CMNT: - Logging state for Inp 1, Emb Pair 1 state
                 TYPE: - Display
                 PAGE: - Logging2
                    Inp Emb.1 state=  cmdID= 42200  "
        ::= { iqupc00CmdEntry 42200 }


    iqupc00Logging2InEmbAudLoggingInpEmb2state OBJECT-TYPE
        SYNTAX            RollCallString
        MAX-ACCESS        read-only
        STATUS            current
        DESCRIPTION
                "CMNT: - Logging state for Inp 1, Emb Pair 2 state
                 TYPE: - Display
                 PAGE: - Logging2
                    Inp Emb.2 state=  cmdID= 42201  "
        ::= { iqupc00CmdEntry 42201 }


    iqupc00Logging2InEmbAudLoggingInpEmb3state OBJECT-TYPE
        SYNTAX            RollCallString
        MAX-ACCESS        read-only
        STATUS            current
        DESCRIPTION
                "CMNT: - Logging state for Inp 1, Emb Pair 3 state
                 TYPE: - Display
                 PAGE: - Logging2
                    Inp Emb.3 state=  cmdID= 42202  "
        ::= { iqupc00CmdEntry 42202 }


    iqupc00Logging2InEmbAudLoggingInpEmb4state OBJECT-TYPE
        SYNTAX            RollCallString
        MAX-ACCESS        read-only
        STATUS            current
        DESCRIPTION
                "CMNT: - Logging state for Inp 1, Emb Pair 4 state
                 TYPE: - Display
                 PAGE: - Logging2
                    Inp Emb.4 state=  cmdID= 42203  "
        ::= { iqupc00CmdEntry 42203 }


    iqupc00Logging2InEmbAudLoggingInpEmb5state OBJECT-TYPE
        SYNTAX            RollCallString
        MAX-ACCESS        read-only
        STATUS            current
        DESCRIPTION
                "CMNT: - Logging state for Inp 1, Emb Pair 5 state
                 TYPE: - Display
                 PAGE: - Logging2
                    Inp Emb.5 state=  cmdID= 42204  "
        ::= { iqupc00CmdEntry 42204 }


    iqupc00Logging2InEmbAudLoggingInpEmb6state OBJECT-TYPE
        SYNTAX            RollCallString
        MAX-ACCESS        read-only
        STATUS            current
        DESCRIPTION
                "CMNT: - Logging state for Inp 1, Emb Pair 6 state
                 TYPE: - Display
                 PAGE: - Logging2
                    Inp Emb.6 state=  cmdID= 42205  "
        ::= { iqupc00CmdEntry 42205 }


    iqupc00Logging2InEmbAudLoggingInpEmb7state OBJECT-TYPE
        SYNTAX            RollCallString
        MAX-ACCESS        read-only
        STATUS            current
        DESCRIPTION
                "CMNT: - Logging state for Inp 1, Emb Pair 7 state
                 TYPE: - Display
                 PAGE: - Logging2
                    Inp Emb.7 state=  cmdID= 42206  "
        ::= { iqupc00CmdEntry 42206 }


    iqupc00Logging2InEmbAudLoggingInpEmb8state OBJECT-TYPE
        SYNTAX            RollCallString
        MAX-ACCESS        read-only
        STATUS            current
        DESCRIPTION
                "CMNT: - Logging state for Inp 1, Emb Pair 8 state
                 TYPE: - Display
                 PAGE: - Logging2
                    Inp Emb.8 state=  cmdID= 42207  "
        ::= { iqupc00CmdEntry 42207 }


    iqupc00Logging2In1EmbAudLoggingLogInp1Emb1state OBJECT-TYPE
        SYNTAX            INTEGER { disable(0), enable(1)  }
        MAX-ACCESS        read-write
        STATUS            current
        DESCRIPTION
                "CMNT: - Enable/Disable logging for Inp 1, Emb Pair 1 state
                 TYPE: - Checkbox
                 PAGE: - Logging2
                    Log Inp1 Emb.1 state  cmdID= 42139  "
        ::= { iqupc00CmdEntry 42139 }


    iqupc00Logging2In1EmbAudLoggingInp1Emb1state OBJECT-TYPE
        SYNTAX            RollCallString
        MAX-ACCESS        read-only
        STATUS            current
        DESCRIPTION
                "CMNT: - Logging state for Inp 1, Emb Pair 1 state
                 TYPE: - Display
                 PAGE: - Logging2
                    Inp1 Emb.1 state=  cmdID= 42339  "
        ::= { iqupc00CmdEntry 42339 }


    iqupc00Logging2In1EmbAudLoggingLogInp1Emb2state OBJECT-TYPE
        SYNTAX            INTEGER { disable(0), enable(1)  }
        MAX-ACCESS        read-write
        STATUS            current
        DESCRIPTION
                "CMNT: - Enable/Disable logging for Inp 1, Emb Pair 2 state
                 TYPE: - Checkbox
                 PAGE: - Logging2
                    Log Inp1 Emb.2 state  cmdID= 42140  "
        ::= { iqupc00CmdEntry 42140 }


    iqupc00Logging2In1EmbAudLoggingInp1Emb2state OBJECT-TYPE
        SYNTAX            RollCallString
        MAX-ACCESS        read-only
        STATUS            current
        DESCRIPTION
                "CMNT: - Logging state for Inp 1, Emb Pair 2 state
                 TYPE: - Display
                 PAGE: - Logging2
                    Inp1 Emb.2 state=  cmdID= 42340  "
        ::= { iqupc00CmdEntry 42340 }


    iqupc00Logging2In1EmbAudLoggingLogInp1Emb3state OBJECT-TYPE
        SYNTAX            INTEGER { disable(0), enable(1)  }
        MAX-ACCESS        read-write
        STATUS            current
        DESCRIPTION
                "CMNT: - Enable/Disable logging for Inp 1, Emb Pair 3 state
                 TYPE: - Checkbox
                 PAGE: - Logging2
                    Log Inp1 Emb.3 state  cmdID= 42141  "
        ::= { iqupc00CmdEntry 42141 }


    iqupc00Logging2In1EmbAudLoggingInp1Emb3state OBJECT-TYPE
        SYNTAX            RollCallString
        MAX-ACCESS        read-only
        STATUS            current
        DESCRIPTION
                "CMNT: - Logging state for Inp 1, Emb Pair 3 state
                 TYPE: - Display
                 PAGE: - Logging2
                    Inp1 Emb.3 state=  cmdID= 42341  "
        ::= { iqupc00CmdEntry 42341 }


    iqupc00Logging2In1EmbAudLoggingLogInp1Emb4state OBJECT-TYPE
        SYNTAX            INTEGER { disable(0), enable(1)  }
        MAX-ACCESS        read-write
        STATUS            current
        DESCRIPTION
                "CMNT: - Enable/Disable logging for Inp 1, Emb Pair 4 state
                 TYPE: - Checkbox
                 PAGE: - Logging2
                    Log Inp1 Emb.4 state  cmdID= 42142  "
        ::= { iqupc00CmdEntry 42142 }


    iqupc00Logging2In1EmbAudLoggingInp1Emb4state OBJECT-TYPE
        SYNTAX            RollCallString
        MAX-ACCESS        read-only
        STATUS            current
        DESCRIPTION
                "CMNT: - Logging state for Inp 1, Emb Pair 4 state
                 TYPE: - Display
                 PAGE: - Logging2
                    Inp1 Emb.4 state=  cmdID= 42342  "
        ::= { iqupc00CmdEntry 42342 }


    iqupc00Logging2In1EmbAudLoggingLogInp1Emb5state OBJECT-TYPE
        SYNTAX            INTEGER { disable(0), enable(1)  }
        MAX-ACCESS        read-write
        STATUS            current
        DESCRIPTION
                "CMNT: - Enable/Disable logging for Inp 1, Emb Pair 5 state
                 TYPE: - Checkbox
                 PAGE: - Logging2
                    Log Inp1 Emb.5 state  cmdID= 42143  "
        ::= { iqupc00CmdEntry 42143 }


    iqupc00Logging2In1EmbAudLoggingInp1Emb5state OBJECT-TYPE
        SYNTAX            RollCallString
        MAX-ACCESS        read-only
        STATUS            current
        DESCRIPTION
                "CMNT: - Logging state for Inp 1, Emb Pair 5 state
                 TYPE: - Display
                 PAGE: - Logging2
                    Inp1 Emb.5 state=  cmdID= 42343  "
        ::= { iqupc00CmdEntry 42343 }


    iqupc00Logging2In1EmbAudLoggingLogInp1Emb6state OBJECT-TYPE
        SYNTAX            INTEGER { disable(0), enable(1)  }
        MAX-ACCESS        read-write
        STATUS            current
        DESCRIPTION
                "CMNT: - Enable/Disable logging for Inp 1, Emb Pair 6 state
                 TYPE: - Checkbox
                 PAGE: - Logging2
                    Log Inp1 Emb.6 state  cmdID= 42144  "
        ::= { iqupc00CmdEntry 42144 }


    iqupc00Logging2In1EmbAudLoggingInp1Emb6state OBJECT-TYPE
        SYNTAX            RollCallString
        MAX-ACCESS        read-only
        STATUS            current
        DESCRIPTION
                "CMNT: - Logging state for Inp 1, Emb Pair 6 state
                 TYPE: - Display
                 PAGE: - Logging2
                    Inp1 Emb.6 state=  cmdID= 42344  "
        ::= { iqupc00CmdEntry 42344 }


    iqupc00Logging2In1EmbAudLoggingLogInp1Emb7state OBJECT-TYPE
        SYNTAX            INTEGER { disable(0), enable(1)  }
        MAX-ACCESS        read-write
        STATUS            current
        DESCRIPTION
                "CMNT: - Enable/Disable logging for Inp 1, Emb Pair 7 state
                 TYPE: - Checkbox
                 PAGE: - Logging2
                    Log Inp1 Emb.7 state  cmdID= 42145  "
        ::= { iqupc00CmdEntry 42145 }


    iqupc00Logging2In1EmbAudLoggingInp1Emb7state OBJECT-TYPE
        SYNTAX            RollCallString
        MAX-ACCESS        read-only
        STATUS            current
        DESCRIPTION
                "CMNT: - Logging state for Inp 1, Emb Pair 7 state
                 TYPE: - Display
                 PAGE: - Logging2
                    Inp1 Emb.7 state=  cmdID= 42345  "
        ::= { iqupc00CmdEntry 42345 }


    iqupc00Logging2In1EmbAudLoggingLogInp1Emb8state OBJECT-TYPE
        SYNTAX            INTEGER { disable(0), enable(1)  }
        MAX-ACCESS        read-write
        STATUS            current
        DESCRIPTION
                "CMNT: - Enable/Disable logging for Inp 1, Emb Pair 8 state
                 TYPE: - Checkbox
                 PAGE: - Logging2
                    Log Inp1 Emb.8 state  cmdID= 42146  "
        ::= { iqupc00CmdEntry 42146 }


    iqupc00Logging2In1EmbAudLoggingInp1Emb8state OBJECT-TYPE
        SYNTAX            RollCallString
        MAX-ACCESS        read-only
        STATUS            current
        DESCRIPTION
                "CMNT: - Logging state for Inp 1, Emb Pair 8 state
                 TYPE: - Display
                 PAGE: - Logging2
                    Inp1 Emb.8 state=  cmdID= 42346  "
        ::= { iqupc00CmdEntry 42346 }


    iqupc00Logging2In2EmbAudLoggingLogInp2Emb1state OBJECT-TYPE
        SYNTAX            INTEGER { disable(0), enable(1)  }
        MAX-ACCESS        read-write
        STATUS            current
        DESCRIPTION
                "CMNT: - Enable/Disable logging for Inp 2, Emb Pair 1 state
                 TYPE: - Checkbox
                 PAGE: - Logging2
                    Log Inp2 Emb.1 state  cmdID= 42147  "
        ::= { iqupc00CmdEntry 42147 }


    iqupc00Logging2In2EmbAudLoggingInp2Emb1state OBJECT-TYPE
        SYNTAX            RollCallString
        MAX-ACCESS        read-only
        STATUS            current
        DESCRIPTION
                "CMNT: - Logging state for Inp 2, Emb Pair 1 state
                 TYPE: - Display
                 PAGE: - Logging2
                    Inp2 Emb.1 state=  cmdID= 42347  "
        ::= { iqupc00CmdEntry 42347 }


    iqupc00Logging2In2EmbAudLoggingLogInp2Emb2state OBJECT-TYPE
        SYNTAX            INTEGER { disable(0), enable(1)  }
        MAX-ACCESS        read-write
        STATUS            current
        DESCRIPTION
                "CMNT: - Enable/Disable logging for Inp 2, Emb Pair 2 state
                 TYPE: - Checkbox
                 PAGE: - Logging2
                    Log Inp2 Emb.2 state  cmdID= 42148  "
        ::= { iqupc00CmdEntry 42148 }


    iqupc00Logging2In2EmbAudLoggingInp2Emb2state OBJECT-TYPE
        SYNTAX            RollCallString
        MAX-ACCESS        read-only
        STATUS            current
        DESCRIPTION
                "CMNT: - Logging state for Inp 2, Emb Pair 2 state
                 TYPE: - Display
                 PAGE: - Logging2
                    Inp2 Emb.2 state=  cmdID= 42348  "
        ::= { iqupc00CmdEntry 42348 }


    iqupc00Logging2In2EmbAudLoggingLogInp2Emb3state OBJECT-TYPE
        SYNTAX            INTEGER { disable(0), enable(1)  }
        MAX-ACCESS        read-write
        STATUS            current
        DESCRIPTION
                "CMNT: - Enable/Disable logging for Inp 2, Emb Pair 3 state
                 TYPE: - Checkbox
                 PAGE: - Logging2
                    Log Inp2 Emb.3 state  cmdID= 42149  "
        ::= { iqupc00CmdEntry 42149 }


    iqupc00Logging2In2EmbAudLoggingInp2Emb3state OBJECT-TYPE
        SYNTAX            RollCallString
        MAX-ACCESS        read-only
        STATUS            current
        DESCRIPTION
                "CMNT: - Logging state for Inp 2, Emb Pair 3 state
                 TYPE: - Display
                 PAGE: - Logging2
                    Inp2 Emb.3 state=  cmdID= 42349  "
        ::= { iqupc00CmdEntry 42349 }


    iqupc00Logging2In2EmbAudLoggingLogInp2Emb4state OBJECT-TYPE
        SYNTAX            INTEGER { disable(0), enable(1)  }
        MAX-ACCESS        read-write
        STATUS            current
        DESCRIPTION
                "CMNT: - Enable/Disable logging for Inp 2, Emb Pair 4 state
                 TYPE: - Checkbox
                 PAGE: - Logging2
                    Log Inp2 Emb.4 state  cmdID= 42150  "
        ::= { iqupc00CmdEntry 42150 }


    iqupc00Logging2In2EmbAudLoggingInp2Emb4state OBJECT-TYPE
        SYNTAX            RollCallString
        MAX-ACCESS        read-only
        STATUS            current
        DESCRIPTION
                "CMNT: - Logging state for Inp 2, Emb Pair 4 state
                 TYPE: - Display
                 PAGE: - Logging2
                    Inp2 Emb.4 state=  cmdID= 42350  "
        ::= { iqupc00CmdEntry 42350 }


    iqupc00Logging2In2EmbAudLoggingLogInp2Emb5state OBJECT-TYPE
        SYNTAX            INTEGER { disable(0), enable(1)  }
        MAX-ACCESS        read-write
        STATUS            current
        DESCRIPTION
                "CMNT: - Enable/Disable logging for Inp 2, Emb Pair 5 state
                 TYPE: - Checkbox
                 PAGE: - Logging2
                    Log Inp2 Emb.5 state  cmdID= 42151  "
        ::= { iqupc00CmdEntry 42151 }


    iqupc00Logging2In2EmbAudLoggingInp2Emb5state OBJECT-TYPE
        SYNTAX            RollCallString
        MAX-ACCESS        read-only
        STATUS            current
        DESCRIPTION
                "CMNT: - Logging state for Inp 2, Emb Pair 5 state
                 TYPE: - Display
                 PAGE: - Logging2
                    Inp2 Emb.5 state=  cmdID= 42351  "
        ::= { iqupc00CmdEntry 42351 }


    iqupc00Logging2In2EmbAudLoggingLogInp2Emb6state OBJECT-TYPE
        SYNTAX            INTEGER { disable(0), enable(1)  }
        MAX-ACCESS        read-write
        STATUS            current
        DESCRIPTION
                "CMNT: - Enable/Disable logging for Inp 2, Emb Pair 6 state
                 TYPE: - Checkbox
                 PAGE: - Logging2
                    Log Inp2 Emb.6 state  cmdID= 42152  "
        ::= { iqupc00CmdEntry 42152 }


    iqupc00Logging2In2EmbAudLoggingInp2Emb6state OBJECT-TYPE
        SYNTAX            RollCallString
        MAX-ACCESS        read-only
        STATUS            current
        DESCRIPTION
                "CMNT: - Logging state for Inp 2, Emb Pair 6 state
                 TYPE: - Display
                 PAGE: - Logging2
                    Inp2 Emb.6 state=  cmdID= 42352  "
        ::= { iqupc00CmdEntry 42352 }


    iqupc00Logging2In2EmbAudLoggingLogInp2Emb7state OBJECT-TYPE
        SYNTAX            INTEGER { disable(0), enable(1)  }
        MAX-ACCESS        read-write
        STATUS            current
        DESCRIPTION
                "CMNT: - Enable/Disable logging for Inp 2, Emb Pair 7 state
                 TYPE: - Checkbox
                 PAGE: - Logging2
                    Log Inp2 Emb.7 state  cmdID= 42153  "
        ::= { iqupc00CmdEntry 42153 }


    iqupc00Logging2In2EmbAudLoggingInp2Emb7state OBJECT-TYPE
        SYNTAX            RollCallString
        MAX-ACCESS        read-only
        STATUS            current
        DESCRIPTION
                "CMNT: - Logging state for Inp 2, Emb Pair 7 state
                 TYPE: - Display
                 PAGE: - Logging2
                    Inp2 Emb.7 state=  cmdID= 42353  "
        ::= { iqupc00CmdEntry 42353 }


    iqupc00Logging2In2EmbAudLoggingLogInp2Emb8state OBJECT-TYPE
        SYNTAX            INTEGER { disable(0), enable(1)  }
        MAX-ACCESS        read-write
        STATUS            current
        DESCRIPTION
                "CMNT: - Enable/Disable logging for Inp 2, Emb Pair 8 state
                 TYPE: - Checkbox
                 PAGE: - Logging2
                    Log Inp2 Emb.8 state  cmdID= 42154  "
        ::= { iqupc00CmdEntry 42154 }


    iqupc00Logging2In2EmbAudLoggingInp2Emb8state OBJECT-TYPE
        SYNTAX            RollCallString
        MAX-ACCESS        read-only
        STATUS            current
        DESCRIPTION
                "CMNT: - Logging state for Inp 2, Emb Pair 8 state
                 TYPE: - Display
                 PAGE: - Logging2
                    Inp2 Emb.8 state=  cmdID= 42354  "
        ::= { iqupc00CmdEntry 42354 }


    iqupc00Logging2DolbyEAlignLogOutEmb1dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.1 dolby  cmdID= 42160  "
        ::= { iqupc00CmdEntry 42160 }


    iqupc00Logging2DolbyEAlignOutEmb1Dolby OBJECT-TYPE
        SYNTAX            RollCallString
        MAX-ACCESS        read-only
        STATUS            current
        DESCRIPTION
                "CMNT: - Logging state for Outp 1, Emb Dolby
                 TYPE: - Display
                 PAGE: - Logging2
                    Out Emb.1 Dolby=  cmdID= 42360  "
        ::= { iqupc00CmdEntry 42360 }


    iqupc00Logging2DolbyEAlignLogOutEmb2dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.2 dolby  cmdID= 42161  "
        ::= { iqupc00CmdEntry 42161 }


    iqupc00Logging2DolbyEAlignOutEmb2Dolby OBJECT-TYPE
        SYNTAX            RollCallString
        MAX-ACCESS        read-only
        STATUS            current
        DESCRIPTION
                "CMNT: - Logging state for Outp 1, Emb Dolby
                 TYPE: - Display
                 PAGE: - Logging2
                    Out Emb.2 Dolby=  cmdID= 42361  "
        ::= { iqupc00CmdEntry 42361 }


    iqupc00Logging2DolbyEAlignLogOutEmb3dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.3 dolby  cmdID= 42162  "
        ::= { iqupc00CmdEntry 42162 }


    iqupc00Logging2DolbyEAlignOutEmb3Dolby OBJECT-TYPE
        SYNTAX            RollCallString
        MAX-ACCESS        read-only
        STATUS            current
        DESCRIPTION
                "CMNT: - Logging state for Outp 1, Emb Dolby
                 TYPE: - Display
                 PAGE: - Logging2
                    Out Emb.3 Dolby=  cmdID= 42362  "
        ::= { iqupc00CmdEntry 42362 }


    iqupc00Logging2DolbyEAlignLogOutEmb4dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.4 dolby  cmdID= 42163  "
        ::= { iqupc00CmdEntry 42163 }


    iqupc00Logging2DolbyEAlignOutEmb4Dolby OBJECT-TYPE
        SYNTAX            RollCallString
        MAX-ACCESS        read-only
        STATUS            current
        DESCRIPTION
                "CMNT: - Logging state for Outp 1, Emb Dolby
                 TYPE: - Display
                 PAGE: - Logging2
                    Out Emb.4 Dolby=  cmdID= 42363  "
        ::= { iqupc00CmdEntry 42363 }


    iqupc00Logging2DolbyEAlignLogOutEmb5dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.5 dolby  cmdID= 42164  "
        ::= { iqupc00CmdEntry 42164 }


    iqupc00Logging2DolbyEAlignOutEmb5Dolby OBJECT-TYPE
        SYNTAX            RollCallString
        MAX-ACCESS        read-only
        STATUS            current
        DESCRIPTION
                "CMNT: - Logging state for Outp 1, Emb Dolby
                 TYPE: - Display
                 PAGE: - Logging2
                    Out Emb.5 Dolby=  cmdID= 42364  "
        ::= { iqupc00CmdEntry 42364 }


    iqupc00Logging2DolbyEAlignLogOutEmb6dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.6 dolby  cmdID= 42165  "
        ::= { iqupc00CmdEntry 42165 }


    iqupc00Logging2DolbyEAlignOutEmb6Dolby OBJECT-TYPE
        SYNTAX            RollCallString
        MAX-ACCESS        read-only
        STATUS            current
        DESCRIPTION
                "CMNT: - Logging state for Outp 1, Emb Dolby
                 TYPE: - Display
                 PAGE: - Logging2
                    Out Emb.6 Dolby=  cmdID= 42365  "
        ::= { iqupc00CmdEntry 42365 }


    iqupc00Logging2DolbyEAlignLogOutEmb7dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.7 dolby  cmdID= 42166  "
        ::= { iqupc00CmdEntry 42166 }


    iqupc00Logging2DolbyEAlignOutEmb7Dolby OBJECT-TYPE
        SYNTAX            RollCallString
        MAX-ACCESS        read-only
        STATUS            current
        DESCRIPTION
                "CMNT: - Logging state for Outp 1, Emb Dolby
                 TYPE: - Display
                 PAGE: - Logging2
                    Out Emb.7 Dolby=  cmdID= 42366  "
        ::= { iqupc00CmdEntry 42366 }


    iqupc00Logging2DolbyEAlignLogOutEmb8dolby OBJECT-TYPE
        SYNTAX            INTEGER { disable(0), enable(1)  }
        MAX-ACCESS        read-write
        STATUS            current
        DESCRIPTION
                "CMNT: - Enable/Disable logging for Out1 Dolby
                 TYPE: - Checkbox
                 PAGE: - Logging2
                    Log Out Emb.8 dolby  cmdID= 42167  "
        ::= { iqupc00CmdEntry 42167 }


    iqupc00Logging2DolbyEAlignOutEmb8Dolby OBJECT-TYPE
        SYNTAX            RollCallString
        MAX-ACCESS        read-only
        STATUS            current
        DESCRIPTION
                "CMNT: - Logging state for Outp 1, Emb Dolby
                 TYPE: - Display
                 PAGE: - Logging2
                    Out Emb.8 Dolby=  cmdID= 42367  "
        ::= { iqupc00CmdEntry 42367 }


    iqupc00Logging2MiscLoggingLogSerialNo OBJECT-TYPE
        SYNTAX            INTEGER { disable(0), enable(1)  }
        MAX-ACCESS        read-write
        STATUS            current
        DESCRIPTION
                "CMNT: - Enable/Disable logging for Serial No.
                 TYPE: - Checkbox
                 PAGE: - Logging2
                    Log Serial No.  cmdID= 35015  "
        ::= { iqupc00CmdEntry 35015 }


    iqupc00Logging2MiscLoggingSerialNo OBJECT-TYPE
        SYNTAX            RollCallString
        MAX-ACCESS        read-only
        STATUS            current
        DESCRIPTION
                "CMNT: - Logging state for Serial No.
                 TYPE: - Display
                 PAGE: - Logging2
                    Serial No.=  cmdID= 36015  "
        ::= { iqupc00CmdEntry 36015 }


    iqupc00Logging2MiscLoggingLogOSVersion OBJECT-TYPE
        SYNTAX            INTEGER { disable(0), enable(1)  }
        MAX-ACCESS        read-write
        STATUS            current
        DESCRIPTION
                "CMNT: - Enable/Disable logging for OS Version
                 TYPE: - Checkbox
                 PAGE: - Logging2
                    Log OS Version  cmdID= 35993  "
        ::= { iqupc00CmdEntry 35993 }


    iqupc00Logging2MiscLoggingOSVersion OBJECT-TYPE
        SYNTAX            RollCallString
        MAX-ACCESS        read-only
        STATUS            current
        DESCRIPTION
                "CMNT: - Logging state for OS Version
                 TYPE: - Display
                 PAGE: - Logging2
                    OS Version=  cmdID= 36993  "
        ::= { iqupc00CmdEntry 36993 }


    iqupc00Logging2MiscLoggingLogBuildNo OBJECT-TYPE
        SYNTAX            INTEGER { disable(0), enable(1)  }
        MAX-ACCESS        read-write
        STATUS            current
        DESCRIPTION
                "CMNT: - Enable/Disable logging for Build No.
                 TYPE: - Checkbox
                 PAGE: - Logging2
                    Log Build No.  cmdID= 35990  "
        ::= { iqupc00CmdEntry 35990 }


    iqupc00Logging2MiscLoggingBuildNo OBJECT-TYPE
        SYNTAX            RollCallString
        MAX-ACCESS        read-only
        STATUS            current
        DESCRIPTION
                "CMNT: - Logging state for Build No.
                 TYPE: - Display
                 PAGE: - Logging2
                    Build No.=  cmdID= 36990  "
        ::= { iqupc00CmdEntry 36990 }


    iqupc00Logging2MiscLoggingLogHardwareVer OBJECT-TYPE
        SYNTAX            INTEGER { disable(0), enable(1)  }
        MAX-ACCESS        read-write
        STATUS            current
        DESCRIPTION
                "CMNT: - Enable/Disable logging for Hardware Ver.
                 TYPE: - Checkbox
                 PAGE: - Logging2
                    Log Hardware Ver.  cmdID= 35992  "
        ::= { iqupc00CmdEntry 35992 }


    iqupc00Logging2MiscLoggingHardwareVer OBJECT-TYPE
        SYNTAX            RollCallString
        MAX-ACCESS        read-only
        STATUS            current
        DESCRIPTION
                "CMNT: - Logging state for Hardware Ver.
                 TYPE: - Display
                 PAGE: - Logging2
                    Hardware Ver.=  cmdID= 36992  "
        ::= { iqupc00CmdEntry 36992 }


    iqupc00Logging2MiscLoggingLogFirmwareVer OBJECT-TYPE
        SYNTAX            INTEGER { disable(0), enable(1)  }
        MAX-ACCESS        read-write
        STATUS            current
        DESCRIPTION
                "CMNT: - Enable/Disable logging for Firmware Ver.
                 TYPE: - Checkbox
                 PAGE: - Logging2
                    Log Firmware Ver.  cmdID= 35991  "
        ::= { iqupc00CmdEntry 35991 }


    iqupc00Logging2MiscLoggingFirmwareVer OBJECT-TYPE
        SYNTAX            RollCallString
        MAX-ACCESS        read-only
        STATUS            current
        DESCRIPTION
                "CMNT: - Logging state for Firmware Ver.
                 TYPE: - Display
                 PAGE: - Logging2
                    Firmware Ver.=  cmdID= 36991  "
        ::= { iqupc00CmdEntry 36991 }


    iqupc00Logging2MiscLoggingLogUpTime OBJECT-TYPE
        SYNTAX            INTEGER { disable(0), enable(1)  }
        MAX-ACCESS        read-write
        STATUS            current
        DESCRIPTION
                "CMNT: - Enable/Disable logging for Up Time
                 TYPE: - Checkbox
                 PAGE: - Logging2
                    Log Up Time  cmdID= 35994  "
        ::= { iqupc00CmdEntry 35994 }


    iqupc00Logging2MiscLoggingUpTime OBJECT-TYPE
        SYNTAX            RollCallString
        MAX-ACCESS        read-only
        STATUS            current
        DESCRIPTION
                "CMNT: - Logging state for Up Time
                 TYPE: - Display
                 PAGE: - Logging2
                    Up Time=  cmdID= 36994  "
        ::= { iqupc00CmdEntry 36994 }


    iqupc00Logging2MiscLoggingLogLicensedOpt OBJECT-TYPE
        SYNTAX            INTEGER { disable(0), enable(1)  }
        MAX-ACCESS        read-write
        STATUS            current
        DESCRIPTION
                "CMNT: - Enable/Disable logging for Display Licensed Options
                 TYPE: - Checkbox
                 PAGE: - Logging2
                    Log Licensed Opt.  cmdID= 35995  "
        ::= { iqupc00CmdEntry 35995 }


    iqupc00Logging2MiscLoggingLicensedOptions OBJECT-TYPE
        SYNTAX            RollCallString
        MAX-ACCESS        read-only
        STATUS            current
        DESCRIPTION
                "CMNT: - Logging Licened Options
                 TYPE: - Display
                 PAGE: - Logging2
                    Licensed Options   cmdID= 36995  "
        ::= { iqupc00CmdEntry 36995 }


    iqupc00Logging2MiscLoggingLogLicensedOpt2 OBJECT-TYPE
        SYNTAX            INTEGER { disable(0), enable(1)  }
        MAX-ACCESS        read-write
        STATUS            current
        DESCRIPTION
                "CMNT: - Enable/Disable logging for Display Licensed Options
                 TYPE: - Checkbox
                 PAGE: - Logging2
                    Log Licensed Opt2.  cmdID= 35996  "
        ::= { iqupc00CmdEntry 35996 }


    iqupc00Logging2MiscLoggingLicensedOptions2 OBJECT-TYPE
        SYNTAX            RollCallString
        MAX-ACCESS        read-only
        STATUS            current
        DESCRIPTION
                "CMNT: - Logging Licened Options
                 TYPE: - Display
                 PAGE: - Logging2
                    Licensed Options 2  cmdID= 36996  "
        ::= { iqupc00CmdEntry 36996 }


    iqupc00Logging2MiscLoggingLogTemp1State OBJECT-TYPE
        SYNTAX            INTEGER { disable(0), enable(1)  }
        MAX-ACCESS        read-write
        STATUS            current
        DESCRIPTION
                "CMNT: - Enable/Disable logging for TEMP 1 STATE
                 TYPE: - Checkbox
                 PAGE: - Logging2
                    Log Temp1State  cmdID= 42137  "
        ::= { iqupc00CmdEntry 42137 }


    iqupc00Logging2MiscLoggingTemp1State OBJECT-TYPE
        SYNTAX            RollCallString
        MAX-ACCESS        read-only
        STATUS            current
        DESCRIPTION
                "CMNT: - Logging state for TEMP_1_STATE
                 TYPE: - Display
                 PAGE: - Logging2
                    Temp1State=  cmdID= 42337  "
        ::= { iqupc00CmdEntry 42337 }


    iqupc00Logging2MiscLoggingLogTemp1Name OBJECT-TYPE
        SYNTAX            INTEGER { disable(0), enable(1)  }
        MAX-ACCESS        read-write
        STATUS            current
        DESCRIPTION
                "CMNT: - Enable/Disable logging for TEMP 1 NAME
                 TYPE: - Checkbox
                 PAGE: - Logging2
                    Log Temp1Name  cmdID= 42138  "
        ::= { iqupc00CmdEntry 42138 }


    iqupc00Logging2MiscLoggingTemp1Name OBJECT-TYPE
        SYNTAX            RollCallString
        MAX-ACCESS        read-only
        STATUS            current
        DESCRIPTION
                "CMNT: - Logging state for TEMP_1_NAME
                 TYPE: - Display
                 PAGE: - Logging2
                    Temp1Name=  cmdID= 42338  "
        ::= { iqupc00CmdEntry 42338 }


    iqupc00Logging2MiscLoggingLogRearId OBJECT-TYPE
        SYNTAX            INTEGER { disable(0), enable(1)  }
        MAX-ACCESS        read-write
        STATUS            current
        DESCRIPTION
                "CMNT: - Enable/Disable logging for Display Rear Id
                 TYPE: - Checkbox
                 PAGE: - Logging2
                    Log RearId  cmdID= 35997  "
        ::= { iqupc00CmdEntry 35997 }


    iqupc00Logging2MiscLoggingRearID OBJECT-TYPE
        SYNTAX            RollCallString
        MAX-ACCESS        read-only
        STATUS            current
        DESCRIPTION
                "CMNT: - Logging Rear ID
                 TYPE: - Display
                 PAGE: - Logging2
                    RearID=  cmdID= 36997  "
        ::= { iqupc00CmdEntry 36997 }


    iqupc00Logging2MiscLoggingLogSlotWidth OBJECT-TYPE
        SYNTAX            INTEGER { disable(0), enable(1)  }
        MAX-ACCESS        read-write
        STATUS            current
        DESCRIPTION
                "CMNT: - Enable/Disable logging for Display Slot Width
                 TYPE: - Checkbox
                 PAGE: - Logging2
                    Log Slot Width  cmdID= 35998  "
        ::= { iqupc00CmdEntry 35998 }


    iqupc00Logging2MiscLoggingSlotWidth OBJECT-TYPE
        SYNTAX            RollCallString
        MAX-ACCESS        read-only
        STATUS            current
        DESCRIPTION
                "CMNT: - Logging Slot width
                 TYPE: - Display
                 PAGE: - Logging2
                    SlotWidth=  cmdID= 36998  "
        ::= { iqupc00CmdEntry 36998 }


    iqupc00Logging2MiscLoggingLogSlotStart OBJECT-TYPE
        SYNTAX            INTEGER { disable(0), enable(1)  }
        MAX-ACCESS        read-write
        STATUS            current
        DESCRIPTION
                "CMNT: - Enable/Disable logging for Display Slot Start
                 TYPE: - Checkbox
                 PAGE: - Logging2
                    Log Slot Start  cmdID= 35999  "
        ::= { iqupc00CmdEntry 35999 }


    iqupc00Logging2MiscLoggingSlotStart OBJECT-TYPE
        SYNTAX            RollCallString
        MAX-ACCESS        read-only
        STATUS            current
        DESCRIPTION
                "CMNT: - Logging Slot start
                 TYPE: - Display
                 PAGE: - Logging2
                    SlotStart=  cmdID= 36999  "
        ::= { iqupc00CmdEntry 36999 }


    iqupc00Logging2MiscLoggingLogRearStatus OBJECT-TYPE
        SYNTAX            INTEGER { disable(0), enable(1)  }
        MAX-ACCESS        read-write
        STATUS            current
        DESCRIPTION
                "CMNT: - Enable/Disable logging for Display Rear Status
                 TYPE: - Checkbox
                 PAGE: - Logging2
                    Log RearStatus  cmdID= 36000  "
        ::= { iqupc00CmdEntry 36000 }


    iqupc00Logging2MiscLoggingRearSTATUS OBJECT-TYPE
        SYNTAX            RollCallString
        MAX-ACCESS        read-only
        STATUS            current
        DESCRIPTION
                "CMNT: - Logging Rear Status
                 TYPE: - Display
                 PAGE: - Logging2
                    RearSTATUS=  cmdID= 37000  "
        ::= { iqupc00CmdEntry 37000 }


    iqupc00RollCallMemoriesRollTrackDisableAll OBJECT-TYPE
        SYNTAX            INTEGER { disable(0), enable(1)  }
        MAX-ACCESS        read-write
        STATUS            current
        DESCRIPTION
                "CMNT: - Disable all rolltrack outputs
                 TYPE: - Checkbox
                 PAGE: - RollCall/Memories
                    Disable All  cmdID= 36104  "
        ::= { iqupc00CmdEntry 36104 }


    iqupc00RollCallMemoriesRollTrackIndex OBJECT-TYPE
        SYNTAX            INTEGER
        MAX-ACCESS        read-write
        STATUS            current
        DESCRIPTION
                "CMNT: - Select rolltrack to edit
                 TYPE: - BarGraph
                 PAGE: - RollCall/Memories
                    Index  cmdID= 36100
                    min= 1  max= 32  step= 1  format= %0.0f  div_scale= 1  preset= 1
                    Min = 1  Max = 32  Step = 1  Preset = 1  "
        ::= { iqupc00CmdEntry 36100 }


    iqupc00RollCallMemoriesRollTrackSource OBJECT-TYPE
        SYNTAX            INTEGER {
                            valUnused(-1),
                            valVideoDelay(0),
                            valInputPresent(2),
                            valInput1Present(3),
                            valInput2Present(4),
                            valAnalogPresent(5),
                            valInputLoss(6),
                            valInput1Loss(7),
                            valInput2Loss(8),
                            valAnalogLoss(9),
                            valInput1Select(10),
                            valInput2Select(11),
                            valAnalogSelect(12),
                            valInput108059p(13),
                            valInput108050p(14),
                            valInput108029i(15),
                            valInput108025i(16),
                            valInput72059p(17),
                            valInput72050p(18),
                            valInput52529i(19),
                            valInput62525i(20),
                            valOutputBlackOn(21),
                            valOutputBlackOff(22),
                            valOutputFreeze(23),
                            valOutputUnFreeze(24),
                            valOutputPatternOn(25),
                            valOutputPatternOff(26),
                            valOutputCaptionOn(27),
                            valOutputCaptionOff(28),
                            valReferenceOK(29),
                            valReferenceLoss(30),
                            valAES1PCM(31),
                            valAES1Data(32),
                            valAES1DolbyE(33),
                            valAES1Loss(34),
                            valAES2PCM(35),
                            valAES2Data(36),
                            valAES2DolbyE(37),
                            valAES2Loss(38),
                            valAES3PCM(39),
                            valAES3Data(40),
                            valAES3DolbyE(41),
                            valAES3Loss(42),
                            valAES4PCM(43),
                            valAES4Data(44),
                            valAES4DolbyE(45),
                            valAES4Loss(46),
                            valAES5PCM(47),
                            valAES5Data(48),
                            valAES5DolbyE(49),
                            valAES5Loss(50),
                            valAES6PCM(51),
                            valAES6Data(52),
                            valAES6DolbyE(53),
                            valAES6Loss(54),
                            valAES7PCM(55),
                            valAES7Data(56),
                            valAES7DolbyE(57),
                            valAES7Loss(58),
                            valAES8PCM(59),
                            valAES8Data(60),
                            valAES8DolbyE(61),
                            valAES8Loss(62),
                            valDisemb1PCM(63),
                            valDisemb1Data(64),
                            valDisemb1DolbyE(65),
                            valDisemb1Loss(66),
                            valDisemb2PCM(67),
                            valDisemb2Data(68),
                            valDisemb2DolbyE(69),
                            valDisemb2Loss(70),
                            valDisemb3PCM(71),
                            valDisemb3Data(72),
                            valDisemb3DolbyE(73),
                            valDisemb3Loss(74),
                            valDisemb4PCM(75),
                            valDisemb4Data(76),
                            valDisemb4DolbyE(77),
                            valDisemb4Loss(78),
                            valDisemb5PCM(79),
                            valDisemb5Data(80),
                            valDisemb5DolbyE(81),
                            valDisemb5Loss(82),
                            valDisemb6PCM(83),
                            valDisemb6Data(84),
                            valDisemb6DolbyE(85),
                            valDisemb6Loss(86),
                            valDisemb7PCM(87),
                            valDisemb7Data(88),
                            valDisemb7DolbyE(89),
                            valDisemb7Loss(90),
                            valDisemb8PCM(91),
                            valDisemb8Data(92),
                            valDisemb8DolbyE(93),
                            valDisemb8Loss(94),
                            valDecoderIPDolbyD(95),
                            valDecoderIPDolbyE(96),
                            valDecoderIPPCM(97),
                            valDecoderIPNoErr(98),
                            valDecoderIPError(99),
                            valExtMetaAbsent(100),
                            valExtMetaInvalid(101),
                            valExtMetaNoAC3(102),
                            valExtMetaNoBSI(103),
                            valExtMetaValid(104),
                            valVideoSyncOK(105),
                            valVideoSyncLoss(106),
                            valEncoderActive(107),
                            valEncoderStopped(108),
                            valEncoderPassthru(109)
                            }
        MAX-ACCESS        read-write
        STATUS            current
        DESCRIPTION
                "CMNT: - Source for Rolltrack
                 TYPE: - RadiobuttonList
                 PAGE: - RollCall/Memories
                    Source  cmdID= 36101
                    Unused  value= -1
                    Video Delay  value= 0
                    Input Present  value= 2
                    Input 1 Present  value= 3
                    Input 2 Present  value= 4
                    Analog Present  value= 5
                    Input Loss  value= 6
                    Input 1 Loss  value= 7
                    Input 2 Loss  value= 8
                    Analog Loss  value= 9
                    Input 1 Select  value= 10
                    Input 2 Select  value= 11
                    Analog Select  value= 12
                    Input 1080/59p  value= 13
                    Input 1080/50p  value= 14
                    Input 1080/29i  value= 15
                    Input 1080/25i  value= 16
                    Input 720/59p  value= 17
                    Input 720/50p  value= 18
                    Input 525/29i  value= 19
                    Input 625/25i  value= 20
                    Output Black On  value= 21
                    Output Black Off  value= 22
                    Output Freeze  value= 23
                    Output UnFreeze  value= 24
                    Output Pattern On  value= 25
                    Output Pattern Off  value= 26
                    Output Caption On  value= 27
                    Output Caption Off  value= 28
                    Reference OK  value= 29
                    Reference Loss  value= 30
                    AES 1 PCM  value= 31
                    AES 1 Data  value= 32
                    AES 1 DolbyE  value= 33
                    AES 1 Loss  value= 34
                    AES 2 PCM  value= 35
                    AES 2 Data  value= 36
                    AES 2 DolbyE  value= 37
                    AES 2 Loss  value= 38
                    AES 3 PCM  value= 39
                    AES 3 Data  value= 40
                    AES 3 DolbyE  value= 41
                    AES 3 Loss  value= 42
                    AES 4 PCM  value= 43
                    AES 4 Data  value= 44
                    AES 4 DolbyE  value= 45
                    AES 4 Loss  value= 46
                    AES 5 PCM  value= 47
                    AES 5 Data  value= 48
                    AES 5 DolbyE  value= 49
                    AES 5 Loss  value= 50
                    AES 6 PCM  value= 51
                    AES 6 Data  value= 52
                    AES 6 DolbyE  value= 53
                    AES 6 Loss  value= 54
                    AES 7 PCM  value= 55
                    AES 7 Data  value= 56
                    AES 7 DolbyE  value= 57
                    AES 7 Loss  value= 58
                    AES 8 PCM  value= 59
                    AES 8 Data  value= 60
                    AES 8 DolbyE  value= 61
                    AES 8 Loss  value= 62
                    Disemb 1 PCM  value= 63
                    Disemb 1 Data  value= 64
                    Disemb 1 DolbyE  value= 65
                    Disemb 1 Loss  value= 66
                    Disemb 2 PCM  value= 67
                    Disemb 2 Data  value= 68
                    Disemb 2 DolbyE  value= 69
                    Disemb 2 Loss  value= 70
                    Disemb 3 PCM  value= 71
                    Disemb 3 Data  value= 72
                    Disemb 3 DolbyE  value= 73
                    Disemb 3 Loss  value= 74
                    Disemb 4 PCM  value= 75
                    Disemb 4 Data  value= 76
                    Disemb 4 DolbyE  value= 77
                    Disemb 4 Loss  value= 78
                    Disemb 5 PCM  value= 79
                    Disemb 5 Data  value= 80
                    Disemb 5 DolbyE  value= 81
                    Disemb 5 Loss  value= 82
                    Disemb 6 PCM  value= 83
                    Disemb 6 Data  value= 84
                    Disemb 6 DolbyE  value= 85
                    Disemb 6 Loss  value= 86
                    Disemb 7 PCM  value= 87
                    Disemb 7 Data  value= 88
                    Disemb 7 DolbyE  value= 89
                    Disemb 7 Loss  value= 90
                    Disemb 8 PCM  value= 91
                    Disemb 8 Data  value= 92
                    Disemb 8 DolbyE  value= 93
                    Disemb 8 Loss  value= 94
                    Decoder I/P Dolby D  value= 95
                    Decoder I/P Dolby E  value= 96
                    Decoder I/P PCM  value= 97
                    Decoder I/P No Err  value= 98
                    Decoder I/P Error  value= 99
                    Ext Meta Absent  value= 100
                    Ext Meta Invalid  value= 101
                    Ext Meta No AC3  value= 102
                    Ext Meta No BSI  value= 103
                    Ext Meta Valid  value= 104
                    Video Sync OK  value= 105
                    Video Sync Loss  value= 106
                    Encoder Active  value= 107
                    Encoder Stopped  value= 108
                    Encoder Passthru  value= 109  "
        ::= { iqupc00CmdEntry 36101 }


    iqupc00RollCallMemoriesRollTrackAddress OBJECT-TYPE
        SYNTAX            RollCallString
        MAX-ACCESS        read-write
        STATUS            current
        DESCRIPTION
                "CMNT: - Unit address for Rolltrack message
                 TYPE: - Editstring
                 PAGE: - RollCall/Memories
                    Address  cmdID= 36102
                    preset= 0000:00:00*0"
        ::= { iqupc00CmdEntry 36102 }


    iqupc00RollCallMemoriesRollTrackCommand OBJECT-TYPE
        SYNTAX            RollCallString
        MAX-ACCESS        read-write
        STATUS            current
        DESCRIPTION
                "CMNT: - Command to send for Rolltrack message
                 TYPE: - Editstring
                 PAGE: - RollCall/Memories
                    Command  cmdID= 36103
                    preset= 000:000\0"
        ::= { iqupc00CmdEntry 36103 }


    iqupc00RollCallMemoriesRollTrackStatus OBJECT-TYPE
        SYNTAX            RollCallString
        MAX-ACCESS        read-only
        STATUS            current
        DESCRIPTION
                "CMNT: - Rolltrack status
                 TYPE: - Display
                 PAGE: - RollCall/Memories
                    Status  cmdID= 36105  "
        ::= { iqupc00CmdEntry 36105 }


    iqupc00RollCallMemoriesRollTrackSending OBJECT-TYPE
        SYNTAX            RollCallString
        MAX-ACCESS        read-only
        STATUS            current
        DESCRIPTION
                "CMNT: - Rolltrack sending status: true/false
                 TYPE: - Display
                 PAGE: - RollCall/Memories
                    Sending  cmdID= 36106  "
        ::= { iqupc00CmdEntry 36106 }


    iqupc00RollCallMemoriesHideGpio OBJECT-TYPE
        SYNTAX            INTEGER
        MAX-ACCESS        read-write
        STATUS            current
        DESCRIPTION
                "CMNT: - 
                 TYPE: - Number
                 PAGE: - RollCall/Memories
                    HideGpio  cmdID= 54
                    min= 0  max= 1  step= 1  format= %d  div_scale= 1  preset= 0
                    Min = 0  Max = 0  Step = 0  Preset = 0  "
        ::= { iqupc00CmdEntry 54 }


    iqupc00RollCallMemoriesHideInpAES14 OBJECT-TYPE
        SYNTAX            INTEGER
        MAX-ACCESS        read-write
        STATUS            current
        DESCRIPTION
                "CMNT: - 
                 TYPE: - Number
                 PAGE: - RollCall/Memories
                    HideInpAES1_4  cmdID= 56
                    min= 0  max= 1  step= 1  format= %d  div_scale= 1  preset= 0
                    Min = 0  Max = 0  Step = 0  Preset = 0  "
        ::= { iqupc00CmdEntry 56 }


    iqupc00RollCallMemoriesHideInpAES18 OBJECT-TYPE
        SYNTAX            INTEGER
        MAX-ACCESS        read-write
        STATUS            current
        DESCRIPTION
                "CMNT: - 
                 TYPE: - Number
                 PAGE: - RollCall/Memories
                    HideInpAES1_8  cmdID= 57
                    min= 0  max= 1  step= 1  format= %d  div_scale= 1  preset= 0
                    Min = 0  Max = 0  Step = 0  Preset = 0  "
        ::= { iqupc00CmdEntry 57 }


    iqupc00RollCallMemoriesHideInpLogAES14 OBJECT-TYPE
        SYNTAX            INTEGER
        MAX-ACCESS        read-write
        STATUS            current
        DESCRIPTION
                "CMNT: - 
                 TYPE: - Number
                 PAGE: - RollCall/Memories
                    HideInpLogAES1_4  cmdID= 55
                    min= 0  max= 1  step= 1  format= %d  div_scale= 1  preset= 0
                    Min = 0  Max = 0  Step = 0  Preset = 0  "
        ::= { iqupc00CmdEntry 55 }


    iqupc00RollCallMemoriesHideInpLogAES18 OBJECT-TYPE
        SYNTAX            INTEGER
        MAX-ACCESS        read-write
        STATUS            current
        DESCRIPTION
                "CMNT: - 
                 TYPE: - Number
                 PAGE: - RollCall/Memories
                    HideInpLogAES1_8  cmdID= 61
                    min= 0  max= 1  step= 1  format= %d  div_scale= 1  preset= 0
                    Min = 0  Max = 0  Step = 0  Preset = 0  "
        ::= { iqupc00CmdEntry 61 }


    iqupc00RollCallMemoriesHideOutAES14 OBJECT-TYPE
        SYNTAX            INTEGER
        MAX-ACCESS        read-write
        STATUS            current
        DESCRIPTION
                "CMNT: - 
                 TYPE: - Number
                 PAGE: - RollCall/Memories
                    HideOutAES1_4  cmdID= 58
                    min= 0  max= 1  step= 1  format= %d  div_scale= 1  preset= 0
                    Min = 0  Max = 0  Step = 0  Preset = 0  "
        ::= { iqupc00CmdEntry 58 }


    iqupc00RollCallMemoriesHideOutAES18 OBJECT-TYPE
        SYNTAX            INTEGER
        MAX-ACCESS        read-write
        STATUS            current
        DESCRIPTION
                "CMNT: - 
                 TYPE: - Number
                 PAGE: - RollCall/Memories
                    HideOutAES1_8  cmdID= 59
                    min= 0  max= 1  step= 1  format= %d  div_scale= 1  preset= 0
                    Min = 0  Max = 0  Step = 0  Preset = 0  "
        ::= { iqupc00CmdEntry 59 }


    iqupc00RollCallMemoriesHideOutLogAES14 OBJECT-TYPE
        SYNTAX            INTEGER
        MAX-ACCESS        read-write
        STATUS            current
        DESCRIPTION
                "CMNT: - 
                 TYPE: - Number
                 PAGE: - RollCall/Memories
                    HideOutLogAES1_4  cmdID= 60
                    min= 0  max= 1  step= 1  format= %d  div_scale= 1  preset= 0
                    Min = 0  Max = 0  Step = 0  Preset = 0  "
        ::= { iqupc00CmdEntry 60 }


    iqupc00RollCallMemoriesHideOutLogAES18 OBJECT-TYPE
        SYNTAX            INTEGER
        MAX-ACCESS        read-write
        STATUS            current
        DESCRIPTION
                "CMNT: - 
                 TYPE: - Number
                 PAGE: - RollCall/Memories
                    HideOutLogAES1_8  cmdID= 62
                    min= 0  max= 1  step= 1  format= %d  div_scale= 1  preset= 0
                    Min = 0  Max = 0  Step = 0  Preset = 0  "
        ::= { iqupc00CmdEntry 62 }


    iqupc00GPIOGPI1GPIO1Mode OBJECT-TYPE
        SYNTAX            INTEGER {
                            valUnused(0),
                            valInputGPI1(1),
                            valOutputGPO1(2)
                            }
        MAX-ACCESS        read-write
        STATUS            current
        DESCRIPTION
                "CMNT: - GPIO-1 Input/Output
                 TYPE: - RadiobuttonList
                 PAGE: - GPIO
                    GPI/O 1 Mode  cmdID= 36120
                    Unused  value= 0
                    Input (GPI1)  value= 1
                    Output (GPO1)  value= 2  "
        ::= { iqupc00CmdEntry 36120 }


    iqupc00GPIOGPI1GPI1IPHighSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Input High action
                 TYPE: - RadiobuttonList
                 PAGE: - GPIO
                    GPI 1 I/P High Select  cmdID= 36121
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqupc00CmdEntry 36121 }


    iqupc00GPIOGPI1GPI1IPLowSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Input Low action
                 TYPE: - RadiobuttonList
                 PAGE: - GPIO
                    GPI 1 I/P Low Select  cmdID= 36125
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqupc00CmdEntry 36125 }


    iqupc00GPIOGPI1GPO1OPSelect OBJECT-TYPE
        SYNTAX            INTEGER {
                            valUnused(-1),
                            valInputOK(0),
                            valInput1OK(50),
                            valInput2OK(51),
                            valAnalogInputOK(52),
                            valInput1Selected(53),
                            valInput2Selected(54),
                            valAnalogIPSelected(55),
                            valBlack(56),
                            valFreeze(57),
                            valPattern(58),
                            valNoUserMemSeld(99),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valNoDispMemSeld(60),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-1 Output action
                 TYPE: - RadiobuttonList
                 PAGE: - GPIO
                    GPO 1 O/P Select  cmdID= 36122
                    Unused  value= -1
                    Input OK  value= 0
                    Input 1 OK  value= 50
                    Input 2 OK  value= 51
                    Analog Input OK  value= 52
                    Input 1 Selected  value= 53
                    Input 2 Selected  value= 54
                    Analog I/P Selected  value= 55
                    Black  value= 56
                    Freeze  value= 57
                    Pattern  value= 58
                    No User Mem Sel'd  value= 99
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    No Disp Mem Sel'd  value= 60
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqupc00CmdEntry 36122 }


    iqupc00GPIOGPI1InvertGPIO1 OBJECT-TYPE
        SYNTAX            INTEGER { disable(0), enable(1)  }
        MAX-ACCESS        read-write
        STATUS            current
        DESCRIPTION
                "CMNT: - GPI-1 Port Invert
                 TYPE: - Checkbox
                 PAGE: - GPIO
                    Invert GPIO 1  cmdID= 36123  "
        ::= { iqupc00CmdEntry 36123 }


    iqupc00GPIOGPI1Status OBJECT-TYPE
        SYNTAX            RollCallString
        MAX-ACCESS        read-only
        STATUS            current
        DESCRIPTION
                "CMNT: - GPIO-1 Status
                 TYPE: - Display
                 PAGE: - GPIO
                    Status  cmdID= 36134  "
        ::= { iqupc00CmdEntry 36134 }


    iqupc00GPIOGPI2GPIO2Mode OBJECT-TYPE
        SYNTAX            INTEGER {
                            valUnused(0),
                            valInputGPI2(1),
                            valOutputGPO2(2)
                            }
        MAX-ACCESS        read-write
        STATUS            current
        DESCRIPTION
                "CMNT: - GPIO-2 Input/Output
                 TYPE: - RadiobuttonList
                 PAGE: - GPIO
                    GPI/O 2 Mode  cmdID= 36130
                    Unused  value= 0
                    Input (GPI2)  value= 1
                    Output (GPO2)  value= 2  "
        ::= { iqupc00CmdEntry 36130 }


    iqupc00GPIOGPI2GPI2IPHighSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Input High action
                 TYPE: - RadiobuttonList
                 PAGE: - GPIO
                    GPI 2 I/P High Select  cmdID= 36131
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqupc00CmdEntry 36131 }


    iqupc00GPIOGPI2GPI2IPLowSelect OBJECT-TYPE
        SYNTAX            INTEGER {
                            valUnused(-1),
                            valSelectInput1(50),
                            valSelectInput2(51),
                            valSelectAnalogInput(52),
                            valBlack(56),
                            valFreeze(57),
                            valPattern(58),
                            valVideoInput(59),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Input Low action
                 TYPE: - RadiobuttonList
                 PAGE: - GPIO
                    GPI 2 I/P Low Select  cmdID= 36137
                    Unused  value= -1
                    Select Input 1  value= 50
                    Select Input 2  value= 51
                    Select Analog Input  value= 52
                    Black  value= 56
                    Freeze  value= 57
                    Pattern  value= 58
                    Video Input  value= 59
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqupc00CmdEntry 36137 }


    iqupc00GPIOGPI2GPO2OPSelect OBJECT-TYPE
        SYNTAX            INTEGER {
                            valUnused(-1),
                            valInputOK(0),
                            valInput1OK(50),
                            valInput2OK(51),
                            valAnalogInputOK(52),
                            valInput1Selected(53),
                            valInput2Selected(54),
                            valAnalogIPSelected(55),
                            valBlack(56),
                            valFreeze(57),
                            valPattern(58),
                            valNoUserMemSeld(99),
                            valUserMemory1(100),
                            valUserMemory2(101),
                            valUserMemory3(102),
                            valUserMemory4(103),
                            valUserMemory5(104),
                            valUserMemory6(105),
                            valUserMemory7(106),
                            valUserMemory8(107),
                            valUserMemory9(108),
                            valUserMemory10(109),
                            valUserMemory11(110),
                            valUserMemory12(111),
                            valUserMemory13(112),
                            valUserMemory14(113),
                            valUserMemory15(114),
                            valUserMemory16(115),
                            valNoDispMemSeld(60),
                            valDisplayMemory1(61),
                            valDisplayMemory2(62),
                            valDisplayMemory3(63),
                            valDisplayMemory4(64),
                            valDisplayMemory5(65),
                            valDisplayMemory6(66),
                            valDisplayMemory7(67),
                            valDisplayMemory8(68),
                            valDisplayMemory9(69),
                            valDisplayMemory10(70),
                            valDisplayMemory11(71),
                            valDisplayMemory12(72),
                            valDisplayMemory13(73),
                            valDisplayMemory14(74),
                            valDisplayMemory15(75),
                            valDisplayMemory16(76),
                            valDisplayMemory17(77),
                            valDisplayMemory18(78),
                            valDisplayMemory19(79),
                            valDisplayMemory20(80),
                            valDisplayMemory21(81),
                            valDisplayMemory22(82),
                            valDisplayMemory23(83),
                            valDisplayMemory24(84),
                            valDisplayMemory25(85),
                            valDisplayMemory26(86),
                            valDisplayMemory27(87),
                            valDisplayMemory28(88),
                            valDisplayMemory29(89),
                            valDisplayMemory30(90),
                            valDisplayMemory31(91),
                            valDisplayMemory32(92)
                            }
        MAX-ACCESS        read-write
        STATUS            current
        DESCRIPTION
                "CMNT: - GPI-2 Output action
                 TYPE: - RadiobuttonList
                 PAGE: - GPIO
                    GPO 2 O/P Select  cmdID= 36132
                    Unused  value= -1
                    Input OK  value= 0
                    Input 1 OK  value= 50
                    Input 2 OK  value= 51
                    Analog Input OK  value= 52
                    Input 1 Selected  value= 53
                    Input 2 Selected  value= 54
                    Analog I/P Selected  value= 55
                    Black  value= 56
                    Freeze  value= 57
                    Pattern  value= 58
                    No User Mem Sel'd  value= 99
                    User Memory 1  value= 100
                    User Memory 2  value= 101
                    User Memory 3  value= 102
                    User Memory 4  value= 103
                    User Memory 5  value= 104
                    User Memory 6  value= 105
                    User Memory 7  value= 106
                    User Memory 8  value= 107
                    User Memory 9  value= 108
                    User Memory 10  value= 109
                    User Memory 11  value= 110
                    User Memory 12  value= 111
                    User Memory 13  value= 112
                    User Memory 14  value= 113
                    User Memory 15  value= 114
                    User Memory 16  value= 115
                    No Disp Mem Sel'd  value= 60
                    Display Memory 1  value= 61
                    Display Memory 2  value= 62
                    Display Memory 3  value= 63
                    Display Memory 4  value= 64
                    Display Memory 5  value= 65
                    Display Memory 6  value= 66
                    Display Memory 7  value= 67
                    Display Memory 8  value= 68
                    Display Memory 9  value= 69
                    Display Memory 10  value= 70
                    Display Memory 11  value= 71
                    Display Memory 12  value= 72
                    Display Memory 13  value= 73
                    Display Memory 14  value= 74
                    Display Memory 15  value= 75
                    Display Memory 16  value= 76
                    Display Memory 17  value= 77
                    Display Memory 18  value= 78
                    Display Memory 19  value= 79
                    Display Memory 20  value= 80
                    Display Memory 21  value= 81
                    Display Memory 22  value= 82
                    Display Memory 23  value= 83
                    Display Memory 24  value= 84
                    Display Memory 25  value= 85
                    Display Memory 26  value= 86
                    Display Memory 27  value= 87
                    Display Memory 28  value= 88
                    Display Memory 29  value= 89
                    Display Memory 30  value= 90
                    Display Memory 31  value= 91
                    Display Memory 32  value= 92  "
        ::= { iqupc00CmdEntry 36132 }


    iqupc00GPIOGPI2InvertGPIO2 OBJECT-TYPE
        SYNTAX            INTEGER { disable(0), enable(1)  }
        MAX-ACCESS        read-write
        STATUS            current
        DESCRIPTION
                "CMNT: - GPI-2 Port Invert
                 TYPE: - Checkbox
                 PAGE: - GPIO
                    Invert GPIO 2  cmdID= 36133  "
        ::= { iqupc00CmdEntry 36133 }


    iqupc00GPIOGPI2Status OBJECT-TYPE
        SYNTAX            RollCallString
        MAX-ACCESS        read-only
        STATUS            current
        DESCRIPTION
                "CMNT: - GPIO-2 Status
                 TYPE: - Display
                 PAGE: - GPIO
                    Status  cmdID= 36135  "
        ::= { iqupc00CmdEntry 36135 }


    iqupc00SetupDisplay OBJECT-TYPE
        SYNTAX            INTEGER {
                            valVideoStatus(0),
                            valAudioStatus(1),
                            valDolbyStatus(2),
                            valRefStatus(3),
                            valLedStatus(4),
                            valAncStatus(5),
                            valAfdStatus(6)
                            }
        MAX-ACCESS        read-write
        STATUS            current
        DESCRIPTION
                "CMNT: - Select Info display to show
                 TYPE: - RadiobuttonList
                 PAGE: - Setup
                    Display  cmdID= 32773
                    VideoStatus  value= 0
                    AudioStatus  value= 1
                    DolbyStatus  value= 2
                    RefStatus  value= 3
                    LedStatus  value= 4
                    AncStatus  value= 5
                    AfdStatus  value= 6  "
        ::= { iqupc00CmdEntry 32773 }


    iqupc00SetupProduct OBJECT-TYPE
        SYNTAX            RollCallString
        MAX-ACCESS        read-only
        STATUS            current
        DESCRIPTION
                "CMNT: - 
                 TYPE: - Display
                 PAGE: - Setup
                    Product  cmdID= 32771  "
        ::= { iqupc00CmdEntry 32771 }


    iqupc00SetupRelease OBJECT-TYPE
        SYNTAX            RollCallString
        MAX-ACCESS        read-only
        STATUS            current
        DESCRIPTION
                "CMNT: - Unit version number
                 TYPE: - Display
                 PAGE: - Setup
                    Release  cmdID= 2  "
        ::= { iqupc00CmdEntry 2 }


    iqupc00SetupBuild OBJECT-TYPE
        SYNTAX            RollCallString
        MAX-ACCESS        read-only
        STATUS            current
        DESCRIPTION
                "CMNT: - Unit build number
                 TYPE: - Display
                 PAGE: - Setup
                    Build  cmdID= 5  "
        ::= { iqupc00CmdEntry 5 }


    iqupc00SetupKOS OBJECT-TYPE
        SYNTAX            RollCallString
        MAX-ACCESS        read-only
        STATUS            current
        DESCRIPTION
                "CMNT: - 
                 TYPE: - Display
                 PAGE: - Setup
                    KOS  cmdID= 32772  "
        ::= { iqupc00CmdEntry 32772 }


    iqupc00SetupSerialNo OBJECT-TYPE
        SYNTAX            RollCallString
        MAX-ACCESS        read-only
        STATUS            current
        DESCRIPTION
                "CMNT: - Unit serial number
                 TYPE: - Display
                 PAGE: - Setup
                    Serial No.  cmdID= 1  "
        ::= { iqupc00CmdEntry 1 }


    iqupc00SetupFactoryDefault OBJECT-TYPE
        SYNTAX            INTEGER { noAction(0),valFactoryDefault(1) }
        MAX-ACCESS        read-write
        STATUS            current
        DESCRIPTION
                "CMNT: - Recall factory defaults
                 TYPE: - Button
                 PAGE: - Setup
                    Factory Default  cmdID= 37002
                    value= 1  "
        ::= { iqupc00CmdEntry 37002 }


    iqupc00SetupRestart OBJECT-TYPE
        SYNTAX            INTEGER { noAction(0),valRestart(1) }
        MAX-ACCESS        read-write
        STATUS            current
        DESCRIPTION
                "CMNT: - Restart unit
                 TYPE: - Button
                 PAGE: - Setup
                    Restart  cmdID= 4
                    value= 1  "
        ::= { iqupc00CmdEntry 4 }


    iqupc00SetupDefaultSettings OBJECT-TYPE
        SYNTAX            INTEGER { noAction(0),valDefaultSettings(1) }
        MAX-ACCESS        read-write
        STATUS            current
        DESCRIPTION
                "CMNT: - Recall factory defaults-KeepMemories
                 TYPE: - Button
                 PAGE: - Setup
                    Default Settings  cmdID= 37001
                    value= 1  "
        ::= { iqupc00CmdEntry 37001 }


    iqupc00SetupSerialNumber OBJECT-TYPE
        SYNTAX            RollCallString
        MAX-ACCESS        read-write
        STATUS            current
        DESCRIPTION
                "CMNT: - Edit serial number (On Factory Test Only)
                 TYPE: - Editstring
                 PAGE: - Setup
                    Serial Number  cmdID= 32774
                    preset= unknown"
        ::= { iqupc00CmdEntry 32774 }


    iqupc00SetupBoardID OBJECT-TYPE
        SYNTAX            INTEGER {
                            valIQUPC00(539),
                            valIQUPC01(540),
                            valIQDNC00(541),
                            valIQDNC01(549),
                            valIQDCC00(542),
                            valIQUDC10(543),
                            valIQUDC11(544),
                            valIQUCC00(548),
                            valIQUAV10(545),
                            valIQMUX33(546),
                            valIQDMX33(547),
                            valIQSYN33(551)
                            }
        MAX-ACCESS        read-write
        STATUS            current
        DESCRIPTION
                "CMNT: - Edit product type (On Factory Test Only)
                 TYPE: - RadiobuttonList
                 PAGE: - Setup
                    BoardID  cmdID= 32776
                    IQUPC00  value= 539
                    IQUPC01  value= 540
                    IQDNC00  value= 541
                    IQDNC01  value= 549
                    IQDCC00  value= 542
                    IQUDC10  value= 543
                    IQUDC11  value= 544
                    IQUCC00  value= 548
                    IQUAV10  value= 545
                    IQMUX33  value= 546
                    IQDMX33  value= 547
                    IQSYN33  value= 551  "
        ::= { iqupc00CmdEntry 32776 }


    iqupc00SetupSaveID OBJECT-TYPE
        SYNTAX            INTEGER { noAction(0),valSaveID(1) }
        MAX-ACCESS        read-write
        STATUS            current
        DESCRIPTION
                "CMNT: - Save serial number/board type (On Factory Test Only)
                 TYPE: - Button
                 PAGE: - Setup
                    Save ID  cmdID= 32775
                    value= 1  "
        ::= { iqupc00CmdEntry 32775 }


    iqupc00SetupFpgaBoardType OBJECT-TYPE
        SYNTAX            RollCallString
        MAX-ACCESS        read-only
        STATUS            current
        DESCRIPTION
                "CMNT: - FPGA board type
                 TYPE: - Display
                 PAGE: - Setup
                    Board Type  cmdID= 33152  "
        ::= { iqupc00CmdEntry 33152 }


    iqupc00SetupFpgaSerialNo OBJECT-TYPE
        SYNTAX            RollCallString
        MAX-ACCESS        read-only
        STATUS            current
        DESCRIPTION
                "CMNT: - FPGA serial number
                 TYPE: - Display
                 PAGE: - Setup
                    Fpga SerialNo  cmdID= 33156  "
        ::= { iqupc00CmdEntry 33156 }


    iqupc00SetupFpgaSoftVer OBJECT-TYPE
        SYNTAX            RollCallString
        MAX-ACCESS        read-only
        STATUS            current
        DESCRIPTION
                "CMNT: - FPGA version number
                 TYPE: - Display
                 PAGE: - Setup
                    Soft Ver  cmdID= 33150  "
        ::= { iqupc00CmdEntry 33150 }


    iqupc00SetupFpgaVer OBJECT-TYPE
        SYNTAX            RollCallString
        MAX-ACCESS        read-only
        STATUS            current
        DESCRIPTION
                "CMNT: - FPGA firmware version number
                 TYPE: - Display
                 PAGE: - Setup
                    Fpga Ver  cmdID= 33157  "
        ::= { iqupc00CmdEntry 33157 }


    iqupc00SetupFpgaTIVer OBJECT-TYPE
        SYNTAX            RollCallString
        MAX-ACCESS        read-only
        STATUS            current
        DESCRIPTION
                "CMNT: - FPGA TI version number
                 TYPE: - Display
                 PAGE: - Setup
                    TI Ver  cmdID= 33160  "
        ::= { iqupc00CmdEntry 33160 }


    iqupc00SetupFpgaDolbyModId OBJECT-TYPE
        SYNTAX            RollCallString
        MAX-ACCESS        read-only
        STATUS            current
        DESCRIPTION
                "CMNT: - FPGA Dolby Module Type
                 TYPE: - Display
                 PAGE: - Setup
                    Dolby Mod Id  cmdID= 33162  "
        ::= { iqupc00CmdEntry 33162 }


    iqupc00SetupFpgaProtVer OBJECT-TYPE
        SYNTAX            RollCallString
        MAX-ACCESS        read-only
        STATUS            current
        DESCRIPTION
                "CMNT: - FPGA protocol version
                 TYPE: - Display
                 PAGE: - Setup
                    Prot Ver  cmdID= 33151  "
        ::= { iqupc00CmdEntry 33151 }


    iqupc00SetupFpgaProgCRC OBJECT-TYPE
        SYNTAX            RollCallString
        MAX-ACCESS        read-only
        STATUS            current
        DESCRIPTION
                "CMNT: - FPGA code CRC
                 TYPE: - Display
                 PAGE: - Setup
                    Prog CRC  cmdID= 33155  "
        ::= { iqupc00CmdEntry 33155 }


    iqupc00SetupFpgaUptime OBJECT-TYPE
        SYNTAX            RollCallString
        MAX-ACCESS        read-only
        STATUS            current
        DESCRIPTION
                "CMNT: - FPGA Uptime
                 TYPE: - Display
                 PAGE: - Setup
                    Uptime  cmdID= 33163  "
        ::= { iqupc00CmdEntry 33163 }


    iqupc00SetupFpgaENGVXPVer OBJECT-TYPE
        SYNTAX            RollCallString
        MAX-ACCESS        read-only
        STATUS            current
        DESCRIPTION
                "CMNT: - FPGA VXP version number
                 TYPE: - Display
                 PAGE: - Setup
                    VXP Ver  cmdID= 33158  "
        ::= { iqupc00CmdEntry 33158 }


    iqupc00SetupFpgaENGSharcVer OBJECT-TYPE
        SYNTAX            RollCallString
        MAX-ACCESS        read-only
        STATUS            current
        DESCRIPTION
                "CMNT: - FPGA Sharc version number
                 TYPE: - Display
                 PAGE: - Setup
                    Sharc Ver  cmdID= 33159  "
        ::= { iqupc00CmdEntry 33159 }


    iqupc00SetupFpgaENGAlteraVer OBJECT-TYPE
        SYNTAX            RollCallString
        MAX-ACCESS        read-only
        STATUS            current
        DESCRIPTION
                "CMNT: - FPGA Altera version number
                 TYPE: - Display
                 PAGE: - Setup
                    Altera Ver  cmdID= 33161  "
        ::= { iqupc00CmdEntry 33161 }


    iqupc00SetupFpgaENGVCCint OBJECT-TYPE
        SYNTAX            RollCallString
        MAX-ACCESS        read-only
        STATUS            current
        DESCRIPTION
                "CMNT: - FPGA Internal Voltage
                 TYPE: - Display
                 PAGE: - Setup
                    VCCint  cmdID= 33164  "
        ::= { iqupc00CmdEntry 33164 }


    iqupc00SetupFpgaENGVCCaux OBJECT-TYPE
        SYNTAX            RollCallString
        MAX-ACCESS        read-only
        STATUS            current
        DESCRIPTION
                "CMNT: - FPGA Aux Voltage
                 TYPE: - Display
                 PAGE: - Setup
                    VCCaux  cmdID= 33165  "
        ::= { iqupc00CmdEntry 33165 }


    iqupc00SetupOptionsOption1 OBJECT-TYPE
        SYNTAX            RollCallString
        MAX-ACCESS        read-only
        STATUS            current
        DESCRIPTION
                "CMNT: - Upmix option
                 TYPE: - Display
                 PAGE: - Setup
                    Option1  cmdID= 33166  "
        ::= { iqupc00CmdEntry 33166 }


    iqupc00SetupOptionsOption2 OBJECT-TYPE
        SYNTAX            RollCallString
        MAX-ACCESS        read-only
        STATUS            current
        DESCRIPTION
                "CMNT: - Dolby Decode option
                 TYPE: - Display
                 PAGE: - Setup
                    Option2  cmdID= 33167  "
        ::= { iqupc00CmdEntry 33167 }


    iqupc00SetupOptionsOption3 OBJECT-TYPE
        SYNTAX            RollCallString
        MAX-ACCESS        read-only
        STATUS            current
        DESCRIPTION
                "CMNT: - Dolby Encode D option
                 TYPE: - Display
                 PAGE: - Setup
                    Option3  cmdID= 33168  "
        ::= { iqupc00CmdEntry 33168 }


    iqupc00SetupOptionsOption4 OBJECT-TYPE
        SYNTAX            RollCallString
        MAX-ACCESS        read-only
        STATUS            current
        DESCRIPTION
                "CMNT: - Dolby Encode E option
                 TYPE: - Display
                 PAGE: - Setup
                    Option4  cmdID= 33169  "
        ::= { iqupc00CmdEntry 33169 }


    iqupc00SetupOptionsOption5 OBJECT-TYPE
        SYNTAX            RollCallString
        MAX-ACCESS        read-only
        STATUS            current
        DESCRIPTION
                "CMNT: - Color corrector option
                 TYPE: - Display
                 PAGE: - Setup
                    Option5  cmdID= 33170  "
        ::= { iqupc00CmdEntry 33170 }


    iqupc00SetupOptionsOption6 OBJECT-TYPE
        SYNTAX            RollCallString
        MAX-ACCESS        read-only
        STATUS            current
        DESCRIPTION
                "CMNT: - Loudness 5.1 option
                 TYPE: - Display
                 PAGE: - Setup
                    Option6  cmdID= 33171  "
        ::= { iqupc00CmdEntry 33171 }


    iqupc00SetupOptionsOption7 OBJECT-TYPE
        SYNTAX            RollCallString
        MAX-ACCESS        read-only
        STATUS            current
        DESCRIPTION
                "CMNT: - Loudness 1x2.0 option
                 TYPE: - Display
                 PAGE: - Setup
                    Option7  cmdID= 33172  "
        ::= { iqupc00CmdEntry 33172 }


    iqupc00SetupOptionsOption8 OBJECT-TYPE
        SYNTAX            RollCallString
        MAX-ACCESS        read-only
        STATUS            current
        DESCRIPTION
                "CMNT: - Loudness 2x2.0 option
                 TYPE: - Display
                 PAGE: - Setup
                    Option8  cmdID= 33173  "
        ::= { iqupc00CmdEntry 33173 }


    iqupc00SetupOptionsOption9 OBJECT-TYPE
        SYNTAX            RollCallString
        MAX-ACCESS        read-only
        STATUS            current
        DESCRIPTION
                "CMNT: - 24 HOUR options
                 TYPE: - Display
                 PAGE: - Setup
                    Option9  cmdID= 33174  "
        ::= { iqupc00CmdEntry 33174 }


    iqupc00SetupOptionsMask OBJECT-TYPE
        SYNTAX            INTEGER
        MAX-ACCESS        read-write
        STATUS            current
        DESCRIPTION
                "CMNT: - Bit mask of current licence options
                 TYPE: - Number
                 PAGE: - Setup
                    OptionsMask  cmdID= 36147
                    min= 0  max= 65535  step= 1  format= %d  div_scale= 1  preset= 0
                    Min = 0  Max = 0  Step = 0  Preset = 0  "
        ::= { iqupc00CmdEntry 36147 }


    iqupc00SetupDemoNonDemoRestart OBJECT-TYPE
        SYNTAX            INTEGER { noAction(0),valNonDemoRestart(1) }
        MAX-ACCESS        read-write
        STATUS            current
        DESCRIPTION
                "CMNT: - hard restart, removes demo options
                 TYPE: - Button
                 PAGE: - Setup
                    NonDemoRestart  cmdID= 43092
                    value= 1  "
        ::= { iqupc00CmdEntry 43092 }


    iqupc00SetupDemoPeriod OBJECT-TYPE
        SYNTAX            INTEGER
        MAX-ACCESS        read-write
        STATUS            current
        DESCRIPTION
                "CMNT: - Factory configured total demo period,
                 TYPE: - Number
                 PAGE: - Setup
                    DemoPeriod  cmdID= 65
                    min= 0  max= 720  step= 1  format= %0.0f Hours  div_scale= 1  preset= 0
                    Min = 0 Hours  Max = 720 Hours  Step = 1 Hours  Preset = 0 Hours  "
        ::= { iqupc00CmdEntry 65 }


    iqupc00SetupDemoRestartMode OBJECT-TYPE
        SYNTAX            INTEGER { disable(0), enable(1)  }
        MAX-ACCESS        read-write
        STATUS            current
        DESCRIPTION
                "CMNT: - Restart mode demo/non-demo
                 TYPE: - Checkbox
                 PAGE: - Setup
                    RestartMode  cmdID= 43093  "
        ::= { iqupc00CmdEntry 43093 }


    iqupc00SetupDemoRemainingDemo OBJECT-TYPE
        SYNTAX            INTEGER
        MAX-ACCESS        read-write
        STATUS            current
        DESCRIPTION
                "CMNT: - demo remaining period,
                 TYPE: - Number
                 PAGE: - Setup
                    RemainingDemo  cmdID= 43091
                    min= 0  max= 50000  step= 1  format= %d  div_scale= 1  preset= 0
                    Min = 0  Max = 0  Step = 0  Preset = 0  "
        ::= { iqupc00CmdEntry 43091 }


    iqupc00SetupDemoRemaining24h OBJECT-TYPE
        SYNTAX            INTEGER
        MAX-ACCESS        read-write
        STATUS            current
        DESCRIPTION
                "CMNT: - demo remaining period before next restart
                 TYPE: - Number
                 PAGE: - Setup
                    Remaining24h  cmdID= 43094
                    min= 0  max= 1440  step= 1  format= %d  div_scale= 1  preset= 0
                    Min = 0  Max = 0  Step = 0  Preset = 0  "
        ::= { iqupc00CmdEntry 43094 }


    iqupc00SetupDemoStatus OBJECT-TYPE
        SYNTAX            INTEGER
        MAX-ACCESS        read-write
        STATUS            current
        DESCRIPTION
                "CMNT: - Factory configured total demo period Status
                 TYPE: - Number
                 PAGE: - Setup
                    DemoStatus  cmdID= 43101
                    min= 0  max= 1  step= 1  format= %0.0f  div_scale= 1  preset= 0
                    Min = 0  Max = 1  Step = 1  Preset = 0  "
        ::= { iqupc00CmdEntry 43101 }


    iqupc00SetupRestartHard OBJECT-TYPE
        SYNTAX            INTEGER { noAction(0),valRestartHard(1) }
        MAX-ACCESS        read-write
        STATUS            current
        DESCRIPTION
                "CMNT: - Restart unit
                 TYPE: - Button
                 PAGE: - Setup
                    Restart Hard  cmdID= 36138
                    value= 1  "
        ::= { iqupc00CmdEntry 36138 }


    iqupc00SetupInput1Name OBJECT-TYPE
        SYNTAX            RollCallString
        MAX-ACCESS        read-write
        STATUS            current
        DESCRIPTION
                "CMNT: - 
                 TYPE: - Editstring
                 PAGE: - Setup
                    Input 1 Name  cmdID= 9000
                    preset= INPUT 1 SERIAL IN"
        ::= { iqupc00CmdEntry 9000 }


    iqupc00SetupInput2Name OBJECT-TYPE
        SYNTAX            RollCallString
        MAX-ACCESS        read-write
        STATUS            current
        DESCRIPTION
                "CMNT: - 
                 TYPE: - Editstring
                 PAGE: - Setup
                    Input 2 Name  cmdID= 9001
                    preset= INPUT 2 SERIAL IN"
        ::= { iqupc00CmdEntry 9001 }


    iqupc00SetupInput3Name OBJECT-TYPE
        SYNTAX            RollCallString
        MAX-ACCESS        read-write
        STATUS            current
        DESCRIPTION
                "CMNT: - 
                 TYPE: - Editstring
                 PAGE: - Setup
                    Input 3 Name  cmdID= 9002
                    preset= INPUT 3 ANALOG IN"
        ::= { iqupc00CmdEntry 9002 }


    iqupc00SetupCalibrationVideoOut8 OBJECT-TYPE
        SYNTAX            INTEGER
        MAX-ACCESS        read-write
        STATUS            current
        DESCRIPTION
                "CMNT: - Analog cal video out 8
                 TYPE: - Number
                 PAGE: - Setup
                    VideoOut8  cmdID= 43097
                    min= -128  max= 127  step= 1  format= %0.0f  div_scale= 1  preset= 0
                    Min = -128  Max = 127  Step = 1  Preset = 0  "
        ::= { iqupc00CmdEntry 43097 }


    iqupc00SetupCalibrationVideoOut10 OBJECT-TYPE
        SYNTAX            INTEGER
        MAX-ACCESS        read-write
        STATUS            current
        DESCRIPTION
                "CMNT: - Analog cal video out 10
                 TYPE: - Number
                 PAGE: - Setup
                    VideoOut10  cmdID= 43099
                    min= -128  max= 127  step= 1  format= %0.0f  div_scale= 1  preset= 0
                    Min = -128  Max = 127  Step = 1  Preset = 0  "
        ::= { iqupc00CmdEntry 43099 }


    iqupc00SetupCalibrationVideoOut11 OBJECT-TYPE
        SYNTAX            INTEGER
        MAX-ACCESS        read-write
        STATUS            current
        DESCRIPTION
                "CMNT: - Analog cal video out 11
                 TYPE: - Number
                 PAGE: - Setup
                    VideoOut11  cmdID= 43100
                    min= -128  max= 127  step= 1  format= %0.0f  div_scale= 1  preset= 0
                    Min = -128  Max = 127  Step = 1  Preset = 0  "
        ::= { iqupc00CmdEntry 43100 }


    iqupc00LKFS1SourceLSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43200
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43200 }


    iqupc00LKFS1SourceRSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43201
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43201 }


    iqupc00LKFS1SourceLSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43202
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43202 }


    iqupc00LKFS1SourceRSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43203
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43203 }


    iqupc00LKFS1SourceCSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 1
                 TYPE: - RadiobuttonList
                 PAGE: - LKFS1
                    Src  cmdID= 43204
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 43204 }


    iqupc00LKFS1ResetSession OBJECT-TYPE
        SYNTAX            INTEGER { noAction(0),valResetSession(1) }
        MAX-ACCESS        read-write
        STATUS            current
        DESCRIPTION
                "CMNT: - lkfs Process 1 sess reset
                 TYPE: - Button
                 PAGE: - LKFS1
                    ResetSession  cmdID= 43211
                    value= 1  "
        ::= { iqupc00CmdEntry 43211 }


    iqupc00LKFS1SessLevel OBJECT-TYPE
        SYNTAX            RollCallString
        MAX-ACCESS        read-only
        STATUS            current
        DESCRIPTION
                "CMNT: - lkfs Process 1 Sess LEVEL
                 TYPE: - Display
                 PAGE: - LKFS1
                    SessLevel  cmdID= 43217  "
        ::= { iqupc00CmdEntry 43217 }


    iqupc00LKFS1SessTime OBJECT-TYPE
        SYNTAX            RollCallString
        MAX-ACCESS        read-only
        STATUS            current
        DESCRIPTION
                "CMNT: - lkfs Process 1 Session Period
                 TYPE: - Display
                 PAGE: - LKFS1
                    SessTime  cmdID= 43225  "
        ::= { iqupc00CmdEntry 43225 }


    iqupc00LKFS1currrate OBJECT-TYPE
        SYNTAX            INTEGER
        MAX-ACCESS        read-write
        STATUS            current
        DESCRIPTION
                "CMNT: - lkfs Process 1 update rate
                 TYPE: - Number
                 PAGE: - LKFS1
                    curr rate  cmdID= 43213
                    min= 1  max= 63  step= 1  format= %0.0f  div_scale= 1  preset= 2
                    Min = 1  Max = 63  Step = 1  Preset = 2  "
        ::= { iqupc00CmdEntry 43213 }


    iqupc00LKFS1CurrLevelTime OBJECT-TYPE
        SYNTAX            RollCallString
        MAX-ACCESS        read-only
        STATUS            current
        DESCRIPTION
                "CMNT: - lkfs Process 1 LEVEL Update Timeout
                 TYPE: - Display
                 PAGE: - LKFS1
                    CurrLevelTime  cmdID= 43221  "
        ::= { iqupc00CmdEntry 43221 }


    iqupc00LKFS1CurrLevel OBJECT-TYPE
        SYNTAX            RollCallString
        MAX-ACCESS        read-only
        STATUS            current
        DESCRIPTION
                "CMNT: - lkfs Process 1 CUR LEVEL
                 TYPE: - Display
                 PAGE: - LKFS1
                    CurrLevel  cmdID= 43215  "
        ::= { iqupc00CmdEntry 43215 }


    iqupc00LKFS1CurrLevel2 OBJECT-TYPE
        SYNTAX            RollCallString
        MAX-ACCESS        read-only
        STATUS            current
        DESCRIPTION
                "CMNT: - lkfs Process 1 CUR LEVEL
                 TYPE: - Display
                 PAGE: - LKFS1
                    CurrLevel2  cmdID= 43226  "
        ::= { iqupc00CmdEntry 43226 }


    iqupc00LKFS1RollMapUpd OBJECT-TYPE
        SYNTAX            RollCallString
        MAX-ACCESS        read-only
        STATUS            current
        DESCRIPTION
                "CMNT: - Audio Loudness updates to rollmap
                 TYPE: - Display
                 PAGE: - LKFS1
                    RollMapUpd  cmdID= 38277  "
        ::= { iqupc00CmdEntry 38277 }


    iqupc00LKFS1UpdateRate OBJECT-TYPE
        SYNTAX            INTEGER {
                            valOn(1),
                            valOff(0)
                            }
        MAX-ACCESS        read-write
        STATUS            current
        DESCRIPTION
                "CMNT: - lkfs Process 1 LEVEL Update
                 TYPE: - RadiobuttonList
                 PAGE: - LKFS1
                    Update Rate  cmdID= 43219
                    On  value= 1
                    Off  value= 0  "
        ::= { iqupc00CmdEntry 43219 }


    iqupc00LKFS2SourceLSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43206
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43206 }


    iqupc00LKFS2SourceRSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43207
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43207 }


    iqupc00LKFS2SourceLSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43208
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43208 }


    iqupc00LKFS2SourceRSSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43209
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    Tone1  value= 16
                    Tone2  value= 17
                    Tone3  value= 18
                    Tone4  value= 19
                    Tone5  value= 20
                    Tone6  value= 21
                    Tone7  value= 22
                    Tone8  value= 23  "
        ::= { iqupc00CmdEntry 43209 }


    iqupc00LKFS2SourceCSrc OBJECT-TYPE
        SYNTAX            INTEGER {
                            valSilence(34),
                            valBus11(0),
                            valBus12(1),
                            valBus21(2),
                            valBus22(3),
                            valBus31(4),
                            valBus32(5),
                            valBus41(6),
                            valBus42(7),
                            valBus51(8),
                            valBus52(9),
                            valBus61(10),
                            valBus62(11),
                            valBus71(12),
                            valBus72(13),
                            valBus81(14),
                            valBus82(15),
                            valLinAc11(24),
                            valLinAc12(25),
                            valLinAc21(26),
                            valLinAc22(27),
                            valLinAc31(28),
                            valLinAc32(29),
                            valLinAc41(30),
                            valLinAc42(31),
                            valTone1(16),
                            valTone2(17),
                            valTone3(18),
                            valTone4(19),
                            valTone5(20),
                            valTone6(21),
                            valTone7(22),
                            valTone8(23)
                            }
        MAX-ACCESS        read-write
        STATUS            current
        DESCRIPTION
                "CMNT: - lkfs Process 2
                 TYPE: - RadiobuttonList
                 PAGE: - LKFS2
                    Src  cmdID= 43210
                    Silence  value= 34
                    Bus1_1  value= 0
                    Bus1_2  value= 1
                    Bus2_1  value= 2
                    Bus2_2  value= 3
                    Bus3_1  value= 4
                    Bus3_2  value= 5
                    Bus4_1  value= 6
                    Bus4_2  value= 7
                    Bus5_1  value= 8
                    Bus5_2  value= 9
                    Bus6_1  value= 10
                    Bus6_2  value= 11
                    Bus7_1  value= 12
                    Bus7_2  value= 13
                    Bus8_1  value= 14
                    Bus8_2  value= 15
                    LinAc1_1  value= 24
                    LinAc1_2  value= 25
                    LinAc2_1  value= 26
                    LinAc2_2  value= 27
                    LinAc3_1  value= 28
                    LinAc3_2  value= 29
                    LinAc4_1  value= 30
                    LinAc4_2  value= 31
                    Tone1  value= 16
                    Tone2  value= 17
                    Tone3  value= 18
                    Tone4  value= 19
                    Tone5  value= 20
                    Tone6  value= 21
                    Tone7  value= 22
                    Tone8  value= 23  "
        ::= { iqupc00CmdEntry 43210 }


    iqupc00LKFS2SessLevel OBJECT-TYPE
        SYNTAX            RollCallString
        MAX-ACCESS        read-only
        STATUS            current
        DESCRIPTION
                "CMNT: - lkfs Process 2 Sess LEVEL
                 TYPE: - Display
                 PAGE: - LKFS2
                    SessLevel  cmdID= 43218  "
        ::= { iqupc00CmdEntry 43218 }


    iqupc00LKFS2CurrLevel OBJECT-TYPE
        SYNTAX            RollCallString
        MAX-ACCESS        read-only
        STATUS            current
        DESCRIPTION
                "CMNT: - lkfs Process 2 CUR LEVEL
                 TYPE: - Display
                 PAGE: - LKFS2
                    CurrLevel  cmdID= 43216  "
        ::= { iqupc00CmdEntry 43216 }


    iqupc00LKFS2CurrLevel2 OBJECT-TYPE
        SYNTAX            RollCallString
        MAX-ACCESS        read-only
        STATUS            current
        DESCRIPTION
                "CMNT: - lkfs Process 2 CUR LEVEL
                 TYPE: - Display
                 PAGE: - LKFS2
                    CurrLevel2  cmdID= 43227  "
        ::= { iqupc00CmdEntry 43227 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S40512345
-- Comments		: Serial number of unit
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 100:10:35:00
-- Comments		: Uptime in days/hours/mins
--
---------------------------------------------------------------------------------------------------
-- Header		: REAR_ID
--
-- MIB ref		: swCardEventLogSlotXX       .7.82.69.65.82.95.73.68
-- absolute OID	: 1.3.6.1.4.1.7995.2.6.1.1.XX.7.82.69.65.82.95.73.68
--
-- Value(s)		: 103
-- Comments		: ID of rear interface
--
---------------------------------------------------------------------------------------------------
-- Header		: OUTPUT_1
--
-- MIB ref		: swCardEventLogSlotXX       .8.79.85.84.80.85.84.95.49
-- absolute OID	: 1.3.6.1.4.1.7995.2.6.1.1.XX.8.79.85.84.80.85.84.95.49
--
-- Value(s)		: INPUT 1
--				: INPUT 2
--				: INPUT 3
-- Comments		:
--
---------------------------------------------------------------------------------------------------
-- Header		: OUTPUT_2
--
-- MIB ref		: swCardEventLogSlotXX       .8.79.85.84.80.85.84.95.50
-- absolute OID	: 1.3.6.1.4.1.7995.2.6.1.1.XX.8.79.85.84.80.85.84.95.50
--
-- Value(s)		: INPUT 1
--				: INPUT 2
--				: INPUT 3
-- Comments		:
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: V115 Release
-- Comments		: Operating system version
--
---------------------------------------------------------------------------------------------------
-- Header		: SLOT_START
--
-- MIB ref		: swCardEventLogSlotXX       .10.83.76.79.84.95.83.84.65.82.84
-- absolute OID	: 1.3.6.1.4.1.7995.2.6.1.1.XX.10.83.76.79.84.95.83.84.65.82.84
--
-- Value(s)		: 7
-- Comments		: First Slot position of rear
--
---------------------------------------------------------------------------------------------------
-- Header		: SLOT_WIDTH
--
-- MIB ref		: swCardEventLogSlotXX       .10.83.76.79.84.95.87.73.68.84.72
-- absolute OID	: 1.3.6.1.4.1.7995.2.6.1.1.XX.10.83.76.79.84.95.87.73.68.84.72
--
-- Value(s)		: 2
--				: 3
-- Comments		: Number of slots rear uses
--
---------------------------------------------------------------------------------------------------
-- Header		: INPUT_1_AFD
--
-- MIB ref		: swCardEventLogSlotXX       .11.73.78.80.85.84.95.49.95.65.70.68
-- absolute OID	: 1.3.6.1.4.1.7995.2.6.1.1.XX.11.73.78.80.85.84.95.49.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
-- Comments		:
--
---------------------------------------------------------------------------------------------------
-- Header		: INPUT_2_AFD
--
-- MIB ref		: swCardEventLogSlotXX       .11.73.78.80.85.84.95.50.95.65.70.68
-- absolute OID	: 1.3.6.1.4.1.7995.2.6.1.1.XX.11.73.78.80.85.84.95.50.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
-- Comments		:
--
---------------------------------------------------------------------------------------------------
-- Header		: REAR_STATUS
--
-- MIB ref		: swCardEventLogSlotXX       .11.82.69.65.82.95.83.84.65.84.85.83
-- absolute OID	: 1.3.6.1.4.1.7995.2.6.1.1.XX.11.82.69.65.82.95.83.84.65.84.85.83
--
-- Value(s)		: OK
--				: WARN:Type Mismatch
-- Comments		: Status of rear
--
---------------------------------------------------------------------------------------------------
-- Header		: TEMP_1_NAME
--
-- MIB ref		: swCardEventLogSlotXX       .11.84.69.77.80.95.49.95.78.65.77.69
-- absolute OID	: 1.3.6.1.4.1.7995.2.6.1.1.XX.11.84.69.77.80.95.49.95.78.65.77.69
--
-- Value(s)		: Temperature FPGA
-- Comments		:
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 0004304563
-- Comments		: Software Build Number
--
---------------------------------------------------------------------------------------------------
-- Header		: INPUT_1_2016
--
-- MIB ref		: swCardEventLogSlotXX       .12.73.78.80.85.84.95.49.95.50.48.49.54
-- absolute OID	: 1.3.6.1.4.1.7995.2.6.1.1.XX.12.73.78.80.85.84.95.49.95.50.48.49.54
--
-- Value(s)		: WARN:None
--				: OK:Present
--				: Disabled:Present
--				: Disabled:None
--				: Unknown
-- Comments		:
--
---------------------------------------------------------------------------------------------------
-- Header		: INPUT_1_NAME
--
-- MIB ref		: swCardEventLogSlotXX       .12.73.78.80.85.84.95.49.95.78.65.77.69
-- absolute OID	: 1.3.6.1.4.1.7995.2.6.1.1.XX.12.73.78.80.85.84.95.49.95.78.65.77.69
--
-- Value(s)		: INPUT 1 SERIAL IN
-- Comments		:
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD/SD/3G SDI
--				: HD/SD SDI
-- Comments		:
--
---------------------------------------------------------------------------------------------------
-- Header		: INPUT_2_2016
--
-- MIB ref		: swCardEventLogSlotXX       .12.73.78.80.85.84.95.50.95.50.48.49.54
-- absolute OID	: 1.3.6.1.4.1.7995.2.6.1.1.XX.12.73.78.80.85.84.95.50.95.50.48.49.54
--
-- Value(s)		: WARN:None
--				: OK:Present
--				: Disabled:Present
--				: Disabled:None
--				: Unknown
-- Comments		:
--
---------------------------------------------------------------------------------------------------
-- Header		: INPUT_2_NAME
--
-- MIB ref		: swCardEventLogSlotXX       .12.73.78.80.85.84.95.50.95.78.65.77.69
-- absolute OID	: 1.3.6.1.4.1.7995.2.6.1.1.XX.12.73.78.80.85.84.95.50.95.78.65.77.69
--
-- Value(s)		: INPUT 2 SERIAL IN
-- Comments		:
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD/SD/3G SDI
--				: HD/SD SDI
-- Comments		:
--
---------------------------------------------------------------------------------------------------
-- Header		: OUTPUT_1_AFD
--
-- MIB ref		: swCardEventLogSlotXX       .12.79.85.84.80.85.84.95.49.95.65.70.68
-- absolute OID	: 1.3.6.1.4.1.7995.2.6.1.1.XX.12.79.85.84.80.85.84.95.49.95.65.70.68
--
-- Value(s)		: Reserved(0)
--				: Reserved(1)
--				: Box 16:9 top
--				: Box 14:9 top
--				: Box>16:9 ctr
--				: Reserved(5)
--				: Reserved(6)
--				: Reserved(7)
--				: Coded Frame
--				: 4:3 center
--				: 16:9 center
--				: 14:9 center
--				: Reserved(12)
--				: 4:3 SP 14:9
--				: 16:9 SP 14:9
--				: 16:9 SP 4:3
-- Comments		:
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: TEMP_1_STATE
--
-- MIB ref		: swCardEventLogSlotXX       .12.84.69.77.80.95.49.95.83.84.65.84.69
-- absolute OID	: 1.3.6.1.4.1.7995.2.6.1.1.XX.12.84.69.77.80.95.49.95.83.84.65.84.69
--
-- Value(s)		: OK
--				: Unknown
--				: WARN_High
--				: FAIL:Fan
-- Comments		:
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
--
-- Value(s)		: SER IN 1
-- Comments		: Text on Rear
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: OK
--				: WARN:Mismatch
--				: FAIL:Lost
-- Comments		:
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
--
-- Value(s)		: SER IN 2
-- Comments		:
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: OK
--				: WARN:Mismatch
--				: FAIL:Lost
-- Comments		:
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: HD/SD SDI
--				: HD/SD/3G SDI
-- Comments		:
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
--
-- Value(s)		: HD/SD SDI
--				: HD/SD/3G SDI
-- Comments		:
--
---------------------------------------------------------------------------------------------------
-- Header		: INPUT_1_ASPECT
--
-- MIB ref		: swCardEventLogSlotXX       .14.73.78.80.85.84.95.49.95.65.83.80.69.67.84
-- absolute OID	: 1.3.6.1.4.1.7995.2.6.1.1.XX.14.73.78.80.85.84.95.49.95.65.83.80.69.67.84
--
-- Value(s)		: Unknown
--				: 16:9
--				: 4/3
-- Comments		:
--
---------------------------------------------------------------------------------------------------
-- Header		: INPUT_2_ASPECT
--
-- MIB ref		: swCardEventLogSlotXX       .14.73.78.80.85.84.95.50.95.65.83.80.69.67.84
-- absolute OID	: 1.3.6.1.4.1.7995.2.6.1.1.XX.14.73.78.80.85.84.95.50.95.65.83.80.69.67.84
--
-- Value(s)		: Unknown
--				: 16:9
--				: 4/3
-- Comments		:
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
--				: WARN:Black
--				: WARN:Freeze
--				: WARN:Pattern
--				: WARN:Input
--				: WARN:Reclocked
--				: WARN:Disabled
-- Comments		:
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
--
-- Value(s)		: OK
--				: WARN:Black
--				: WARN:Freeze
--				: WARN:Pattern
--				: WARN:Input
--				: WARN:Reclocked
--				: WARN:Disabled
-- Comments		:
--
---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
--
-- Value(s)		: WARN:Freerun
--				: OK:Reference
--				: OK:Input
-- Comments		: Internal genlock state
--
---------------------------------------------------------------------------------------------------
-- Header		: OUTPUT_1_ASPECT
--
-- MIB ref		: swCardEventLogSlotXX       .15.79.85.84.80.85.84.95.49.95.65.83.80.69.67.84
-- absolute OID	: 1.3.6.1.4.1.7995.2.6.1.1.XX.15.79.85.84.80.85.84.95.49.95.65.83.80.69.67.84
--
-- Value(s)		: Unknown
--				: 16:9
--				: 4/3
-- Comments		:
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 520505115
-- Comments		: Fpga version number
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: RGMPP1C
-- Comments		:
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: WARN
-- Comments		:
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: LOST
--				: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: WARN
-- Comments		:
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: LOST
--				: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
--
-- Value(s)		: FAIL:Bad File
--				: WARN:NONE
--				: FAIL:No File
--				: SDHD
--				: SDHD:3G
-- Comments		:
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
--
-- Value(s)		: OK:Off
--				: WARN:On[CaptionText]
-- Comments		:
--
---------------------------------------------------------------------------------------------------
-- Header		: OUTPUT_2_CAPTION
--
-- MIB ref		: swCardEventLogSlotXX       .16.79.85.84.80.85.84.95.50.95.67.65.80.84.73.79.78
-- absolute OID	: 1.3.6.1.4.1.7995.2.6.1.1.XX.16.79.85.84.80.85.84.95.50.95.67.65.80.84.73.79.78
--
-- Value(s)		: OK:Off
--				: WARN:On[CaptionText]
-- Comments		:
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: OK:Tri-Level
--				: OK:Bi-Level
--				: WARN:Unknown
-- Comments		:
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
--
-- Value(s)		: 525/29i
--				: 625/25i
--				: 720/50p
--				: 720/59p
--				: 1080/25i
--				: 1080/29i
--				: 1080/23pSF
--				: 1080/25pSF
--				: 1080/25p
--				: 1080/29p
--				: 1080/50p-A
--				: 1080/59p-A
-- Comments		:
--
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: WARN:Mismatch
--				: FAIL:Lost
-- Comments		: External ref state
--
---------------------------------------------------------------------------------------------------
-- Header		: INPUT_1_SDI_ERRSEC
--
-- MIB ref		: swCardEventLogSlotXX       .18.73.78.80.85.84.95.49.95.83.68.73.95.69.82.82.83.69.67
-- absolute OID	: 1.3.6.1.4.1.7995.2.6.1.1.XX.18.73.78.80.85.84.95.49.95.83.68.73.95.69.82.82.83.69.67
--
-- Value(s)		: 0
--				: 1
--				: 2
-- Comments		: Number of error seconds
--
---------------------------------------------------------------------------------------------------
-- Header		: INPUT_2_SDI_ERRSEC
--
-- MIB ref		: swCardEventLogSlotXX       .18.73.78.80.85.84.95.50.95.83.68.73.95.69.82.82.83.69.67
-- absolute OID	: 1.3.6.1.4.1.7995.2.6.1.1.XX.18.73.78.80.85.84.95.50.95.83.68.73.95.69.82.82.83.69.67
--
-- Value(s)		: 0
--				: 1
--				: 2
-- Comments		: Number of error seconds
--
---------------------------------------------------------------------------------------------------
-- Header		: LICENSED_OPTIONS_2
--
-- MIB ref		: swCardEventLogSlotXX       .18.76.73.67.69.78.83.69.68.95.79.80.84.73.79.78.83.95.50
-- absolute OID	: 1.3.6.1.4.1.7995.2.6.1.1.XX.18.76.73.67.69.78.83.69.68.95.79.80.84.73.79.78.83.95.50
--
-- Value(s)		: FAIL:No File
--				: FAIL:Bad SerialNum
--				: WARN:Type??
--				: FAIL:Type Unknown
--				: WARN:Type Mismatch
--				: WARN:Bad File
--				: FAIL:Invalid
--				: OK:0 Options(s)
--				: OK:1 Options(s)
-- Comments		:
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: WARN
-- Comments		:
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: WARN
-- Comments		:
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: LOST
--				: 525/29i
--				: 625/25i
--				: 720/50p
--				: 720/59p
--				: 1080/25i
--				: 1080/29i
-- Comments		:
--
---------------------------------------------------------------------------------------------------
-- Header		: INPUT_1_SDI_ANC_ERRSECS
--
-- MIB ref		: swCardEventLogSlotXX       .23.73.78.80.85.84.95.49.95.83.68.73.95.65.78.67.95.69.82.82.83.69.67.83
-- absolute OID	: 1.3.6.1.4.1.7995.2.6.1.1.XX.23.73.78.80.85.84.95.49.95.83.68.73.95.65.78.67.95.69.82.82.83.69.67.83
--
-- Value(s)		: 0
--				: 1
--				: 2
-- Comments		: Number of error seconds
--
---------------------------------------------------------------------------------------------------
-- Header		: INPUT_2_SDI_ANC_ERRSECS
--
-- MIB ref		: swCardEventLogSlotXX       .23.73.78.80.85.84.95.50.95.83.68.73.95.65.78.67.95.69.82.82.83.69.67.83
-- absolute OID	: 1.3.6.1.4.1.7995.2.6.1.1.XX.23.73.78.80.85.84.95.50.95.83.68.73.95.65.78.67.95.69.82.82.83.69.67.83
--
-- Value(s)		: 0
--				: 1
--				: 2
-- Comments		: Number of error seconds
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: OK:PCM
--				: OK:Data
--				: OK:DolbyE
--				: WARN:Unknown
--				: FAIL:Lost
--				: FAIL:Input Lost
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: OK:PCM
--				: OK:Data
--				: OK:DolbyE
--				: WARN:Unknown
--				: FAIL:Lost
--				: FAIL:Input Lost
-- Comments		:
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
--
-- Value(s)		: OK:PCM
--				: OK:Data
--				: OK:DolbyE
--				: WARN:Unknown
--				: FAIL:Lost
--				: FAIL:Input Lost
--				: WARN:Silent PCM
--				: WARN:Overload PCM
--				: FAIL:Mixed
--				: OK
--				: WARN:Silent
--				: WARN:Overload
--				: FAIL:Data
--				: FAIL:DolbyE
-- Comments		:
--
---------------------------------------------------------------------------------------------------
-- Header		: OUTPUT_1_EMBEDDED_AUDIO_1_DOLBY
--
-- MIB ref		: swCardEventLogSlotXX       .31.79.85.84.80.85.84.95.49.95.69.77.66.69.68.68.69.68.95.65.85.68.73.79.95.49.95.68.79.76.66.89
-- absolute OID	: 1.3.6.1.4.1.7995.2.6.1.1.XX.31.79.85.84.80.85.84.95.49.95.69.77.66.69.68.68.69.68.95.65.85.68.73.79.95.49.95.68.79.76.66.89
--
-- Value(s)		: NONE
--				: OK
--				: WARN:Early
--				: WARN:Late
--				: FAIL:Early
--				: FAIL:Late
-- Comments		:
--
---------------------------------------------------------------------------------------------------
