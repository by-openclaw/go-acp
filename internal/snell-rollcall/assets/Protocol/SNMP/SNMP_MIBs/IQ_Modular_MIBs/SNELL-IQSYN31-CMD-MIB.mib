-- ************************************************************************************
-- Snell&Wilcox Card:IQSYN31
--        Module Id#:527
--       Command Set:6
--          Filename:SNELL-IQSYN31-CMD-MIB.mib
--            Author:Jonathan Riches
--              Date:12/08/2010
--              Time:14:27
--
-- Copyright (c) 2010 Snell & Wilcox Ltd
-- All rights reserved.
--
-- ************************************************************************************

SNELL-IQSYN31-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQSYN31,
    moduleIQSYN31MIB
        FROM SNELL-WILCOX-PRODUCT-REG;

 moduleIQSYN31CmdMi MODULE-IDENTITY
    LAST-UPDATED "1008121427Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQSYN31MIB 1 }




--********************************************************************************
--*
--*  Snell Wilcox Card:
--*  command set:
--*  list commands/menus:
--*
--******************************************************************************
	iqsyn31CmdTable OBJECT-TYPE
		SYNTAX			SEQUENCE OF Iqsyn31CmdEntry
		MAX-ACCESS		not-accessible
		STATUS			current
		DESCRIPTION
				"Note the instance of this table is relected in the command set Version"
		::= { moduleIQSYN31 1 }

	iqsyn31CmdEntry OBJECT-TYPE
		SYNTAX		Iqsyn31CmdEntry
		MAX-ACCESS		not-accessible
		STATUS			current
		DESCRIPTION
				"Entry in command table."
		INDEX	{ iqsyn31SlotIndex }
		::= { iqsyn31CmdTable 1 }

	Iqsyn31CmdEntry ::=
		SEQUENCE {
			iqsyn31SlotIndex
				Unsigned32,
			iqsyn31Channel1VideoVANCBlank1
				INTEGER,
			iqsyn31Video1625BlankLinesLine231
				INTEGER,
			iqsyn31Video1625BlankLinesLine3361
				INTEGER,
			iqsyn31Video1525BlankLinesLine211
				INTEGER,
			iqsyn31Video1525BlankLinesLine221
				INTEGER,
			iqsyn31Video1525BlankLinesLine2831
				INTEGER,
			iqsyn31Video1525BlankLinesLine2841
				INTEGER,
			iqsyn31Channel1VideoFreeze
				INTEGER,
			iqsyn31Channel1VideoManualFreeze
				INTEGER,
			iqsyn31Channel1VideoDefault
				INTEGER,
			iqsyn31Channel1VideoPatSelect
				INTEGER,
			iqsyn31Channel1VideoProcAmpEnable
				INTEGER,
			iqsyn31Channel1VideoBlackLevel
				INTEGER,
			iqsyn31Channel1VideoHueAdjust
				INTEGER,
			iqsyn31Channel1VideoMasterVideoGain
				INTEGER,
			iqsyn31Channel1VideoYGain
				INTEGER,
			iqsyn31Channel1VideoCbCrGain
				INTEGER,
			iqsyn31Channel1VideoYCTiming
				INTEGER,
			iqsyn31Channel1VideoPictureposition
				INTEGER,
			iqsyn31Channel1VideoModalIndex
				INTEGER,
			iqsyn31Channel1VideoYCTimingnm
				INTEGER,
			iqsyn31Channel1VideoPicturepositionnm
				INTEGER,
			iqsyn31Channel1VideoCaption
				INTEGER,
			iqsyn31Channel1VideoText
				RollCallString,
			iqsyn31Channel1AudioHANKBlank1
				INTEGER,
			iqsyn31EmbeddersEmbedder11Enable
				INTEGER,
			iqsyn31EmbeddersEmbedder11SourceLNonPCMPair1
				INTEGER,
			iqsyn31EmbeddersEmbedder11SourceRPair1
				INTEGER,
			iqsyn31EmbeddersEmbedder11MutePair1
				INTEGER,
			iqsyn31EmbeddersEmbedder11InvertLPair1
				INTEGER,
			iqsyn31EmbeddersEmbedder11InvertRPair1
				INTEGER,
			iqsyn31EmbeddersEmbedder11GainLPair1
				INTEGER,
			iqsyn31EmbeddersEmbedder11GainRPair1
				INTEGER,
			iqsyn31EmbeddersEmbedder11PairModePair1
				INTEGER,
			iqsyn31EmbeddersEmbedder11SourceLNonPCMPair2
				INTEGER,
			iqsyn31EmbeddersEmbedder11SourceRPair2
				INTEGER,
			iqsyn31EmbeddersEmbedder11MutePair2
				INTEGER,
			iqsyn31EmbeddersEmbedder11InvertLPair2
				INTEGER,
			iqsyn31EmbeddersEmbedder11InvertRPair2
				INTEGER,
			iqsyn31EmbeddersEmbedder11GainLPair2
				INTEGER,
			iqsyn31EmbeddersEmbedder11GainRPair2
				INTEGER,
			iqsyn31EmbeddersEmbedder11PairModePair2
				INTEGER,
			iqsyn31EmbeddersEmbedder12Enable
				INTEGER,
			iqsyn31EmbeddersEmbedder12SourceLNonPCMPair1
				INTEGER,
			iqsyn31EmbeddersEmbedder12SourceRPair1
				INTEGER,
			iqsyn31EmbeddersEmbedder12MutePair1
				INTEGER,
			iqsyn31EmbeddersEmbedder12InvertLPair1
				INTEGER,
			iqsyn31EmbeddersEmbedder12InvertRPair1
				INTEGER,
			iqsyn31EmbeddersEmbedder12GainLPair1
				INTEGER,
			iqsyn31EmbeddersEmbedder12GainRPair1
				INTEGER,
			iqsyn31EmbeddersEmbedder12PairModePair1
				INTEGER,
			iqsyn31EmbeddersEmbedder12SourceLNonPCMPair2
				INTEGER,
			iqsyn31EmbeddersEmbedder12SourceRPair2
				INTEGER,
			iqsyn31EmbeddersEmbedder12MutePair2
				INTEGER,
			iqsyn31EmbeddersEmbedder12InvertLPair2
				INTEGER,
			iqsyn31EmbeddersEmbedder12InvertRPair2
				INTEGER,
			iqsyn31EmbeddersEmbedder12GainLPair2
				INTEGER,
			iqsyn31EmbeddersEmbedder12GainRPair2
				INTEGER,
			iqsyn31EmbeddersEmbedder12PairModePair2
				INTEGER,
			iqsyn31EmbeddersEmbedder13Enable
				INTEGER,
			iqsyn31EmbeddersEmbedder13SourceLNonPCMPair1
				INTEGER,
			iqsyn31EmbeddersEmbedder13SourceRPair1
				INTEGER,
			iqsyn31EmbeddersEmbedder13MutePair1
				INTEGER,
			iqsyn31EmbeddersEmbedder13InvertLPair1
				INTEGER,
			iqsyn31EmbeddersEmbedder13InvertRPair1
				INTEGER,
			iqsyn31EmbeddersEmbedder13GainLPair1
				INTEGER,
			iqsyn31EmbeddersEmbedder13GainRPair1
				INTEGER,
			iqsyn31EmbeddersEmbedder13PairModePair1
				INTEGER,
			iqsyn31EmbeddersEmbedder13SourceLNonPCMPair2
				INTEGER,
			iqsyn31EmbeddersEmbedder13SourceRPair2
				INTEGER,
			iqsyn31EmbeddersEmbedder13MutePair2
				INTEGER,
			iqsyn31EmbeddersEmbedder13InvertLPair2
				INTEGER,
			iqsyn31EmbeddersEmbedder13InvertRPair2
				INTEGER,
			iqsyn31EmbeddersEmbedder13GainLPair2
				INTEGER,
			iqsyn31EmbeddersEmbedder13GainRPair2
				INTEGER,
			iqsyn31EmbeddersEmbedder13PairModePair2
				INTEGER,
			iqsyn31EmbeddersEmbedder14Enable
				INTEGER,
			iqsyn31EmbeddersEmbedder14SourceLNonPCMPair1
				INTEGER,
			iqsyn31EmbeddersEmbedder14SourceRPair1
				INTEGER,
			iqsyn31EmbeddersEmbedder14MutePair1
				INTEGER,
			iqsyn31EmbeddersEmbedder14InvertLPair1
				INTEGER,
			iqsyn31EmbeddersEmbedder14InvertRPair1
				INTEGER,
			iqsyn31EmbeddersEmbedder14GainLPair1
				INTEGER,
			iqsyn31EmbeddersEmbedder14GainRPair1
				INTEGER,
			iqsyn31EmbeddersEmbedder14PairModePair1
				INTEGER,
			iqsyn31EmbeddersEmbedder14SourceLNonPCMPair2
				INTEGER,
			iqsyn31EmbeddersEmbedder14SourceRPair2
				INTEGER,
			iqsyn31EmbeddersEmbedder14MutePair2
				INTEGER,
			iqsyn31EmbeddersEmbedder14InvertLPair2
				INTEGER,
			iqsyn31EmbeddersEmbedder14InvertRPair2
				INTEGER,
			iqsyn31EmbeddersEmbedder14GainLPair2
				INTEGER,
			iqsyn31EmbeddersEmbedder14GainRPair2
				INTEGER,
			iqsyn31EmbeddersEmbedder14PairModePair2
				INTEGER,
			iqsyn31Channel1AudioFrequency
				INTEGER,
			iqsyn31Channel1AudioChannelident
				INTEGER,
			iqsyn31Channel1AudioTotaldelay
				RollCallString,
			iqsyn31Channel1AudioActiveVideodelay
				RollCallString,
			iqsyn31Channel1Audiomanualdelay
				RollCallString,
			iqsyn31Channel1AudioTrack14delay
				RollCallString,
			iqsyn31Channel1AudioTrack15delay
				RollCallString,
			iqsyn31Channel1AudioTrack16delay
				RollCallString,
			iqsyn31Channel1AudioTrack17delay
				RollCallString,
			iqsyn31Channel1AudioVideodelayEnable
				INTEGER,
			iqsyn31Channel1AudiomanualdelayEnable
				INTEGER,
			iqsyn31Channel1AudioTrack14delayEnable
				INTEGER,
			iqsyn31Channel1AudioTrack15delayEnable
				INTEGER,
			iqsyn31Channel1AudioTrack16delayEnable
				INTEGER,
			iqsyn31Channel1AudioTrack17delayEnable
				INTEGER,
			iqsyn31Channel1AudioCoarse
				INTEGER,
			iqsyn31Channel1AudioFine
				INTEGER,
			iqsyn31Channel1AudioDolbyEautoalign
				INTEGER,
			iqsyn31Channel1AudioSilenceLevel
				INTEGER,
			iqsyn31Channel1AudioOverloadLevel
				INTEGER,
			iqsyn31Channel1AudioWarningTimer
				INTEGER,
			iqsyn31Channel2VideoVANCBlank2
				INTEGER,
			iqsyn31Video2625BlankLinesLine232
				INTEGER,
			iqsyn31Video2625BlankLinesLine3362
				INTEGER,
			iqsyn31Video2525BlankLinesLine212
				INTEGER,
			iqsyn31Video2525BlankLinesLine222
				INTEGER,
			iqsyn31Video2525BlankLinesLine2832
				INTEGER,
			iqsyn31Video2525BlankLinesLine2842
				INTEGER,
			iqsyn31Channel2Video5025
				INTEGER,
			iqsyn31Channel2VideoManualFreeze
				INTEGER,
			iqsyn31Channel2VideoDefault
				INTEGER,
			iqsyn31Channel2VideoPatSelect
				INTEGER,
			iqsyn31Channel2VideoProcAmpEnable
				INTEGER,
			iqsyn31Channel2VideoBlackLevel
				INTEGER,
			iqsyn31Channel2VideoHueAdjust
				INTEGER,
			iqsyn31Channel2VideoMasterVideoGain
				INTEGER,
			iqsyn31Channel2VideoYGain
				INTEGER,
			iqsyn31Channel2VideoCbCrGain
				INTEGER,
			iqsyn31Channel2VideoYCTiming
				INTEGER,
			iqsyn31Channel2VideoPictureposition
				INTEGER,
			iqsyn31Channel2VideoModalIndex
				INTEGER,
			iqsyn31Channel2VideoYCTimingnm
				INTEGER,
			iqsyn31Channel2VideoPicturepositionnm
				INTEGER,
			iqsyn31Channel2VideoCaption
				INTEGER,
			iqsyn31Channel2VideoText
				RollCallString,
			iqsyn31Channel2AudioHANKBlank2
				INTEGER,
			iqsyn31EmbeddersEmbedder21Enable
				INTEGER,
			iqsyn31EmbeddersEmbedder21SourceLNonPCMPair1
				INTEGER,
			iqsyn31EmbeddersEmbedder21SourceRPair1
				INTEGER,
			iqsyn31EmbeddersEmbedder21MutePair1
				INTEGER,
			iqsyn31EmbeddersEmbedder21InvertLPair1
				INTEGER,
			iqsyn31EmbeddersEmbedder21InvertRPair1
				INTEGER,
			iqsyn31EmbeddersEmbedder21GainLPair1
				INTEGER,
			iqsyn31EmbeddersEmbedder21GainRPair1
				INTEGER,
			iqsyn31EmbeddersEmbedder21PairModePair1
				INTEGER,
			iqsyn31EmbeddersEmbedder21SourceLNonPCMPair2
				INTEGER,
			iqsyn31EmbeddersEmbedder21SourceRPair2
				INTEGER,
			iqsyn31EmbeddersEmbedder21MutePair2
				INTEGER,
			iqsyn31EmbeddersEmbedder21InvertLPair2
				INTEGER,
			iqsyn31EmbeddersEmbedder21InvertRPair2
				INTEGER,
			iqsyn31EmbeddersEmbedder21GainLPair2
				INTEGER,
			iqsyn31EmbeddersEmbedder21GainRPair2
				INTEGER,
			iqsyn31EmbeddersEmbedder21PairModePair2
				INTEGER,
			iqsyn31EmbeddersEmbedder22Enable
				INTEGER,
			iqsyn31EmbeddersEmbedder22SourceLNonPCMPair1
				INTEGER,
			iqsyn31EmbeddersEmbedder22SourceRPair1
				INTEGER,
			iqsyn31EmbeddersEmbedder22MutePair1
				INTEGER,
			iqsyn31EmbeddersEmbedder22InvertLPair1
				INTEGER,
			iqsyn31EmbeddersEmbedder22InvertRPair1
				INTEGER,
			iqsyn31EmbeddersEmbedder22GainLPair1
				INTEGER,
			iqsyn31EmbeddersEmbedder22GainRPair1
				INTEGER,
			iqsyn31EmbeddersEmbedder22PairModePair1
				INTEGER,
			iqsyn31EmbeddersEmbedder22SourceLNonPCMPair2
				INTEGER,
			iqsyn31EmbeddersEmbedder22SourceRPair2
				INTEGER,
			iqsyn31EmbeddersEmbedder22MutePair2
				INTEGER,
			iqsyn31EmbeddersEmbedder22InvertLPair2
				INTEGER,
			iqsyn31EmbeddersEmbedder22InvertRPair2
				INTEGER,
			iqsyn31EmbeddersEmbedder22GainLPair2
				INTEGER,
			iqsyn31EmbeddersEmbedder22GainRPair2
				INTEGER,
			iqsyn31EmbeddersEmbedder22PairModePair2
				INTEGER,
			iqsyn31EmbeddersEmbedder23Enable
				INTEGER,
			iqsyn31EmbeddersEmbedder23SourceLNonPCMPair1
				INTEGER,
			iqsyn31EmbeddersEmbedder23SourceRPair1
				INTEGER,
			iqsyn31EmbeddersEmbedder23MutePair1
				INTEGER,
			iqsyn31EmbeddersEmbedder23InvertLPair1
				INTEGER,
			iqsyn31EmbeddersEmbedder23InvertRPair1
				INTEGER,
			iqsyn31EmbeddersEmbedder23GainLPair1
				INTEGER,
			iqsyn31EmbeddersEmbedder23GainRPair1
				INTEGER,
			iqsyn31EmbeddersEmbedder23PairModePair1
				INTEGER,
			iqsyn31EmbeddersEmbedder23SourceLNonPCMPair2
				INTEGER,
			iqsyn31EmbeddersEmbedder23SourceRPair2
				INTEGER,
			iqsyn31EmbeddersEmbedder23MutePair2
				INTEGER,
			iqsyn31EmbeddersEmbedder23InvertLPair2
				INTEGER,
			iqsyn31EmbeddersEmbedder23InvertRPair2
				INTEGER,
			iqsyn31EmbeddersEmbedder23GainLPair2
				INTEGER,
			iqsyn31EmbeddersEmbedder23GainRPair2
				INTEGER,
			iqsyn31EmbeddersEmbedder23PairModePair2
				INTEGER,
			iqsyn31EmbeddersEmbedder24Enable
				INTEGER,
			iqsyn31EmbeddersEmbedder24SourceLNonPCMPair1
				INTEGER,
			iqsyn31EmbeddersEmbedder24SourceRPair1
				INTEGER,
			iqsyn31EmbeddersEmbedder24MutePair1
				INTEGER,
			iqsyn31EmbeddersEmbedder24InvertLPair1
				INTEGER,
			iqsyn31EmbeddersEmbedder24InvertRPair1
				INTEGER,
			iqsyn31EmbeddersEmbedder24GainLPair1
				INTEGER,
			iqsyn31EmbeddersEmbedder24GainRPair1
				INTEGER,
			iqsyn31EmbeddersEmbedder24PairModePair1
				INTEGER,
			iqsyn31EmbeddersEmbedder24SourceLNonPCMPair2
				INTEGER,
			iqsyn31EmbeddersEmbedder24SourceRPair2
				INTEGER,
			iqsyn31EmbeddersEmbedder24MutePair2
				INTEGER,
			iqsyn31EmbeddersEmbedder24InvertLPair2
				INTEGER,
			iqsyn31EmbeddersEmbedder24InvertRPair2
				INTEGER,
			iqsyn31EmbeddersEmbedder24GainLPair2
				INTEGER,
			iqsyn31EmbeddersEmbedder24GainRPair2
				INTEGER,
			iqsyn31EmbeddersEmbedder24PairModePair2
				INTEGER,
			iqsyn31Channel2AudioFrequency
				INTEGER,
			iqsyn31Channel2AudioChannelident
				INTEGER,
			iqsyn31Channel2AudioTotaldelay
				RollCallString,
			iqsyn31Channel2AudioActiveVideodelay
				RollCallString,
			iqsyn31Channel2Audiomanualdelay
				RollCallString,
			iqsyn31Channel2AudioVideodelayInternalEnable
				INTEGER,
			iqsyn31Channel2AudiomanualdelayEnable
				INTEGER,
			iqsyn31Channel2AudioTrack14delayEnable
				INTEGER,
			iqsyn31Channel2AudioTrack15delayEnable
				INTEGER,
			iqsyn31Channel2AudioTrack16delayEnable
				INTEGER,
			iqsyn31Channel2AudioTrack17delayEnable
				INTEGER,
			iqsyn31Channel2AudioCoarse
				INTEGER,
			iqsyn31Channel2AudioFine
				INTEGER,
			iqsyn31Channel2AudioDolbyEautoalign
				INTEGER,
			iqsyn31Channel2AudioSilenceLevel
				INTEGER,
			iqsyn31Channel2AudioOverloadLevel
				INTEGER,
			iqsyn31Channel2AudioWarningTimer
				INTEGER,
			iqsyn31CommonGenlockMode
				INTEGER,
			iqsyn31CommonGenlockFreerunFrequency
				INTEGER,
			iqsyn31CommonGenlockGenlockHPhase
				INTEGER,
			iqsyn31CommonGenlockGenlockVPhase
				INTEGER,
			iqsyn31CommonGenlockVideoHdelay
				INTEGER,
			iqsyn31CommonGenlockVideoVdelay
				INTEGER,
			iqsyn31CommonGenlockVideo1Fdelay
				INTEGER,
			iqsyn31CommonGenlockVideo2Fdelay
				INTEGER,
			iqsyn31CommonGenlockGenlocksaveindex
				INTEGER,
			iqsyn31CommonGenlockGenlockHPhaseRT
				INTEGER,
			iqsyn31CommonGenlockGenlockVPhaseRT
				INTEGER,
			iqsyn31CommonGenlockVideoHdelayRT
				INTEGER,
			iqsyn31CommonGenlockVideoVdelayRT
				INTEGER,
			iqsyn31DefaultOutputStd
				INTEGER,
			iqsyn31CommonGenlock108050pB
				INTEGER,
			iqsyn31CommonGenlock108059pB
				INTEGER,
			iqsyn31CommonGenlock108050pA
				INTEGER,
			iqsyn31CommonGenlock108059pA
				INTEGER,
			iqsyn31CommonGenlock108029i
				INTEGER,
			iqsyn31CommonGenlock108025i
				INTEGER,
			iqsyn31CommonGenlock72059p
				INTEGER,
			iqsyn31CommonGenlock72050p
				INTEGER,
			iqsyn31CommonGenlock52529i
				INTEGER,
			iqsyn31CommonGenlock62525i
				INTEGER,
			iqsyn31CommonMemoriesSelMemory
				INTEGER,
			iqsyn31CommonMemoriesSetMemName
				RollCallString,
			iqsyn31CommonMemoriesRecallMemory
				INTEGER,
			iqsyn31CommonMemoriesSaveMemory
				INTEGER,
			iqsyn31CommonMemoriesLastUserMemory
				RollCallString,
			iqsyn31CommonMemoriesClearMemory
				INTEGER,
			iqsyn31MemoriesMemoryNamesMemory1Name
				RollCallString,
			iqsyn31MemoriesMemoryNamesMemory2Name
				RollCallString,
			iqsyn31MemoriesMemoryNamesMemory3Name
				RollCallString,
			iqsyn31MemoriesMemoryNamesMemory4Name
				RollCallString,
			iqsyn31MemoriesMemoryNamesMemory5Name
				RollCallString,
			iqsyn31MemoriesMemoryNamesMemory6Name
				RollCallString,
			iqsyn31MemoriesMemoryNamesMemory7Name
				RollCallString,
			iqsyn31MemoriesMemoryNamesMemory8Name
				RollCallString,
			iqsyn31MemoriesMemoryNamesMemory9Name
				RollCallString,
			iqsyn31MemoriesMemoryNamesMemory10Name
				RollCallString,
			iqsyn31MemoriesMemoryNamesMemory11Name
				RollCallString,
			iqsyn31MemoriesMemoryNamesMemory12Name
				RollCallString,
			iqsyn31MemoriesMemoryNamesMemory13Name
				RollCallString,
			iqsyn31MemoriesMemoryNamesMemory14Name
				RollCallString,
			iqsyn31MemoriesMemoryNamesMemory15Name
				RollCallString,
			iqsyn31MemoriesMemoryNamesMemory16Name
				RollCallString,
			iqsyn31CommonSetupUptimeLogEnable
				INTEGER,
			iqsyn31CommonSetupUptimeLogString
				RollCallString,
			iqsyn31CommonSetupOSVersionLogEnable
				INTEGER,
			iqsyn31CommonSetupOSVersionLogString
				RollCallString,
			iqsyn31CommonSetupHardwareVersionLogEnable
				INTEGER,
			iqsyn31CommonSetupHardwareVersionLogString
				RollCallString,
			iqsyn31CommonSetupBuildNumberLogEnable
				INTEGER,
			iqsyn31CommonSetupBuildNumberLogString
				RollCallString,
			iqsyn31CommonSetupSerialNumberLogEnable
				INTEGER,
			iqsyn31CommonSetupSerialNumberLogString
				RollCallString,
			iqsyn31CommonSetupLicensedOptionsLogEnable
				INTEGER,
			iqsyn31CommonSetupLicensedOptionsLogString
				RollCallString,
			iqsyn31CommonSetupFirmwareVersionLogEnable
				INTEGER,
			iqsyn31CommonSetupFirmwareVersionLogString
				RollCallString,
			iqsyn31CommonSetupInput1LogEnable
				INTEGER,
			iqsyn31CommonSetupInput1LogString
				RollCallString,
			iqsyn31CommonSetupInput1StandardLogEnable
				INTEGER,
			iqsyn31CommonSetupInput1StandardLogString
				RollCallString,
			iqsyn31CommonSetupInput1TypeLogEnable
				INTEGER,
			iqsyn31CommonSetupInput1TypeLogString
				RollCallString,
			iqsyn31CommonSetupInput1IdentLogEnable
				INTEGER,
			iqsyn31CommonSetupInput1IdentLogString
				RollCallString,
			iqsyn31CommonSetupIn1SDIERRSLogEnable
				INTEGER,
			iqsyn31CommonSetupIn1SDIERRSLogString
				RollCallString,
			iqsyn31CommonSetupIn1SDIANCERRSLogEnable
				INTEGER,
			iqsyn31CommonSetupIn1SDIANCERRSLogString
				RollCallString,
			iqsyn31CommonSetupInput1Audio1LogEnable
				INTEGER,
			iqsyn31CommonSetupInput1Audio1LogString
				RollCallString,
			iqsyn31CommonSetupInput1Audio2LogEnable
				INTEGER,
			iqsyn31CommonSetupInput1Audio2LogString
				RollCallString,
			iqsyn31CommonSetupInput1Audio3LogEnable
				INTEGER,
			iqsyn31CommonSetupInput1Audio3LogString
				RollCallString,
			iqsyn31CommonSetupInput1Audio4LogEnable
				INTEGER,
			iqsyn31CommonSetupInput1Audio4LogString
				RollCallString,
			iqsyn31CommonSetupInput1Audio5LogEnable
				INTEGER,
			iqsyn31CommonSetupInput1Audio5LogString
				RollCallString,
			iqsyn31CommonSetupInput1Audio6LogEnable
				INTEGER,
			iqsyn31CommonSetupInput1Audio6LogString
				RollCallString,
			iqsyn31CommonSetupInput1Audio7LogEnable
				INTEGER,
			iqsyn31CommonSetupInput1Audio7LogString
				RollCallString,
			iqsyn31CommonSetupInput1Audio8LogEnable
				INTEGER,
			iqsyn31CommonSetupInput1Audio8LogString
				RollCallString,
			iqsyn31CommonSetupOutput1TypeLogEnable
				INTEGER,
			iqsyn31CommonSetupOutput1TypeLogString
				RollCallString,
			iqsyn31CommonSetupOutput1StateLogEnable
				INTEGER,
			iqsyn31CommonSetupOutput1StateLogString
				RollCallString,
			iqsyn31CommonSetupOutput1StdLogEnable
				INTEGER,
			iqsyn31CommonSetupOutput1StdLogString
				RollCallString,
			iqsyn31CommonSetupOutput1CaptionLogEnable
				INTEGER,
			iqsyn31CommonSetupOutput1CaptionLogString
				RollCallString,
			iqsyn31CommonSetupInput2LogEnable
				INTEGER,
			iqsyn31CommonSetupInput2LogString
				RollCallString,
			iqsyn31CommonSetupInput2StandardLogEnable
				INTEGER,
			iqsyn31CommonSetupInput2StandardLogString
				RollCallString,
			iqsyn31CommonSetupInput2TypeLogEnable
				INTEGER,
			iqsyn31CommonSetupInput2TypeLogString
				RollCallString,
			iqsyn31CommonSetupInput2IdentLogEnable
				INTEGER,
			iqsyn31CommonSetupInput2IdentLogString
				RollCallString,
			iqsyn31CommonSetupIn2SDIERRSLogEnable
				INTEGER,
			iqsyn31CommonSetupIn2SDIERRSLogString
				RollCallString,
			iqsyn31CommonSetupIn2SDIANCERRSLogEnable
				INTEGER,
			iqsyn31CommonSetupIn2SDIANCERRSLogString
				RollCallString,
			iqsyn31CommonSetupInput2Audio1LogEnable
				INTEGER,
			iqsyn31CommonSetupInput2Audio1LogString
				RollCallString,
			iqsyn31CommonSetupInput2Audio2LogEnable
				INTEGER,
			iqsyn31CommonSetupInput2Audio2LogString
				RollCallString,
			iqsyn31CommonSetupInput2Audio3LogEnable
				INTEGER,
			iqsyn31CommonSetupInput2Audio3LogString
				RollCallString,
			iqsyn31CommonSetupInput2Audio4LogEnable
				INTEGER,
			iqsyn31CommonSetupInput2Audio4LogString
				RollCallString,
			iqsyn31CommonSetupInput2Audio5LogEnable
				INTEGER,
			iqsyn31CommonSetupInput2Audio5LogString
				RollCallString,
			iqsyn31CommonSetupInput2Audio6LogEnable
				INTEGER,
			iqsyn31CommonSetupInput2Audio6LogString
				RollCallString,
			iqsyn31CommonSetupInput2Audio7LogEnable
				INTEGER,
			iqsyn31CommonSetupInput2Audio7LogString
				RollCallString,
			iqsyn31CommonSetupInput2Audio8LogEnable
				INTEGER,
			iqsyn31CommonSetupInput2Audio8LogString
				RollCallString,
			iqsyn31CommonSetupOutput2TypeLogEnable
				INTEGER,
			iqsyn31CommonSetupOutput2TypeLogString
				RollCallString,
			iqsyn31CommonSetupOutput2StateLogEnable
				INTEGER,
			iqsyn31CommonSetupOutput2StateLogString
				RollCallString,
			iqsyn31CommonSetupOutput2StdLogEnable
				INTEGER,
			iqsyn31CommonSetupOutput2StdLogString
				RollCallString,
			iqsyn31CommonSetupOutput2CaptionLogEnable
				INTEGER,
			iqsyn31CommonSetupOutput2CaptionLogString
				RollCallString,
			iqsyn31CommonSetupop1embed11LogEnable
				INTEGER,
			iqsyn31CommonSetupop1embed11LogString
				RollCallString,
			iqsyn31CommonSetupop1embed12LogEnable
				INTEGER,
			iqsyn31CommonSetupop1embed12LogString
				RollCallString,
			iqsyn31CommonSetupop1embed21LogEnable
				INTEGER,
			iqsyn31CommonSetupop1embed21LogString
				RollCallString,
			iqsyn31CommonSetupop1embed22LogEnable
				INTEGER,
			iqsyn31CommonSetupop1embed22LogString
				RollCallString,
			iqsyn31CommonSetupop1embed31LogEnable
				INTEGER,
			iqsyn31CommonSetupop1embed31LogString
				RollCallString,
			iqsyn31CommonSetupop1embed32LogEnable
				INTEGER,
			iqsyn31CommonSetupop1embed32LogString
				RollCallString,
			iqsyn31CommonSetupop1embed41LogEnable
				INTEGER,
			iqsyn31CommonSetupop1embed41LogString
				RollCallString,
			iqsyn31CommonSetupop1embed42LogEnable
				INTEGER,
			iqsyn31CommonSetupop1embed42LogString
				RollCallString,
			iqsyn31CommonSetupop1embed51LogEnable
				INTEGER,
			iqsyn31CommonSetupop1embed51LogString
				RollCallString,
			iqsyn31CommonSetupop1embed52LogEnable
				INTEGER,
			iqsyn31CommonSetupop1embed52LogString
				RollCallString,
			iqsyn31CommonSetupop1embed61LogEnable
				INTEGER,
			iqsyn31CommonSetupop1embed61LogString
				RollCallString,
			iqsyn31CommonSetupop1embed62LogEnable
				INTEGER,
			iqsyn31CommonSetupop1embed62LogString
				RollCallString,
			iqsyn31CommonSetupop1embed71LogEnable
				INTEGER,
			iqsyn31CommonSetupop1embed71LogString
				RollCallString,
			iqsyn31CommonSetupop1embed72LogEnable
				INTEGER,
			iqsyn31CommonSetupop1embed72LogString
				RollCallString,
			iqsyn31CommonSetupop1embed81LogEnable
				INTEGER,
			iqsyn31CommonSetupop1embed81LogString
				RollCallString,
			iqsyn31CommonSetupop1embed82LogEnable
				INTEGER,
			iqsyn31CommonSetupop1embed82LogString
				RollCallString,
			iqsyn31CommonSetupop2embed11LogEnable
				INTEGER,
			iqsyn31CommonSetupop2embed11LogString
				RollCallString,
			iqsyn31CommonSetupop2embed12LogEnable
				INTEGER,
			iqsyn31CommonSetupop2embed12LogString
				RollCallString,
			iqsyn31CommonSetupop2embed21LogEnable
				INTEGER,
			iqsyn31CommonSetupop2embed21LogString
				RollCallString,
			iqsyn31CommonSetupop2embed22LogEnable
				INTEGER,
			iqsyn31CommonSetupop2embed22LogString
				RollCallString,
			iqsyn31CommonSetupop2embed31LogEnable
				INTEGER,
			iqsyn31CommonSetupop2embed31LogString
				RollCallString,
			iqsyn31CommonSetupop2embed32LogEnable
				INTEGER,
			iqsyn31CommonSetupop2embed32LogString
				RollCallString,
			iqsyn31CommonSetupop2embed41LogEnable
				INTEGER,
			iqsyn31CommonSetupop2embed41LogString
				RollCallString,
			iqsyn31CommonSetupop2embed42LogEnable
				INTEGER,
			iqsyn31CommonSetupop2embed42LogString
				RollCallString,
			iqsyn31CommonSetupop2embed51LogEnable
				INTEGER,
			iqsyn31CommonSetupop2embed51LogString
				RollCallString,
			iqsyn31CommonSetupop2embed52LogEnable
				INTEGER,
			iqsyn31CommonSetupop2embed52LogString
				RollCallString,
			iqsyn31CommonSetupop2embed61LogEnable
				INTEGER,
			iqsyn31CommonSetupop2embed61LogString
				RollCallString,
			iqsyn31CommonSetupop2embed62LogEnable
				INTEGER,
			iqsyn31CommonSetupop2embed62LogString
				RollCallString,
			iqsyn31CommonSetupop2embed71LogEnable
				INTEGER,
			iqsyn31CommonSetupop2embed71LogString
				RollCallString,
			iqsyn31CommonSetupop2embed72LogEnable
				INTEGER,
			iqsyn31CommonSetupop2embed72LogString
				RollCallString,
			iqsyn31CommonSetupop2embed81LogEnable
				INTEGER,
			iqsyn31CommonSetupop2embed81LogString
				RollCallString,
			iqsyn31CommonSetupop2embed82LogEnable
				INTEGER,
			iqsyn31CommonSetupop2embed82LogString
				RollCallString,
			iqsyn31CommonSetupGenlock1StateLogEnable
				INTEGER,
			iqsyn31CommonSetupGenlock1StateLogString
				RollCallString,
			iqsyn31CommonSetupRef1StateLogEnable
				INTEGER,
			iqsyn31CommonSetupRef1StateLogString
				RollCallString,
			iqsyn31CommonSetupRef1StandardLogEnable
				INTEGER,
			iqsyn31CommonSetupRef1StandardLogString
				RollCallString,
			iqsyn31CommonSetupRef1TypeLogEnable
				INTEGER,
			iqsyn31CommonSetupRef1TypeLogString
				RollCallString,
			iqsyn31CommonStatusProduct
				RollCallString,
			iqsyn31CommonStatusSoftwareVersion
				RollCallString,
			iqsyn31CommonStatusSerialNo
				RollCallString,
			iqsyn31CommonStatusFactoryDefaults
				INTEGER,
			iqsyn31CommonStatusDefaultSetting
				INTEGER,
			iqsyn31CommonStatusRestart
				INTEGER,
			iqsyn31CommonStatusBuild
				RollCallString,
			iqsyn31CommonStatusPCB
				RollCallString,
			iqsyn31CommonStatusKOSVersion
				RollCallString,
			iqsyn31CommonStatusFirmwareVersion
				RollCallString,
			iqsyn31CommonStatusUpTime
				RollCallString,
			iqsyn31CommonStatus
				INTEGER
		}

	iqsyn31SlotIndex OBJECT-TYPE
		SYNTAX		Unsigned32
		MAX-ACCESS		not-accessible
		STATUS			current
		DESCRIPTION
				"The unique Index value for each slot.  Its value
					ranges between 1 and the value of slotNumber."
		::= { iqsyn31CmdEntry 99999 }


	iqsyn31Channel1VideoVANCBlank1 OBJECT-TYPE
		SYNTAX		INTEGER { disable(0), enable(1) }
		MAX-ACCESS		read-write
		STATUS			current
		DESCRIPTION
				"TYPE: - Checkbox
				 PAGE: - Channel 1- Video
					VANC Blank 1  cmdID= 3949 "
		::= { iqsyn31CmdEntry 3949 }


	iqsyn31Video1625BlankLinesLine231 OBJECT-TYPE
		SYNTAX		INTEGER { disable(0), enable(1) }
		MAX-ACCESS		read-write
		STATUS			current
		DESCRIPTION
				"TYPE: - Checkbox
				 PAGE: - Channel 1- Video
					Line 23 1  cmdID= 3951 "
		::= { iqsyn31CmdEntry 3951 }


	iqsyn31Video1625BlankLinesLine3361 OBJECT-TYPE
		SYNTAX		INTEGER { disable(0), enable(1) }
		MAX-ACCESS		read-write
		STATUS			current
		DESCRIPTION
				"TYPE: - Checkbox
				 PAGE: - Channel 1- Video
					Line 336 1  cmdID= 3952 "
		::= { iqsyn31CmdEntry 3952 }


	iqsyn31Video1525BlankLinesLine211 OBJECT-TYPE
		SYNTAX		INTEGER { disable(0), enable(1) }
		MAX-ACCESS		read-write
		STATUS			current
		DESCRIPTION
				"TYPE: - Checkbox
				 PAGE: - Channel 1- Video
					Line 21 1  cmdID= 3953 "
		::= { iqsyn31CmdEntry 3953 }


	iqsyn31Video1525BlankLinesLine221 OBJECT-TYPE
		SYNTAX		INTEGER { disable(0), enable(1) }
		MAX-ACCESS		read-write
		STATUS			current
		DESCRIPTION
				"TYPE: - Checkbox
				 PAGE: - Channel 1- Video
					Line 22 1  cmdID= 3955 "
		::= { iqsyn31CmdEntry 3955 }


	iqsyn31Video1525BlankLinesLine2831 OBJECT-TYPE
		SYNTAX		INTEGER { disable(0), enable(1) }
		MAX-ACCESS		read-write
		STATUS			current
		DESCRIPTION
				"TYPE: - Checkbox
				 PAGE: - Channel 1- Video
					Line 283 1  cmdID= 3954 "
		::= { iqsyn31CmdEntry 3954 }


	iqsyn31Video1525BlankLinesLine2841 OBJECT-TYPE
		SYNTAX		INTEGER { disable(0), enable(1) }
		MAX-ACCESS		read-write
		STATUS			current
		DESCRIPTION
				"TYPE: - Checkbox
				 PAGE: - Channel 1- Video
					Line 284 1  cmdID= 3956 "
		::= { iqsyn31CmdEntry 3956 }


	iqsyn31Channel1VideoFreeze OBJECT-TYPE
		SYNTAX		INTEGER {
							valField(0),
							valFrame(1)
							}
		MAX-ACCESS		read-write
		STATUS			current
		DESCRIPTION
				"TYPE: - Button
				 PAGE: - Channel 1- Video
					Field  cmdID= 5023  value= 0
					Frame  cmdID= 5023  value= 1  "
		::= { iqsyn31CmdEntry 5023 }


	iqsyn31Channel1VideoManualFreeze OBJECT-TYPE
		SYNTAX		INTEGER { disable(0), enable(1) }
		MAX-ACCESS		read-write
		STATUS			current
		DESCRIPTION
				"TYPE: - Checkbox
				 PAGE: - Channel 1- Video
					Manual Freeze  cmdID= 5022 "
		::= { iqsyn31CmdEntry 5022 }


	iqsyn31Channel1VideoDefault OBJECT-TYPE
		SYNTAX		INTEGER {
							valBlack(0),
							valFreeze(1),
							valPattern(2)
							}
		MAX-ACCESS		read-write
		STATUS			current
		DESCRIPTION
				"TYPE: - Button
				 PAGE: - Channel 1- Video
					Black  cmdID= 2623  value= 0
					Freeze  cmdID= 2623  value= 1
					Pattern  cmdID= 2623  value= 2  "
		::= { iqsyn31CmdEntry 2623 }


	iqsyn31Channel1VideoPatSelect OBJECT-TYPE
		SYNTAX		INTEGER {
							valOff(0),
							valBlack(1),
							valBars(2)
							}
		MAX-ACCESS		read-write
		STATUS			current
		DESCRIPTION
				"TYPE: - Button
				 PAGE: - Channel 1- Video
					Off  cmdID= 2624  value= 0
					Black  cmdID= 2624  value= 1
					Bars  cmdID= 2624  value= 2  "
		::= { iqsyn31CmdEntry 2624 }


	iqsyn31Channel1VideoProcAmpEnable OBJECT-TYPE
		SYNTAX		INTEGER { disable(0), enable(1) }
		MAX-ACCESS		read-write
		STATUS			current
		DESCRIPTION
				"TYPE: - Checkbox
				 PAGE: - Channel 1- Video
					ProcAmp Enable  cmdID= 2864 "
		::= { iqsyn31CmdEntry 2864 }


	iqsyn31Channel1VideoBlackLevel OBJECT-TYPE
		SYNTAX		INTEGER
		MAX-ACCESS		read-write
		STATUS			current
		DESCRIPTION
				"TYPE: - Number
				 PAGE: - Channel 1- Video
					Black Level  cmdID= 2708  min= -1000  max= 1000  step= 8  format= %3.1fmV  divscale= 10
					Min = -100.0mV  Max = 100.0mV  Step = 0.8mV "
		::= { iqsyn31CmdEntry 2708 }


	iqsyn31Channel1VideoHueAdjust OBJECT-TYPE
		SYNTAX		INTEGER
		MAX-ACCESS		read-write
		STATUS			current
		DESCRIPTION
				"TYPE: - Number
				 PAGE: - Channel 1- Video
					Hue Adjust  cmdID= 3622  min= -180  max= 180  step= 1  format= %1.0fdeg  divscale= 1
					Min = -180deg  Max = 180deg  Step = 1deg "
		::= { iqsyn31CmdEntry 3622 }


	iqsyn31Channel1VideoMasterVideoGain OBJECT-TYPE
		SYNTAX		INTEGER
		MAX-ACCESS		read-write
		STATUS			current
		DESCRIPTION
				"TYPE: - Number
				 PAGE: - Channel 1- Video
					Master Video Gain  cmdID= 3780  min= -60  max= 60  step= 1  format= %0.1fdB  divscale= 10
					Min = -6.0dB  Max = 6.0dB  Step = 0.1dB "
		::= { iqsyn31CmdEntry 3780 }


	iqsyn31Channel1VideoYGain OBJECT-TYPE
		SYNTAX		INTEGER
		MAX-ACCESS		read-write
		STATUS			current
		DESCRIPTION
				"TYPE: - Number
				 PAGE: - Channel 1- Video
					Y Gain  cmdID= 2707  min= -60  max= 60  step= 1  format= %0.1fdB  divscale= 10
					Min = -6.0dB  Max = 6.0dB  Step = 0.1dB "
		::= { iqsyn31CmdEntry 2707 }


	iqsyn31Channel1VideoCbCrGain OBJECT-TYPE
		SYNTAX		INTEGER
		MAX-ACCESS		read-write
		STATUS			current
		DESCRIPTION
				"TYPE: - Number
				 PAGE: - Channel 1- Video
					Cb/Cr Gain  cmdID= 2706  min= -60  max= 60  step= 1  format= %0.1fdB  divscale= 10
					Min = -6.0dB  Max = 6.0dB  Step = 0.1dB "
		::= { iqsyn31CmdEntry 2706 }


	iqsyn31Channel1VideoYCTiming OBJECT-TYPE
		SYNTAX		INTEGER
		MAX-ACCESS		read-write
		STATUS			current
		DESCRIPTION
				"TYPE: - Number
				 PAGE: - Channel 1- Video
					Y/C Timing  cmdID= 2924  min= -8  max= 8  step= 2  format= %1.0f pixels  divscale= 1
					Min = -8 pixels  Max = 8 pixels  Step = 2 pixels "
		::= { iqsyn31CmdEntry 2924 }


	iqsyn31Channel1VideoPictureposition OBJECT-TYPE
		SYNTAX		INTEGER
		MAX-ACCESS		read-write
		STATUS			current
		DESCRIPTION
				"TYPE: - Number
				 PAGE: - Channel 1- Video
					Picture position  cmdID= 2709  min= -8  max= 8  step= 2  format= %1.0f pixels  divscale= 1
					Min = -8 pixels  Max = 8 pixels  Step = 2 pixels "
		::= { iqsyn31CmdEntry 2709 }


	iqsyn31Channel1VideoModalIndex OBJECT-TYPE
		SYNTAX		INTEGER
		MAX-ACCESS		read-write
		STATUS			current
		DESCRIPTION
				"TYPE: - Number
				 PAGE: - Channel 1- Video
					Modal Index  cmdID= 5006  min= 0  max= 1  step= 1  format= %1.0f  divscale= 1
					Min = 0  Max = 1  Step = 1 "
		::= { iqsyn31CmdEntry 5006 }


	iqsyn31Channel1VideoYCTimingnm OBJECT-TYPE
		SYNTAX		INTEGER
		MAX-ACCESS		read-write
		STATUS			current
		DESCRIPTION
				"TYPE: - Number
				 PAGE: - Channel 1- Video
					Y/C Timing nm  cmdID= 5008  min= -16  max= 16  step= 2  format= %1.0f pixels  divscale= 1
					Min = -16 pixels  Max = 16 pixels  Step = 2 pixels "
		::= { iqsyn31CmdEntry 5008 }


	iqsyn31Channel1VideoPicturepositionnm OBJECT-TYPE
		SYNTAX		INTEGER
		MAX-ACCESS		read-write
		STATUS			current
		DESCRIPTION
				"TYPE: - Number
				 PAGE: - Channel 1- Video
					Picture position nm  cmdID= 5007  min= -16  max= 16  step= 2  format= %1.0f pixels  divscale= 1
					Min = -16 pixels  Max = 16 pixels  Step = 2 pixels "
		::= { iqsyn31CmdEntry 5007 }


	iqsyn31Channel1VideoCaption OBJECT-TYPE
		SYNTAX		INTEGER {
							valOff(0),
							valOn(1)
							}
		MAX-ACCESS		read-write
		STATUS			current
		DESCRIPTION
				"TYPE: - Button
				 PAGE: - Channel 1- Video
					Off  cmdID= 1037  value= 0
					On  cmdID= 1037  value= 1  "
		::= { iqsyn31CmdEntry 1037 }


	iqsyn31Channel1VideoText OBJECT-TYPE
		SYNTAX		RollCallString
		MAX-ACCESS		read-write
		STATUS			current
		DESCRIPTION
				"TYPE: - Editstring
				 PAGE: - Channel 1- Video
					Text  cmdID= 1041  "
		::= { iqsyn31CmdEntry 1041 }


	iqsyn31Channel1AudioHANKBlank1 OBJECT-TYPE
		SYNTAX		INTEGER { disable(0), enable(1) }
		MAX-ACCESS		read-write
		STATUS			current
		DESCRIPTION
				"TYPE: - Checkbox
				 PAGE: - Channel 1- Audio
					HANK Blank 1  cmdID= 3947 "
		::= { iqsyn31CmdEntry 3947 }


	iqsyn31EmbeddersEmbedder11Enable OBJECT-TYPE
		SYNTAX		INTEGER { disable(0), enable(1) }
		MAX-ACCESS		read-write
		STATUS			current
		DESCRIPTION
				"TYPE: - Checkbox
				 PAGE: - Channel 1- Audio- Embedders- Embedder 1 1
					Enable  cmdID= 5066 "
		::= { iqsyn31CmdEntry 5066 }


	iqsyn31EmbeddersEmbedder11SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 1
					Source L / Non-PCM  cmdID= 5034
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5034 }


	iqsyn31EmbeddersEmbedder11SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 1
					Source R  cmdID= 5035
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5035 }


	iqsyn31EmbeddersEmbedder11MutePair1 OBJECT-TYPE
		SYNTAX		INTEGER { disable(0), enable(1) }
		MAX-ACCESS		read-write
		STATUS			current
		DESCRIPTION
				"TYPE: - Checkbox
				 PAGE: - Channel 1- Audio- Embedders- Embedder 1 1
					Mute  cmdID= 3240 "
		::= { iqsyn31CmdEntry 3240 }


	iqsyn31EmbeddersEmbedder11InvertLPair1 OBJECT-TYPE
		SYNTAX		INTEGER { disable(0), enable(1) }
		MAX-ACCESS		read-write
		STATUS			current
		DESCRIPTION
				"TYPE: - Checkbox
				 PAGE: - Channel 1- Audio- Embedders- Embedder 1 1
					Invert L  cmdID= 3160 "
		::= { iqsyn31CmdEntry 3160 }


	iqsyn31EmbeddersEmbedder11InvertRPair1 OBJECT-TYPE
		SYNTAX		INTEGER { disable(0), enable(1) }
		MAX-ACCESS		read-write
		STATUS			current
		DESCRIPTION
				"TYPE: - Checkbox
				 PAGE: - Channel 1- Audio- Embedders- Embedder 1 1
					Invert R  cmdID= 3161 "
		::= { iqsyn31CmdEntry 3161 }


	iqsyn31EmbeddersEmbedder11GainLPair1 OBJECT-TYPE
		SYNTAX		INTEGER
		MAX-ACCESS		read-write
		STATUS			current
		DESCRIPTION
				"TYPE: - Number
				 PAGE: - Channel 1- Audio- Embedders- Embedder 1 1
					Gain L  cmdID= 3080  min= -720  max= 120  step= 1  format= %0.1fdB  divscale= 10
					Min = -72.0dB  Max = 12.0dB  Step = 0.1dB "
		::= { iqsyn31CmdEntry 3080 }


	iqsyn31EmbeddersEmbedder11GainRPair1 OBJECT-TYPE
		SYNTAX		INTEGER
		MAX-ACCESS		read-write
		STATUS			current
		DESCRIPTION
				"TYPE: - Number
				 PAGE: - Channel 1- Audio- Embedders- Embedder 1 1
					Gain R  cmdID= 3081  min= -720  max= 120  step= 1  format= %0.1fdB  divscale= 10
					Min = -72.0dB  Max = 12.0dB  Step = 0.1dB "
		::= { iqsyn31CmdEntry 3081 }


	iqsyn31EmbeddersEmbedder11PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 1
					Pair Mode  cmdID= 3930
					2 Channel PCM  value= 0
					Stereo PCM  value= 1
					nonPCM  value= 2  "
		::= { iqsyn31CmdEntry 3930 }


	iqsyn31EmbeddersEmbedder11SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 1
					Source L / Non-PCM  cmdID= 5036
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5036 }


	iqsyn31EmbeddersEmbedder11SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 1
					Source R  cmdID= 5037
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5037 }


	iqsyn31EmbeddersEmbedder11MutePair2 OBJECT-TYPE
		SYNTAX		INTEGER { disable(0), enable(1) }
		MAX-ACCESS		read-write
		STATUS			current
		DESCRIPTION
				"TYPE: - Checkbox
				 PAGE: - Channel 1- Audio- Embedders- Embedder 1 1
					Mute  cmdID= 3241 "
		::= { iqsyn31CmdEntry 3241 }


	iqsyn31EmbeddersEmbedder11InvertLPair2 OBJECT-TYPE
		SYNTAX		INTEGER { disable(0), enable(1) }
		MAX-ACCESS		read-write
		STATUS			current
		DESCRIPTION
				"TYPE: - Checkbox
				 PAGE: - Channel 1- Audio- Embedders- Embedder 1 1
					Invert L  cmdID= 3162 "
		::= { iqsyn31CmdEntry 3162 }


	iqsyn31EmbeddersEmbedder11InvertRPair2 OBJECT-TYPE
		SYNTAX		INTEGER { disable(0), enable(1) }
		MAX-ACCESS		read-write
		STATUS			current
		DESCRIPTION
				"TYPE: - Checkbox
				 PAGE: - Channel 1- Audio- Embedders- Embedder 1 1
					Invert R  cmdID= 3163 "
		::= { iqsyn31CmdEntry 3163 }


	iqsyn31EmbeddersEmbedder11GainLPair2 OBJECT-TYPE
		SYNTAX		INTEGER
		MAX-ACCESS		read-write
		STATUS			current
		DESCRIPTION
				"TYPE: - Number
				 PAGE: - Channel 1- Audio- Embedders- Embedder 1 1
					Gain L  cmdID= 3082  min= -720  max= 120  step= 1  format= %0.1fdB  divscale= 10
					Min = -72.0dB  Max = 12.0dB  Step = 0.1dB "
		::= { iqsyn31CmdEntry 3082 }


	iqsyn31EmbeddersEmbedder11GainRPair2 OBJECT-TYPE
		SYNTAX		INTEGER
		MAX-ACCESS		read-write
		STATUS			current
		DESCRIPTION
				"TYPE: - Number
				 PAGE: - Channel 1- Audio- Embedders- Embedder 1 1
					Gain R  cmdID= 3083  min= -720  max= 120  step= 1  format= %0.1fdB  divscale= 10
					Min = -72.0dB  Max = 12.0dB  Step = 0.1dB "
		::= { iqsyn31CmdEntry 3083 }


	iqsyn31EmbeddersEmbedder11PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 1
					Pair Mode  cmdID= 3931
					2 Channel PCM  value= 0
					Stereo PCM  value= 1
					nonPCM  value= 2  "
		::= { iqsyn31CmdEntry 3931 }


	iqsyn31EmbeddersEmbedder12Enable OBJECT-TYPE
		SYNTAX		INTEGER { disable(0), enable(1) }
		MAX-ACCESS		read-write
		STATUS			current
		DESCRIPTION
				"TYPE: - Checkbox
				 PAGE: - Channel 1- Audio- Embedders- Embedder 1 2
					Enable  cmdID= 5067 "
		::= { iqsyn31CmdEntry 5067 }


	iqsyn31EmbeddersEmbedder12SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 2
					Source L / Non-PCM  cmdID= 5038
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5038 }


	iqsyn31EmbeddersEmbedder12SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 2
					Source R  cmdID= 5039
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5039 }


	iqsyn31EmbeddersEmbedder12MutePair1 OBJECT-TYPE
		SYNTAX		INTEGER { disable(0), enable(1) }
		MAX-ACCESS		read-write
		STATUS			current
		DESCRIPTION
				"TYPE: - Checkbox
				 PAGE: - Channel 1- Audio- Embedders- Embedder 1 2
					Mute  cmdID= 3242 "
		::= { iqsyn31CmdEntry 3242 }


	iqsyn31EmbeddersEmbedder12InvertLPair1 OBJECT-TYPE
		SYNTAX		INTEGER { disable(0), enable(1) }
		MAX-ACCESS		read-write
		STATUS			current
		DESCRIPTION
				"TYPE: - Checkbox
				 PAGE: - Channel 1- Audio- Embedders- Embedder 1 2
					Invert L  cmdID= 3164 "
		::= { iqsyn31CmdEntry 3164 }


	iqsyn31EmbeddersEmbedder12InvertRPair1 OBJECT-TYPE
		SYNTAX		INTEGER { disable(0), enable(1) }
		MAX-ACCESS		read-write
		STATUS			current
		DESCRIPTION
				"TYPE: - Checkbox
				 PAGE: - Channel 1- Audio- Embedders- Embedder 1 2
					Invert R  cmdID= 3165 "
		::= { iqsyn31CmdEntry 3165 }


	iqsyn31EmbeddersEmbedder12GainLPair1 OBJECT-TYPE
		SYNTAX		INTEGER
		MAX-ACCESS		read-write
		STATUS			current
		DESCRIPTION
				"TYPE: - Number
				 PAGE: - Channel 1- Audio- Embedders- Embedder 1 2
					Gain L  cmdID= 3084  min= -720  max= 120  step= 1  format= %0.1fdB  divscale= 10
					Min = -72.0dB  Max = 12.0dB  Step = 0.1dB "
		::= { iqsyn31CmdEntry 3084 }


	iqsyn31EmbeddersEmbedder12GainRPair1 OBJECT-TYPE
		SYNTAX		INTEGER
		MAX-ACCESS		read-write
		STATUS			current
		DESCRIPTION
				"TYPE: - Number
				 PAGE: - Channel 1- Audio- Embedders- Embedder 1 2
					Gain R  cmdID= 3085  min= -720  max= 120  step= 1  format= %0.1fdB  divscale= 10
					Min = -72.0dB  Max = 12.0dB  Step = 0.1dB "
		::= { iqsyn31CmdEntry 3085 }


	iqsyn31EmbeddersEmbedder12PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 2
					Pair Mode  cmdID= 3932
					2 Channel PCM  value= 0
					Stereo PCM  value= 1
					nonPCM  value= 2  "
		::= { iqsyn31CmdEntry 3932 }


	iqsyn31EmbeddersEmbedder12SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 2
					Source L / Non-PCM  cmdID= 5040
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5040 }


	iqsyn31EmbeddersEmbedder12SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 2
					Source R  cmdID= 5041
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5041 }


	iqsyn31EmbeddersEmbedder12MutePair2 OBJECT-TYPE
		SYNTAX		INTEGER { disable(0), enable(1) }
		MAX-ACCESS		read-write
		STATUS			current
		DESCRIPTION
				"TYPE: - Checkbox
				 PAGE: - Channel 1- Audio- Embedders- Embedder 1 2
					Mute  cmdID= 3243 "
		::= { iqsyn31CmdEntry 3243 }


	iqsyn31EmbeddersEmbedder12InvertLPair2 OBJECT-TYPE
		SYNTAX		INTEGER { disable(0), enable(1) }
		MAX-ACCESS		read-write
		STATUS			current
		DESCRIPTION
				"TYPE: - Checkbox
				 PAGE: - Channel 1- Audio- Embedders- Embedder 1 2
					Invert L  cmdID= 3166 "
		::= { iqsyn31CmdEntry 3166 }


	iqsyn31EmbeddersEmbedder12InvertRPair2 OBJECT-TYPE
		SYNTAX		INTEGER { disable(0), enable(1) }
		MAX-ACCESS		read-write
		STATUS			current
		DESCRIPTION
				"TYPE: - Checkbox
				 PAGE: - Channel 1- Audio- Embedders- Embedder 1 2
					Invert R  cmdID= 3167 "
		::= { iqsyn31CmdEntry 3167 }


	iqsyn31EmbeddersEmbedder12GainLPair2 OBJECT-TYPE
		SYNTAX		INTEGER
		MAX-ACCESS		read-write
		STATUS			current
		DESCRIPTION
				"TYPE: - Number
				 PAGE: - Channel 1- Audio- Embedders- Embedder 1 2
					Gain L  cmdID= 3086  min= -720  max= 120  step= 1  format= %0.1fdB  divscale= 10
					Min = -72.0dB  Max = 12.0dB  Step = 0.1dB "
		::= { iqsyn31CmdEntry 3086 }


	iqsyn31EmbeddersEmbedder12GainRPair2 OBJECT-TYPE
		SYNTAX		INTEGER
		MAX-ACCESS		read-write
		STATUS			current
		DESCRIPTION
				"TYPE: - Number
				 PAGE: - Channel 1- Audio- Embedders- Embedder 1 2
					Gain R  cmdID= 3087  min= -720  max= 120  step= 1  format= %0.1fdB  divscale= 10
					Min = -72.0dB  Max = 12.0dB  Step = 0.1dB "
		::= { iqsyn31CmdEntry 3087 }


	iqsyn31EmbeddersEmbedder12PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 2
					Pair Mode  cmdID= 3933
					2 Channel PCM  value= 0
					Stereo PCM  value= 1
					nonPCM  value= 2  "
		::= { iqsyn31CmdEntry 3933 }


	iqsyn31EmbeddersEmbedder13Enable OBJECT-TYPE
		SYNTAX		INTEGER { disable(0), enable(1) }
		MAX-ACCESS		read-write
		STATUS			current
		DESCRIPTION
				"TYPE: - Checkbox
				 PAGE: - Channel 1- Audio- Embedders- Embedder 1 3
					Enable  cmdID= 5068 "
		::= { iqsyn31CmdEntry 5068 }


	iqsyn31EmbeddersEmbedder13SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 3
					Source L / Non-PCM  cmdID= 5042
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5042 }


	iqsyn31EmbeddersEmbedder13SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 3
					Source R  cmdID= 5043
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5043 }


	iqsyn31EmbeddersEmbedder13MutePair1 OBJECT-TYPE
		SYNTAX		INTEGER { disable(0), enable(1) }
		MAX-ACCESS		read-write
		STATUS			current
		DESCRIPTION
				"TYPE: - Checkbox
				 PAGE: - Channel 1- Audio- Embedders- Embedder 1 3
					Mute  cmdID= 3244 "
		::= { iqsyn31CmdEntry 3244 }


	iqsyn31EmbeddersEmbedder13InvertLPair1 OBJECT-TYPE
		SYNTAX		INTEGER { disable(0), enable(1) }
		MAX-ACCESS		read-write
		STATUS			current
		DESCRIPTION
				"TYPE: - Checkbox
				 PAGE: - Channel 1- Audio- Embedders- Embedder 1 3
					Invert L  cmdID= 3168 "
		::= { iqsyn31CmdEntry 3168 }


	iqsyn31EmbeddersEmbedder13InvertRPair1 OBJECT-TYPE
		SYNTAX		INTEGER { disable(0), enable(1) }
		MAX-ACCESS		read-write
		STATUS			current
		DESCRIPTION
				"TYPE: - Checkbox
				 PAGE: - Channel 1- Audio- Embedders- Embedder 1 3
					Invert R  cmdID= 3169 "
		::= { iqsyn31CmdEntry 3169 }


	iqsyn31EmbeddersEmbedder13GainLPair1 OBJECT-TYPE
		SYNTAX		INTEGER
		MAX-ACCESS		read-write
		STATUS			current
		DESCRIPTION
				"TYPE: - Number
				 PAGE: - Channel 1- Audio- Embedders- Embedder 1 3
					Gain L  cmdID= 3088  min= -720  max= 120  step= 1  format= %0.1fdB  divscale= 10
					Min = -72.0dB  Max = 12.0dB  Step = 0.1dB "
		::= { iqsyn31CmdEntry 3088 }


	iqsyn31EmbeddersEmbedder13GainRPair1 OBJECT-TYPE
		SYNTAX		INTEGER
		MAX-ACCESS		read-write
		STATUS			current
		DESCRIPTION
				"TYPE: - Number
				 PAGE: - Channel 1- Audio- Embedders- Embedder 1 3
					Gain R  cmdID= 3089  min= -720  max= 120  step= 1  format= %0.1fdB  divscale= 10
					Min = -72.0dB  Max = 12.0dB  Step = 0.1dB "
		::= { iqsyn31CmdEntry 3089 }


	iqsyn31EmbeddersEmbedder13PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 3
					Pair Mode  cmdID= 3934
					2 Channel PCM  value= 0
					Stereo PCM  value= 1
					nonPCM  value= 2  "
		::= { iqsyn31CmdEntry 3934 }


	iqsyn31EmbeddersEmbedder13SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 3
					Source L / Non-PCM  cmdID= 5044
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5044 }


	iqsyn31EmbeddersEmbedder13SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 3
					Source R  cmdID= 5045
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5045 }


	iqsyn31EmbeddersEmbedder13MutePair2 OBJECT-TYPE
		SYNTAX		INTEGER { disable(0), enable(1) }
		MAX-ACCESS		read-write
		STATUS			current
		DESCRIPTION
				"TYPE: - Checkbox
				 PAGE: - Channel 1- Audio- Embedders- Embedder 1 3
					Mute  cmdID= 3245 "
		::= { iqsyn31CmdEntry 3245 }


	iqsyn31EmbeddersEmbedder13InvertLPair2 OBJECT-TYPE
		SYNTAX		INTEGER { disable(0), enable(1) }
		MAX-ACCESS		read-write
		STATUS			current
		DESCRIPTION
				"TYPE: - Checkbox
				 PAGE: - Channel 1- Audio- Embedders- Embedder 1 3
					Invert L  cmdID= 3170 "
		::= { iqsyn31CmdEntry 3170 }


	iqsyn31EmbeddersEmbedder13InvertRPair2 OBJECT-TYPE
		SYNTAX		INTEGER { disable(0), enable(1) }
		MAX-ACCESS		read-write
		STATUS			current
		DESCRIPTION
				"TYPE: - Checkbox
				 PAGE: - Channel 1- Audio- Embedders- Embedder 1 3
					Invert R  cmdID= 3171 "
		::= { iqsyn31CmdEntry 3171 }


	iqsyn31EmbeddersEmbedder13GainLPair2 OBJECT-TYPE
		SYNTAX		INTEGER
		MAX-ACCESS		read-write
		STATUS			current
		DESCRIPTION
				"TYPE: - Number
				 PAGE: - Channel 1- Audio- Embedders- Embedder 1 3
					Gain L  cmdID= 3090  min= -720  max= 120  step= 1  format= %0.1fdB  divscale= 10
					Min = -72.0dB  Max = 12.0dB  Step = 0.1dB "
		::= { iqsyn31CmdEntry 3090 }


	iqsyn31EmbeddersEmbedder13GainRPair2 OBJECT-TYPE
		SYNTAX		INTEGER
		MAX-ACCESS		read-write
		STATUS			current
		DESCRIPTION
				"TYPE: - Number
				 PAGE: - Channel 1- Audio- Embedders- Embedder 1 3
					Gain R  cmdID= 3091  min= -720  max= 120  step= 1  format= %0.1fdB  divscale= 10
					Min = -72.0dB  Max = 12.0dB  Step = 0.1dB "
		::= { iqsyn31CmdEntry 3091 }


	iqsyn31EmbeddersEmbedder13PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 3
					Pair Mode  cmdID= 3935
					2 Channel PCM  value= 0
					Stereo PCM  value= 1
					nonPCM  value= 2  "
		::= { iqsyn31CmdEntry 3935 }


	iqsyn31EmbeddersEmbedder14Enable OBJECT-TYPE
		SYNTAX		INTEGER { disable(0), enable(1) }
		MAX-ACCESS		read-write
		STATUS			current
		DESCRIPTION
				"TYPE: - Checkbox
				 PAGE: - Channel 1- Audio- Embedders- Embedder 1 4
					Enable  cmdID= 5069 "
		::= { iqsyn31CmdEntry 5069 }


	iqsyn31EmbeddersEmbedder14SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 4
					Source L / Non-PCM  cmdID= 5046
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5046 }


	iqsyn31EmbeddersEmbedder14SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 4
					Source R  cmdID= 5047
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5047 }


	iqsyn31EmbeddersEmbedder14MutePair1 OBJECT-TYPE
		SYNTAX		INTEGER { disable(0), enable(1) }
		MAX-ACCESS		read-write
		STATUS			current
		DESCRIPTION
				"TYPE: - Checkbox
				 PAGE: - Channel 1- Audio- Embedders- Embedder 1 4
					Mute  cmdID= 3246 "
		::= { iqsyn31CmdEntry 3246 }


	iqsyn31EmbeddersEmbedder14InvertLPair1 OBJECT-TYPE
		SYNTAX		INTEGER { disable(0), enable(1) }
		MAX-ACCESS		read-write
		STATUS			current
		DESCRIPTION
				"TYPE: - Checkbox
				 PAGE: - Channel 1- Audio- Embedders- Embedder 1 4
					Invert L  cmdID= 3172 "
		::= { iqsyn31CmdEntry 3172 }


	iqsyn31EmbeddersEmbedder14InvertRPair1 OBJECT-TYPE
		SYNTAX		INTEGER { disable(0), enable(1) }
		MAX-ACCESS		read-write
		STATUS			current
		DESCRIPTION
				"TYPE: - Checkbox
				 PAGE: - Channel 1- Audio- Embedders- Embedder 1 4
					Invert R  cmdID= 3173 "
		::= { iqsyn31CmdEntry 3173 }


	iqsyn31EmbeddersEmbedder14GainLPair1 OBJECT-TYPE
		SYNTAX		INTEGER
		MAX-ACCESS		read-write
		STATUS			current
		DESCRIPTION
				"TYPE: - Number
				 PAGE: - Channel 1- Audio- Embedders- Embedder 1 4
					Gain L  cmdID= 3092  min= -720  max= 120  step= 1  format= %0.1fdB  divscale= 10
					Min = -72.0dB  Max = 12.0dB  Step = 0.1dB "
		::= { iqsyn31CmdEntry 3092 }


	iqsyn31EmbeddersEmbedder14GainRPair1 OBJECT-TYPE
		SYNTAX		INTEGER
		MAX-ACCESS		read-write
		STATUS			current
		DESCRIPTION
				"TYPE: - Number
				 PAGE: - Channel 1- Audio- Embedders- Embedder 1 4
					Gain R  cmdID= 3093  min= -720  max= 120  step= 1  format= %0.1fdB  divscale= 10
					Min = -72.0dB  Max = 12.0dB  Step = 0.1dB "
		::= { iqsyn31CmdEntry 3093 }


	iqsyn31EmbeddersEmbedder14PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 4
					Pair Mode  cmdID= 3936
					2 Channel PCM  value= 0
					Stereo PCM  value= 1
					nonPCM  value= 2  "
		::= { iqsyn31CmdEntry 3936 }


	iqsyn31EmbeddersEmbedder14SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 1- Audio- Embedders- Embedder 1 4
					Source L / Non-PCM  cmdID= 5048
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5048 }


	iqsyn31EmbeddersEmbedder14SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 1- Audio- Embedders- Embedder 1 4
					Source R  cmdID= 5049
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5049 }


	iqsyn31EmbeddersEmbedder14MutePair2 OBJECT-TYPE
		SYNTAX		INTEGER { disable(0), enable(1) }
		MAX-ACCESS		read-write
		STATUS			current
		DESCRIPTION
				"TYPE: - Checkbox
				 PAGE: - Channel 1- Audio- Embedders- Embedder 1 4
					Mute  cmdID= 3247 "
		::= { iqsyn31CmdEntry 3247 }


	iqsyn31EmbeddersEmbedder14InvertLPair2 OBJECT-TYPE
		SYNTAX		INTEGER { disable(0), enable(1) }
		MAX-ACCESS		read-write
		STATUS			current
		DESCRIPTION
				"TYPE: - Checkbox
				 PAGE: - Channel 1- Audio- Embedders- Embedder 1 4
					Invert L  cmdID= 3174 "
		::= { iqsyn31CmdEntry 3174 }


	iqsyn31EmbeddersEmbedder14InvertRPair2 OBJECT-TYPE
		SYNTAX		INTEGER { disable(0), enable(1) }
		MAX-ACCESS		read-write
		STATUS			current
		DESCRIPTION
				"TYPE: - Checkbox
				 PAGE: - Channel 1- Audio- Embedders- Embedder 1 4
					Invert R  cmdID= 3175 "
		::= { iqsyn31CmdEntry 3175 }


	iqsyn31EmbeddersEmbedder14GainLPair2 OBJECT-TYPE
		SYNTAX		INTEGER
		MAX-ACCESS		read-write
		STATUS			current
		DESCRIPTION
				"TYPE: - Number
				 PAGE: - Channel 1- Audio- Embedders- Embedder 1 4
					Gain L  cmdID= 3094  min= -720  max= 120  step= 1  format= %0.1fdB  divscale= 10
					Min = -72.0dB  Max = 12.0dB  Step = 0.1dB "
		::= { iqsyn31CmdEntry 3094 }


	iqsyn31EmbeddersEmbedder14GainRPair2 OBJECT-TYPE
		SYNTAX		INTEGER
		MAX-ACCESS		read-write
		STATUS			current
		DESCRIPTION
				"TYPE: - Number
				 PAGE: - Channel 1- Audio- Embedders- Embedder 1 4
					Gain R  cmdID= 3095  min= -720  max= 120  step= 1  format= %0.1fdB  divscale= 10
					Min = -72.0dB  Max = 12.0dB  Step = 0.1dB "
		::= { iqsyn31CmdEntry 3095 }


	iqsyn31EmbeddersEmbedder14PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 1- Audio- Embedders- Embedder 1 4
					Pair Mode  cmdID= 3937
					2 Channel PCM  value= 0
					Stereo PCM  value= 1
					nonPCM  value= 2  "
		::= { iqsyn31CmdEntry 3937 }


	iqsyn31Channel1AudioFrequency OBJECT-TYPE
		SYNTAX		INTEGER
		MAX-ACCESS		read-write
		STATUS			current
		DESCRIPTION
				"TYPE: - Number
				 PAGE: - Channel 1- Audio
					Frequency  cmdID= 2487  min= 100  max= 10000  step= 100  format= %5.0fHz  divscale= 1
					Min =   100Hz  Max = 10000Hz  Step =   100Hz "
		::= { iqsyn31CmdEntry 2487 }


	iqsyn31Channel1AudioChannelident OBJECT-TYPE
		SYNTAX		INTEGER { disable(0), enable(1) }
		MAX-ACCESS		read-write
		STATUS			current
		DESCRIPTION
				"TYPE: - Checkbox
				 PAGE: - Channel 1- Audio
					Channel ident  cmdID= 5030 "
		::= { iqsyn31CmdEntry 5030 }


	iqsyn31Channel1AudioTotaldelay OBJECT-TYPE
		SYNTAX		RollCallString
		MAX-ACCESS		read-only
		STATUS			current
		DESCRIPTION
				"TYPE: - Display
				 PAGE: - Channel 1- Audio
					Total delay  cmdID= 5084  format=   "
		::= { iqsyn31CmdEntry 5084 }


	iqsyn31Channel1AudioActiveVideodelay OBJECT-TYPE
		SYNTAX		RollCallString
		MAX-ACCESS		read-only
		STATUS			current
		DESCRIPTION
				"TYPE: - Display
				 PAGE: - Channel 1- Audio
					Video delay  cmdID= 5074  format=   "
		::= { iqsyn31CmdEntry 5074 }


	iqsyn31Channel1Audiomanualdelay OBJECT-TYPE
		SYNTAX		RollCallString
		MAX-ACCESS		read-only
		STATUS			current
		DESCRIPTION
				"TYPE: - Display
				 PAGE: - Channel 1- Audio
					manual delay  cmdID= 5076  format=   "
		::= { iqsyn31CmdEntry 5076 }


	iqsyn31Channel1AudioTrack14delay OBJECT-TYPE
		SYNTAX		RollCallString
		MAX-ACCESS		read-only
		STATUS			current
		DESCRIPTION
				"TYPE: - Display
				 PAGE: - Channel 1- Audio
					Track 14 delay  cmdID= 3924  format=   "
		::= { iqsyn31CmdEntry 3924 }


	iqsyn31Channel1AudioTrack15delay OBJECT-TYPE
		SYNTAX		RollCallString
		MAX-ACCESS		read-only
		STATUS			current
		DESCRIPTION
				"TYPE: - Display
				 PAGE: - Channel 1- Audio
					Track 15 delay  cmdID= 3925  format=   "
		::= { iqsyn31CmdEntry 3925 }


	iqsyn31Channel1AudioTrack16delay OBJECT-TYPE
		SYNTAX		RollCallString
		MAX-ACCESS		read-only
		STATUS			current
		DESCRIPTION
				"TYPE: - Display
				 PAGE: - Channel 1- Audio
					Track 16 delay  cmdID= 3926  format=   "
		::= { iqsyn31CmdEntry 3926 }


	iqsyn31Channel1AudioTrack17delay OBJECT-TYPE
		SYNTAX		RollCallString
		MAX-ACCESS		read-only
		STATUS			current
		DESCRIPTION
				"TYPE: - Display
				 PAGE: - Channel 1- Audio
					Track 17 delay  cmdID= 3927  format=   "
		::= { iqsyn31CmdEntry 3927 }


	iqsyn31Channel1AudioVideodelayEnable OBJECT-TYPE
		SYNTAX		INTEGER { disable(0), enable(1) }
		MAX-ACCESS		read-write
		STATUS			current
		DESCRIPTION
				"TYPE: - Checkbox
				 PAGE: - Channel 1- Audio
					Video delay  cmdID= 5078 "
		::= { iqsyn31CmdEntry 5078 }


	iqsyn31Channel1AudiomanualdelayEnable OBJECT-TYPE
		SYNTAX		INTEGER { disable(0), enable(1) }
		MAX-ACCESS		read-write
		STATUS			current
		DESCRIPTION
				"TYPE: - Checkbox
				 PAGE: - Channel 1- Audio
					manual delay  cmdID= 5079 "
		::= { iqsyn31CmdEntry 5079 }


	iqsyn31Channel1AudioTrack14delayEnable OBJECT-TYPE
		SYNTAX		INTEGER { disable(0), enable(1) }
		MAX-ACCESS		read-write
		STATUS			current
		DESCRIPTION
				"TYPE: - Checkbox
				 PAGE: - Channel 1- Audio
					Track 14 delay  cmdID= 5080 "
		::= { iqsyn31CmdEntry 5080 }


	iqsyn31Channel1AudioTrack15delayEnable OBJECT-TYPE
		SYNTAX		INTEGER { disable(0), enable(1) }
		MAX-ACCESS		read-write
		STATUS			current
		DESCRIPTION
				"TYPE: - Checkbox
				 PAGE: - Channel 1- Audio
					Track 15 delay  cmdID= 5081 "
		::= { iqsyn31CmdEntry 5081 }


	iqsyn31Channel1AudioTrack16delayEnable OBJECT-TYPE
		SYNTAX		INTEGER { disable(0), enable(1) }
		MAX-ACCESS		read-write
		STATUS			current
		DESCRIPTION
				"TYPE: - Checkbox
				 PAGE: - Channel 1- Audio
					Track 16 delay  cmdID= 5082 "
		::= { iqsyn31CmdEntry 5082 }


	iqsyn31Channel1AudioTrack17delayEnable OBJECT-TYPE
		SYNTAX		INTEGER { disable(0), enable(1) }
		MAX-ACCESS		read-write
		STATUS			current
		DESCRIPTION
				"TYPE: - Checkbox
				 PAGE: - Channel 1- Audio
					Track 17 delay  cmdID= 5083 "
		::= { iqsyn31CmdEntry 5083 }


	iqsyn31Channel1AudioCoarse OBJECT-TYPE
		SYNTAX		INTEGER
		MAX-ACCESS		read-write
		STATUS			current
		DESCRIPTION
				"TYPE: - Number
				 PAGE: - Channel 1- Audio
					Coarse  cmdID= 5075  min= 0  max= 1750  step= 5  format= %5.3fs  divscale= 1000
					Min = 0.000s  Max = 1.750s  Step = 0.005s "
		::= { iqsyn31CmdEntry 5075 }


	iqsyn31Channel1AudioFine OBJECT-TYPE
		SYNTAX		INTEGER
		MAX-ACCESS		read-write
		STATUS			current
		DESCRIPTION
				"TYPE: - Number
				 PAGE: - Channel 1- Audio
					Fine  cmdID= 5077  min= -2500  max= 2500  step= 5  format= %0.1fms  divscale= 10
					Min = -250.0ms  Max = 250.0ms  Step = 0.5ms "
		::= { iqsyn31CmdEntry 5077 }


	iqsyn31Channel1AudioDolbyEautoalign OBJECT-TYPE
		SYNTAX		INTEGER { disable(0), enable(1) }
		MAX-ACCESS		read-write
		STATUS			current
		DESCRIPTION
				"TYPE: - Checkbox
				 PAGE: - Channel 1- Audio
					Dolby E auto align  cmdID= 5032 "
		::= { iqsyn31CmdEntry 5032 }


	iqsyn31Channel1AudioSilenceLevel OBJECT-TYPE
		SYNTAX		INTEGER
		MAX-ACCESS		read-write
		STATUS			current
		DESCRIPTION
				"TYPE: - Number
				 PAGE: - Channel 1- Audio
					Silence Level  cmdID= 3061  min= -80  max= 0  step= 1  format= %1.0f dB  divscale= 1
					Min = -80 dB  Max = 0 dB  Step = 1 dB "
		::= { iqsyn31CmdEntry 3061 }


	iqsyn31Channel1AudioOverloadLevel OBJECT-TYPE
		SYNTAX		INTEGER
		MAX-ACCESS		read-write
		STATUS			current
		DESCRIPTION
				"TYPE: - Number
				 PAGE: - Channel 1- Audio
					Overload Level  cmdID= 3064  min= -80  max= 0  step= 1  format= %1.0f dB  divscale= 1
					Min = -80 dB  Max = 0 dB  Step = 1 dB "
		::= { iqsyn31CmdEntry 3064 }


	iqsyn31Channel1AudioWarningTimer OBJECT-TYPE
		SYNTAX		INTEGER
		MAX-ACCESS		read-write
		STATUS			current
		DESCRIPTION
				"TYPE: - Number
				 PAGE: - Channel 1- Audio
					Warning Timer  cmdID= 3065  min= 1  max= 20  step= 1  format= %1.0f sec  divscale= 1
					Min = 1 sec  Max = 20 sec  Step = 1 sec "
		::= { iqsyn31CmdEntry 3065 }


	iqsyn31Channel2VideoVANCBlank2 OBJECT-TYPE
		SYNTAX		INTEGER { disable(0), enable(1) }
		MAX-ACCESS		read-write
		STATUS			current
		DESCRIPTION
				"TYPE: - Checkbox
				 PAGE: - Channel 2- Video
					VANC Blank 2  cmdID= 3950 "
		::= { iqsyn31CmdEntry 3950 }


	iqsyn31Video2625BlankLinesLine232 OBJECT-TYPE
		SYNTAX		INTEGER { disable(0), enable(1) }
		MAX-ACCESS		read-write
		STATUS			current
		DESCRIPTION
				"TYPE: - Checkbox
				 PAGE: - Channel 2- Video
					Line 23 2  cmdID= 3971 "
		::= { iqsyn31CmdEntry 3971 }


	iqsyn31Video2625BlankLinesLine3362 OBJECT-TYPE
		SYNTAX		INTEGER { disable(0), enable(1) }
		MAX-ACCESS		read-write
		STATUS			current
		DESCRIPTION
				"TYPE: - Checkbox
				 PAGE: - Channel 2- Video
					Line 336 2  cmdID= 3972 "
		::= { iqsyn31CmdEntry 3972 }


	iqsyn31Video2525BlankLinesLine212 OBJECT-TYPE
		SYNTAX		INTEGER { disable(0), enable(1) }
		MAX-ACCESS		read-write
		STATUS			current
		DESCRIPTION
				"TYPE: - Checkbox
				 PAGE: - Channel 2- Video
					Line 21 2  cmdID= 3973 "
		::= { iqsyn31CmdEntry 3973 }


	iqsyn31Video2525BlankLinesLine222 OBJECT-TYPE
		SYNTAX		INTEGER { disable(0), enable(1) }
		MAX-ACCESS		read-write
		STATUS			current
		DESCRIPTION
				"TYPE: - Checkbox
				 PAGE: - Channel 2- Video
					Line 22 2  cmdID= 3974 "
		::= { iqsyn31CmdEntry 3974 }


	iqsyn31Video2525BlankLinesLine2832 OBJECT-TYPE
		SYNTAX		INTEGER { disable(0), enable(1) }
		MAX-ACCESS		read-write
		STATUS			current
		DESCRIPTION
				"TYPE: - Checkbox
				 PAGE: - Channel 2- Video
					Line 283 2  cmdID= 3975 "
		::= { iqsyn31CmdEntry 3975 }


	iqsyn31Video2525BlankLinesLine2842 OBJECT-TYPE
		SYNTAX		INTEGER { disable(0), enable(1) }
		MAX-ACCESS		read-write
		STATUS			current
		DESCRIPTION
				"TYPE: - Checkbox
				 PAGE: - Channel 2- Video
					Line 284 2  cmdID= 3976 "
		::= { iqsyn31CmdEntry 3976 }


	iqsyn31Channel2Video5025 OBJECT-TYPE
		SYNTAX		INTEGER {
							valField(0),
							valFrame(1)
							}
		MAX-ACCESS		read-write
		STATUS			current
		DESCRIPTION
				"TYPE: - Button
				 PAGE: - Channel 2- Video
					Field  cmdID= 5025  value= 0
					Frame  cmdID= 5025  value= 1  "
		::= { iqsyn31CmdEntry 5025 }


	iqsyn31Channel2VideoManualFreeze OBJECT-TYPE
		SYNTAX		INTEGER { disable(0), enable(1) }
		MAX-ACCESS		read-write
		STATUS			current
		DESCRIPTION
				"TYPE: - Checkbox
				 PAGE: - Channel 2- Video
					Manual Freeze  cmdID= 5024 "
		::= { iqsyn31CmdEntry 5024 }


	iqsyn31Channel2VideoDefault OBJECT-TYPE
		SYNTAX		INTEGER {
							valBlack(0),
							valFreeze(1),
							valPattern(2)
							}
		MAX-ACCESS		read-write
		STATUS			current
		DESCRIPTION
				"TYPE: - Button
				 PAGE: - Channel 2- Video
					Black  cmdID= 2628  value= 0
					Freeze  cmdID= 2628  value= 1
					Pattern  cmdID= 2628  value= 2  "
		::= { iqsyn31CmdEntry 2628 }


	iqsyn31Channel2VideoPatSelect OBJECT-TYPE
		SYNTAX		INTEGER {
							valOff(0),
							valBlack(1),
							valBars(2)
							}
		MAX-ACCESS		read-write
		STATUS			current
		DESCRIPTION
				"TYPE: - Button
				 PAGE: - Channel 2- Video
					Off  cmdID= 2629  value= 0
					Black  cmdID= 2629  value= 1
					Bars  cmdID= 2629  value= 2  "
		::= { iqsyn31CmdEntry 2629 }


	iqsyn31Channel2VideoProcAmpEnable OBJECT-TYPE
		SYNTAX		INTEGER { disable(0), enable(1) }
		MAX-ACCESS		read-write
		STATUS			current
		DESCRIPTION
				"TYPE: - Checkbox
				 PAGE: - Channel 2- Video
					ProcAmp Enable  cmdID= 2865 "
		::= { iqsyn31CmdEntry 2865 }


	iqsyn31Channel2VideoBlackLevel OBJECT-TYPE
		SYNTAX		INTEGER
		MAX-ACCESS		read-write
		STATUS			current
		DESCRIPTION
				"TYPE: - Number
				 PAGE: - Channel 2- Video
					Black Level  cmdID= 2712  min= -1000  max= 1000  step= 8  format= %3.1fmV  divscale= 10
					Min = -100.0mV  Max = 100.0mV  Step = 0.8mV "
		::= { iqsyn31CmdEntry 2712 }


	iqsyn31Channel2VideoHueAdjust OBJECT-TYPE
		SYNTAX		INTEGER
		MAX-ACCESS		read-write
		STATUS			current
		DESCRIPTION
				"TYPE: - Number
				 PAGE: - Channel 2- Video
					Hue Adjust  cmdID= 3630  min= -180  max= 180  step= 1  format= %1.0fdeg  divscale= 1
					Min = -180deg  Max = 180deg  Step = 1deg "
		::= { iqsyn31CmdEntry 3630 }


	iqsyn31Channel2VideoMasterVideoGain OBJECT-TYPE
		SYNTAX		INTEGER
		MAX-ACCESS		read-write
		STATUS			current
		DESCRIPTION
				"TYPE: - Number
				 PAGE: - Channel 2- Video
					Master Video Gain  cmdID= 3788  min= -60  max= 60  step= 1  format= %0.1fdB  divscale= 10
					Min = -6.0dB  Max = 6.0dB  Step = 0.1dB "
		::= { iqsyn31CmdEntry 3788 }


	iqsyn31Channel2VideoYGain OBJECT-TYPE
		SYNTAX		INTEGER
		MAX-ACCESS		read-write
		STATUS			current
		DESCRIPTION
				"TYPE: - Number
				 PAGE: - Channel 2- Video
					Y Gain  cmdID= 2711  min= -60  max= 60  step= 1  format= %0.1fdB  divscale= 10
					Min = -6.0dB  Max = 6.0dB  Step = 0.1dB "
		::= { iqsyn31CmdEntry 2711 }


	iqsyn31Channel2VideoCbCrGain OBJECT-TYPE
		SYNTAX		INTEGER
		MAX-ACCESS		read-write
		STATUS			current
		DESCRIPTION
				"TYPE: - Number
				 PAGE: - Channel 2- Video
					Cb/Cr Gain  cmdID= 2710  min= -60  max= 60  step= 1  format= %0.1fdB  divscale= 10
					Min = -6.0dB  Max = 6.0dB  Step = 0.1dB "
		::= { iqsyn31CmdEntry 2710 }


	iqsyn31Channel2VideoYCTiming OBJECT-TYPE
		SYNTAX		INTEGER
		MAX-ACCESS		read-write
		STATUS			current
		DESCRIPTION
				"TYPE: - Number
				 PAGE: - Channel 2- Video
					Y/C Timing  cmdID= 2925  min= -8  max= 8  step= 2  format= %1.0f pixels  divscale= 1
					Min = -8 pixels  Max = 8 pixels  Step = 2 pixels "
		::= { iqsyn31CmdEntry 2925 }


	iqsyn31Channel2VideoPictureposition OBJECT-TYPE
		SYNTAX		INTEGER
		MAX-ACCESS		read-write
		STATUS			current
		DESCRIPTION
				"TYPE: - Number
				 PAGE: - Channel 2- Video
					Picture position  cmdID= 2713  min= -8  max= 8  step= 2  format= %1.0f pixels  divscale= 1
					Min = -8 pixels  Max = 8 pixels  Step = 2 pixels "
		::= { iqsyn31CmdEntry 2713 }


	iqsyn31Channel2VideoModalIndex OBJECT-TYPE
		SYNTAX		INTEGER
		MAX-ACCESS		read-write
		STATUS			current
		DESCRIPTION
				"TYPE: - Number
				 PAGE: - Channel 2- Video
					Modal Index  cmdID= 5009  min= 0  max= 1  step= 1  format= %1.0f  divscale= 1
					Min = 0  Max = 1  Step = 1 "
		::= { iqsyn31CmdEntry 5009 }


	iqsyn31Channel2VideoYCTimingnm OBJECT-TYPE
		SYNTAX		INTEGER
		MAX-ACCESS		read-write
		STATUS			current
		DESCRIPTION
				"TYPE: - Number
				 PAGE: - Channel 2- Video
					Y/C Timing nm  cmdID= 5011  min= -16  max= 16  step= 2  format= %1.0f pixels  divscale= 1
					Min = -16 pixels  Max = 16 pixels  Step = 2 pixels "
		::= { iqsyn31CmdEntry 5011 }


	iqsyn31Channel2VideoPicturepositionnm OBJECT-TYPE
		SYNTAX		INTEGER
		MAX-ACCESS		read-write
		STATUS			current
		DESCRIPTION
				"TYPE: - Number
				 PAGE: - Channel 2- Video
					Picture position nm  cmdID= 5010  min= -16  max= 16  step= 2  format= %1.0f pixels  divscale= 1
					Min = -16 pixels  Max = 16 pixels  Step = 2 pixels "
		::= { iqsyn31CmdEntry 5010 }


	iqsyn31Channel2VideoCaption OBJECT-TYPE
		SYNTAX		INTEGER {
							valOff(0),
							valOn(1)
							}
		MAX-ACCESS		read-write
		STATUS			current
		DESCRIPTION
				"TYPE: - Button
				 PAGE: - Channel 2- Video
					Off  cmdID= 1039  value= 0
					On  cmdID= 1039  value= 1  "
		::= { iqsyn31CmdEntry 1039 }


	iqsyn31Channel2VideoText OBJECT-TYPE
		SYNTAX		RollCallString
		MAX-ACCESS		read-write
		STATUS			current
		DESCRIPTION
				"TYPE: - Editstring
				 PAGE: - Channel 2- Video
					Text  cmdID= 1040  "
		::= { iqsyn31CmdEntry 1040 }


	iqsyn31Channel2AudioHANKBlank2 OBJECT-TYPE
		SYNTAX		INTEGER { disable(0), enable(1) }
		MAX-ACCESS		read-write
		STATUS			current
		DESCRIPTION
				"TYPE: - Checkbox
				 PAGE: - Channel 2- Audio
					HANK Blank 2  cmdID= 3948 "
		::= { iqsyn31CmdEntry 3948 }


	iqsyn31EmbeddersEmbedder21Enable OBJECT-TYPE
		SYNTAX		INTEGER { disable(0), enable(1) }
		MAX-ACCESS		read-write
		STATUS			current
		DESCRIPTION
				"TYPE: - Checkbox
				 PAGE: - Channel 2- Audio- Embedders- Embedder 2 1
					Enable  cmdID= 5070 "
		::= { iqsyn31CmdEntry 5070 }


	iqsyn31EmbeddersEmbedder21SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 1
					Source L / Non-PCM  cmdID= 5050
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5050 }


	iqsyn31EmbeddersEmbedder21SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 1
					Source R  cmdID= 5051
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5051 }


	iqsyn31EmbeddersEmbedder21MutePair1 OBJECT-TYPE
		SYNTAX		INTEGER { disable(0), enable(1) }
		MAX-ACCESS		read-write
		STATUS			current
		DESCRIPTION
				"TYPE: - Checkbox
				 PAGE: - Channel 2- Audio- Embedders- Embedder 2 1
					Mute  cmdID= 3248 "
		::= { iqsyn31CmdEntry 3248 }


	iqsyn31EmbeddersEmbedder21InvertLPair1 OBJECT-TYPE
		SYNTAX		INTEGER { disable(0), enable(1) }
		MAX-ACCESS		read-write
		STATUS			current
		DESCRIPTION
				"TYPE: - Checkbox
				 PAGE: - Channel 2- Audio- Embedders- Embedder 2 1
					Invert L  cmdID= 3176 "
		::= { iqsyn31CmdEntry 3176 }


	iqsyn31EmbeddersEmbedder21InvertRPair1 OBJECT-TYPE
		SYNTAX		INTEGER { disable(0), enable(1) }
		MAX-ACCESS		read-write
		STATUS			current
		DESCRIPTION
				"TYPE: - Checkbox
				 PAGE: - Channel 2- Audio- Embedders- Embedder 2 1
					Invert R  cmdID= 3177 "
		::= { iqsyn31CmdEntry 3177 }


	iqsyn31EmbeddersEmbedder21GainLPair1 OBJECT-TYPE
		SYNTAX		INTEGER
		MAX-ACCESS		read-write
		STATUS			current
		DESCRIPTION
				"TYPE: - Number
				 PAGE: - Channel 2- Audio- Embedders- Embedder 2 1
					Gain L  cmdID= 3096  min= -720  max= 120  step= 1  format= %0.1fdB  divscale= 10
					Min = -72.0dB  Max = 12.0dB  Step = 0.1dB "
		::= { iqsyn31CmdEntry 3096 }


	iqsyn31EmbeddersEmbedder21GainRPair1 OBJECT-TYPE
		SYNTAX		INTEGER
		MAX-ACCESS		read-write
		STATUS			current
		DESCRIPTION
				"TYPE: - Number
				 PAGE: - Channel 2- Audio- Embedders- Embedder 2 1
					Gain R  cmdID= 3097  min= -720  max= 120  step= 1  format= %0.1fdB  divscale= 10
					Min = -72.0dB  Max = 12.0dB  Step = 0.1dB "
		::= { iqsyn31CmdEntry 3097 }


	iqsyn31EmbeddersEmbedder21PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 1
					Pair Mode  cmdID= 3938
					2 Channel PCM  value= 0
					Stereo PCM  value= 1
					nonPCM  value= 2  "
		::= { iqsyn31CmdEntry 3938 }


	iqsyn31EmbeddersEmbedder21SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 1
					Source L / Non-PCM  cmdID= 5052
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5052 }


	iqsyn31EmbeddersEmbedder21SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 1
					Source R  cmdID= 5053
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5053 }


	iqsyn31EmbeddersEmbedder21MutePair2 OBJECT-TYPE
		SYNTAX		INTEGER { disable(0), enable(1) }
		MAX-ACCESS		read-write
		STATUS			current
		DESCRIPTION
				"TYPE: - Checkbox
				 PAGE: - Channel 2- Audio- Embedders- Embedder 2 1
					Mute  cmdID= 3249 "
		::= { iqsyn31CmdEntry 3249 }


	iqsyn31EmbeddersEmbedder21InvertLPair2 OBJECT-TYPE
		SYNTAX		INTEGER { disable(0), enable(1) }
		MAX-ACCESS		read-write
		STATUS			current
		DESCRIPTION
				"TYPE: - Checkbox
				 PAGE: - Channel 2- Audio- Embedders- Embedder 2 1
					Invert L  cmdID= 3178 "
		::= { iqsyn31CmdEntry 3178 }


	iqsyn31EmbeddersEmbedder21InvertRPair2 OBJECT-TYPE
		SYNTAX		INTEGER { disable(0), enable(1) }
		MAX-ACCESS		read-write
		STATUS			current
		DESCRIPTION
				"TYPE: - Checkbox
				 PAGE: - Channel 2- Audio- Embedders- Embedder 2 1
					Invert R  cmdID= 3179 "
		::= { iqsyn31CmdEntry 3179 }


	iqsyn31EmbeddersEmbedder21GainLPair2 OBJECT-TYPE
		SYNTAX		INTEGER
		MAX-ACCESS		read-write
		STATUS			current
		DESCRIPTION
				"TYPE: - Number
				 PAGE: - Channel 2- Audio- Embedders- Embedder 2 1
					Gain L  cmdID= 3098  min= -720  max= 120  step= 1  format= %0.1fdB  divscale= 10
					Min = -72.0dB  Max = 12.0dB  Step = 0.1dB "
		::= { iqsyn31CmdEntry 3098 }


	iqsyn31EmbeddersEmbedder21GainRPair2 OBJECT-TYPE
		SYNTAX		INTEGER
		MAX-ACCESS		read-write
		STATUS			current
		DESCRIPTION
				"TYPE: - Number
				 PAGE: - Channel 2- Audio- Embedders- Embedder 2 1
					Gain R  cmdID= 3099  min= -720  max= 120  step= 1  format= %0.1fdB  divscale= 10
					Min = -72.0dB  Max = 12.0dB  Step = 0.1dB "
		::= { iqsyn31CmdEntry 3099 }


	iqsyn31EmbeddersEmbedder21PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 1
					Pair Mode  cmdID= 3939
					2 Channel PCM  value= 0
					Stereo PCM  value= 1
					nonPCM  value= 2  "
		::= { iqsyn31CmdEntry 3939 }


	iqsyn31EmbeddersEmbedder22Enable OBJECT-TYPE
		SYNTAX		INTEGER { disable(0), enable(1) }
		MAX-ACCESS		read-write
		STATUS			current
		DESCRIPTION
				"TYPE: - Checkbox
				 PAGE: - Channel 2- Audio- Embedders- Embedder 2 2
					Enable  cmdID= 5071 "
		::= { iqsyn31CmdEntry 5071 }


	iqsyn31EmbeddersEmbedder22SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 2
					Source L / Non-PCM  cmdID= 5054
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5054 }


	iqsyn31EmbeddersEmbedder22SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 2
					Source R  cmdID= 5055
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5055 }


	iqsyn31EmbeddersEmbedder22MutePair1 OBJECT-TYPE
		SYNTAX		INTEGER { disable(0), enable(1) }
		MAX-ACCESS		read-write
		STATUS			current
		DESCRIPTION
				"TYPE: - Checkbox
				 PAGE: - Channel 2- Audio- Embedders- Embedder 2 2
					Mute  cmdID= 3250 "
		::= { iqsyn31CmdEntry 3250 }


	iqsyn31EmbeddersEmbedder22InvertLPair1 OBJECT-TYPE
		SYNTAX		INTEGER { disable(0), enable(1) }
		MAX-ACCESS		read-write
		STATUS			current
		DESCRIPTION
				"TYPE: - Checkbox
				 PAGE: - Channel 2- Audio- Embedders- Embedder 2 2
					Invert L  cmdID= 3180 "
		::= { iqsyn31CmdEntry 3180 }


	iqsyn31EmbeddersEmbedder22InvertRPair1 OBJECT-TYPE
		SYNTAX		INTEGER { disable(0), enable(1) }
		MAX-ACCESS		read-write
		STATUS			current
		DESCRIPTION
				"TYPE: - Checkbox
				 PAGE: - Channel 2- Audio- Embedders- Embedder 2 2
					Invert R  cmdID= 3181 "
		::= { iqsyn31CmdEntry 3181 }


	iqsyn31EmbeddersEmbedder22GainLPair1 OBJECT-TYPE
		SYNTAX		INTEGER
		MAX-ACCESS		read-write
		STATUS			current
		DESCRIPTION
				"TYPE: - Number
				 PAGE: - Channel 2- Audio- Embedders- Embedder 2 2
					Gain L  cmdID= 3100  min= -720  max= 120  step= 1  format= %0.1fdB  divscale= 10
					Min = -72.0dB  Max = 12.0dB  Step = 0.1dB "
		::= { iqsyn31CmdEntry 3100 }


	iqsyn31EmbeddersEmbedder22GainRPair1 OBJECT-TYPE
		SYNTAX		INTEGER
		MAX-ACCESS		read-write
		STATUS			current
		DESCRIPTION
				"TYPE: - Number
				 PAGE: - Channel 2- Audio- Embedders- Embedder 2 2
					Gain R  cmdID= 3101  min= -720  max= 120  step= 1  format= %0.1fdB  divscale= 10
					Min = -72.0dB  Max = 12.0dB  Step = 0.1dB "
		::= { iqsyn31CmdEntry 3101 }


	iqsyn31EmbeddersEmbedder22PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 2
					Pair Mode  cmdID= 3940
					2 Channel PCM  value= 0
					Stereo PCM  value= 1
					nonPCM  value= 2  "
		::= { iqsyn31CmdEntry 3940 }


	iqsyn31EmbeddersEmbedder22SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 2
					Source L / Non-PCM  cmdID= 5056
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5056 }


	iqsyn31EmbeddersEmbedder22SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 2
					Source R  cmdID= 5057
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5057 }


	iqsyn31EmbeddersEmbedder22MutePair2 OBJECT-TYPE
		SYNTAX		INTEGER { disable(0), enable(1) }
		MAX-ACCESS		read-write
		STATUS			current
		DESCRIPTION
				"TYPE: - Checkbox
				 PAGE: - Channel 2- Audio- Embedders- Embedder 2 2
					Mute  cmdID= 3251 "
		::= { iqsyn31CmdEntry 3251 }


	iqsyn31EmbeddersEmbedder22InvertLPair2 OBJECT-TYPE
		SYNTAX		INTEGER { disable(0), enable(1) }
		MAX-ACCESS		read-write
		STATUS			current
		DESCRIPTION
				"TYPE: - Checkbox
				 PAGE: - Channel 2- Audio- Embedders- Embedder 2 2
					Invert L  cmdID= 3182 "
		::= { iqsyn31CmdEntry 3182 }


	iqsyn31EmbeddersEmbedder22InvertRPair2 OBJECT-TYPE
		SYNTAX		INTEGER { disable(0), enable(1) }
		MAX-ACCESS		read-write
		STATUS			current
		DESCRIPTION
				"TYPE: - Checkbox
				 PAGE: - Channel 2- Audio- Embedders- Embedder 2 2
					Invert R  cmdID= 3183 "
		::= { iqsyn31CmdEntry 3183 }


	iqsyn31EmbeddersEmbedder22GainLPair2 OBJECT-TYPE
		SYNTAX		INTEGER
		MAX-ACCESS		read-write
		STATUS			current
		DESCRIPTION
				"TYPE: - Number
				 PAGE: - Channel 2- Audio- Embedders- Embedder 2 2
					Gain L  cmdID= 3102  min= -720  max= 120  step= 1  format= %0.1fdB  divscale= 10
					Min = -72.0dB  Max = 12.0dB  Step = 0.1dB "
		::= { iqsyn31CmdEntry 3102 }


	iqsyn31EmbeddersEmbedder22GainRPair2 OBJECT-TYPE
		SYNTAX		INTEGER
		MAX-ACCESS		read-write
		STATUS			current
		DESCRIPTION
				"TYPE: - Number
				 PAGE: - Channel 2- Audio- Embedders- Embedder 2 2
					Gain R  cmdID= 3103  min= -720  max= 120  step= 1  format= %0.1fdB  divscale= 10
					Min = -72.0dB  Max = 12.0dB  Step = 0.1dB "
		::= { iqsyn31CmdEntry 3103 }


	iqsyn31EmbeddersEmbedder22PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 2
					Pair Mode  cmdID= 3941
					2 Channel PCM  value= 0
					Stereo PCM  value= 1
					nonPCM  value= 2  "
		::= { iqsyn31CmdEntry 3941 }


	iqsyn31EmbeddersEmbedder23Enable OBJECT-TYPE
		SYNTAX		INTEGER { disable(0), enable(1) }
		MAX-ACCESS		read-write
		STATUS			current
		DESCRIPTION
				"TYPE: - Checkbox
				 PAGE: - Channel 2- Audio- Embedders- Embedder 2 3
					Enable  cmdID= 5072 "
		::= { iqsyn31CmdEntry 5072 }


	iqsyn31EmbeddersEmbedder23SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 3
					Source L / Non-PCM  cmdID= 5058
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5058 }


	iqsyn31EmbeddersEmbedder23SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 3
					Source R  cmdID= 5059
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5059 }


	iqsyn31EmbeddersEmbedder23MutePair1 OBJECT-TYPE
		SYNTAX		INTEGER { disable(0), enable(1) }
		MAX-ACCESS		read-write
		STATUS			current
		DESCRIPTION
				"TYPE: - Checkbox
				 PAGE: - Channel 2- Audio- Embedders- Embedder 2 3
					Mute  cmdID= 3252 "
		::= { iqsyn31CmdEntry 3252 }


	iqsyn31EmbeddersEmbedder23InvertLPair1 OBJECT-TYPE
		SYNTAX		INTEGER { disable(0), enable(1) }
		MAX-ACCESS		read-write
		STATUS			current
		DESCRIPTION
				"TYPE: - Checkbox
				 PAGE: - Channel 2- Audio- Embedders- Embedder 2 3
					Invert L  cmdID= 3184 "
		::= { iqsyn31CmdEntry 3184 }


	iqsyn31EmbeddersEmbedder23InvertRPair1 OBJECT-TYPE
		SYNTAX		INTEGER { disable(0), enable(1) }
		MAX-ACCESS		read-write
		STATUS			current
		DESCRIPTION
				"TYPE: - Checkbox
				 PAGE: - Channel 2- Audio- Embedders- Embedder 2 3
					Invert R  cmdID= 3185 "
		::= { iqsyn31CmdEntry 3185 }


	iqsyn31EmbeddersEmbedder23GainLPair1 OBJECT-TYPE
		SYNTAX		INTEGER
		MAX-ACCESS		read-write
		STATUS			current
		DESCRIPTION
				"TYPE: - Number
				 PAGE: - Channel 2- Audio- Embedders- Embedder 2 3
					Gain L  cmdID= 3104  min= -720  max= 120  step= 1  format= %0.1fdB  divscale= 10
					Min = -72.0dB  Max = 12.0dB  Step = 0.1dB "
		::= { iqsyn31CmdEntry 3104 }


	iqsyn31EmbeddersEmbedder23GainRPair1 OBJECT-TYPE
		SYNTAX		INTEGER
		MAX-ACCESS		read-write
		STATUS			current
		DESCRIPTION
				"TYPE: - Number
				 PAGE: - Channel 2- Audio- Embedders- Embedder 2 3
					Gain R  cmdID= 3105  min= -720  max= 120  step= 1  format= %0.1fdB  divscale= 10
					Min = -72.0dB  Max = 12.0dB  Step = 0.1dB "
		::= { iqsyn31CmdEntry 3105 }


	iqsyn31EmbeddersEmbedder23PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 3
					Pair Mode  cmdID= 3942
					2 Channel PCM  value= 0
					Stereo PCM  value= 1
					nonPCM  value= 2  "
		::= { iqsyn31CmdEntry 3942 }


	iqsyn31EmbeddersEmbedder23SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 3
					Source L / Non-PCM  cmdID= 5060
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5060 }


	iqsyn31EmbeddersEmbedder23SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 3
					Source R  cmdID= 5061
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5061 }


	iqsyn31EmbeddersEmbedder23MutePair2 OBJECT-TYPE
		SYNTAX		INTEGER { disable(0), enable(1) }
		MAX-ACCESS		read-write
		STATUS			current
		DESCRIPTION
				"TYPE: - Checkbox
				 PAGE: - Channel 2- Audio- Embedders- Embedder 2 3
					Mute  cmdID= 3253 "
		::= { iqsyn31CmdEntry 3253 }


	iqsyn31EmbeddersEmbedder23InvertLPair2 OBJECT-TYPE
		SYNTAX		INTEGER { disable(0), enable(1) }
		MAX-ACCESS		read-write
		STATUS			current
		DESCRIPTION
				"TYPE: - Checkbox
				 PAGE: - Channel 2- Audio- Embedders- Embedder 2 3
					Invert L  cmdID= 3186 "
		::= { iqsyn31CmdEntry 3186 }


	iqsyn31EmbeddersEmbedder23InvertRPair2 OBJECT-TYPE
		SYNTAX		INTEGER { disable(0), enable(1) }
		MAX-ACCESS		read-write
		STATUS			current
		DESCRIPTION
				"TYPE: - Checkbox
				 PAGE: - Channel 2- Audio- Embedders- Embedder 2 3
					Invert R  cmdID= 3187 "
		::= { iqsyn31CmdEntry 3187 }


	iqsyn31EmbeddersEmbedder23GainLPair2 OBJECT-TYPE
		SYNTAX		INTEGER
		MAX-ACCESS		read-write
		STATUS			current
		DESCRIPTION
				"TYPE: - Number
				 PAGE: - Channel 2- Audio- Embedders- Embedder 2 3
					Gain L  cmdID= 3106  min= -720  max= 120  step= 1  format= %0.1fdB  divscale= 10
					Min = -72.0dB  Max = 12.0dB  Step = 0.1dB "
		::= { iqsyn31CmdEntry 3106 }


	iqsyn31EmbeddersEmbedder23GainRPair2 OBJECT-TYPE
		SYNTAX		INTEGER
		MAX-ACCESS		read-write
		STATUS			current
		DESCRIPTION
				"TYPE: - Number
				 PAGE: - Channel 2- Audio- Embedders- Embedder 2 3
					Gain R  cmdID= 3107  min= -720  max= 120  step= 1  format= %0.1fdB  divscale= 10
					Min = -72.0dB  Max = 12.0dB  Step = 0.1dB "
		::= { iqsyn31CmdEntry 3107 }


	iqsyn31EmbeddersEmbedder23PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 3
					Pair Mode  cmdID= 3943
					2 Channel PCM  value= 0
					Stereo PCM  value= 1
					nonPCM  value= 2  "
		::= { iqsyn31CmdEntry 3943 }


	iqsyn31EmbeddersEmbedder24Enable OBJECT-TYPE
		SYNTAX		INTEGER { disable(0), enable(1) }
		MAX-ACCESS		read-write
		STATUS			current
		DESCRIPTION
				"TYPE: - Checkbox
				 PAGE: - Channel 2- Audio- Embedders- Embedder 2 4
					Enable  cmdID= 5073 "
		::= { iqsyn31CmdEntry 5073 }


	iqsyn31EmbeddersEmbedder24SourceLNonPCMPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 4
					Source L / Non-PCM  cmdID= 5062
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5062 }


	iqsyn31EmbeddersEmbedder24SourceRPair1 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 4
					Source R  cmdID= 5063
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5063 }


	iqsyn31EmbeddersEmbedder24MutePair1 OBJECT-TYPE
		SYNTAX		INTEGER { disable(0), enable(1) }
		MAX-ACCESS		read-write
		STATUS			current
		DESCRIPTION
				"TYPE: - Checkbox
				 PAGE: - Channel 2- Audio- Embedders- Embedder 2 4
					Mute  cmdID= 3254 "
		::= { iqsyn31CmdEntry 3254 }


	iqsyn31EmbeddersEmbedder24InvertLPair1 OBJECT-TYPE
		SYNTAX		INTEGER { disable(0), enable(1) }
		MAX-ACCESS		read-write
		STATUS			current
		DESCRIPTION
				"TYPE: - Checkbox
				 PAGE: - Channel 2- Audio- Embedders- Embedder 2 4
					Invert L  cmdID= 3188 "
		::= { iqsyn31CmdEntry 3188 }


	iqsyn31EmbeddersEmbedder24InvertRPair1 OBJECT-TYPE
		SYNTAX		INTEGER { disable(0), enable(1) }
		MAX-ACCESS		read-write
		STATUS			current
		DESCRIPTION
				"TYPE: - Checkbox
				 PAGE: - Channel 2- Audio- Embedders- Embedder 2 4
					Invert R  cmdID= 3189 "
		::= { iqsyn31CmdEntry 3189 }


	iqsyn31EmbeddersEmbedder24GainLPair1 OBJECT-TYPE
		SYNTAX		INTEGER
		MAX-ACCESS		read-write
		STATUS			current
		DESCRIPTION
				"TYPE: - Number
				 PAGE: - Channel 2- Audio- Embedders- Embedder 2 4
					Gain L  cmdID= 3108  min= -720  max= 120  step= 1  format= %0.1fdB  divscale= 10
					Min = -72.0dB  Max = 12.0dB  Step = 0.1dB "
		::= { iqsyn31CmdEntry 3108 }


	iqsyn31EmbeddersEmbedder24GainRPair1 OBJECT-TYPE
		SYNTAX		INTEGER
		MAX-ACCESS		read-write
		STATUS			current
		DESCRIPTION
				"TYPE: - Number
				 PAGE: - Channel 2- Audio- Embedders- Embedder 2 4
					Gain R  cmdID= 3109  min= -720  max= 120  step= 1  format= %0.1fdB  divscale= 10
					Min = -72.0dB  Max = 12.0dB  Step = 0.1dB "
		::= { iqsyn31CmdEntry 3109 }


	iqsyn31EmbeddersEmbedder24PairModePair1 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 4
					Pair Mode  cmdID= 3944
					2 Channel PCM  value= 0
					Stereo PCM  value= 1
					nonPCM  value= 2  "
		::= { iqsyn31CmdEntry 3944 }


	iqsyn31EmbeddersEmbedder24SourceLNonPCMPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(32),
							valSilence(34)
							}
		MAX-ACCESS		read-write
		STATUS			current
		DESCRIPTION
				"TYPE: - RadiobuttonList
				 PAGE: - Channel 2- Audio- Embedders- Embedder 2 4
					Source L / Non-PCM  cmdID= 5064
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 32
					Silence  value= 34  "
		::= { iqsyn31CmdEntry 5064 }


	iqsyn31EmbeddersEmbedder24SourceRPair2 OBJECT-TYPE
		SYNTAX		INTEGER {
							valDisembed11(0),
							valDisembed12(1),
							valDisembed21(2),
							valDisembed22(3),
							valDisembed31(4),
							valDisembed32(5),
							valDisembed41(6),
							valDisembed42(7),
							valDisembed51(8),
							valDisembed52(9),
							valDisembed61(10),
							valDisembed62(11),
							valDisembed71(12),
							valDisembed72(13),
							valDisembed81(14),
							valDisembed82(15),
							valTone(33),
							valSilence(34)
							}
		MAX-ACCESS		read-write
		STATUS			current
		DESCRIPTION
				"TYPE: - RadiobuttonList
				 PAGE: - Channel 2- Audio- Embedders- Embedder 2 4
					Source R  cmdID= 5065
					Dis-embed 11  value= 0
					Dis-embed 12  value= 1
					Dis-embed 21  value= 2
					Dis-embed 22  value= 3
					Dis-embed 31  value= 4
					Dis-embed 32  value= 5
					Dis-embed 41  value= 6
					Dis-embed 42  value= 7
					Dis-embed 51  value= 8
					Dis-embed 52  value= 9
					Dis-embed 61  value= 10
					Dis-embed 62  value= 11
					Dis-embed 71  value= 12
					Dis-embed 72  value= 13
					Dis-embed 81  value= 14
					Dis-embed 82  value= 15
					Tone  value= 33
					Silence  value= 34  "
		::= { iqsyn31CmdEntry 5065 }


	iqsyn31EmbeddersEmbedder24MutePair2 OBJECT-TYPE
		SYNTAX		INTEGER { disable(0), enable(1) }
		MAX-ACCESS		read-write
		STATUS			current
		DESCRIPTION
				"TYPE: - Checkbox
				 PAGE: - Channel 2- Audio- Embedders- Embedder 2 4
					Mute  cmdID= 3255 "
		::= { iqsyn31CmdEntry 3255 }


	iqsyn31EmbeddersEmbedder24InvertLPair2 OBJECT-TYPE
		SYNTAX		INTEGER { disable(0), enable(1) }
		MAX-ACCESS		read-write
		STATUS			current
		DESCRIPTION
				"TYPE: - Checkbox
				 PAGE: - Channel 2- Audio- Embedders- Embedder 2 4
					Invert L  cmdID= 3190 "
		::= { iqsyn31CmdEntry 3190 }


	iqsyn31EmbeddersEmbedder24InvertRPair2 OBJECT-TYPE
		SYNTAX		INTEGER { disable(0), enable(1) }
		MAX-ACCESS		read-write
		STATUS			current
		DESCRIPTION
				"TYPE: - Checkbox
				 PAGE: - Channel 2- Audio- Embedders- Embedder 2 4
					Invert R  cmdID= 3191 "
		::= { iqsyn31CmdEntry 3191 }


	iqsyn31EmbeddersEmbedder24GainLPair2 OBJECT-TYPE
		SYNTAX		INTEGER
		MAX-ACCESS		read-write
		STATUS			current
		DESCRIPTION
				"TYPE: - Number
				 PAGE: - Channel 2- Audio- Embedders- Embedder 2 4
					Gain L  cmdID= 3110  min= -720  max= 120  step= 1  format= %0.1fdB  divscale= 10
					Min = -72.0dB  Max = 12.0dB  Step = 0.1dB "
		::= { iqsyn31CmdEntry 3110 }


	iqsyn31EmbeddersEmbedder24GainRPair2 OBJECT-TYPE
		SYNTAX		INTEGER
		MAX-ACCESS		read-write
		STATUS			current
		DESCRIPTION
				"TYPE: - Number
				 PAGE: - Channel 2- Audio- Embedders- Embedder 2 4
					Gain R  cmdID= 3111  min= -720  max= 120  step= 1  format= %0.1fdB  divscale= 10
					Min = -72.0dB  Max = 12.0dB  Step = 0.1dB "
		::= { iqsyn31CmdEntry 3111 }


	iqsyn31EmbeddersEmbedder24PairModePair2 OBJECT-TYPE
		SYNTAX		INTEGER {
							val2ChannelPCM(0),
							valStereoPCM(1),
							valnonPCM(2)
							}
		MAX-ACCESS		read-write
		STATUS			current
		DESCRIPTION
				"TYPE: - RadiobuttonList
				 PAGE: - Channel 2- Audio- Embedders- Embedder 2 4
					Pair Mode  cmdID= 3945
					2 Channel PCM  value= 0
					Stereo PCM  value= 1
					nonPCM  value= 2  "
		::= { iqsyn31CmdEntry 3945 }


	iqsyn31Channel2AudioFrequency OBJECT-TYPE
		SYNTAX		INTEGER
		MAX-ACCESS		read-write
		STATUS			current
		DESCRIPTION
				"TYPE: - Number
				 PAGE: - Channel 2- Audio
					Frequency  cmdID= 2488  min= 100  max= 10000  step= 100  format= %5.0fHz  divscale= 1
					Min =   100Hz  Max = 10000Hz  Step =   100Hz "
		::= { iqsyn31CmdEntry 2488 }


	iqsyn31Channel2AudioChannelident OBJECT-TYPE
		SYNTAX		INTEGER { disable(0), enable(1) }
		MAX-ACCESS		read-write
		STATUS			current
		DESCRIPTION
				"TYPE: - Checkbox
				 PAGE: - Channel 2- Audio
					Channel ident  cmdID= 5031 "
		::= { iqsyn31CmdEntry 5031 }


	iqsyn31Channel2AudioTotaldelay OBJECT-TYPE
		SYNTAX		RollCallString
		MAX-ACCESS		read-only
		STATUS			current
		DESCRIPTION
				"TYPE: - Display
				 PAGE: - Channel 2- Audio
					Total delay  cmdID= 5095  format=   "
		::= { iqsyn31CmdEntry 5095 }


	iqsyn31Channel2AudioActiveVideodelay OBJECT-TYPE
		SYNTAX		RollCallString
		MAX-ACCESS		read-only
		STATUS			current
		DESCRIPTION
				"TYPE: - Display
				 PAGE: - Channel 2- Audio
					Video delay  cmdID= 5085  format=   "
		::= { iqsyn31CmdEntry 5085 }


	iqsyn31Channel2Audiomanualdelay OBJECT-TYPE
		SYNTAX		RollCallString
		MAX-ACCESS		read-only
		STATUS			current
		DESCRIPTION
				"TYPE: - Display
				 PAGE: - Channel 2- Audio
					manual delay  cmdID= 5087  format=   "
		::= { iqsyn31CmdEntry 5087 }


	iqsyn31Channel2AudioVideodelayInternalEnable OBJECT-TYPE
		SYNTAX		INTEGER { disable(0), enable(1) }
		MAX-ACCESS		read-write
		STATUS			current
		DESCRIPTION
				"TYPE: - Checkbox
				 PAGE: - Channel 2- Audio
					Video delay  cmdID= 5089 "
		::= { iqsyn31CmdEntry 5089 }


	iqsyn31Channel2AudiomanualdelayEnable OBJECT-TYPE
		SYNTAX		INTEGER { disable(0), enable(1) }
		MAX-ACCESS		read-write
		STATUS			current
		DESCRIPTION
				"TYPE: - Checkbox
				 PAGE: - Channel 2- Audio
					manual delay  cmdID= 5090 "
		::= { iqsyn31CmdEntry 5090 }


	iqsyn31Channel2AudioTrack14delayEnable OBJECT-TYPE
		SYNTAX		INTEGER { disable(0), enable(1) }
		MAX-ACCESS		read-write
		STATUS			current
		DESCRIPTION
				"TYPE: - Checkbox
				 PAGE: - Channel 2- Audio
					Track 14 delay  cmdID= 5091 "
		::= { iqsyn31CmdEntry 5091 }


	iqsyn31Channel2AudioTrack15delayEnable OBJECT-TYPE
		SYNTAX		INTEGER { disable(0), enable(1) }
		MAX-ACCESS		read-write
		STATUS			current
		DESCRIPTION
				"TYPE: - Checkbox
				 PAGE: - Channel 2- Audio
					Track 15 delay  cmdID= 5092 "
		::= { iqsyn31CmdEntry 5092 }


	iqsyn31Channel2AudioTrack16delayEnable OBJECT-TYPE
		SYNTAX		INTEGER { disable(0), enable(1) }
		MAX-ACCESS		read-write
		STATUS			current
		DESCRIPTION
				"TYPE: - Checkbox
				 PAGE: - Channel 2- Audio
					Track 16 delay  cmdID= 5093 "
		::= { iqsyn31CmdEntry 5093 }


	iqsyn31Channel2AudioTrack17delayEnable OBJECT-TYPE
		SYNTAX		INTEGER { disable(0), enable(1) }
		MAX-ACCESS		read-write
		STATUS			current
		DESCRIPTION
				"TYPE: - Checkbox
				 PAGE: - Channel 2- Audio
					Track 17 delay  cmdID= 5094 "
		::= { iqsyn31CmdEntry 5094 }


	iqsyn31Channel2AudioCoarse OBJECT-TYPE
		SYNTAX		INTEGER
		MAX-ACCESS		read-write
		STATUS			current
		DESCRIPTION
				"TYPE: - Number
				 PAGE: - Channel 2- Audio
					Coarse  cmdID= 5086  min= 0  max= 1750  step= 5  format= %5.3fs  divscale= 1000
					Min = 0.000s  Max = 1.750s  Step = 0.005s "
		::= { iqsyn31CmdEntry 5086 }


	iqsyn31Channel2AudioFine OBJECT-TYPE
		SYNTAX		INTEGER
		MAX-ACCESS		read-write
		STATUS			current
		DESCRIPTION
				"TYPE: - Number
				 PAGE: - Channel 2- Audio
					Fine  cmdID= 5088  min= -2500  max= 2500  step= 5  format= %0.1fms  divscale= 10
					Min = -250.0ms  Max = 250.0ms  Step = 0.5ms "
		::= { iqsyn31CmdEntry 5088 }


	iqsyn31Channel2AudioDolbyEautoalign OBJECT-TYPE
		SYNTAX		INTEGER { disable(0), enable(1) }
		MAX-ACCESS		read-write
		STATUS			current
		DESCRIPTION
				"TYPE: - Checkbox
				 PAGE: - Channel 2- Audio
					Dolby E auto align  cmdID= 5033 "
		::= { iqsyn31CmdEntry 5033 }


	iqsyn31Channel2AudioSilenceLevel OBJECT-TYPE
		SYNTAX		INTEGER
		MAX-ACCESS		read-write
		STATUS			current
		DESCRIPTION
				"TYPE: - Number
				 PAGE: - Channel 2- Audio
					Silence Level  cmdID= 3066  min= -80  max= 0  step= 1  format= %1.0f dB  divscale= 1
					Min = -80 dB  Max = 0 dB  Step = 1 dB "
		::= { iqsyn31CmdEntry 3066 }


	iqsyn31Channel2AudioOverloadLevel OBJECT-TYPE
		SYNTAX		INTEGER
		MAX-ACCESS		read-write
		STATUS			current
		DESCRIPTION
				"TYPE: - Number
				 PAGE: - Channel 2- Audio
					Overload Level  cmdID= 3069  min= -80  max= 0  step= 1  format= %1.0f dB  divscale= 1
					Min = -80 dB  Max = 0 dB  Step = 1 dB "
		::= { iqsyn31CmdEntry 3069 }


	iqsyn31Channel2AudioWarningTimer OBJECT-TYPE
		SYNTAX		INTEGER
		MAX-ACCESS		read-write
		STATUS			current
		DESCRIPTION
				"TYPE: - Number
				 PAGE: - Channel 2- Audio
					Warning Timer  cmdID= 3070  min= 1  max= 20  step= 1  format= %1.0f sec  divscale= 1
					Min = 1 sec  Max = 20 sec  Step = 1 sec "
		::= { iqsyn31CmdEntry 3070 }


	iqsyn31CommonGenlockMode OBJECT-TYPE
		SYNTAX		INTEGER {
							valFreerun(2),
							valLocktoReference(0),
							valLocktoInput(1)
							}
		MAX-ACCESS		read-write
		STATUS			current
		DESCRIPTION
				"TYPE: - Button
				 PAGE: - Common- Genlock
					Freerun  cmdID= 3674  value= 2
					Lock to Reference  cmdID= 3674  value= 0
					Lock to Input  cmdID= 3674  value= 1  "
		::= { iqsyn31CmdEntry 3674 }


	iqsyn31CommonGenlockFreerunFrequency OBJECT-TYPE
		SYNTAX		INTEGER
		MAX-ACCESS		read-write
		STATUS			current
		DESCRIPTION
				"TYPE: - Number
				 PAGE: - Common- Genlock
					Freerun Frequency  cmdID= 2449  min= -200  max= 200  step= 1  format= %.0f  divscale= 1
					Min = -200  Max = 200  Step = 1 "
		::= { iqsyn31CmdEntry 2449 }


	iqsyn31CommonGenlockGenlockHPhase OBJECT-TYPE
		SYNTAX		INTEGER
		MAX-ACCESS		read-write
		STATUS			current
		DESCRIPTION
				"TYPE: - Number
				 PAGE: - Common- Genlock
					Genlock H Phase  cmdID= 3790  min= -1320  max= 1320  step= 1  format= %.0f pixels  divscale= 1
					Min = -1320 pixels  Max = 1320 pixels  Step = 1 pixels "
		::= { iqsyn31CmdEntry 3790 }


	iqsyn31CommonGenlockGenlockVPhase OBJECT-TYPE
		SYNTAX		INTEGER
		MAX-ACCESS		read-write
		STATUS			current
		DESCRIPTION
				"TYPE: - Number
				 PAGE: - Common- Genlock
					Genlock V Phase  cmdID= 3791  min= -562  max= 562  step= 1  format= %.0f lines  divscale= 1
					Min = -562 lines  Max = 562 lines  Step = 1 lines "
		::= { iqsyn31CmdEntry 3791 }


	iqsyn31CommonGenlockVideoHdelay OBJECT-TYPE
		SYNTAX		INTEGER
		MAX-ACCESS		read-write
		STATUS			current
		DESCRIPTION
				"TYPE: - Number
				 PAGE: - Common- Genlock
					Video H delay  cmdID= 3794  min= 0  max= 2640  step= 1  format= %.0f pixels  divscale= 1
					Min = 0 pixels  Max = 2640 pixels  Step = 1 pixels "
		::= { iqsyn31CmdEntry 3794 }


	iqsyn31CommonGenlockVideoVdelay OBJECT-TYPE
		SYNTAX		INTEGER
		MAX-ACCESS		read-write
		STATUS			current
		DESCRIPTION
				"TYPE: - Number
				 PAGE: - Common- Genlock
					Video V delay  cmdID= 3795  min= 0  max= 1125  step= 1  format= %.0f lines  divscale= 1
					Min = 0 lines  Max = 1125 lines  Step = 1 lines "
		::= { iqsyn31CmdEntry 3795 }


	iqsyn31CommonGenlockVideo1Fdelay OBJECT-TYPE
		SYNTAX		INTEGER
		MAX-ACCESS		read-write
		STATUS			current
		DESCRIPTION
				"TYPE: - Number
				 PAGE: - Common- Genlock
					Video 1 F delay  cmdID= 3796  min= 0  max= 3  step= 1  format= %.0f frames  divscale= 1
					Min = 0 frames  Max = 3 frames  Step = 1 frames "
		::= { iqsyn31CmdEntry 3796 }


	iqsyn31CommonGenlockVideo2Fdelay OBJECT-TYPE
		SYNTAX		INTEGER
		MAX-ACCESS		read-write
		STATUS			current
		DESCRIPTION
				"TYPE: - Number
				 PAGE: - Common- Genlock
					Video 2 F delay  cmdID= 3799  min= 0  max= 3  step= 1  format= %.0f frames  divscale= 1
					Min = 0 frames  Max = 3 frames  Step = 1 frames "
		::= { iqsyn31CmdEntry 3799 }


	iqsyn31CommonGenlockGenlocksaveindex OBJECT-TYPE
		SYNTAX		INTEGER
		MAX-ACCESS		read-write
		STATUS			current
		DESCRIPTION
				"TYPE: - Number
				 PAGE: - Common- Genlock
					Genlock save index  cmdID= 3991  min= 0  max= 10  step= 1  format= %.0f  divscale= 1
					Min = 0  Max = 10  Step = 1 "
		::= { iqsyn31CmdEntry 3991 }


	iqsyn31CommonGenlockGenlockHPhaseRT OBJECT-TYPE
		SYNTAX		INTEGER
		MAX-ACCESS		read-write
		STATUS			current
		DESCRIPTION
				"TYPE: - Number
				 PAGE: - Common- Genlock
					Genlock H Phase  cmdID= 3992  min= -1320  max= 1320  step= 1  format= %.0f pixels  divscale= 1
					Min = -1320 pixels  Max = 1320 pixels  Step = 1 pixels "
		::= { iqsyn31CmdEntry 3992 }


	iqsyn31CommonGenlockGenlockVPhaseRT OBJECT-TYPE
		SYNTAX		INTEGER
		MAX-ACCESS		read-write
		STATUS			current
		DESCRIPTION
				"TYPE: - Number
				 PAGE: - Common- Genlock
					Genlock V Phase  cmdID= 3993  min= -562  max= 562  step= 1  format= %.0f lines  divscale= 1
					Min = -562 lines  Max = 562 lines  Step = 1 lines "
		::= { iqsyn31CmdEntry 3993 }


	iqsyn31CommonGenlockVideoHdelayRT OBJECT-TYPE
		SYNTAX		INTEGER
		MAX-ACCESS		read-write
		STATUS			current
		DESCRIPTION
				"TYPE: - Number
				 PAGE: - Common- Genlock
					Video H delay  cmdID= 3994  min= 0  max= 2640  step= 1  format= %.0f pixels  divscale= 1
					Min = 0 pixels  Max = 2640 pixels  Step = 1 pixels "
		::= { iqsyn31CmdEntry 3994 }


	iqsyn31CommonGenlockVideoVdelayRT OBJECT-TYPE
		SYNTAX		INTEGER
		MAX-ACCESS		read-write
		STATUS			current
		DESCRIPTION
				"TYPE: - Number
				 PAGE: - Common- Genlock
					Video V delay  cmdID= 3995  min= 0  max= 1125  step= 1  format= %.0f lines  divscale= 1
					Min = 0 lines  Max = 1125 lines  Step = 1 lines "
		::= { iqsyn31CmdEntry 3995 }


	iqsyn31DefaultOutputStd OBJECT-TYPE
		SYNTAX		INTEGER {
							valLastKnownGood(1),
							val108050pB(25),
							val108059pB(26),
							val108050pA(22),
							val108059pA(23),
							val108029i(18),
							val108025i(17),
							val72059p(10),
							val72050p(9),
							val52529i(3),
							val62525i(2)
							}
		MAX-ACCESS		read-write
		STATUS			current
		DESCRIPTION
				"TYPE: - Button
				 PAGE: - Common- Genlock
					Last Known Good  cmdID= 3793  value= 1
					1080/50p-B  cmdID= 3793  value= 25
					1080/59p-B  cmdID= 3793  value= 26
					1080/50p-A  cmdID= 3793  value= 22
					1080/59p-A  cmdID= 3793  value= 23
					1080/29i  cmdID= 3793  value= 18
					1080/25i  cmdID= 3793  value= 17
					720/59p  cmdID= 3793  value= 10
					720/50p  cmdID= 3793  value= 9
					525/29i  cmdID= 3793  value= 3
					625/25i  cmdID= 3793  value= 2  "
		::= { iqsyn31CmdEntry 3793 }


	iqsyn31CommonGenlock108050pB OBJECT-TYPE
		SYNTAX		INTEGER { disable(0), enable(1) }
		MAX-ACCESS		read-write
		STATUS			current
		DESCRIPTION
				"TYPE: - Checkbox
				 PAGE: - Common- Genlock
					1080/50p-B  cmdID= 3825 "
		::= { iqsyn31CmdEntry 3825 }


	iqsyn31CommonGenlock108059pB OBJECT-TYPE
		SYNTAX		INTEGER { disable(0), enable(1) }
		MAX-ACCESS		read-write
		STATUS			current
		DESCRIPTION
				"TYPE: - Checkbox
				 PAGE: - Common- Genlock
					1080/59p-B  cmdID= 3826 "
		::= { iqsyn31CmdEntry 3826 }


	iqsyn31CommonGenlock108050pA OBJECT-TYPE
		SYNTAX		INTEGER { disable(0), enable(1) }
		MAX-ACCESS		read-write
		STATUS			current
		DESCRIPTION
				"TYPE: - Checkbox
				 PAGE: - Common- Genlock
					1080/50p-A  cmdID= 3822 "
		::= { iqsyn31CmdEntry 3822 }


	iqsyn31CommonGenlock108059pA OBJECT-TYPE
		SYNTAX		INTEGER { disable(0), enable(1) }
		MAX-ACCESS		read-write
		STATUS			current
		DESCRIPTION
				"TYPE: - Checkbox
				 PAGE: - Common- Genlock
					1080/59p-A  cmdID= 3823 "
		::= { iqsyn31CmdEntry 3823 }


	iqsyn31CommonGenlock108029i OBJECT-TYPE
		SYNTAX		INTEGER { disable(0), enable(1) }
		MAX-ACCESS		read-write
		STATUS			current
		DESCRIPTION
				"TYPE: - Checkbox
				 PAGE: - Common- Genlock
					1080/29i  cmdID= 3818 "
		::= { iqsyn31CmdEntry 3818 }


	iqsyn31CommonGenlock108025i OBJECT-TYPE
		SYNTAX		INTEGER { disable(0), enable(1) }
		MAX-ACCESS		read-write
		STATUS			current
		DESCRIPTION
				"TYPE: - Checkbox
				 PAGE: - Common- Genlock
					1080/25i  cmdID= 3817 "
		::= { iqsyn31CmdEntry 3817 }


	iqsyn31CommonGenlock72059p OBJECT-TYPE
		SYNTAX		INTEGER { disable(0), enable(1) }
		MAX-ACCESS		read-write
		STATUS			current
		DESCRIPTION
				"TYPE: - Checkbox
				 PAGE: - Common- Genlock
					720/59p  cmdID= 3810 "
		::= { iqsyn31CmdEntry 3810 }


	iqsyn31CommonGenlock72050p OBJECT-TYPE
		SYNTAX		INTEGER { disable(0), enable(1) }
		MAX-ACCESS		read-write
		STATUS			current
		DESCRIPTION
				"TYPE: - Checkbox
				 PAGE: - Common- Genlock
					720/50p  cmdID= 3809 "
		::= { iqsyn31CmdEntry 3809 }


	iqsyn31CommonGenlock52529i OBJECT-TYPE
		SYNTAX		INTEGER { disable(0), enable(1) }
		MAX-ACCESS		read-write
		STATUS			current
		DESCRIPTION
				"TYPE: - Checkbox
				 PAGE: - Common- Genlock
					525/29i  cmdID= 3803 "
		::= { iqsyn31CmdEntry 3803 }


	iqsyn31CommonGenlock62525i OBJECT-TYPE
		SYNTAX		INTEGER { disable(0), enable(1) }
		MAX-ACCESS		read-write
		STATUS			current
		DESCRIPTION
				"TYPE: - Checkbox
				 PAGE: - Common- Genlock
					625/25i  cmdID= 3802 "
		::= { iqsyn31CmdEntry 3802 }


	iqsyn31CommonMemoriesSelMemory OBJECT-TYPE
		SYNTAX		INTEGER {
							valUserMemory1(1),
							valUserMemory2(2),
							valUserMemory3(3),
							valUserMemory4(4),
							valUserMemory5(5),
							valUserMemory6(6),
							valUserMemory7(7),
							valUserMemory8(8),
							valUserMemory9(9),
							valUserMemory10(10),
							valUserMemory11(11),
							valUserMemory12(12),
							valUserMemory13(13),
							valUserMemory14(14),
							valUserMemory15(15),
							valUserMemory16(16)
							}
		MAX-ACCESS		read-write
		STATUS			current
		DESCRIPTION
				"TYPE: - RadiobuttonList
				 PAGE: - Common- Memories
					Sel Memory  cmdID= 37101
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqsyn31CmdEntry 37101 }


	iqsyn31CommonMemoriesSetMemName OBJECT-TYPE
		SYNTAX		RollCallString
		MAX-ACCESS		read-write
		STATUS			current
		DESCRIPTION
				"TYPE: - Editstring
				 PAGE: - Common- Memories
					SetMemName  cmdID= 37103  "
		::= { iqsyn31CmdEntry 37103 }


	iqsyn31CommonMemoriesRecallMemory OBJECT-TYPE
		SYNTAX		INTEGER {
							valNoneSelected(0),
							valUserMemory1(1),
							valUserMemory2(2),
							valUserMemory3(3),
							valUserMemory4(4),
							valUserMemory5(5),
							valUserMemory6(6),
							valUserMemory7(7),
							valUserMemory8(8),
							valUserMemory9(9),
							valUserMemory10(10),
							valUserMemory11(11),
							valUserMemory12(12),
							valUserMemory13(13),
							valUserMemory14(14),
							valUserMemory15(15),
							valUserMemory16(16)
							}
		MAX-ACCESS		read-write
		STATUS			current
		DESCRIPTION
				"TYPE: - RadiobuttonList
				 PAGE: - Common- Memories
					Recall Memory  cmdID= 37100
					None Selected  value= 0
					User Memory 1  value= 1
					User Memory 2  value= 2
					User Memory 3  value= 3
					User Memory 4  value= 4
					User Memory 5  value= 5
					User Memory 6  value= 6
					User Memory 7  value= 7
					User Memory 8  value= 8
					User Memory 9  value= 9
					User Memory 10  value= 10
					User Memory 11  value= 11
					User Memory 12  value= 12
					User Memory 13  value= 13
					User Memory 14  value= 14
					User Memory 15  value= 15
					User Memory 16  value= 16  "
		::= { iqsyn31CmdEntry 37100 }


	iqsyn31CommonMemoriesSaveMemory OBJECT-TYPE
		SYNTAX		INTEGER { noAction(0),valSaveMemory(1) }
		MAX-ACCESS		read-write
		STATUS			current
		DESCRIPTION
				"TYPE: - Button
				 PAGE: - Common- Memories
					Save Memory  cmdID= 37102  value= 1  "
		::= { iqsyn31CmdEntry 37102 }


	iqsyn31CommonMemoriesLastUserMemory OBJECT-TYPE
		SYNTAX		RollCallString
		MAX-ACCESS		read-only
		STATUS			current
		DESCRIPTION
				"TYPE: - Display
				 PAGE: - Common- Memories
					Last User Memory  cmdID= 37104  format=   "
		::= { iqsyn31CmdEntry 37104 }


	iqsyn31CommonMemoriesClearMemory OBJECT-TYPE
		SYNTAX		INTEGER { noAction(0),valClearMemory(1) }
		MAX-ACCESS		read-write
		STATUS			current
		DESCRIPTION
				"TYPE: - Button
				 PAGE: - Common- Memories
					Clear Memory  cmdID= 37105  value= 1  "
		::= { iqsyn31CmdEntry 37105 }


	iqsyn31MemoriesMemoryNamesMemory1Name OBJECT-TYPE
		SYNTAX		RollCallString
		MAX-ACCESS		read-only
		STATUS			current
		DESCRIPTION
				"TYPE: - Display
				 PAGE: - Common- Memories
					Memory 1 Name  cmdID= 37106  format=   "
		::= { iqsyn31CmdEntry 37106 }


	iqsyn31MemoriesMemoryNamesMemory2Name OBJECT-TYPE
		SYNTAX		RollCallString
		MAX-ACCESS		read-only
		STATUS			current
		DESCRIPTION
				"TYPE: - Display
				 PAGE: - Common- Memories
					Memory 2 Name  cmdID= 37107  format=   "
		::= { iqsyn31CmdEntry 37107 }


	iqsyn31MemoriesMemoryNamesMemory3Name OBJECT-TYPE
		SYNTAX		RollCallString
		MAX-ACCESS		read-only
		STATUS			current
		DESCRIPTION
				"TYPE: - Display
				 PAGE: - Common- Memories
					Memory 3 Name  cmdID= 37108  format=   "
		::= { iqsyn31CmdEntry 37108 }


	iqsyn31MemoriesMemoryNamesMemory4Name OBJECT-TYPE
		SYNTAX		RollCallString
		MAX-ACCESS		read-only
		STATUS			current
		DESCRIPTION
				"TYPE: - Display
				 PAGE: - Common- Memories
					Memory 4 Name  cmdID= 37109  format=   "
		::= { iqsyn31CmdEntry 37109 }


	iqsyn31MemoriesMemoryNamesMemory5Name OBJECT-TYPE
		SYNTAX		RollCallString
		MAX-ACCESS		read-only
		STATUS			current
		DESCRIPTION
				"TYPE: - Display
				 PAGE: - Common- Memories
					Memory 5 Name  cmdID= 37110  format=   "
		::= { iqsyn31CmdEntry 37110 }


	iqsyn31MemoriesMemoryNamesMemory6Name OBJECT-TYPE
		SYNTAX		RollCallString
		MAX-ACCESS		read-only
		STATUS			current
		DESCRIPTION
				"TYPE: - Display
				 PAGE: - Common- Memories
					Memory 6 Name  cmdID= 37111  format=   "
		::= { iqsyn31CmdEntry 37111 }


	iqsyn31MemoriesMemoryNamesMemory7Name OBJECT-TYPE
		SYNTAX		RollCallString
		MAX-ACCESS		read-only
		STATUS			current
		DESCRIPTION
				"TYPE: - Display
				 PAGE: - Common- Memories
					Memory 7 Name  cmdID= 37112  format=   "
		::= { iqsyn31CmdEntry 37112 }


	iqsyn31MemoriesMemoryNamesMemory8Name OBJECT-TYPE
		SYNTAX		RollCallString
		MAX-ACCESS		read-only
		STATUS			current
		DESCRIPTION
				"TYPE: - Display
				 PAGE: - Common- Memories
					Memory 8 Name  cmdID= 37113  format=   "
		::= { iqsyn31CmdEntry 37113 }


	iqsyn31MemoriesMemoryNamesMemory9Name OBJECT-TYPE
		SYNTAX		RollCallString
		MAX-ACCESS		read-only
		STATUS			current
		DESCRIPTION
				"TYPE: - Display
				 PAGE: - Common- Memories
					Memory 9 Name  cmdID= 37114  format=   "
		::= { iqsyn31CmdEntry 37114 }


	iqsyn31MemoriesMemoryNamesMemory10Name OBJECT-TYPE
		SYNTAX		RollCallString
		MAX-ACCESS		read-only
		STATUS			current
		DESCRIPTION
				"TYPE: - Display
				 PAGE: - Common- Memories
					Memory 10 Name  cmdID= 37115  format=   "
		::= { iqsyn31CmdEntry 37115 }


	iqsyn31MemoriesMemoryNamesMemory11Name OBJECT-TYPE
		SYNTAX		RollCallString
		MAX-ACCESS		read-only
		STATUS			current
		DESCRIPTION
				"TYPE: - Display
				 PAGE: - Common- Memories
					Memory 11 Name  cmdID= 37116  format=   "
		::= { iqsyn31CmdEntry 37116 }


	iqsyn31MemoriesMemoryNamesMemory12Name OBJECT-TYPE
		SYNTAX		RollCallString
		MAX-ACCESS		read-only
		STATUS			current
		DESCRIPTION
				"TYPE: - Display
				 PAGE: - Common- Memories
					Memory 12 Name  cmdID= 37117  format=   "
		::= { iqsyn31CmdEntry 37117 }


	iqsyn31MemoriesMemoryNamesMemory13Name OBJECT-TYPE
		SYNTAX		RollCallString
		MAX-ACCESS		read-only
		STATUS			current
		DESCRIPTION
				"TYPE: - Display
				 PAGE: - Common- Memories
					Memory 13 Name  cmdID= 37118  format=   "
		::= { iqsyn31CmdEntry 37118 }


	iqsyn31MemoriesMemoryNamesMemory14Name OBJECT-TYPE
		SYNTAX		RollCallString
		MAX-ACCESS		read-only
		STATUS			current
		DESCRIPTION
				"TYPE: - Display
				 PAGE: - Common- Memories
					Memory 14 Name  cmdID= 37119  format=   "
		::= { iqsyn31CmdEntry 37119 }


	iqsyn31MemoriesMemoryNamesMemory15Name OBJECT-TYPE
		SYNTAX		RollCallString
		MAX-ACCESS		read-only
		STATUS			current
		DESCRIPTION
				"TYPE: - Display
				 PAGE: - Common- Memories
					Memory 15 Name  cmdID= 37120  format=   "
		::= { iqsyn31CmdEntry 37120 }


	iqsyn31MemoriesMemoryNamesMemory16Name OBJECT-TYPE
		SYNTAX		RollCallString
		MAX-ACCESS		read-only
		STATUS			current
		DESCRIPTION
				"TYPE: - Display
				 PAGE: - Common- Memories
					Memory 16 Name  cmdID= 37121  format=   "
		::= { iqsyn31CmdEntry 37121 }


	iqsyn31CommonSetupUptimeLogEnable OBJECT-TYPE
		SYNTAX		INTEGER { disable(0), enable(1) }
		MAX-ACCESS		read-write
		STATUS			current
		DESCRIPTION
				"TYPE: - Checkbox
				 PAGE: - Common- Setup
					Uptime  cmdID= 4998 "
		::= { iqsyn31CmdEntry 4998 }


	iqsyn31CommonSetupUptimeLogString OBJECT-TYPE
		SYNTAX		RollCallString
		MAX-ACCESS		read-only
		STATUS			current
		DESCRIPTION
				"TYPE: - Display
				 PAGE: - Common- Setup
					Uptime=  cmdID= 4999  format=   "
		::= { iqsyn31CmdEntry 4999 }


	iqsyn31CommonSetupOSVersionLogEnable OBJECT-TYPE
		SYNTAX		INTEGER { disable(0), enable(1) }
		MAX-ACCESS		read-write
		STATUS			current
		DESCRIPTION
				"TYPE: - Checkbox
				 PAGE: - Common- Setup
					OS Version  cmdID= 4994 "
		::= { iqsyn31CmdEntry 4994 }


	iqsyn31CommonSetupOSVersionLogString OBJECT-TYPE
		SYNTAX		RollCallString
		MAX-ACCESS		read-only
		STATUS			current
		DESCRIPTION
				"TYPE: - Display
				 PAGE: - Common- Setup
					OS Version=  cmdID= 4995  format=   "
		::= { iqsyn31CmdEntry 4995 }


	iqsyn31CommonSetupHardwareVersionLogEnable OBJECT-TYPE
		SYNTAX		INTEGER { disable(0), enable(1) }
		MAX-ACCESS		read-write
		STATUS			current
		DESCRIPTION
				"TYPE: - Checkbox
				 PAGE: - Common- Setup
					Hardware Version  cmdID= 4996 "
		::= { iqsyn31CmdEntry 4996 }


	iqsyn31CommonSetupHardwareVersionLogString OBJECT-TYPE
		SYNTAX		RollCallString
		MAX-ACCESS		read-only
		STATUS			current
		DESCRIPTION
				"TYPE: - Display
				 PAGE: - Common- Setup
					Hardware Version=  cmdID= 4997  format=   "
		::= { iqsyn31CmdEntry 4997 }


	iqsyn31CommonSetupBuildNumberLogEnable OBJECT-TYPE
		SYNTAX		INTEGER { disable(0), enable(1) }
		MAX-ACCESS		read-write
		STATUS			current
		DESCRIPTION
				"TYPE: - Checkbox
				 PAGE: - Common- Setup
					Build Number  cmdID= 4992 "
		::= { iqsyn31CmdEntry 4992 }


	iqsyn31CommonSetupBuildNumberLogString OBJECT-TYPE
		SYNTAX		RollCallString
		MAX-ACCESS		read-only
		STATUS			current
		DESCRIPTION
				"TYPE: - Display
				 PAGE: - Common- Setup
					Build Number=  cmdID= 4993  format=   "
		::= { iqsyn31CmdEntry 4993 }


	iqsyn31CommonSetupSerialNumberLogEnable OBJECT-TYPE
		SYNTAX		INTEGER { disable(0), enable(1) }
		MAX-ACCESS		read-write
		STATUS			current
		DESCRIPTION
				"TYPE: - Checkbox
				 PAGE: - Common- Setup
					Serial Number  cmdID= 4990 "
		::= { iqsyn31CmdEntry 4990 }


	iqsyn31CommonSetupSerialNumberLogString OBJECT-TYPE
		SYNTAX		RollCallString
		MAX-ACCESS		read-only
		STATUS			current
		DESCRIPTION
				"TYPE: - Display
				 PAGE: - Common- Setup
					Serial Number=  cmdID= 4991  format=   "
		::= { iqsyn31CmdEntry 4991 }


	iqsyn31CommonSetupLicensedOptionsLogEnable OBJECT-TYPE
		SYNTAX		INTEGER { disable(0), enable(1) }
		MAX-ACCESS		read-write
		STATUS			current
		DESCRIPTION
				"TYPE: - Checkbox
				 PAGE: - Common- Setup
					Licensed Options  cmdID= 4988 "
		::= { iqsyn31CmdEntry 4988 }


	iqsyn31CommonSetupLicensedOptionsLogString OBJECT-TYPE
		SYNTAX		RollCallString
		MAX-ACCESS		read-only
		STATUS			current
		DESCRIPTION
				"TYPE: - Display
				 PAGE: - Common- Setup
					Licensed Options=  cmdID= 4989  format=   "
		::= { iqsyn31CmdEntry 4989 }


	iqsyn31CommonSetupFirmwareVersionLogEnable OBJECT-TYPE
		SYNTAX		INTEGER { disable(0), enable(1) }
		MAX-ACCESS		read-write
		STATUS			current
		DESCRIPTION
				"TYPE: - Checkbox
				 PAGE: - Common- Setup
					Firmware Version  cmdID= 4986 "
		::= { iqsyn31CmdEntry 4986 }


	iqsyn31CommonSetupFirmwareVersionLogString OBJECT-TYPE
		SYNTAX		RollCallString
		MAX-ACCESS		read-only
		STATUS			current
		DESCRIPTION
				"TYPE: - Display
				 PAGE: - Common- Setup
					Firmware Version=  cmdID= 4987  format=   "
		::= { iqsyn31CmdEntry 4987 }


	iqsyn31CommonSetupInput1LogEnable OBJECT-TYPE
		SYNTAX		INTEGER { disable(0), enable(1) }
		MAX-ACCESS		read-write
		STATUS			current
		DESCRIPTION
				"TYPE: - Checkbox
				 PAGE: - Common- Setup
					Input 1  cmdID= 4000 "
		::= { iqsyn31CmdEntry 4000 }


	iqsyn31CommonSetupInput1LogString OBJECT-TYPE
		SYNTAX		RollCallString
		MAX-ACCESS		read-only
		STATUS			current
		DESCRIPTION
				"TYPE: - Display
				 PAGE: - Common- Setup
					Input 1=  cmdID= 4001  format=   "
		::= { iqsyn31CmdEntry 4001 }


	iqsyn31CommonSetupInput1StandardLogEnable OBJECT-TYPE
		SYNTAX		INTEGER { disable(0), enable(1) }
		MAX-ACCESS		read-write
		STATUS			current
		DESCRIPTION
				"TYPE: - Checkbox
				 PAGE: - Common- Setup
					Input 1 Standard  cmdID= 4004 "
		::= { iqsyn31CmdEntry 4004 }


	iqsyn31CommonSetupInput1StandardLogString OBJECT-TYPE
		SYNTAX		RollCallString
		MAX-ACCESS		read-only
		STATUS			current
		DESCRIPTION
				"TYPE: - Display
				 PAGE: - Common- Setup
					Input 1 Standard=  cmdID= 4005  format=   "
		::= { iqsyn31CmdEntry 4005 }


	iqsyn31CommonSetupInput1TypeLogEnable OBJECT-TYPE
		SYNTAX		INTEGER { disable(0), enable(1) }
		MAX-ACCESS		read-write
		STATUS			current
		DESCRIPTION
				"TYPE: - Checkbox
				 PAGE: - Common- Setup
					Input 1 Type  cmdID= 4024 "
		::= { iqsyn31CmdEntry 4024 }


	iqsyn31CommonSetupInput1TypeLogString OBJECT-TYPE
		SYNTAX		RollCallString
		MAX-ACCESS		read-only
		STATUS			current
		DESCRIPTION
				"TYPE: - Display
				 PAGE: - Common- Setup
					Input 1 Type=  cmdID= 4025  format=   "
		::= { iqsyn31CmdEntry 4025 }


	iqsyn31CommonSetupInput1IdentLogEnable OBJECT-TYPE
		SYNTAX		INTEGER { disable(0), enable(1) }
		MAX-ACCESS		read-write
		STATUS			current
		DESCRIPTION
				"TYPE: - Checkbox
				 PAGE: - Common- Setup
					Input 1 Ident  cmdID= 4028 "
		::= { iqsyn31CmdEntry 4028 }


	iqsyn31CommonSetupInput1IdentLogString OBJECT-TYPE
		SYNTAX		RollCallString
		MAX-ACCESS		read-only
		STATUS			current
		DESCRIPTION
				"TYPE: - Display
				 PAGE: - Common- Setup
					Input 1 Ident=  cmdID= 4029  format=   "
		::= { iqsyn31CmdEntry 4029 }


	iqsyn31CommonSetupIn1SDIERRSLogEnable OBJECT-TYPE
		SYNTAX		INTEGER { disable(0), enable(1) }
		MAX-ACCESS		read-write
		STATUS			current
		DESCRIPTION
				"TYPE: - Checkbox
				 PAGE: - Common- Setup
					In 1 SDI ERRS  cmdID= 4012 "
		::= { iqsyn31CmdEntry 4012 }


	iqsyn31CommonSetupIn1SDIERRSLogString OBJECT-TYPE
		SYNTAX		RollCallString
		MAX-ACCESS		read-only
		STATUS			current
		DESCRIPTION
				"TYPE: - Display
				 PAGE: - Common- Setup
					In 1 SDI ERRS=  cmdID= 4013  format=   "
		::= { iqsyn31CmdEntry 4013 }


	iqsyn31CommonSetupIn1SDIANCERRSLogEnable OBJECT-TYPE
		SYNTAX		INTEGER { disable(0), enable(1) }
		MAX-ACCESS		read-write
		STATUS			current
		DESCRIPTION
				"TYPE: - Checkbox
				 PAGE: - Common- Setup
					In 1 SDI ANC ERRS  cmdID= 4020 "
		::= { iqsyn31CmdEntry 4020 }


	iqsyn31CommonSetupIn1SDIANCERRSLogString OBJECT-TYPE
		SYNTAX		RollCallString
		MAX-ACCESS		read-only
		STATUS			current
		DESCRIPTION
				"TYPE: - Display
				 PAGE: - Common- Setup
					In 1 SDI ANC ERRS=  cmdID= 4021  format=   "
		::= { iqsyn31CmdEntry 4021 }


	iqsyn31CommonSetupInput1Audio1LogEnable OBJECT-TYPE
		SYNTAX		INTEGER { disable(0), enable(1) }
		MAX-ACCESS		read-write
		STATUS			current
		DESCRIPTION
				"TYPE: - Checkbox
				 PAGE: - Common- Setup
					Input 1 Audio 1  cmdID= 3852 "
		::= { iqsyn31CmdEntry 3852 }


	iqsyn31CommonSetupInput1Audio1LogString OBJECT-TYPE
		SYNTAX		RollCallString
		MAX-ACCESS		read-only
		STATUS			current
		DESCRIPTION
				"TYPE: - Display
				 PAGE: - Common- Setup
					Input 1 Audio 1=  cmdID= 3853  format=   "
		::= { iqsyn31CmdEntry 3853 }


	iqsyn31CommonSetupInput1Audio2LogEnable OBJECT-TYPE
		SYNTAX		INTEGER { disable(0), enable(1) }
		MAX-ACCESS		read-write
		STATUS			current
		DESCRIPTION
				"TYPE: - Checkbox
				 PAGE: - Common- Setup
					Input 1 Audio 2  cmdID= 3854 "
		::= { iqsyn31CmdEntry 3854 }


	iqsyn31CommonSetupInput1Audio2LogString OBJECT-TYPE
		SYNTAX		RollCallString
		MAX-ACCESS		read-only
		STATUS			current
		DESCRIPTION
				"TYPE: - Display
				 PAGE: - Common- Setup
					Input 1 Audio 2=  cmdID= 3855  format=   "
		::= { iqsyn31CmdEntry 3855 }


	iqsyn31CommonSetupInput1Audio3LogEnable OBJECT-TYPE
		SYNTAX		INTEGER { disable(0), enable(1) }
		MAX-ACCESS		read-write
		STATUS			current
		DESCRIPTION
				"TYPE: - Checkbox
				 PAGE: - Common- Setup
					Input 1 Audio 3  cmdID= 3856 "
		::= { iqsyn31CmdEntry 3856 }


	iqsyn31CommonSetupInput1Audio3LogString OBJECT-TYPE
		SYNTAX		RollCallString
		MAX-ACCESS		read-only
		STATUS			current
		DESCRIPTION
				"TYPE: - Display
				 PAGE: - Common- Setup
					Input 1 Audio 3=  cmdID= 3857  format=   "
		::= { iqsyn31CmdEntry 3857 }


	iqsyn31CommonSetupInput1Audio4LogEnable OBJECT-TYPE
		SYNTAX		INTEGER { disable(0), enable(1) }
		MAX-ACCESS		read-write
		STATUS			current
		DESCRIPTION
				"TYPE: - Checkbox
				 PAGE: - Common- Setup
					Input 1 Audio 4  cmdID= 3858 "
		::= { iqsyn31CmdEntry 3858 }


	iqsyn31CommonSetupInput1Audio4LogString OBJECT-TYPE
		SYNTAX		RollCallString
		MAX-ACCESS		read-only
		STATUS			current
		DESCRIPTION
				"TYPE: - Display
				 PAGE: - Common- Setup
					Input 1 Audio 4=  cmdID= 3859  format=   "
		::= { iqsyn31CmdEntry 3859 }


	iqsyn31CommonSetupInput1Audio5LogEnable OBJECT-TYPE
		SYNTAX		INTEGER { disable(0), enable(1) }
		MAX-ACCESS		read-write
		STATUS			current
		DESCRIPTION
				"TYPE: - Checkbox
				 PAGE: - Common- Setup
					Input 1 Audio 5  cmdID= 3860 "
		::= { iqsyn31CmdEntry 3860 }


	iqsyn31CommonSetupInput1Audio5LogString OBJECT-TYPE
		SYNTAX		RollCallString
		MAX-ACCESS		read-only
		STATUS			current
		DESCRIPTION
				"TYPE: - Display
				 PAGE: - Common- Setup
					Input 1 Audio 5=  cmdID= 3861  format=   "
		::= { iqsyn31CmdEntry 3861 }


	iqsyn31CommonSetupInput1Audio6LogEnable OBJECT-TYPE
		SYNTAX		INTEGER { disable(0), enable(1) }
		MAX-ACCESS		read-write
		STATUS			current
		DESCRIPTION
				"TYPE: - Checkbox
				 PAGE: - Common- Setup
					Input 1 Audio 6  cmdID= 3862 "
		::= { iqsyn31CmdEntry 3862 }


	iqsyn31CommonSetupInput1Audio6LogString OBJECT-TYPE
		SYNTAX		RollCallString
		MAX-ACCESS		read-only
		STATUS			current
		DESCRIPTION
				"TYPE: - Display
				 PAGE: - Common- Setup
					Input 1 Audio 6=  cmdID= 3863  format=   "
		::= { iqsyn31CmdEntry 3863 }


	iqsyn31CommonSetupInput1Audio7LogEnable OBJECT-TYPE
		SYNTAX		INTEGER { disable(0), enable(1) }
		MAX-ACCESS		read-write
		STATUS			current
		DESCRIPTION
				"TYPE: - Checkbox
				 PAGE: - Common- Setup
					Input 1 Audio 7  cmdID= 3864 "
		::= { iqsyn31CmdEntry 3864 }


	iqsyn31CommonSetupInput1Audio7LogString OBJECT-TYPE
		SYNTAX		RollCallString
		MAX-ACCESS		read-only
		STATUS			current
		DESCRIPTION
				"TYPE: - Display
				 PAGE: - Common- Setup
					Input 1 Audio 7=  cmdID= 3865  format=   "
		::= { iqsyn31CmdEntry 3865 }


	iqsyn31CommonSetupInput1Audio8LogEnable OBJECT-TYPE
		SYNTAX		INTEGER { disable(0), enable(1) }
		MAX-ACCESS		read-write
		STATUS			current
		DESCRIPTION
				"TYPE: - Checkbox
				 PAGE: - Common- Setup
					Input 1 Audio 8  cmdID= 3866 "
		::= { iqsyn31CmdEntry 3866 }


	iqsyn31CommonSetupInput1Audio8LogString OBJECT-TYPE
		SYNTAX		RollCallString
		MAX-ACCESS		read-only
		STATUS			current
		DESCRIPTION
				"TYPE: - Display
				 PAGE: - Common- Setup
					Input 1 Audio 8=  cmdID= 3867  format=   "
		::= { iqsyn31CmdEntry 3867 }


	iqsyn31CommonSetupOutput1TypeLogEnable OBJECT-TYPE
		SYNTAX		INTEGER { disable(0), enable(1) }
		MAX-ACCESS		read-write
		STATUS			current
		DESCRIPTION
				"TYPE: - Checkbox
				 PAGE: - Common- Setup
					Output 1 Type  cmdID= 4192 "
		::= { iqsyn31CmdEntry 4192 }


	iqsyn31CommonSetupOutput1TypeLogString OBJECT-TYPE
		SYNTAX		RollCallString
		MAX-ACCESS		read-only
		STATUS			current
		DESCRIPTION
				"TYPE: - Display
				 PAGE: - Common- Setup
					Output 1 Type=  cmdID= 4193  format=   "
		::= { iqsyn31CmdEntry 4193 }


	iqsyn31CommonSetupOutput1StateLogEnable OBJECT-TYPE
		SYNTAX		INTEGER { disable(0), enable(1) }
		MAX-ACCESS		read-write
		STATUS			current
		DESCRIPTION
				"TYPE: - Checkbox
				 PAGE: - Common- Setup
					Output 1 State  cmdID= 4196 "
		::= { iqsyn31CmdEntry 4196 }


	iqsyn31CommonSetupOutput1StateLogString OBJECT-TYPE
		SYNTAX		RollCallString
		MAX-ACCESS		read-only
		STATUS			current
		DESCRIPTION
				"TYPE: - Display
				 PAGE: - Common- Setup
					Output 1 State=  cmdID= 4197  format=   "
		::= { iqsyn31CmdEntry 4197 }


	iqsyn31CommonSetupOutput1StdLogEnable OBJECT-TYPE
		SYNTAX		INTEGER { disable(0), enable(1) }
		MAX-ACCESS		read-write
		STATUS			current
		DESCRIPTION
				"TYPE: - Checkbox
				 PAGE: - Common- Setup
					Output 1 Std  cmdID= 4200 "
		::= { iqsyn31CmdEntry 4200 }


	iqsyn31CommonSetupOutput1StdLogString OBJECT-TYPE
		SYNTAX		RollCallString
		MAX-ACCESS		read-only
		STATUS			current
		DESCRIPTION
				"TYPE: - Display
				 PAGE: - Common- Setup
					Output 1 Std=  cmdID= 4201  format=   "
		::= { iqsyn31CmdEntry 4201 }


	iqsyn31CommonSetupOutput1CaptionLogEnable OBJECT-TYPE
		SYNTAX		INTEGER { disable(0), enable(1) }
		MAX-ACCESS		read-write
		STATUS			current
		DESCRIPTION
				"TYPE: - Checkbox
				 PAGE: - Common- Setup
					Output 1 Caption  cmdID= 4204 "
		::= { iqsyn31CmdEntry 4204 }


	iqsyn31CommonSetupOutput1CaptionLogString OBJECT-TYPE
		SYNTAX		RollCallString
		MAX-ACCESS		read-only
		STATUS			current
		DESCRIPTION
				"TYPE: - Display
				 PAGE: - Common- Setup
					Output 1 Caption=  cmdID= 4205  format=   "
		::= { iqsyn31CmdEntry 4205 }


	iqsyn31CommonSetupInput2LogEnable OBJECT-TYPE
		SYNTAX		INTEGER { disable(0), enable(1) }
		MAX-ACCESS		read-write
		STATUS			current
		DESCRIPTION
				"TYPE: - Checkbox
				 PAGE: - Common- Setup
					Input 2  cmdID= 4002 "
		::= { iqsyn31CmdEntry 4002 }


	iqsyn31CommonSetupInput2LogString OBJECT-TYPE
		SYNTAX		RollCallString
		MAX-ACCESS		read-only
		STATUS			current
		DESCRIPTION
				"TYPE: - Display
				 PAGE: - Common- Setup
					Input 2=  cmdID= 4003  format=   "
		::= { iqsyn31CmdEntry 4003 }


	iqsyn31CommonSetupInput2StandardLogEnable OBJECT-TYPE
		SYNTAX		INTEGER { disable(0), enable(1) }
		MAX-ACCESS		read-write
		STATUS			current
		DESCRIPTION
				"TYPE: - Checkbox
				 PAGE: - Common- Setup
					Input 2 Standard  cmdID= 4006 "
		::= { iqsyn31CmdEntry 4006 }


	iqsyn31CommonSetupInput2StandardLogString OBJECT-TYPE
		SYNTAX		RollCallString
		MAX-ACCESS		read-only
		STATUS			current
		DESCRIPTION
				"TYPE: - Display
				 PAGE: - Common- Setup
					Input 2 Standard=  cmdID= 4007  format=   "
		::= { iqsyn31CmdEntry 4007 }


	iqsyn31CommonSetupInput2TypeLogEnable OBJECT-TYPE
		SYNTAX		INTEGER { disable(0), enable(1) }
		MAX-ACCESS		read-write
		STATUS			current
		DESCRIPTION
				"TYPE: - Checkbox
				 PAGE: - Common- Setup
					Input 2 Type  cmdID= 4026 "
		::= { iqsyn31CmdEntry 4026 }


	iqsyn31CommonSetupInput2TypeLogString OBJECT-TYPE
		SYNTAX		RollCallString
		MAX-ACCESS		read-only
		STATUS			current
		DESCRIPTION
				"TYPE: - Display
				 PAGE: - Common- Setup
					Input 2 Type=  cmdID= 4027  format=   "
		::= { iqsyn31CmdEntry 4027 }


	iqsyn31CommonSetupInput2IdentLogEnable OBJECT-TYPE
		SYNTAX		INTEGER { disable(0), enable(1) }
		MAX-ACCESS		read-write
		STATUS			current
		DESCRIPTION
				"TYPE: - Checkbox
				 PAGE: - Common- Setup
					Input 2 Ident  cmdID= 4030 "
		::= { iqsyn31CmdEntry 4030 }


	iqsyn31CommonSetupInput2IdentLogString OBJECT-TYPE
		SYNTAX		RollCallString
		MAX-ACCESS		read-only
		STATUS			current
		DESCRIPTION
				"TYPE: - Display
				 PAGE: - Common- Setup
					Input 2 Ident=  cmdID= 4031  format=   "
		::= { iqsyn31CmdEntry 4031 }


	iqsyn31CommonSetupIn2SDIERRSLogEnable OBJECT-TYPE
		SYNTAX		INTEGER { disable(0), enable(1) }
		MAX-ACCESS		read-write
		STATUS			current
		DESCRIPTION
				"TYPE: - Checkbox
				 PAGE: - Common- Setup
					In 2 SDI ERRS  cmdID= 4014 "
		::= { iqsyn31CmdEntry 4014 }


	iqsyn31CommonSetupIn2SDIERRSLogString OBJECT-TYPE
		SYNTAX		RollCallString
		MAX-ACCESS		read-only
		STATUS			current
		DESCRIPTION
				"TYPE: - Display
				 PAGE: - Common- Setup
					In 2 SDI ERRS=  cmdID= 4015  format=   "
		::= { iqsyn31CmdEntry 4015 }


	iqsyn31CommonSetupIn2SDIANCERRSLogEnable OBJECT-TYPE
		SYNTAX		INTEGER { disable(0), enable(1) }
		MAX-ACCESS		read-write
		STATUS			current
		DESCRIPTION
				"TYPE: - Checkbox
				 PAGE: - Common- Setup
					In 2 SDI ANC ERRS  cmdID= 4022 "
		::= { iqsyn31CmdEntry 4022 }


	iqsyn31CommonSetupIn2SDIANCERRSLogString OBJECT-TYPE
		SYNTAX		RollCallString
		MAX-ACCESS		read-only
		STATUS			current
		DESCRIPTION
				"TYPE: - Display
				 PAGE: - Common- Setup
					In 2 SDI ANC ERRS=  cmdID= 4023  format=   "
		::= { iqsyn31CmdEntry 4023 }


	iqsyn31CommonSetupInput2Audio1LogEnable OBJECT-TYPE
		SYNTAX		INTEGER { disable(0), enable(1) }
		MAX-ACCESS		read-write
		STATUS			current
		DESCRIPTION
				"TYPE: - Checkbox
				 PAGE: - Common- Setup
					Input 2 Audio 1  cmdID= 3868 "
		::= { iqsyn31CmdEntry 3868 }


	iqsyn31CommonSetupInput2Audio1LogString OBJECT-TYPE
		SYNTAX		RollCallString
		MAX-ACCESS		read-only
		STATUS			current
		DESCRIPTION
				"TYPE: - Display
				 PAGE: - Common- Setup
					Input 2 Audio 1=  cmdID= 3869  format=   "
		::= { iqsyn31CmdEntry 3869 }


	iqsyn31CommonSetupInput2Audio2LogEnable OBJECT-TYPE
		SYNTAX		INTEGER { disable(0), enable(1) }
		MAX-ACCESS		read-write
		STATUS			current
		DESCRIPTION
				"TYPE: - Checkbox
				 PAGE: - Common- Setup
					Input 2 Audio 2  cmdID= 3870 "
		::= { iqsyn31CmdEntry 3870 }


	iqsyn31CommonSetupInput2Audio2LogString OBJECT-TYPE
		SYNTAX		RollCallString
		MAX-ACCESS		read-only
		STATUS			current
		DESCRIPTION
				"TYPE: - Display
				 PAGE: - Common- Setup
					Input 2 Audio 2=  cmdID= 3871  format=   "
		::= { iqsyn31CmdEntry 3871 }


	iqsyn31CommonSetupInput2Audio3LogEnable OBJECT-TYPE
		SYNTAX		INTEGER { disable(0), enable(1) }
		MAX-ACCESS		read-write
		STATUS			current
		DESCRIPTION
				"TYPE: - Checkbox
				 PAGE: - Common- Setup
					Input 2 Audio 3  cmdID= 3872 "
		::= { iqsyn31CmdEntry 3872 }


	iqsyn31CommonSetupInput2Audio3LogString OBJECT-TYPE
		SYNTAX		RollCallString
		MAX-ACCESS		read-only
		STATUS			current
		DESCRIPTION
				"TYPE: - Display
				 PAGE: - Common- Setup
					Input 2 Audio 3=  cmdID= 3873  format=   "
		::= { iqsyn31CmdEntry 3873 }


	iqsyn31CommonSetupInput2Audio4LogEnable OBJECT-TYPE
		SYNTAX		INTEGER { disable(0), enable(1) }
		MAX-ACCESS		read-write
		STATUS			current
		DESCRIPTION
				"TYPE: - Checkbox
				 PAGE: - Common- Setup
					Input 2 Audio 4  cmdID= 3874 "
		::= { iqsyn31CmdEntry 3874 }


	iqsyn31CommonSetupInput2Audio4LogString OBJECT-TYPE
		SYNTAX		RollCallString
		MAX-ACCESS		read-only
		STATUS			current
		DESCRIPTION
				"TYPE: - Display
				 PAGE: - Common- Setup
					Input 2 Audio 4=  cmdID= 3875  format=   "
		::= { iqsyn31CmdEntry 3875 }


	iqsyn31CommonSetupInput2Audio5LogEnable OBJECT-TYPE
		SYNTAX		INTEGER { disable(0), enable(1) }
		MAX-ACCESS		read-write
		STATUS			current
		DESCRIPTION
				"TYPE: - Checkbox
				 PAGE: - Common- Setup
					Input 2 Audio 5  cmdID= 3876 "
		::= { iqsyn31CmdEntry 3876 }


	iqsyn31CommonSetupInput2Audio5LogString OBJECT-TYPE
		SYNTAX		RollCallString
		MAX-ACCESS		read-only
		STATUS			current
		DESCRIPTION
				"TYPE: - Display
				 PAGE: - Common- Setup
					Input 2 Audio 5=  cmdID= 3877  format=   "
		::= { iqsyn31CmdEntry 3877 }


	iqsyn31CommonSetupInput2Audio6LogEnable OBJECT-TYPE
		SYNTAX		INTEGER { disable(0), enable(1) }
		MAX-ACCESS		read-write
		STATUS			current
		DESCRIPTION
				"TYPE: - Checkbox
				 PAGE: - Common- Setup
					Input 2 Audio 6  cmdID= 3878 "
		::= { iqsyn31CmdEntry 3878 }


	iqsyn31CommonSetupInput2Audio6LogString OBJECT-TYPE
		SYNTAX		RollCallString
		MAX-ACCESS		read-only
		STATUS			current
		DESCRIPTION
				"TYPE: - Display
				 PAGE: - Common- Setup
					Input 2 Audio 6=  cmdID= 3879  format=   "
		::= { iqsyn31CmdEntry 3879 }


	iqsyn31CommonSetupInput2Audio7LogEnable OBJECT-TYPE
		SYNTAX		INTEGER { disable(0), enable(1) }
		MAX-ACCESS		read-write
		STATUS			current
		DESCRIPTION
				"TYPE: - Checkbox
				 PAGE: - Common- Setup
					Input 2 Audio 7  cmdID= 3880 "
		::= { iqsyn31CmdEntry 3880 }


	iqsyn31CommonSetupInput2Audio7LogString OBJECT-TYPE
		SYNTAX		RollCallString
		MAX-ACCESS		read-only
		STATUS			current
		DESCRIPTION
				"TYPE: - Display
				 PAGE: - Common- Setup
					Input 2 Audio 7=  cmdID= 3881  format=   "
		::= { iqsyn31CmdEntry 3881 }


	iqsyn31CommonSetupInput2Audio8LogEnable OBJECT-TYPE
		SYNTAX		INTEGER { disable(0), enable(1) }
		MAX-ACCESS		read-write
		STATUS			current
		DESCRIPTION
				"TYPE: - Checkbox
				 PAGE: - Common- Setup
					Input 2 Audio 8  cmdID= 3882 "
		::= { iqsyn31CmdEntry 3882 }


	iqsyn31CommonSetupInput2Audio8LogString OBJECT-TYPE
		SYNTAX		RollCallString
		MAX-ACCESS		read-only
		STATUS			current
		DESCRIPTION
				"TYPE: - Display
				 PAGE: - Common- Setup
					Input 2 Audio 8=  cmdID= 3883  format=   "
		::= { iqsyn31CmdEntry 3883 }


	iqsyn31CommonSetupOutput2TypeLogEnable OBJECT-TYPE
		SYNTAX		INTEGER { disable(0), enable(1) }
		MAX-ACCESS		read-write
		STATUS			current
		DESCRIPTION
				"TYPE: - Checkbox
				 PAGE: - Common- Setup
					Output 2 Type  cmdID= 4194 "
		::= { iqsyn31CmdEntry 4194 }


	iqsyn31CommonSetupOutput2TypeLogString OBJECT-TYPE
		SYNTAX		RollCallString
		MAX-ACCESS		read-only
		STATUS			current
		DESCRIPTION
				"TYPE: - Display
				 PAGE: - Common- Setup
					Output 2 Type=  cmdID= 4195  format=   "
		::= { iqsyn31CmdEntry 4195 }


	iqsyn31CommonSetupOutput2StateLogEnable OBJECT-TYPE
		SYNTAX		INTEGER { disable(0), enable(1) }
		MAX-ACCESS		read-write
		STATUS			current
		DESCRIPTION
				"TYPE: - Checkbox
				 PAGE: - Common- Setup
					Output 2 State  cmdID= 4198 "
		::= { iqsyn31CmdEntry 4198 }


	iqsyn31CommonSetupOutput2StateLogString OBJECT-TYPE
		SYNTAX		RollCallString
		MAX-ACCESS		read-only
		STATUS			current
		DESCRIPTION
				"TYPE: - Display
				 PAGE: - Common- Setup
					Output 2 State=  cmdID= 4199  format=   "
		::= { iqsyn31CmdEntry 4199 }


	iqsyn31CommonSetupOutput2StdLogEnable OBJECT-TYPE
		SYNTAX		INTEGER { disable(0), enable(1) }
		MAX-ACCESS		read-write
		STATUS			current
		DESCRIPTION
				"TYPE: - Checkbox
				 PAGE: - Common- Setup
					Output 2 Std  cmdID= 4202 "
		::= { iqsyn31CmdEntry 4202 }


	iqsyn31CommonSetupOutput2StdLogString OBJECT-TYPE
		SYNTAX		RollCallString
		MAX-ACCESS		read-only
		STATUS			current
		DESCRIPTION
				"TYPE: - Display
				 PAGE: - Common- Setup
					Output 2 Std=  cmdID= 4203  format=   "
		::= { iqsyn31CmdEntry 4203 }


	iqsyn31CommonSetupOutput2CaptionLogEnable OBJECT-TYPE
		SYNTAX		INTEGER { disable(0), enable(1) }
		MAX-ACCESS		read-write
		STATUS			current
		DESCRIPTION
				"TYPE: - Checkbox
				 PAGE: - Common- Setup
					Output 2 Caption  cmdID= 4206 "
		::= { iqsyn31CmdEntry 4206 }


	iqsyn31CommonSetupOutput2CaptionLogString OBJECT-TYPE
		SYNTAX		RollCallString
		MAX-ACCESS		read-only
		STATUS			current
		DESCRIPTION
				"TYPE: - Display
				 PAGE: - Common- Setup
					Output 2 Caption=  cmdID= 4207  format=   "
		::= { iqsyn31CmdEntry 4207 }


	iqsyn31CommonSetupop1embed11LogEnable OBJECT-TYPE
		SYNTAX		INTEGER { disable(0), enable(1) }
		MAX-ACCESS		read-write
		STATUS			current
		DESCRIPTION
				"TYPE: - Checkbox
				 PAGE: - Common- Setup
					op1embed11  cmdID= 4064 "
		::= { iqsyn31CmdEntry 4064 }


	iqsyn31CommonSetupop1embed11LogString OBJECT-TYPE
		SYNTAX		RollCallString
		MAX-ACCESS		read-only
		STATUS			current
		DESCRIPTION
				"TYPE: - Display
				 PAGE: - Common- Setup
					op1embed11=  cmdID= 4065  format=   "
		::= { iqsyn31CmdEntry 4065 }


	iqsyn31CommonSetupop1embed12LogEnable OBJECT-TYPE
		SYNTAX		INTEGER { disable(0), enable(1) }
		MAX-ACCESS		read-write
		STATUS			current
		DESCRIPTION
				"TYPE: - Checkbox
				 PAGE: - Common- Setup
					op1embed12  cmdID= 4068 "
		::= { iqsyn31CmdEntry 4068 }


	iqsyn31CommonSetupop1embed12LogString OBJECT-TYPE
		SYNTAX		RollCallString
		MAX-ACCESS		read-only
		STATUS			current
		DESCRIPTION
				"TYPE: - Display
				 PAGE: - Common- Setup
					op1embed12=  cmdID= 4069  format=   "
		::= { iqsyn31CmdEntry 4069 }


	iqsyn31CommonSetupop1embed21LogEnable OBJECT-TYPE
		SYNTAX		INTEGER { disable(0), enable(1) }
		MAX-ACCESS		read-write
		STATUS			current
		DESCRIPTION
				"TYPE: - Checkbox
				 PAGE: - Common- Setup
					op1embed21  cmdID= 4072 "
		::= { iqsyn31CmdEntry 4072 }


	iqsyn31CommonSetupop1embed21LogString OBJECT-TYPE
		SYNTAX		RollCallString
		MAX-ACCESS		read-only
		STATUS			current
		DESCRIPTION
				"TYPE: - Display
				 PAGE: - Common- Setup
					op1embed21=  cmdID= 4073  format=   "
		::= { iqsyn31CmdEntry 4073 }


	iqsyn31CommonSetupop1embed22LogEnable OBJECT-TYPE
		SYNTAX		INTEGER { disable(0), enable(1) }
		MAX-ACCESS		read-write
		STATUS			current
		DESCRIPTION
				"TYPE: - Checkbox
				 PAGE: - Common- Setup
					op1embed22  cmdID= 4076 "
		::= { iqsyn31CmdEntry 4076 }


	iqsyn31CommonSetupop1embed22LogString OBJECT-TYPE
		SYNTAX		RollCallString
		MAX-ACCESS		read-only
		STATUS			current
		DESCRIPTION
				"TYPE: - Display
				 PAGE: - Common- Setup
					op1embed22=  cmdID= 4077  format=   "
		::= { iqsyn31CmdEntry 4077 }


	iqsyn31CommonSetupop1embed31LogEnable OBJECT-TYPE
		SYNTAX		INTEGER { disable(0), enable(1) }
		MAX-ACCESS		read-write
		STATUS			current
		DESCRIPTION
				"TYPE: - Checkbox
				 PAGE: - Common- Setup
					op1embed31  cmdID= 4080 "
		::= { iqsyn31CmdEntry 4080 }


	iqsyn31CommonSetupop1embed31LogString OBJECT-TYPE
		SYNTAX		RollCallString
		MAX-ACCESS		read-only
		STATUS			current
		DESCRIPTION
				"TYPE: - Display
				 PAGE: - Common- Setup
					op1embed31=  cmdID= 4081  format=   "
		::= { iqsyn31CmdEntry 4081 }


	iqsyn31CommonSetupop1embed32LogEnable OBJECT-TYPE
		SYNTAX		INTEGER { disable(0), enable(1) }
		MAX-ACCESS		read-write
		STATUS			current
		DESCRIPTION
				"TYPE: - Checkbox
				 PAGE: - Common- Setup
					op1embed32  cmdID= 4084 "
		::= { iqsyn31CmdEntry 4084 }


	iqsyn31CommonSetupop1embed32LogString OBJECT-TYPE
		SYNTAX		RollCallString
		MAX-ACCESS		read-only
		STATUS			current
		DESCRIPTION
				"TYPE: - Display
				 PAGE: - Common- Setup
					op1embed32=  cmdID= 4085  format=   "
		::= { iqsyn31CmdEntry 4085 }


	iqsyn31CommonSetupop1embed41LogEnable OBJECT-TYPE
		SYNTAX		INTEGER { disable(0), enable(1) }
		MAX-ACCESS		read-write
		STATUS			current
		DESCRIPTION
				"TYPE: - Checkbox
				 PAGE: - Common- Setup
					op1embed41  cmdID= 4088 "
		::= { iqsyn31CmdEntry 4088 }


	iqsyn31CommonSetupop1embed41LogString OBJECT-TYPE
		SYNTAX		RollCallString
		MAX-ACCESS		read-only
		STATUS			current
		DESCRIPTION
				"TYPE: - Display
				 PAGE: - Common- Setup
					op1embed41=  cmdID= 4089  format=   "
		::= { iqsyn31CmdEntry 4089 }


	iqsyn31CommonSetupop1embed42LogEnable OBJECT-TYPE
		SYNTAX		INTEGER { disable(0), enable(1) }
		MAX-ACCESS		read-write
		STATUS			current
		DESCRIPTION
				"TYPE: - Checkbox
				 PAGE: - Common- Setup
					op1embed42  cmdID= 4092 "
		::= { iqsyn31CmdEntry 4092 }


	iqsyn31CommonSetupop1embed42LogString OBJECT-TYPE
		SYNTAX		RollCallString
		MAX-ACCESS		read-only
		STATUS			current
		DESCRIPTION
				"TYPE: - Display
				 PAGE: - Common- Setup
					op1embed42=  cmdID= 4093  format=   "
		::= { iqsyn31CmdEntry 4093 }


	iqsyn31CommonSetupop1embed51LogEnable OBJECT-TYPE
		SYNTAX		INTEGER { disable(0), enable(1) }
		MAX-ACCESS		read-write
		STATUS			current
		DESCRIPTION
				"TYPE: - Checkbox
				 PAGE: - Common- Setup
					op1embed51  cmdID= 4096 "
		::= { iqsyn31CmdEntry 4096 }


	iqsyn31CommonSetupop1embed51LogString OBJECT-TYPE
		SYNTAX		RollCallString
		MAX-ACCESS		read-only
		STATUS			current
		DESCRIPTION
				"TYPE: - Display
				 PAGE: - Common- Setup
					op1embed51=  cmdID= 4097  format=   "
		::= { iqsyn31CmdEntry 4097 }


	iqsyn31CommonSetupop1embed52LogEnable OBJECT-TYPE
		SYNTAX		INTEGER { disable(0), enable(1) }
		MAX-ACCESS		read-write
		STATUS			current
		DESCRIPTION
				"TYPE: - Checkbox
				 PAGE: - Common- Setup
					op1embed52  cmdID= 4100 "
		::= { iqsyn31CmdEntry 4100 }


	iqsyn31CommonSetupop1embed52LogString OBJECT-TYPE
		SYNTAX		RollCallString
		MAX-ACCESS		read-only
		STATUS			current
		DESCRIPTION
				"TYPE: - Display
				 PAGE: - Common- Setup
					op1embed52=  cmdID= 4101  format=   "
		::= { iqsyn31CmdEntry 4101 }


	iqsyn31CommonSetupop1embed61LogEnable OBJECT-TYPE
		SYNTAX		INTEGER { disable(0), enable(1) }
		MAX-ACCESS		read-write
		STATUS			current
		DESCRIPTION
				"TYPE: - Checkbox
				 PAGE: - Common- Setup
					op1embed61  cmdID= 4104 "
		::= { iqsyn31CmdEntry 4104 }


	iqsyn31CommonSetupop1embed61LogString OBJECT-TYPE
		SYNTAX		RollCallString
		MAX-ACCESS		read-only
		STATUS			current
		DESCRIPTION
				"TYPE: - Display
				 PAGE: - Common- Setup
					op1embed61=  cmdID= 4105  format=   "
		::= { iqsyn31CmdEntry 4105 }


	iqsyn31CommonSetupop1embed62LogEnable OBJECT-TYPE
		SYNTAX		INTEGER { disable(0), enable(1) }
		MAX-ACCESS		read-write
		STATUS			current
		DESCRIPTION
				"TYPE: - Checkbox
				 PAGE: - Common- Setup
					op1embed62  cmdID= 4108 "
		::= { iqsyn31CmdEntry 4108 }


	iqsyn31CommonSetupop1embed62LogString OBJECT-TYPE
		SYNTAX		RollCallString
		MAX-ACCESS		read-only
		STATUS			current
		DESCRIPTION
				"TYPE: - Display
				 PAGE: - Common- Setup
					op1embed62=  cmdID= 4109  format=   "
		::= { iqsyn31CmdEntry 4109 }


	iqsyn31CommonSetupop1embed71LogEnable OBJECT-TYPE
		SYNTAX		INTEGER { disable(0), enable(1) }
		MAX-ACCESS		read-write
		STATUS			current
		DESCRIPTION
				"TYPE: - Checkbox
				 PAGE: - Common- Setup
					op1embed71  cmdID= 4112 "
		::= { iqsyn31CmdEntry 4112 }


	iqsyn31CommonSetupop1embed71LogString OBJECT-TYPE
		SYNTAX		RollCallString
		MAX-ACCESS		read-only
		STATUS			current
		DESCRIPTION
				"TYPE: - Display
				 PAGE: - Common- Setup
					op1embed71=  cmdID= 4113  format=   "
		::= { iqsyn31CmdEntry 4113 }


	iqsyn31CommonSetupop1embed72LogEnable OBJECT-TYPE
		SYNTAX		INTEGER { disable(0), enable(1) }
		MAX-ACCESS		read-write
		STATUS			current
		DESCRIPTION
				"TYPE: - Checkbox
				 PAGE: - Common- Setup
					op1embed72  cmdID= 4116 "
		::= { iqsyn31CmdEntry 4116 }


	iqsyn31CommonSetupop1embed72LogString OBJECT-TYPE
		SYNTAX		RollCallString
		MAX-ACCESS		read-only
		STATUS			current
		DESCRIPTION
				"TYPE: - Display
				 PAGE: - Common- Setup
					op1embed72=  cmdID= 4117  format=   "
		::= { iqsyn31CmdEntry 4117 }


	iqsyn31CommonSetupop1embed81LogEnable OBJECT-TYPE
		SYNTAX		INTEGER { disable(0), enable(1) }
		MAX-ACCESS		read-write
		STATUS			current
		DESCRIPTION
				"TYPE: - Checkbox
				 PAGE: - Common- Setup
					op1embed81  cmdID= 4120 "
		::= { iqsyn31CmdEntry 4120 }


	iqsyn31CommonSetupop1embed81LogString OBJECT-TYPE
		SYNTAX		RollCallString
		MAX-ACCESS		read-only
		STATUS			current
		DESCRIPTION
				"TYPE: - Display
				 PAGE: - Common- Setup
					op1embed81=  cmdID= 4121  format=   "
		::= { iqsyn31CmdEntry 4121 }


	iqsyn31CommonSetupop1embed82LogEnable OBJECT-TYPE
		SYNTAX		INTEGER { disable(0), enable(1) }
		MAX-ACCESS		read-write
		STATUS			current
		DESCRIPTION
				"TYPE: - Checkbox
				 PAGE: - Common- Setup
					op1embed82  cmdID= 4124 "
		::= { iqsyn31CmdEntry 4124 }


	iqsyn31CommonSetupop1embed82LogString OBJECT-TYPE
		SYNTAX		RollCallString
		MAX-ACCESS		read-only
		STATUS			current
		DESCRIPTION
				"TYPE: - Display
				 PAGE: - Common- Setup
					op1embed82=  cmdID= 4125  format=   "
		::= { iqsyn31CmdEntry 4125 }


	iqsyn31CommonSetupop2embed11LogEnable OBJECT-TYPE
		SYNTAX		INTEGER { disable(0), enable(1) }
		MAX-ACCESS		read-write
		STATUS			current
		DESCRIPTION
				"TYPE: - Checkbox
				 PAGE: - Common- Setup
					op2embed11  cmdID= 4066 "
		::= { iqsyn31CmdEntry 4066 }


	iqsyn31CommonSetupop2embed11LogString OBJECT-TYPE
		SYNTAX		RollCallString
		MAX-ACCESS		read-only
		STATUS			current
		DESCRIPTION
				"TYPE: - Display
				 PAGE: - Common- Setup
					op2embed11=  cmdID= 4067  format=   "
		::= { iqsyn31CmdEntry 4067 }


	iqsyn31CommonSetupop2embed12LogEnable OBJECT-TYPE
		SYNTAX		INTEGER { disable(0), enable(1) }
		MAX-ACCESS		read-write
		STATUS			current
		DESCRIPTION
				"TYPE: - Checkbox
				 PAGE: - Common- Setup
					op2embed12  cmdID= 4070 "
		::= { iqsyn31CmdEntry 4070 }


	iqsyn31CommonSetupop2embed12LogString OBJECT-TYPE
		SYNTAX		RollCallString
		MAX-ACCESS		read-only
		STATUS			current
		DESCRIPTION
				"TYPE: - Display
				 PAGE: - Common- Setup
					op2embed12=  cmdID= 4071  format=   "
		::= { iqsyn31CmdEntry 4071 }


	iqsyn31CommonSetupop2embed21LogEnable OBJECT-TYPE
		SYNTAX		INTEGER { disable(0), enable(1) }
		MAX-ACCESS		read-write
		STATUS			current
		DESCRIPTION
				"TYPE: - Checkbox
				 PAGE: - Common- Setup
					op2embed21  cmdID= 4074 "
		::= { iqsyn31CmdEntry 4074 }


	iqsyn31CommonSetupop2embed21LogString OBJECT-TYPE
		SYNTAX		RollCallString
		MAX-ACCESS		read-only
		STATUS			current
		DESCRIPTION
				"TYPE: - Display
				 PAGE: - Common- Setup
					op2embed21=  cmdID= 4075  format=   "
		::= { iqsyn31CmdEntry 4075 }


	iqsyn31CommonSetupop2embed22LogEnable OBJECT-TYPE
		SYNTAX		INTEGER { disable(0), enable(1) }
		MAX-ACCESS		read-write
		STATUS			current
		DESCRIPTION
				"TYPE: - Checkbox
				 PAGE: - Common- Setup
					op2embed22  cmdID= 4078 "
		::= { iqsyn31CmdEntry 4078 }


	iqsyn31CommonSetupop2embed22LogString OBJECT-TYPE
		SYNTAX		RollCallString
		MAX-ACCESS		read-only
		STATUS			current
		DESCRIPTION
				"TYPE: - Display
				 PAGE: - Common- Setup
					op2embed22=  cmdID= 4079  format=   "
		::= { iqsyn31CmdEntry 4079 }


	iqsyn31CommonSetupop2embed31LogEnable OBJECT-TYPE
		SYNTAX		INTEGER { disable(0), enable(1) }
		MAX-ACCESS		read-write
		STATUS			current
		DESCRIPTION
				"TYPE: - Checkbox
				 PAGE: - Common- Setup
					op2embed31  cmdID= 4082 "
		::= { iqsyn31CmdEntry 4082 }


	iqsyn31CommonSetupop2embed31LogString OBJECT-TYPE
		SYNTAX		RollCallString
		MAX-ACCESS		read-only
		STATUS			current
		DESCRIPTION
				"TYPE: - Display
				 PAGE: - Common- Setup
					op2embed31=  cmdID= 4083  format=   "
		::= { iqsyn31CmdEntry 4083 }


	iqsyn31CommonSetupop2embed32LogEnable OBJECT-TYPE
		SYNTAX		INTEGER { disable(0), enable(1) }
		MAX-ACCESS		read-write
		STATUS			current
		DESCRIPTION
				"TYPE: - Checkbox
				 PAGE: - Common- Setup
					op2embed32  cmdID= 4086 "
		::= { iqsyn31CmdEntry 4086 }


	iqsyn31CommonSetupop2embed32LogString OBJECT-TYPE
		SYNTAX		RollCallString
		MAX-ACCESS		read-only
		STATUS			current
		DESCRIPTION
				"TYPE: - Display
				 PAGE: - Common- Setup
					op2embed32=  cmdID= 4087  format=   "
		::= { iqsyn31CmdEntry 4087 }


	iqsyn31CommonSetupop2embed41LogEnable OBJECT-TYPE
		SYNTAX		INTEGER { disable(0), enable(1) }
		MAX-ACCESS		read-write
		STATUS			current
		DESCRIPTION
				"TYPE: - Checkbox
				 PAGE: - Common- Setup
					op2embed41  cmdID= 4090 "
		::= { iqsyn31CmdEntry 4090 }


	iqsyn31CommonSetupop2embed41LogString OBJECT-TYPE
		SYNTAX		RollCallString
		MAX-ACCESS		read-only
		STATUS			current
		DESCRIPTION
				"TYPE: - Display
				 PAGE: - Common- Setup
					op2embed41=  cmdID= 4091  format=   "
		::= { iqsyn31CmdEntry 4091 }


	iqsyn31CommonSetupop2embed42LogEnable OBJECT-TYPE
		SYNTAX		INTEGER { disable(0), enable(1) }
		MAX-ACCESS		read-write
		STATUS			current
		DESCRIPTION
				"TYPE: - Checkbox
				 PAGE: - Common- Setup
					op2embed42  cmdID= 4094 "
		::= { iqsyn31CmdEntry 4094 }


	iqsyn31CommonSetupop2embed42LogString OBJECT-TYPE
		SYNTAX		RollCallString
		MAX-ACCESS		read-only
		STATUS			current
		DESCRIPTION
				"TYPE: - Display
				 PAGE: - Common- Setup
					op2embed42=  cmdID= 4095  format=   "
		::= { iqsyn31CmdEntry 4095 }


	iqsyn31CommonSetupop2embed51LogEnable OBJECT-TYPE
		SYNTAX		INTEGER { disable(0), enable(1) }
		MAX-ACCESS		read-write
		STATUS			current
		DESCRIPTION
				"TYPE: - Checkbox
				 PAGE: - Common- Setup
					op2embed51  cmdID= 4098 "
		::= { iqsyn31CmdEntry 4098 }


	iqsyn31CommonSetupop2embed51LogString OBJECT-TYPE
		SYNTAX		RollCallString
		MAX-ACCESS		read-only
		STATUS			current
		DESCRIPTION
				"TYPE: - Display
				 PAGE: - Common- Setup
					op2embed51=  cmdID= 4099  format=   "
		::= { iqsyn31CmdEntry 4099 }


	iqsyn31CommonSetupop2embed52LogEnable OBJECT-TYPE
		SYNTAX		INTEGER { disable(0), enable(1) }
		MAX-ACCESS		read-write
		STATUS			current
		DESCRIPTION
				"TYPE: - Checkbox
				 PAGE: - Common- Setup
					op2embed52  cmdID= 4102 "
		::= { iqsyn31CmdEntry 4102 }


	iqsyn31CommonSetupop2embed52LogString OBJECT-TYPE
		SYNTAX		RollCallString
		MAX-ACCESS		read-only
		STATUS			current
		DESCRIPTION
				"TYPE: - Display
				 PAGE: - Common- Setup
					op2embed52=  cmdID= 4103  format=   "
		::= { iqsyn31CmdEntry 4103 }


	iqsyn31CommonSetupop2embed61LogEnable OBJECT-TYPE
		SYNTAX		INTEGER { disable(0), enable(1) }
		MAX-ACCESS		read-write
		STATUS			current
		DESCRIPTION
				"TYPE: - Checkbox
				 PAGE: - Common- Setup
					op2embed61  cmdID= 4106 "
		::= { iqsyn31CmdEntry 4106 }


	iqsyn31CommonSetupop2embed61LogString OBJECT-TYPE
		SYNTAX		RollCallString
		MAX-ACCESS		read-only
		STATUS			current
		DESCRIPTION
				"TYPE: - Display
				 PAGE: - Common- Setup
					op2embed61=  cmdID= 4107  format=   "
		::= { iqsyn31CmdEntry 4107 }


	iqsyn31CommonSetupop2embed62LogEnable OBJECT-TYPE
		SYNTAX		INTEGER { disable(0), enable(1) }
		MAX-ACCESS		read-write
		STATUS			current
		DESCRIPTION
				"TYPE: - Checkbox
				 PAGE: - Common- Setup
					op2embed62  cmdID= 4110 "
		::= { iqsyn31CmdEntry 4110 }


	iqsyn31CommonSetupop2embed62LogString OBJECT-TYPE
		SYNTAX		RollCallString
		MAX-ACCESS		read-only
		STATUS			current
		DESCRIPTION
				"TYPE: - Display
				 PAGE: - Common- Setup
					op2embed62=  cmdID= 4111  format=   "
		::= { iqsyn31CmdEntry 4111 }


	iqsyn31CommonSetupop2embed71LogEnable OBJECT-TYPE
		SYNTAX		INTEGER { disable(0), enable(1) }
		MAX-ACCESS		read-write
		STATUS			current
		DESCRIPTION
				"TYPE: - Checkbox
				 PAGE: - Common- Setup
					op2embed71  cmdID= 4114 "
		::= { iqsyn31CmdEntry 4114 }


	iqsyn31CommonSetupop2embed71LogString OBJECT-TYPE
		SYNTAX		RollCallString
		MAX-ACCESS		read-only
		STATUS			current
		DESCRIPTION
				"TYPE: - Display
				 PAGE: - Common- Setup
					op2embed71=  cmdID= 4115  format=   "
		::= { iqsyn31CmdEntry 4115 }


	iqsyn31CommonSetupop2embed72LogEnable OBJECT-TYPE
		SYNTAX		INTEGER { disable(0), enable(1) }
		MAX-ACCESS		read-write
		STATUS			current
		DESCRIPTION
				"TYPE: - Checkbox
				 PAGE: - Common- Setup
					op2embed72  cmdID= 4118 "
		::= { iqsyn31CmdEntry 4118 }


	iqsyn31CommonSetupop2embed72LogString OBJECT-TYPE
		SYNTAX		RollCallString
		MAX-ACCESS		read-only
		STATUS			current
		DESCRIPTION
				"TYPE: - Display
				 PAGE: - Common- Setup
					op2embed72=  cmdID= 4119  format=   "
		::= { iqsyn31CmdEntry 4119 }


	iqsyn31CommonSetupop2embed81LogEnable OBJECT-TYPE
		SYNTAX		INTEGER { disable(0), enable(1) }
		MAX-ACCESS		read-write
		STATUS			current
		DESCRIPTION
				"TYPE: - Checkbox
				 PAGE: - Common- Setup
					op2embed81  cmdID= 4122 "
		::= { iqsyn31CmdEntry 4122 }


	iqsyn31CommonSetupop2embed81LogString OBJECT-TYPE
		SYNTAX		RollCallString
		MAX-ACCESS		read-only
		STATUS			current
		DESCRIPTION
				"TYPE: - Display
				 PAGE: - Common- Setup
					op2embed81=  cmdID= 4123  format=   "
		::= { iqsyn31CmdEntry 4123 }


	iqsyn31CommonSetupop2embed82LogEnable OBJECT-TYPE
		SYNTAX		INTEGER { disable(0), enable(1) }
		MAX-ACCESS		read-write
		STATUS			current
		DESCRIPTION
				"TYPE: - Checkbox
				 PAGE: - Common- Setup
					op2embed82  cmdID= 4126 "
		::= { iqsyn31CmdEntry 4126 }


	iqsyn31CommonSetupop2embed82LogString OBJECT-TYPE
		SYNTAX		RollCallString
		MAX-ACCESS		read-only
		STATUS			current
		DESCRIPTION
				"TYPE: - Display
				 PAGE: - Common- Setup
					op2embed82=  cmdID= 4127  format=   "
		::= { iqsyn31CmdEntry 4127 }


	iqsyn31CommonSetupGenlock1StateLogEnable OBJECT-TYPE
		SYNTAX		INTEGER { disable(0), enable(1) }
		MAX-ACCESS		read-write
		STATUS			current
		DESCRIPTION
				"TYPE: - Checkbox
				 PAGE: - Common- Setup
					Genlock 1 State  cmdID= 4052 "
		::= { iqsyn31CmdEntry 4052 }


	iqsyn31CommonSetupGenlock1StateLogString OBJECT-TYPE
		SYNTAX		RollCallString
		MAX-ACCESS		read-only
		STATUS			current
		DESCRIPTION
				"TYPE: - Display
				 PAGE: - Common- Setup
					Genlock 1 State=  cmdID= 4053  format=   "
		::= { iqsyn31CmdEntry 4053 }


	iqsyn31CommonSetupRef1StateLogEnable OBJECT-TYPE
		SYNTAX		INTEGER { disable(0), enable(1) }
		MAX-ACCESS		read-write
		STATUS			current
		DESCRIPTION
				"TYPE: - Checkbox
				 PAGE: - Common- Setup
					Ref 1 State  cmdID= 4040 "
		::= { iqsyn31CmdEntry 4040 }


	iqsyn31CommonSetupRef1StateLogString OBJECT-TYPE
		SYNTAX		RollCallString
		MAX-ACCESS		read-only
		STATUS			current
		DESCRIPTION
				"TYPE: - Display
				 PAGE: - Common- Setup
					Ref 1 State=  cmdID= 4041  format=   "
		::= { iqsyn31CmdEntry 4041 }


	iqsyn31CommonSetupRef1StandardLogEnable OBJECT-TYPE
		SYNTAX		INTEGER { disable(0), enable(1) }
		MAX-ACCESS		read-write
		STATUS			current
		DESCRIPTION
				"TYPE: - Checkbox
				 PAGE: - Common- Setup
					Ref 1 Standard  cmdID= 4044 "
		::= { iqsyn31CmdEntry 4044 }


	iqsyn31CommonSetupRef1StandardLogString OBJECT-TYPE
		SYNTAX		RollCallString
		MAX-ACCESS		read-only
		STATUS			current
		DESCRIPTION
				"TYPE: - Display
				 PAGE: - Common- Setup
					Ref 1 Standard=  cmdID= 4045  format=   "
		::= { iqsyn31CmdEntry 4045 }


	iqsyn31CommonSetupRef1TypeLogEnable OBJECT-TYPE
		SYNTAX		INTEGER { disable(0), enable(1) }
		MAX-ACCESS		read-write
		STATUS			current
		DESCRIPTION
				"TYPE: - Checkbox
				 PAGE: - Common- Setup
					Ref 1 Type  cmdID= 4048 "
		::= { iqsyn31CmdEntry 4048 }


	iqsyn31CommonSetupRef1TypeLogString OBJECT-TYPE
		SYNTAX		RollCallString
		MAX-ACCESS		read-only
		STATUS			current
		DESCRIPTION
				"TYPE: - Display
				 PAGE: - Common- Setup
					Ref 1 Type=  cmdID= 4049  format=   "
		::= { iqsyn31CmdEntry 4049 }


	iqsyn31CommonStatusProduct OBJECT-TYPE
		SYNTAX		RollCallString
		MAX-ACCESS		read-only
		STATUS			current
		DESCRIPTION
				"TYPE: - Display
				 PAGE: - Common- Status
					Product  cmdID= 5000  format=   "
		::= { iqsyn31CmdEntry 5000 }


	iqsyn31CommonStatusSoftwareVersion OBJECT-TYPE
		SYNTAX		RollCallString
		MAX-ACCESS		read-only
		STATUS			current
		DESCRIPTION
				"TYPE: - Display
				 PAGE: - Common- Status
					Software Version  cmdID= 2  format=   "
		::= { iqsyn31CmdEntry 2 }


	iqsyn31CommonStatusSerialNo OBJECT-TYPE
		SYNTAX		RollCallString
		MAX-ACCESS		read-only
		STATUS			current
		DESCRIPTION
				"TYPE: - Display
				 PAGE: - Common- Status
					Serial No  cmdID= 1  format=   "
		::= { iqsyn31CmdEntry 1 }


	iqsyn31CommonStatusFactoryDefaults OBJECT-TYPE
		SYNTAX		INTEGER { noAction(0),valFactoryDefaults(1) }
		MAX-ACCESS		read-write
		STATUS			current
		DESCRIPTION
				"TYPE: - Button
				 PAGE: - Common- Status
					Factory Defaults  cmdID= 5020  value= 1  "
		::= { iqsyn31CmdEntry 5020 }


	iqsyn31CommonStatusDefaultSetting OBJECT-TYPE
		SYNTAX		INTEGER { noAction(0),valDefaultSetting(1) }
		MAX-ACCESS		read-write
		STATUS			current
		DESCRIPTION
				"TYPE: - Button
				 PAGE: - Common- Status
					Default Setting  cmdID= 5021  value= 1  "
		::= { iqsyn31CmdEntry 5021 }


	iqsyn31CommonStatusRestart OBJECT-TYPE
		SYNTAX		INTEGER { noAction(0),valRestart(1) }
		MAX-ACCESS		read-write
		STATUS			current
		DESCRIPTION
				"TYPE: - Button
				 PAGE: - Common- Status
					Restart  cmdID= 4  value= 1  "
		::= { iqsyn31CmdEntry 4 }


	iqsyn31CommonStatusBuild OBJECT-TYPE
		SYNTAX		RollCallString
		MAX-ACCESS		read-only
		STATUS			current
		DESCRIPTION
				"TYPE: - Display
				 PAGE: - Common- Status
					Build  cmdID= 5  format=   "
		::= { iqsyn31CmdEntry 5 }


	iqsyn31CommonStatusPCB OBJECT-TYPE
		SYNTAX		RollCallString
		MAX-ACCESS		read-only
		STATUS			current
		DESCRIPTION
				"TYPE: - Display
				 PAGE: - Common- Status
					PCB  cmdID= 6  format=   "
		::= { iqsyn31CmdEntry 6 }


	iqsyn31CommonStatusKOSVersion OBJECT-TYPE
		SYNTAX		RollCallString
		MAX-ACCESS		read-only
		STATUS			current
		DESCRIPTION
				"TYPE: - Display
				 PAGE: - Common- Status
					KOS Version  cmdID= 7  format=   "
		::= { iqsyn31CmdEntry 7 }


	iqsyn31CommonStatusFirmwareVersion OBJECT-TYPE
		SYNTAX		RollCallString
		MAX-ACCESS		read-only
		STATUS			current
		DESCRIPTION
				"TYPE: - Display
				 PAGE: - Common- Status
					Firmware Version  cmdID= 5001  format=   "
		::= { iqsyn31CmdEntry 5001 }


	iqsyn31CommonStatusUpTime OBJECT-TYPE
		SYNTAX		RollCallString
		MAX-ACCESS		read-only
		STATUS			current
		DESCRIPTION
				"TYPE: - Display
				 PAGE: - Common- Status
					Up Time  cmdID= 8  format=   "
		::= { iqsyn31CmdEntry 8 }


	iqsyn31CommonStatus OBJECT-TYPE
		SYNTAX		INTEGER {
							valVideo(0),
							valAudioInput(1),
							valReference(2)
							}
		MAX-ACCESS		read-write
		STATUS			current
		DESCRIPTION
				"TYPE: - Button
				 PAGE: - Common- Status
					Video  cmdID= 1915  value= 0
					AudioInput  cmdID= 1915  value= 1
					Reference  cmdID= 1915  value= 2  "
		::= { iqsyn31CmdEntry 1915 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  The OID for FAULT on slot 12 for swCardEventLogTable is 1.3.6.1.4.1.7995.2.6.1.1.12. 5.  70.65.85.76.84
--                                                         |        base            |Slt|Len| F  A  U  L  T|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
--
-- Value(s)		: S50052163
-- Comments		: Module serial number
--
---------------------------------------------------------------------------------------------------
-- Header		: MSG
--
-- MIB ref		: swCardEventLogSlotXX       .3.77.83.71
-- absolute OID	: 1.3.6.1.4.1.7995.2.6.1.1.XX.3.77.83.71
--
-- Value(s)		: UNIT PRESENT
--				: UNIT LOST
-- Comments		: State of module presence.
--
---------------------------------------------------------------------------------------------------
-- Header		: UPTIME
--
-- MIB ref		: swCardEventLogSlotXX       .6.85.80.84.73.77.69
-- absolute OID	: 1.3.6.1.4.1.7995.2.6.1.1.XX.6.85.80.84.73.77.69
--
-- Value(s)		: 000:00:24:00
-- Comments		: Time since last restart ddd:hh:mm:ss
--
---------------------------------------------------------------------------------------------------
-- Header		: SESSIONS
--
-- MIB ref		: swCardEventLogSlotXX       .8.83.69.83.83.73.79.78.83
-- absolute OID	: 1.3.6.1.4.1.7995.2.6.1.1.XX.8.83.69.83.83.73.79.78.83
--
-- Value(s)		: 0
-- Comments		: Number of current control sessions.
--
---------------------------------------------------------------------------------------------------
-- Header		: OS_VERSION
--
-- MIB ref		: swCardEventLogSlotXX       .10.79.83.95.86.69.82.83.73.79.78
-- absolute OID	: 1.3.6.1.4.1.7995.2.6.1.1.XX.10.79.83.95.86.69.82.83.73.79.78
--
-- Value(s)		: V115 Release
-- Comments		: Operating system name and version
--
---------------------------------------------------------------------------------------------------
-- Header		: BUILD_NUMBER
--
-- MIB ref		: swCardEventLogSlotXX       .12.66.85.73.76.68.95.78.85.77.66.69.82
-- absolute OID	: 1.3.6.1.4.1.7995.2.6.1.1.XX.12.66.85.73.76.68.95.78.85.77.66.69.82
--
-- Value(s)		: 2317.2318.2329
-- Comments		: Software build number - BSP and APP
--
---------------------------------------------------------------------------------------------------
-- Header		: INPUT_1_TYPE
--
-- MIB ref		: swCardEventLogSlotXX       .12.73.78.80.85.84.95.49.95.84.89.80.69
-- absolute OID	: 1.3.6.1.4.1.7995.2.6.1.1.XX.12.73.78.80.85.84.95.49.95.84.89.80.69
--
-- Value(s)		: HD/SD/3G SDI
-- Comments		: Input type as specified by unit's configuration
--
---------------------------------------------------------------------------------------------------
-- Header		: INPUT_2_TYPE
--
-- MIB ref		: swCardEventLogSlotXX       .12.73.78.80.85.84.95.50.95.84.89.80.69
-- absolute OID	: 1.3.6.1.4.1.7995.2.6.1.1.XX.12.73.78.80.85.84.95.50.95.84.89.80.69
--
-- Value(s)		: HD/SD/3G SDI
-- Comments		: Input type as specified by unit's configuration
--
---------------------------------------------------------------------------------------------------
-- Header		: RESTARTED_AT
--
-- MIB ref		: swCardEventLogSlotXX       .12.82.69.83.84.65.82.84.69.68.95.65.84
-- absolute OID	: 1.3.6.1.4.1.7995.2.6.1.1.XX.12.82.69.83.84.65.82.84.69.68.95.65.84
--
-- Value(s)		: 2010-01-27T10:41:47Z
-- Comments		: Time of last restart
--
---------------------------------------------------------------------------------------------------
-- Header		: INPUT_1_IDENT
--
-- MIB ref		: swCardEventLogSlotXX       .13.73.78.80.85.84.95.49.95.73.68.69.78.84
-- absolute OID	: 1.3.6.1.4.1.7995.2.6.1.1.XX.13.73.78.80.85.84.95.49.95.73.68.69.78.84
--
-- Value(s)		: SERIAL IN 1
-- Comments		: Input ID
--
---------------------------------------------------------------------------------------------------
-- Header		: INPUT_1_STATE
--
-- MIB ref		: swCardEventLogSlotXX       .13.73.78.80.85.84.95.49.95.83.84.65.84.69
-- absolute OID	: 1.3.6.1.4.1.7995.2.6.1.1.XX.13.73.78.80.85.84.95.49.95.83.84.65.84.69
--
-- Value(s)		: OK
--				: WARN:Mismatch
--				: FAIL:Lost
-- Comments		: Input state
--
---------------------------------------------------------------------------------------------------
-- Header		: INPUT_2_IDENT
--
-- MIB ref		: swCardEventLogSlotXX       .13.73.78.80.85.84.95.50.95.73.68.69.78.84
-- absolute OID	: 1.3.6.1.4.1.7995.2.6.1.1.XX.13.73.78.80.85.84.95.50.95.73.68.69.78.84
--
-- Value(s)		: SERIAL IN 2
-- Comments		: Input ID
--
---------------------------------------------------------------------------------------------------
-- Header		: INPUT_2_STATE
--
-- MIB ref		: swCardEventLogSlotXX       .13.73.78.80.85.84.95.50.95.83.84.65.84.69
-- absolute OID	: 1.3.6.1.4.1.7995.2.6.1.1.XX.13.73.78.80.85.84.95.50.95.83.84.65.84.69
--
-- Value(s)		: OK
--				: WARN:Mismatch
--				: FAIL:Lost
-- Comments		: Input state
--
---------------------------------------------------------------------------------------------------
-- Header		: LAST_MOFIFIED
--
-- MIB ref		: swCardEventLogSlotXX       .13.76.65.83.84.95.77.79.70.73.70.73.69.68
-- absolute OID	: 1.3.6.1.4.1.7995.2.6.1.1.XX.13.76.65.83.84.95.77.79.70.73.70.73.69.68
--
-- Value(s)		: 2010-01-27T10:45:05Z
-- Comments		: Time of last control modification.
--
---------------------------------------------------------------------------------------------------
-- Header		: OUTPUT_1_TYPE
--
-- MIB ref		: swCardEventLogSlotXX       .13.79.85.84.80.85.84.95.49.95.84.89.80.69
-- absolute OID	: 1.3.6.1.4.1.7995.2.6.1.1.XX.13.79.85.84.80.85.84.95.49.95.84.89.80.69
--
-- Value(s)		: 3G / HD / SD SDI
-- Comments		: Output type as specified by unit's configuration
--
---------------------------------------------------------------------------------------------------
-- Header		: OUTPUT_2_TYPE
--
-- MIB ref		: swCardEventLogSlotXX       .13.79.85.84.80.85.84.95.50.95.84.89.80.69
-- absolute OID	: 1.3.6.1.4.1.7995.2.6.1.1.XX.13.79.85.84.80.85.84.95.50.95.84.89.80.69
--
-- Value(s)		: 3G / HD / SD SDI
-- Comments		: Output type as specified by unit's configuration
--
---------------------------------------------------------------------------------------------------
-- Header		: OUTPUT_1_STATE
--
-- MIB ref		: swCardEventLogSlotXX       .14.79.85.84.80.85.84.95.49.95.83.84.65.84.69
-- absolute OID	: 1.3.6.1.4.1.7995.2.6.1.1.XX.14.79.85.84.80.85.84.95.49.95.83.84.65.84.69
--
-- Value(s)		: OK
--				: WARN:Pattern
--				: WARN:Black
--				: WARN:Freeze
-- Comments		: Output state
--
---------------------------------------------------------------------------------------------------
-- Header		: OUTPUT_2_STATE
--
-- MIB ref		: swCardEventLogSlotXX       .14.79.85.84.80.85.84.95.50.95.83.84.65.84.69
-- absolute OID	: 1.3.6.1.4.1.7995.2.6.1.1.XX.14.79.85.84.80.85.84.95.50.95.83.84.65.84.69
--
-- Value(s)		: OK
--				: WARN:Pattern
--				: WARN:Black
--				: WARN:Freeze
-- Comments		: Output state
--

---------------------------------------------------------------------------------------------------
-- Header		: GENLOCK_1_STATE
--
-- MIB ref		: swCardEventLogSlotXX       .15.71.69.78.76.79.67.75.95.49.95.83.84.65.84.69
-- absolute OID	: 1.3.6.1.4.1.7995.2.6.1.1.XX.15.71.69.78.76.79.67.75.95.49.95.83.84.65.84.69
--
-- Value(s)		: OK:Reference
--				: OK:Input
--				: WARN:Freerun
--				: WARN:CrossLock
-- Comments		: Genlock state
--
---------------------------------------------------------------------------------------------------
-- Header		: FIRMWARE_VERSION
--
-- MIB ref		: swCardEventLogSlotXX       .16.70.73.82.77.87.65.82.69.95.86.69.82.83.73.79.78
-- absolute OID	: 1.3.6.1.4.1.7995.2.6.1.1.XX.16.70.73.82.77.87.65.82.69.95.86.69.82.83.73.79.78
--
-- Value(s)		: 2325
-- Comments		: FPGA version(s)
--
---------------------------------------------------------------------------------------------------
-- Header		: HARDWARE_VERSION
--
-- MIB ref		: swCardEventLogSlotXX       .16.72.65.82.68.87.65.82.69.95.86.69.82.83.73.79.78
-- absolute OID	: 1.3.6.1.4.1.7995.2.6.1.1.XX.16.72.65.82.68.87.65.82.69.95.86.69.82.83.73.79.78
--
-- Value(s)		: HDBASP1B
-- Comments		: Hardware build version
--
---------------------------------------------------------------------------------------------------
-- Header		: INPUT_1_SDI_ERRS
--
-- MIB ref		: swCardEventLogSlotXX       .16.73.78.80.85.84.95.49.95.83.68.73.95.69.82.82.83
-- absolute OID	: 1.3.6.1.4.1.7995.2.6.1.1.XX.16.73.78.80.85.84.95.49.95.83.68.73.95.69.82.82.83
--
-- Value(s)		: OK
--				: WARN
-- Comments		: SDI errors
--
---------------------------------------------------------------------------------------------------
-- Header		: INPUT_1_STANDARD
--
-- MIB ref		: swCardEventLogSlotXX       .16.73.78.80.85.84.95.49.95.83.84.65.78.68.65.82.68
-- absolute OID	: 1.3.6.1.4.1.7995.2.6.1.1.XX.16.73.78.80.85.84.95.49.95.83.84.65.78.68.65.82.68
--
-- Value(s)		: LOST
--				: 1080/59p-B
--				: 1080/50p-B
--				: 1080/59p-A
--				: 1080/50p-A
--				: 1080/29i
--				: 1080/25i
--				: 720/59p
--				: 720/50p
--				: 525/29i
--				: 625/25i
--				: WARN:Unknown
-- Comments		: Current input signal standard
--
---------------------------------------------------------------------------------------------------
-- Header		: INPUT_2_SDI_ERRS
--
-- MIB ref		: swCardEventLogSlotXX       .16.73.78.80.85.84.95.50.95.83.68.73.95.69.82.82.83
-- absolute OID	: 1.3.6.1.4.1.7995.2.6.1.1.XX.16.73.78.80.85.84.95.50.95.83.68.73.95.69.82.82.83
--
-- Value(s)		: OK
--				: WARN
-- Comments		: SDI errors
--
---------------------------------------------------------------------------------------------------
-- Header		: INPUT_2_STANDARD
--
-- MIB ref		: swCardEventLogSlotXX       .16.73.78.80.85.84.95.50.95.83.84.65.78.68.65.82.68
-- absolute OID	: 1.3.6.1.4.1.7995.2.6.1.1.XX.16.73.78.80.85.84.95.50.95.83.84.65.78.68.65.82.68
--
-- Value(s)		: LOST
--				: 1080/59p-B
--				: 1080/50p-B
--				: 1080/59p-A
--				: 1080/50p-A
--				: 1080/29i
--				: 1080/25i
--				: 720/59p
--				: 720/50p
--				: 525/29i
--				: 625/25i
--				: WARN:Unknown
-- Comments		: Current input signal standard
--
---------------------------------------------------------------------------------------------------
-- Header		: LICENSED_OPTIONS
--
-- MIB ref		: swCardEventLogSlotXX       .16.76.73.67.69.78.83.69.68.95.79.80.84.73.79.78.83
-- absolute OID	: 1.3.6.1.4.1.7995.2.6.1.1.XX.16.76.73.67.69.78.83.69.68.95.79.80.84.73.79.78.83
--
-- Value(s)		:  if applicable"
--				: SDHD;3G
-- Comments		: "Licensed options
--
---------------------------------------------------------------------------------------------------
-- Header		: OUTPUT_1_CAPTION
--
-- MIB ref		: swCardEventLogSlotXX       .16.79.85.84.80.85.84.95.49.95.67.65.80.84.73.79.78
-- absolute OID	: 1.3.6.1.4.1.7995.2.6.1.1.XX.16.79.85.84.80.85.84.95.49.95.67.65.80.84.73.79.78
--
-- Value(s)		: OK:Off
-- Comments		: Caption on/off
--
---------------------------------------------------------------------------------------------------
-- Header		: OUTPUT_2_CAPTION
--
-- MIB ref		: swCardEventLogSlotXX       .16.79.85.84.80.85.84.95.50.95.67.65.80.84.73.79.78
-- absolute OID	: 1.3.6.1.4.1.7995.2.6.1.1.XX.16.79.85.84.80.85.84.95.50.95.67.65.80.84.73.79.78
--
-- Value(s)		: OK:Off
-- Comments		: Caption on/off
--
---------------------------------------------------------------------------------------------------
-- Header		: REFERENCE_1_TYPE
--
-- MIB ref		: swCardEventLogSlotXX       .16.82.69.70.69.82.69.78.67.69.95.49.95.84.89.80.69
-- absolute OID	: 1.3.6.1.4.1.7995.2.6.1.1.XX.16.82.69.70.69.82.69.78.67.69.95.49.95.84.89.80.69
--
-- Value(s)		: OK:TriLevel
--				: OK:Bi-Level
--				: WARN:Unknown
-- Comments		: Reference type
--
---------------------------------------------------------------------------------------------------
-- Header		: OUTPUT_1_STANDARD
--
-- MIB ref		: swCardEventLogSlotXX       .17.79.85.84.80.85.84.95.49.95.83.84.65.78.68.65.82.68
-- absolute OID	: 1.3.6.1.4.1.7995.2.6.1.1.XX.17.79.85.84.80.85.84.95.49.95.83.84.65.78.68.65.82.68
--
-- Value(s)		: LOST
--				: 1080/59p-B
--				: 1080/50p-B
--				: 1080/59p-A
--				: 1080/50p-A
--				: 1080/29i
--				: 1080/25i
--				: 720/59p
--				: 720/50p
--				: 525/29i
--				: 625/25i
--				: WARN:Unknown
-- Comments		: Current output video standard
--
---------------------------------------------------------------------------------------------------
-- Header		: OUTPUT_2_STANDARD
--
-- MIB ref		: swCardEventLogSlotXX       .17.79.85.84.80.85.84.95.50.95.83.84.65.78.68.65.82.68
-- absolute OID	: 1.3.6.1.4.1.7995.2.6.1.1.XX.17.79.85.84.80.85.84.95.50.95.83.84.65.78.68.65.82.68
--
-- Value(s)		: LOST
--				: 1080/59p-B
--				: 1080/50p-B
--				: 1080/59p-A
--				: 1080/50p-A
--				: 1080/29i
--				: 1080/25i
--				: 720/59p
--				: 720/50p
--				: 525/29i
--				: 625/25i
--				: WARN:Unknown
-- Comments		: Current output video standard
---------------------------------------------------------------------------------------------------
-- Header		: REFERENCE_1_STATE
--
-- MIB ref		: swCardEventLogSlotXX       .17.82.69.70.69.82.69.78.67.69.95.49.95.83.84.65.84.69
-- absolute OID	: 1.3.6.1.4.1.7995.2.6.1.1.XX.17.82.69.70.69.82.69.78.67.69.95.49.95.83.84.65.84.69
--
-- Value(s)		: OK
--				: FAIL:Lost
-- Comments		: Reference state
--
---------------------------------------------------------------------------------------------------
-- Header		: INPUT_1_SDI_ANC_ERRS
--
-- MIB ref		: swCardEventLogSlotXX       .20.73.78.80.85.84.95.49.95.83.68.73.95.65.78.67.95.69.82.82.83
-- absolute OID	: 1.3.6.1.4.1.7995.2.6.1.1.XX.20.73.78.80.85.84.95.49.95.83.68.73.95.65.78.67.95.69.82.82.83
--
-- Value(s)		: OK
--				: WARN
-- Comments		: ANC errors
--
---------------------------------------------------------------------------------------------------
-- Header		: INPUT_2_SDI_ANC_ERRS
--
-- MIB ref		: swCardEventLogSlotXX       .20.73.78.80.85.84.95.50.95.83.68.73.95.65.78.67.95.69.82.82.83
-- absolute OID	: 1.3.6.1.4.1.7995.2.6.1.1.XX.20.73.78.80.85.84.95.50.95.83.68.73.95.65.78.67.95.69.82.82.83
--
-- Value(s)		: OK
--				: WARN
-- Comments		: ANC errors
--
---------------------------------------------------------------------------------------------------
-- Header		: REFERENCE_1_STANDARD
--
-- MIB ref		: swCardEventLogSlotXX       .20.82.69.70.69.82.69.78.67.69.95.49.95.83.84.65.78.68.65.82.68
-- absolute OID	: 1.3.6.1.4.1.7995.2.6.1.1.XX.20.82.69.70.69.82.69.78.67.69.95.49.95.83.84.65.78.68.65.82.68
--
-- Value(s)		: LOST
--				: 1080/59p-B
--				: 1080/50p-B
--				: 1080/59p-A
--				: 1080/50p-A
--				: 1080/29i
--				: 1080/25i
--				: 720/59p
--				: 720/50p
--				: 525/29i
--				: 625/25i
--				: WARN:Unknown
-- Comments		: Reference video standard
--
---------------------------------------------------------------------------------------------------
-- Header		: INPUT_1_EMBEDDED_AUDIO_1_STATE
--
-- MIB ref		: swCardEventLogSlotXX       .30.73.78.80.85.84.95.49.95.69.77.66.69.68.68.69.68.95.65.85.68.73.79.95.49.95.83.84.65.84.69
-- absolute OID	: 1.3.6.1.4.1.7995.2.6.1.1.XX.30.73.78.80.85.84.95.49.95.69.77.66.69.68.68.69.68.95.65.85.68.73.79.95.49.95.83.84.65.84.69
--
-- Value(s)		: OK:PCM
--				: OK:Data
--				: OK:DolbyE
--				: WARN:No Input
--				: FAIL:Lost
-- Comments		: Current embedded input 1 audio state
--
---------------------------------------------------------------------------------------------------
-- Header		: INPUT_1_EMBEDDED_AUDIO_2_STATE
--
-- MIB ref		: swCardEventLogSlotXX       .30.73.78.80.85.84.95.49.95.69.77.66.69.68.68.69.68.95.65.85.68.73.79.95.50.95.83.84.65.84.69
-- absolute OID	: 1.3.6.1.4.1.7995.2.6.1.1.XX.30.73.78.80.85.84.95.49.95.69.77.66.69.68.68.69.68.95.65.85.68.73.79.95.50.95.83.84.65.84.69
--
-- Value(s)		: OK:PCM
--				: OK:Data
--				: OK:DolbyE
--				: WARN:No Input
--				: FAIL:Lost
-- Comments		:
--
---------------------------------------------------------------------------------------------------
-- Header		: INPUT_1_EMBEDDED_AUDIO_3_STATE
--
-- MIB ref		: swCardEventLogSlotXX       .30.73.78.80.85.84.95.49.95.69.77.66.69.68.68.69.68.95.65.85.68.73.79.95.51.95.83.84.65.84.69
-- absolute OID	: 1.3.6.1.4.1.7995.2.6.1.1.XX.30.73.78.80.85.84.95.49.95.69.77.66.69.68.68.69.68.95.65.85.68.73.79.95.51.95.83.84.65.84.69
--
-- Value(s)		: OK:PCM
--				: OK:Data
--				: OK:DolbyE
--				: WARN:No Input
--				: FAIL:Lost
-- Comments		:
--
---------------------------------------------------------------------------------------------------
-- Header		: INPUT_1_EMBEDDED_AUDIO_4_STATE
--
-- MIB ref		: swCardEventLogSlotXX       .30.73.78.80.85.84.95.49.95.69.77.66.69.68.68.69.68.95.65.85.68.73.79.95.52.95.83.84.65.84.69
-- absolute OID	: 1.3.6.1.4.1.7995.2.6.1.1.XX.30.73.78.80.85.84.95.49.95.69.77.66.69.68.68.69.68.95.65.85.68.73.79.95.52.95.83.84.65.84.69
--
-- Value(s)		: OK:PCM
--				: OK:Data
--				: OK:DolbyE
--				: WARN:No Input
--				: FAIL:Lost
-- Comments		:
--
---------------------------------------------------------------------------------------------------
-- Header		: INPUT_1_EMBEDDED_AUDIO_5_STATE
--
-- MIB ref		: swCardEventLogSlotXX       .30.73.78.80.85.84.95.49.95.69.77.66.69.68.68.69.68.95.65.85.68.73.79.95.53.95.83.84.65.84.69
-- absolute OID	: 1.3.6.1.4.1.7995.2.6.1.1.XX.30.73.78.80.85.84.95.49.95.69.77.66.69.68.68.69.68.95.65.85.68.73.79.95.53.95.83.84.65.84.69
--
-- Value(s)		: OK:PCM
--				: OK:Data
--				: OK:DolbyE
--				: WARN:No Input
--				: FAIL:Lost
-- Comments		:
--
---------------------------------------------------------------------------------------------------
-- Header		: INPUT_1_EMBEDDED_AUDIO_6_STATE
--
-- MIB ref		: swCardEventLogSlotXX       .30.73.78.80.85.84.95.49.95.69.77.66.69.68.68.69.68.95.65.85.68.73.79.95.54.95.83.84.65.84.69
-- absolute OID	: 1.3.6.1.4.1.7995.2.6.1.1.XX.30.73.78.80.85.84.95.49.95.69.77.66.69.68.68.69.68.95.65.85.68.73.79.95.54.95.83.84.65.84.69
--
-- Value(s)		: OK:PCM
--				: OK:Data
--				: OK:DolbyE
--				: WARN:No Input
--				: FAIL:Lost
-- Comments		:
--
---------------------------------------------------------------------------------------------------
-- Header		: INPUT_1_EMBEDDED_AUDIO_7_STATE
--
-- MIB ref		: swCardEventLogSlotXX       .30.73.78.80.85.84.95.49.95.69.77.66.69.68.68.69.68.95.65.85.68.73.79.95.55.95.83.84.65.84.69
-- absolute OID	: 1.3.6.1.4.1.7995.2.6.1.1.XX.30.73.78.80.85.84.95.49.95.69.77.66.69.68.68.69.68.95.65.85.68.73.79.95.55.95.83.84.65.84.69
--
-- Value(s)		: OK:PCM
--				: OK:Data
--				: OK:DolbyE
--				: WARN:No Input
--				: FAIL:Lost
-- Comments		:
--
---------------------------------------------------------------------------------------------------
-- Header		: INPUT_1_EMBEDDED_AUDIO_8_STATE
--
-- MIB ref		: swCardEventLogSlotXX       .30.73.78.80.85.84.95.49.95.69.77.66.69.68.68.69.68.95.65.85.68.73.79.95.56.95.83.84.65.84.69
-- absolute OID	: 1.3.6.1.4.1.7995.2.6.1.1.XX.30.73.78.80.85.84.95.49.95.69.77.66.69.68.68.69.68.95.65.85.68.73.79.95.56.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_1_STATE
--
-- MIB ref		: swCardEventLogSlotXX       .30.73.78.80.85.84.95.50.95.69.77.66.69.68.68.69.68.95.65.85.68.73.79.95.49.95.83.84.65.84.69
-- absolute OID	: 1.3.6.1.4.1.7995.2.6.1.1.XX.30.73.78.80.85.84.95.50.95.69.77.66.69.68.68.69.68.95.65.85.68.73.79.95.49.95.83.84.65.84.69
--
-- Value(s)		: OK:PCM
--				: OK:Data
--				: OK:DolbyE
--				: WARN:No Input
--				: FAIL:Lost
-- Comments		: Current embedded input 2 audio state
--
---------------------------------------------------------------------------------------------------
-- Header		: INPUT_2_EMBEDDED_AUDIO_2_STATE
--
-- MIB ref		: swCardEventLogSlotXX       .30.73.78.80.85.84.95.50.95.69.77.66.69.68.68.69.68.95.65.85.68.73.79.95.50.95.83.84.65.84.69
-- absolute OID	: 1.3.6.1.4.1.7995.2.6.1.1.XX.30.73.78.80.85.84.95.50.95.69.77.66.69.68.68.69.68.95.65.85.68.73.79.95.50.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_3_STATE
--
-- MIB ref		: swCardEventLogSlotXX       .30.73.78.80.85.84.95.50.95.69.77.66.69.68.68.69.68.95.65.85.68.73.79.95.51.95.83.84.65.84.69
-- absolute OID	: 1.3.6.1.4.1.7995.2.6.1.1.XX.30.73.78.80.85.84.95.50.95.69.77.66.69.68.68.69.68.95.65.85.68.73.79.95.51.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_4_STATE
--
-- MIB ref		: swCardEventLogSlotXX       .30.73.78.80.85.84.95.50.95.69.77.66.69.68.68.69.68.95.65.85.68.73.79.95.52.95.83.84.65.84.69
-- absolute OID	: 1.3.6.1.4.1.7995.2.6.1.1.XX.30.73.78.80.85.84.95.50.95.69.77.66.69.68.68.69.68.95.65.85.68.73.79.95.52.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_5_STATE
--
-- MIB ref		: swCardEventLogSlotXX       .30.73.78.80.85.84.95.50.95.69.77.66.69.68.68.69.68.95.65.85.68.73.79.95.53.95.83.84.65.84.69
-- absolute OID	: 1.3.6.1.4.1.7995.2.6.1.1.XX.30.73.78.80.85.84.95.50.95.69.77.66.69.68.68.69.68.95.65.85.68.73.79.95.53.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_6_STATE
--
-- MIB ref		: swCardEventLogSlotXX       .30.73.78.80.85.84.95.50.95.69.77.66.69.68.68.69.68.95.65.85.68.73.79.95.54.95.83.84.65.84.69
-- absolute OID	: 1.3.6.1.4.1.7995.2.6.1.1.XX.30.73.78.80.85.84.95.50.95.69.77.66.69.68.68.69.68.95.65.85.68.73.79.95.54.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_7_STATE
--
-- MIB ref		: swCardEventLogSlotXX       .30.73.78.80.85.84.95.50.95.69.77.66.69.68.68.69.68.95.65.85.68.73.79.95.55.95.83.84.65.84.69
-- absolute OID	: 1.3.6.1.4.1.7995.2.6.1.1.XX.30.73.78.80.85.84.95.50.95.69.77.66.69.68.68.69.68.95.65.85.68.73.79.95.55.95.83.84.65.84.69
--
-- Value(s)		: OK:PCM
--				: OK:Data
--				: OK:DolbyE
--				: WARN:No Input
--				: FAIL:Lost
-- Comments		:
--
---------------------------------------------------------------------------------------------------
-- Header		: INPUT_2_EMBEDDED_AUDIO_8_STATE
--
-- MIB ref		: swCardEventLogSlotXX       .30.73.78.80.85.84.95.50.95.69.77.66.69.68.68.69.68.95.65.85.68.73.79.95.56.95.83.84.65.84.69
-- absolute OID	: 1.3.6.1.4.1.7995.2.6.1.1.XX.30.73.78.80.85.84.95.50.95.69.77.66.69.68.68.69.68.95.65.85.68.73.79.95.56.95.83.84.65.84.69
--
-- Value(s)		: OK:PCM
--				: OK:Data
--				: OK:DolbyE
--				: WARN:No Input
--				: FAIL:Lost
-- Comments		:
--
---------------------------------------------------------------------------------------------------
-- Header		: OUTPUT_1_EMBED_AUDIO_1_1_STATE
--
-- MIB ref		: swCardEventLogSlotXX       .30.79.85.84.80.85.84.95.49.95.69.77.66.69.68.95.65.85.68.73.79.95.49.95.49.95.83.84.65.84.69
-- absolute OID	: 1.3.6.1.4.1.7995.2.6.1.1.XX.30.79.85.84.80.85.84.95.49.95.69.77.66.69.68.95.65.85.68.73.79.95.49.95.49.95.83.84.65.84.69
--
-- Value(s)		: OK:PCM
--				: OK:Data
--				: OK:DolbyE
--				: WARN:Silent PCM
--				: WARN:Overload PCM
--				: FAIL_Input Lost
-- Comments		: Current embedded output 2 audio state
--
---------------------------------------------------------------------------------------------------
-- Header		: OUTPUT_1_EMBED_AUDIO_1_2_STATE
--
-- MIB ref		: swCardEventLogSlotXX       .30.79.85.84.80.85.84.95.49.95.69.77.66.69.68.95.65.85.68.73.79.95.49.95.50.95.83.84.65.84.69
-- absolute OID	: 1.3.6.1.4.1.7995.2.6.1.1.XX.30.79.85.84.80.85.84.95.49.95.69.77.66.69.68.95.65.85.68.73.79.95.49.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_2_1_STATE
--
-- MIB ref		: swCardEventLogSlotXX       .30.79.85.84.80.85.84.95.49.95.69.77.66.69.68.95.65.85.68.73.79.95.50.95.49.95.83.84.65.84.69
-- absolute OID	: 1.3.6.1.4.1.7995.2.6.1.1.XX.30.79.85.84.80.85.84.95.49.95.69.77.66.69.68.95.65.85.68.73.79.95.50.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_2_2_STATE
--
-- MIB ref		: swCardEventLogSlotXX       .30.79.85.84.80.85.84.95.49.95.69.77.66.69.68.95.65.85.68.73.79.95.50.95.50.95.83.84.65.84.69
-- absolute OID	: 1.3.6.1.4.1.7995.2.6.1.1.XX.30.79.85.84.80.85.84.95.49.95.69.77.66.69.68.95.65.85.68.73.79.95.50.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_3_1_STATE
--
-- MIB ref		: swCardEventLogSlotXX       .30.79.85.84.80.85.84.95.49.95.69.77.66.69.68.95.65.85.68.73.79.95.51.95.49.95.83.84.65.84.69
-- absolute OID	: 1.3.6.1.4.1.7995.2.6.1.1.XX.30.79.85.84.80.85.84.95.49.95.69.77.66.69.68.95.65.85.68.73.79.95.51.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_3_2_STATE
--
-- MIB ref		: swCardEventLogSlotXX       .30.79.85.84.80.85.84.95.49.95.69.77.66.69.68.95.65.85.68.73.79.95.51.95.50.95.83.84.65.84.69
-- absolute OID	: 1.3.6.1.4.1.7995.2.6.1.1.XX.30.79.85.84.80.85.84.95.49.95.69.77.66.69.68.95.65.85.68.73.79.95.51.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_4_1_STATE
--
-- MIB ref		: swCardEventLogSlotXX       .30.79.85.84.80.85.84.95.49.95.69.77.66.69.68.95.65.85.68.73.79.95.52.95.49.95.83.84.65.84.69
-- absolute OID	: 1.3.6.1.4.1.7995.2.6.1.1.XX.30.79.85.84.80.85.84.95.49.95.69.77.66.69.68.95.65.85.68.73.79.95.52.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_4_2_STATE
--
-- MIB ref		: swCardEventLogSlotXX       .30.79.85.84.80.85.84.95.49.95.69.77.66.69.68.95.65.85.68.73.79.95.52.95.50.95.83.84.65.84.69
-- absolute OID	: 1.3.6.1.4.1.7995.2.6.1.1.XX.30.79.85.84.80.85.84.95.49.95.69.77.66.69.68.95.65.85.68.73.79.95.52.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_5_1_STATE
--
-- MIB ref		: swCardEventLogSlotXX       .30.79.85.84.80.85.84.95.49.95.69.77.66.69.68.95.65.85.68.73.79.95.53.95.49.95.83.84.65.84.69
-- absolute OID	: 1.3.6.1.4.1.7995.2.6.1.1.XX.30.79.85.84.80.85.84.95.49.95.69.77.66.69.68.95.65.85.68.73.79.95.53.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_5_2_STATE
--
-- MIB ref		: swCardEventLogSlotXX       .30.79.85.84.80.85.84.95.49.95.69.77.66.69.68.95.65.85.68.73.79.95.53.95.50.95.83.84.65.84.69
-- absolute OID	: 1.3.6.1.4.1.7995.2.6.1.1.XX.30.79.85.84.80.85.84.95.49.95.69.77.66.69.68.95.65.85.68.73.79.95.53.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_6_1_STATE
--
-- MIB ref		: swCardEventLogSlotXX       .30.79.85.84.80.85.84.95.49.95.69.77.66.69.68.95.65.85.68.73.79.95.54.95.49.95.83.84.65.84.69
-- absolute OID	: 1.3.6.1.4.1.7995.2.6.1.1.XX.30.79.85.84.80.85.84.95.49.95.69.77.66.69.68.95.65.85.68.73.79.95.54.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_6_2_STATE
--
-- MIB ref		: swCardEventLogSlotXX       .30.79.85.84.80.85.84.95.49.95.69.77.66.69.68.95.65.85.68.73.79.95.54.95.50.95.83.84.65.84.69
-- absolute OID	: 1.3.6.1.4.1.7995.2.6.1.1.XX.30.79.85.84.80.85.84.95.49.95.69.77.66.69.68.95.65.85.68.73.79.95.54.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_7_1_STATE
--
-- MIB ref		: swCardEventLogSlotXX       .30.79.85.84.80.85.84.95.49.95.69.77.66.69.68.95.65.85.68.73.79.95.55.95.49.95.83.84.65.84.69
-- absolute OID	: 1.3.6.1.4.1.7995.2.6.1.1.XX.30.79.85.84.80.85.84.95.49.95.69.77.66.69.68.95.65.85.68.73.79.95.55.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_7_2_STATE
--
-- MIB ref		: swCardEventLogSlotXX       .30.79.85.84.80.85.84.95.49.95.69.77.66.69.68.95.65.85.68.73.79.95.55.95.50.95.83.84.65.84.69
-- absolute OID	: 1.3.6.1.4.1.7995.2.6.1.1.XX.30.79.85.84.80.85.84.95.49.95.69.77.66.69.68.95.65.85.68.73.79.95.55.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_8_1_STATE
--
-- MIB ref		: swCardEventLogSlotXX       .30.79.85.84.80.85.84.95.49.95.69.77.66.69.68.95.65.85.68.73.79.95.56.95.49.95.83.84.65.84.69
-- absolute OID	: 1.3.6.1.4.1.7995.2.6.1.1.XX.30.79.85.84.80.85.84.95.49.95.69.77.66.69.68.95.65.85.68.73.79.95.56.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_1_EMBED_AUDIO_8_2_STATE
--
-- MIB ref		: swCardEventLogSlotXX       .30.79.85.84.80.85.84.95.49.95.69.77.66.69.68.95.65.85.68.73.79.95.56.95.50.95.83.84.65.84.69
-- absolute OID	: 1.3.6.1.4.1.7995.2.6.1.1.XX.30.79.85.84.80.85.84.95.49.95.69.77.66.69.68.95.65.85.68.73.79.95.56.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_1_1_STATE
--
-- MIB ref		: swCardEventLogSlotXX       .30.79.85.84.80.85.84.95.50.95.69.77.66.69.68.95.65.85.68.73.79.95.49.95.49.95.83.84.65.84.69
-- absolute OID	: 1.3.6.1.4.1.7995.2.6.1.1.XX.30.79.85.84.80.85.84.95.50.95.69.77.66.69.68.95.65.85.68.73.79.95.49.95.49.95.83.84.65.84.69
--
-- Value(s)		: OK:PCM
--				: OK:Data
--				: OK:DolbyE
--				: WARN:Silent PCM
--				: WARN:Overload PCM
--				: FAIL_Input Lost
-- Comments		: Current embedded output 2 audio state
--
---------------------------------------------------------------------------------------------------
-- Header		: OUTPUT_2_EMBED_AUDIO_1_2_STATE
--
-- MIB ref		: swCardEventLogSlotXX       .30.79.85.84.80.85.84.95.50.95.69.77.66.69.68.95.65.85.68.73.79.95.49.95.50.95.83.84.65.84.69
-- absolute OID	: 1.3.6.1.4.1.7995.2.6.1.1.XX.30.79.85.84.80.85.84.95.50.95.69.77.66.69.68.95.65.85.68.73.79.95.49.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_2_1_STATE
--
-- MIB ref		: swCardEventLogSlotXX       .30.79.85.84.80.85.84.95.50.95.69.77.66.69.68.95.65.85.68.73.79.95.50.95.49.95.83.84.65.84.69
-- absolute OID	: 1.3.6.1.4.1.7995.2.6.1.1.XX.30.79.85.84.80.85.84.95.50.95.69.77.66.69.68.95.65.85.68.73.79.95.50.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_2_2_STATE
--
-- MIB ref		: swCardEventLogSlotXX       .30.79.85.84.80.85.84.95.50.95.69.77.66.69.68.95.65.85.68.73.79.95.50.95.50.95.83.84.65.84.69
-- absolute OID	: 1.3.6.1.4.1.7995.2.6.1.1.XX.30.79.85.84.80.85.84.95.50.95.69.77.66.69.68.95.65.85.68.73.79.95.50.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_3_1_STATE
--
-- MIB ref		: swCardEventLogSlotXX       .30.79.85.84.80.85.84.95.50.95.69.77.66.69.68.95.65.85.68.73.79.95.51.95.49.95.83.84.65.84.69
-- absolute OID	: 1.3.6.1.4.1.7995.2.6.1.1.XX.30.79.85.84.80.85.84.95.50.95.69.77.66.69.68.95.65.85.68.73.79.95.51.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_3_2_STATE
--
-- MIB ref		: swCardEventLogSlotXX       .30.79.85.84.80.85.84.95.50.95.69.77.66.69.68.95.65.85.68.73.79.95.51.95.50.95.83.84.65.84.69
-- absolute OID	: 1.3.6.1.4.1.7995.2.6.1.1.XX.30.79.85.84.80.85.84.95.50.95.69.77.66.69.68.95.65.85.68.73.79.95.51.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_4_1_STATE
--
-- MIB ref		: swCardEventLogSlotXX       .30.79.85.84.80.85.84.95.50.95.69.77.66.69.68.95.65.85.68.73.79.95.52.95.49.95.83.84.65.84.69
-- absolute OID	: 1.3.6.1.4.1.7995.2.6.1.1.XX.30.79.85.84.80.85.84.95.50.95.69.77.66.69.68.95.65.85.68.73.79.95.52.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_4_2_STATE
--
-- MIB ref		: swCardEventLogSlotXX       .30.79.85.84.80.85.84.95.50.95.69.77.66.69.68.95.65.85.68.73.79.95.52.95.50.95.83.84.65.84.69
-- absolute OID	: 1.3.6.1.4.1.7995.2.6.1.1.XX.30.79.85.84.80.85.84.95.50.95.69.77.66.69.68.95.65.85.68.73.79.95.52.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_5_1_STATE
--
-- MIB ref		: swCardEventLogSlotXX       .30.79.85.84.80.85.84.95.50.95.69.77.66.69.68.95.65.85.68.73.79.95.53.95.49.95.83.84.65.84.69
-- absolute OID	: 1.3.6.1.4.1.7995.2.6.1.1.XX.30.79.85.84.80.85.84.95.50.95.69.77.66.69.68.95.65.85.68.73.79.95.53.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_5_2_STATE
--
-- MIB ref		: swCardEventLogSlotXX       .30.79.85.84.80.85.84.95.50.95.69.77.66.69.68.95.65.85.68.73.79.95.53.95.50.95.83.84.65.84.69
-- absolute OID	: 1.3.6.1.4.1.7995.2.6.1.1.XX.30.79.85.84.80.85.84.95.50.95.69.77.66.69.68.95.65.85.68.73.79.95.53.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_6_1_STATE
--
-- MIB ref		: swCardEventLogSlotXX       .30.79.85.84.80.85.84.95.50.95.69.77.66.69.68.95.65.85.68.73.79.95.54.95.49.95.83.84.65.84.69
-- absolute OID	: 1.3.6.1.4.1.7995.2.6.1.1.XX.30.79.85.84.80.85.84.95.50.95.69.77.66.69.68.95.65.85.68.73.79.95.54.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_6_2_STATE
--
-- MIB ref		: swCardEventLogSlotXX       .30.79.85.84.80.85.84.95.50.95.69.77.66.69.68.95.65.85.68.73.79.95.54.95.50.95.83.84.65.84.69
-- absolute OID	: 1.3.6.1.4.1.7995.2.6.1.1.XX.30.79.85.84.80.85.84.95.50.95.69.77.66.69.68.95.65.85.68.73.79.95.54.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_7_1_STATE
--
-- MIB ref		: swCardEventLogSlotXX       .30.79.85.84.80.85.84.95.50.95.69.77.66.69.68.95.65.85.68.73.79.95.55.95.49.95.83.84.65.84.69
-- absolute OID	: 1.3.6.1.4.1.7995.2.6.1.1.XX.30.79.85.84.80.85.84.95.50.95.69.77.66.69.68.95.65.85.68.73.79.95.55.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_7_2_STATE
--
-- MIB ref		: swCardEventLogSlotXX       .30.79.85.84.80.85.84.95.50.95.69.77.66.69.68.95.65.85.68.73.79.95.55.95.50.95.83.84.65.84.69
-- absolute OID	: 1.3.6.1.4.1.7995.2.6.1.1.XX.30.79.85.84.80.85.84.95.50.95.69.77.66.69.68.95.65.85.68.73.79.95.55.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_8_1_STATE
--
-- MIB ref		: swCardEventLogSlotXX       .30.79.85.84.80.85.84.95.50.95.69.77.66.69.68.95.65.85.68.73.79.95.56.95.49.95.83.84.65.84.69
-- absolute OID	: 1.3.6.1.4.1.7995.2.6.1.1.XX.30.79.85.84.80.85.84.95.50.95.69.77.66.69.68.95.65.85.68.73.79.95.56.95.49.95.83.84.65.84.69
--
-- Value(s)		: OK:PCM
--				: OK:Data
--				: OK:DolbyE
--				: WARN:Silent PCM
--				: WARN:Overload PCM
--				: FAIL_Input Lost
-- Comments		:
--
---------------------------------------------------------------------------------------------------
-- Header		: OUTPUT_2_EMBED_AUDIO_8_2_STATE
--
-- MIB ref		: swCardEventLogSlotXX       .30.79.85.84.80.85.84.95.50.95.69.77.66.69.68.95.65.85.68.73.79.95.56.95.50.95.83.84.65.84.69
-- absolute OID	: 1.3.6.1.4.1.7995.2.6.1.1.XX.30.79.85.84.80.85.84.95.50.95.69.77.66.69.68.95.65.85.68.73.79.95.56.95.50.95.83.84.65.84.69
--
-- Value(s)		: OK:PCM
--				: OK:Data
--				: OK:DolbyE
--				: WARN:Silent PCM
--				: WARN:Overload PCM
--				: FAIL_Input Lost
-- Comments		:
--
---------------------------------------------------------------------------------------------------
