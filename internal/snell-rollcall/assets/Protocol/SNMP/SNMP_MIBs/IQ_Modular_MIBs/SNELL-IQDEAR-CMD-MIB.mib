-- ************************************************************************************
-- Snell&Wilcox Card:IQDEAR
--        Module Id#:301
--       Command Set:5
--          Filename:SNELL-IQDEAR-CMD-MIB.mib
--            Author:Jonathan Riches
--              Date:04/07/2005
--              Time:12:59
--
-- Copyright (c) 2005 Snell & Wilcox Ltd
-- All rights reserved.
--
-- ************************************************************************************

SNELL-IQDEAR-CMD DEFINITIONS ::= BEGIN

IMPORTS
    OBJECT-TYPE,
    NOTIFICATION-TYPE,
    MODULE-IDENTITY,
    OBJECT-IDENTITY,
    Counter32,
    Gauge32,
    Unsigned32
        FROM SNMPv2-SMI


    OBJECT-GROUP,
    MODULE-COMPLIANCE,
    AGENT-CAPABILITIES
        FROM SNMPv2-CONF

    RollCallString
        FROM SNELL-WILCOX-TC


    moduleIQDEAR,
    moduleIQDEARMIB
        FROM SNELL-WILCOX-PRODUCT-REG;

 moduleIQDEARCmdMi MODULE-IDENTITY
    LAST-UPDATED "0507041259Z"
    ORGANIZATION "Snell & Wilcox Ltd"
    CONTACT-INFO
        "Primary Author:Jonathan Riches

         postal:    Southleigh Park House
                    Eastleigh Road
                    Havant, Hants
                    PO9 2PE
         phone:     +44 (0)23 92489000
         email:     snmp.support@snellwilcox.com"
    DESCRIPTION
        "This file defines the Snell Wilcox  card, command set  translations."
    ::= { moduleIQDEARMIB 1 }




--********************************************************************************
--*
--*  Snell Wilcox Card:
--*  command set:
--*  list commands/menus:
--*
--******************************************************************************
	iqdearCmdTable OBJECT-TYPE
		SYNTAX			SEQUENCE OF IqdearCmdEntry
		MAX-ACCESS		not-accessible
		STATUS			current
		DESCRIPTION
				"Note the instance of this table is relected in the command set Version"
		::= { moduleIQDEAR 1 }

	iqdearCmdEntry OBJECT-TYPE
		SYNTAX		IqdearCmdEntry
		MAX-ACCESS		not-accessible
		STATUS			current
		DESCRIPTION
				"Entry in command table."
		INDEX	{ iqdearSlotIndex }
		::= { iqdearCmdTable 1 }

	IqdearCmdEntry ::=
		SEQUENCE {
			iqdearSlotIndex
				Unsigned32,
			iqdearPairAExtractorA
				INTEGER,
			iqdearPairAEmbedderA
				INTEGER,
			iqdearPairBExtractorB
				INTEGER,
			iqdearPairBEmbedderB
				INTEGER,
			iqdearEDH
				INTEGER,
			iqdearDisplay
				INTEGER,
			iqdearMemoriesNamesMemory1
				RollCallString,
			iqdearMemoriesNamesMemory2
				RollCallString,
			iqdearMemoriesNamesMemory3
				RollCallString,
			iqdearMemoriesNamesMemory4
				RollCallString,
			iqdearMemoriesNamesMemory5
				RollCallString,
			iqdearMemoriesNamesMemory6
				RollCallString,
			iqdearMemoriesNamesMemory7
				RollCallString,
			iqdearMemoriesNamesMemory8
				RollCallString,
			iqdearMemoriesRecall
				INTEGER,
			iqdearMemoriesSave
				INTEGER,
			iqdearMemoriesClearAll
				INTEGER,
			iqdearSetupGPIEnableGPI
				INTEGER,
			iqdearSetupGPIGPI1
				INTEGER,
			iqdearSetupGPIGPI2
				INTEGER,
			iqdearSetupLoggingSDIInputState
				INTEGER,
			iqdearSetupLoggingSDIAudioState
				INTEGER,
			iqdearSetupLoggingEDHErrors
				INTEGER,
			iqdearSetupPresetUnit
				INTEGER,
			iqdearSetupVersion
				RollCallString,
			iqdearSetupSerialNo
				RollCallString
		}

	iqdearSlotIndex OBJECT-TYPE
		SYNTAX		Unsigned32
		MAX-ACCESS		not-accessible
		STATUS			current
		DESCRIPTION
				"The unique Index value for each slot.  Its value
					ranges between 1 and the value of slotNumber."
		::= { iqdearCmdEntry 0 }


	iqdearPairAExtractorA OBJECT-TYPE
		SYNTAX		INTEGER
		MAX-ACCESS		read-write
		STATUS			current
		DESCRIPTION
				"TYPE: - Number
					Extractor_A  cmdID= 13  min= 1  max= 8  step= 1  format= PAIR %0.0f  div_scale= 1 
					Min = PAIR 1  Max = PAIR 8  Step = PAIR 1 "
		::= { iqdearCmdEntry 13 }


	iqdearPairAEmbedderA OBJECT-TYPE
		SYNTAX		INTEGER
		MAX-ACCESS		read-write
		STATUS			current
		DESCRIPTION
				"TYPE: - Number
					Embedder_A  cmdID= 17  min= 0  max= 8  step= 1  format= PAIR %0.0f  div_scale= 1 
					Min = PAIR 0  Max = PAIR 8  Step = PAIR 1 "
		::= { iqdearCmdEntry 17 }


	iqdearPairBExtractorB OBJECT-TYPE
		SYNTAX		INTEGER
		MAX-ACCESS		read-write
		STATUS			current
		DESCRIPTION
				"TYPE: - Number
					Extractor_B  cmdID= 14  min= 1  max= 8  step= 1  format= PAIR %0.0f  div_scale= 1 
					Min = PAIR 1  Max = PAIR 8  Step = PAIR 1 "
		::= { iqdearCmdEntry 14 }


	iqdearPairBEmbedderB OBJECT-TYPE
		SYNTAX		INTEGER
		MAX-ACCESS		read-write
		STATUS			current
		DESCRIPTION
				"TYPE: - Number
					Embedder_B  cmdID= 18  min= 0  max= 8  step= 1  format= PAIR %0.0f  div_scale= 1 
					Min = PAIR 0  Max = PAIR 8  Step = PAIR 1 "
		::= { iqdearCmdEntry 18 }


	iqdearEDH OBJECT-TYPE
		SYNTAX		INTEGER {
							val_Reset_Stats(1)
							}
		MAX-ACCESS		read-write
		STATUS			current
		DESCRIPTION
				"TYPE: - RadiobuttonList
					EDH  cmdID= 6 
					Reset_Stats  value= 1  "
		::= { iqdearCmdEntry 6 }


	iqdearDisplay OBJECT-TYPE
		SYNTAX		INTEGER {
							val_Status(0),
							val_SDI_Embedded_Pairs(2),
							val_Output_Pairs(1),
							val_EDH_Statistics(3),
							val_Pair_A_Level_Meter(4),
							val_Pair_B_Level_Meter(5)
							}
		MAX-ACCESS		read-write
		STATUS			current
		DESCRIPTION
				"TYPE: - RadiobuttonList
					Display  cmdID= 5 
					Status  value= 0  
					SDI_Embedded_Pairs  value= 2  
					Output_Pairs  value= 1  
					EDH_Statistics  value= 3  
					Pair_A_Level_Meter  value= 4  
					Pair_B_Level_Meter  value= 5  "
		::= { iqdearCmdEntry 5 }


	iqdearMemoriesNamesMemory1 OBJECT-TYPE
		SYNTAX		RollCallString
		MAX-ACCESS		read-write
		STATUS			current
		DESCRIPTION
				"TYPE: - Editstring
					Memory_1  cmdID= 63  "
		::= { iqdearCmdEntry 63 }


	iqdearMemoriesNamesMemory2 OBJECT-TYPE
		SYNTAX		RollCallString
		MAX-ACCESS		read-write
		STATUS			current
		DESCRIPTION
				"TYPE: - Editstring
					Memory_2  cmdID= 64  "
		::= { iqdearCmdEntry 64 }


	iqdearMemoriesNamesMemory3 OBJECT-TYPE
		SYNTAX		RollCallString
		MAX-ACCESS		read-write
		STATUS			current
		DESCRIPTION
				"TYPE: - Editstring
					Memory_3  cmdID= 65  "
		::= { iqdearCmdEntry 65 }


	iqdearMemoriesNamesMemory4 OBJECT-TYPE
		SYNTAX		RollCallString
		MAX-ACCESS		read-write
		STATUS			current
		DESCRIPTION
				"TYPE: - Editstring
					Memory_4  cmdID= 66  "
		::= { iqdearCmdEntry 66 }


	iqdearMemoriesNamesMemory5 OBJECT-TYPE
		SYNTAX		RollCallString
		MAX-ACCESS		read-write
		STATUS			current
		DESCRIPTION
				"TYPE: - Editstring
					Memory_5  cmdID= 67  "
		::= { iqdearCmdEntry 67 }


	iqdearMemoriesNamesMemory6 OBJECT-TYPE
		SYNTAX		RollCallString
		MAX-ACCESS		read-write
		STATUS			current
		DESCRIPTION
				"TYPE: - Editstring
					Memory_6  cmdID= 68  "
		::= { iqdearCmdEntry 68 }


	iqdearMemoriesNamesMemory7 OBJECT-TYPE
		SYNTAX		RollCallString
		MAX-ACCESS		read-write
		STATUS			current
		DESCRIPTION
				"TYPE: - Editstring
					Memory_7  cmdID= 69  "
		::= { iqdearCmdEntry 69 }


	iqdearMemoriesNamesMemory8 OBJECT-TYPE
		SYNTAX		RollCallString
		MAX-ACCESS		read-write
		STATUS			current
		DESCRIPTION
				"TYPE: - Editstring
					Memory_8  cmdID= 70  "
		::= { iqdearCmdEntry 70 }


	iqdearMemoriesRecall OBJECT-TYPE
		SYNTAX		INTEGER {
							val_Memory_1(0),
							val_Memory_2(1),
							val_Memory_3(2),
							val_Memory_4(3),
							val_Memory_5(4),
							val_Memory_6(5),
							val_Memory_7(6),
							val_Memory_8(7)
							}
		MAX-ACCESS		read-write
		STATUS			current
		DESCRIPTION
				"TYPE: - RadiobuttonList
					Recall  cmdID= 60 
					Memory_1  value= 0  
					Memory_2  value= 1  
					Memory_3  value= 2  
					Memory_4  value= 3  
					Memory_5  value= 4  
					Memory_6  value= 5  
					Memory_7  value= 6  
					Memory_8  value= 7  "
		::= { iqdearCmdEntry 60 }


	iqdearMemoriesSave OBJECT-TYPE
		SYNTAX		INTEGER {
							val_Memory_1(0),
							val_Memory_2(1),
							val_Memory_3(2),
							val_Memory_4(3),
							val_Memory_5(4),
							val_Memory_6(5),
							val_Memory_7(6),
							val_Memory_8(7)
							}
		MAX-ACCESS		read-write
		STATUS			current
		DESCRIPTION
				"TYPE: - RadiobuttonList
					Save  cmdID= 61 
					Memory_1  value= 0  
					Memory_2  value= 1  
					Memory_3  value= 2  
					Memory_4  value= 3  
					Memory_5  value= 4  
					Memory_6  value= 5  
					Memory_7  value= 6  
					Memory_8  value= 7  "
		::= { iqdearCmdEntry 61 }


	iqdearMemoriesClearAll OBJECT-TYPE
		SYNTAX		INTEGER { noAction(0),val_Clear_All(1) }
		MAX-ACCESS		read-write
		STATUS			current
		DESCRIPTION
				"TYPE: - Button
					Clear_All  cmdID= 62  value= 1  "
		::= { iqdearCmdEntry 62 }


	iqdearSetupGPIEnableGPI OBJECT-TYPE
		SYNTAX		INTEGER { disable(0), enable(1) }
		MAX-ACCESS		read-write
		STATUS			current
		DESCRIPTION
				"TYPE: - Checkbox
					Enable_GPI  cmdID= 22 "
		::= { iqdearCmdEntry 22 }


	iqdearSetupGPIGPI1 OBJECT-TYPE
		SYNTAX		INTEGER
		MAX-ACCESS		read-write
		STATUS			current
		DESCRIPTION
				"TYPE: - Number
					GPI_1  cmdID= 19  min= -1  max= 7  step= 1  format= %.0f  div_scale= 1 
					Min = -1  Max = 7  Step = 1 "
		::= { iqdearCmdEntry 19 }


	iqdearSetupGPIGPI2 OBJECT-TYPE
		SYNTAX		INTEGER
		MAX-ACCESS		read-write
		STATUS			current
		DESCRIPTION
				"TYPE: - Number
					GPI_2  cmdID= 20  min= -1  max= 7  step= 1  format= %.0f  div_scale= 1 
					Min = -1  Max = 7  Step = 1 "
		::= { iqdearCmdEntry 20 }


	iqdearSetupLoggingSDIInputState OBJECT-TYPE
		SYNTAX		INTEGER { disable(0), enable(1) }
		MAX-ACCESS		read-write
		STATUS			current
		DESCRIPTION
				"TYPE: - Checkbox
					SDI_Input_State  cmdID= 23 "
		::= { iqdearCmdEntry 23 }


	iqdearSetupLoggingSDIAudioState OBJECT-TYPE
		SYNTAX		INTEGER { disable(0), enable(1) }
		MAX-ACCESS		read-write
		STATUS			current
		DESCRIPTION
				"TYPE: - Checkbox
					SDI_Audio_State  cmdID= 26 "
		::= { iqdearCmdEntry 26 }


	iqdearSetupLoggingEDHErrors OBJECT-TYPE
		SYNTAX		INTEGER { disable(0), enable(1) }
		MAX-ACCESS		read-write
		STATUS			current
		DESCRIPTION
				"TYPE: - Checkbox
					EDH_Errors  cmdID= 24 "
		::= { iqdearCmdEntry 24 }


	iqdearSetupPresetUnit OBJECT-TYPE
		SYNTAX		INTEGER { noAction(0),val_Preset_Unit(1) }
		MAX-ACCESS		read-write
		STATUS			current
		DESCRIPTION
				"TYPE: - Button
					Preset_Unit  cmdID= 3  value= 1  "
		::= { iqdearCmdEntry 3 }


	iqdearSetupVersion OBJECT-TYPE
		SYNTAX		RollCallString
		MAX-ACCESS		read-only
		STATUS			current
		DESCRIPTION
				"TYPE: - Display
					Version  cmdID= 2  format=   "
		::= { iqdearCmdEntry 2 }


	iqdearSetupSerialNo OBJECT-TYPE
		SYNTAX		RollCallString
		MAX-ACCESS		read-only
		STATUS			current
		DESCRIPTION
				"TYPE: - Display
					Serial_No  cmdID= 1  format=   "
		::= { iqdearCmdEntry 1 }

END
---------------------------------------------------------------------------------------------------
--  Logging
--  (HEADER=VALUE)
--  Logging values are stored in the swCardEventLogTable, each OID entry represents each slot
--  position.  The indexing of the table works using the log header string. For example if the
--  header is "FAULT", the index OID starts with the length of the header ie 5, followed by the
--  ASCII values for each letter 70 65 85 76 84.
--  Index for "FAULT" .5.70.65.85.76.84
--  To OID for FAULT on slot 12 for swCardEventLogTable is 1.3.6.1.4.1.7995.2.6.1.1.12. 5.  70.65.85.76.84
--                                                         |-------base-----------|Slt|Len|-F--A--U--L--T-|
--  An SNMP GET on this OID will return the Log value associated with FAULT for slot 12 eg "NONE" (FAULT=NONE)
--
---------------------------------------------------------------------------------------------------
-- Header		: SN
--
-- MIB ref		: swCardEventLogSlotXX       .2.83.78
-- absolute OID	: 1.3.6.1.4.1.7995.2.6.1.1.XX.2.83.78
-- Vary			: NO
--
-- Value(s)		: 
--				: 
-- Comments		: 
--
---------------------------------------------------------------------------------------------------
-- Header		: AES
--
-- MIB ref		: swCardEventLogSlotXX       .3.65.69.83
-- absolute OID	: 1.3.6.1.4.1.7995.2.6.1.1.XX.3.65.69.83
-- Vary			: YES
--
-- Value(s)		: OK:INPUT_A;INPUT_B
--				: OK:INPUT_A;INPUT_B;INPUT_C;INPUT_D
--				: FAIL:INPUT_A;INPUT_B;INPUT_C;INPUT_D
--				: FAIL:INPUT_A;INPUT_B;INPUT_C
--				: FAIL:INPUT_A;INPUT_B;INPUT_D
--				: FAIL:INPUT_A;INPUT_C;INPUT_D
--				: FAIL:INPUT_B;INPUT_C;INPUT_D
--				: FAIL:INPUT_A;INPUT_B
--				: FAIL:INPUT_A;INPUT_C
--				: FAIL:INPUT_A;INPUT_D
--				: FAIL:INPUT_B;INPUT_C
--				: FAIL:INPUT_B;INPUT_D
--				: FAIL:INPUT_C;INPUT_D
--				: FAIL:INPUT_A
--				: FAIL:INPUT_B
--				: FAIL:INPUT_C
--				: FAIL:INPUT_D
-- Comments		: 
--
---------------------------------------------------------------------------------------------------
-- Header		: EDH
--
-- MIB ref		: swCardEventLogSlotXX       .3.69.68.72
-- absolute OID	: 1.3.6.1.4.1.7995.2.6.1.1.XX.3.69.68.72
-- Vary			: YES
--
-- Value(s)		: NONE
--				: OK
--				: FAIL
--				: RESET
-- Comments		: 
--
---------------------------------------------------------------------------------------------------
-- Header		: MSG
--
-- MIB ref		: swCardEventLogSlotXX       .3.77.83.71
-- absolute OID	: 1.3.6.1.4.1.7995.2.6.1.1.XX.3.77.83.71
-- Vary			: YES
--
-- Value(s)		: UNIT PRESENT
--				: UNIT LOST
-- Comments		: 
--
---------------------------------------------------------------------------------------------------
-- Header		: STD
--
-- MIB ref		: swCardEventLogSlotXX       .3.83.84.68
-- absolute OID	: 1.3.6.1.4.1.7995.2.6.1.1.XX.3.83.84.68
-- Vary			: YES
--
-- Value(s)		: UNKNOWN
--				: 525
--              : 625
-- Comments		: NTSC
--              : PAL
--
---------------------------------------------------------------------------------------------------
-- Header		: AUDIO
--
-- MIB ref		: swCardEventLogSlotXX       .5.65.85.68.73.79
-- absolute OID	: 1.3.6.1.4.1.7995.2.6.1.1.XX.5.65.85.68.73.79
-- Vary			: YES
--
-- Value(s)		: ----------------
--				: 1---------------
--				: 1-2-------------
--				: 1-2-3-----------
--				: 1-2-3-4---------
--				: 1-2-3-4-5-------
--				: 1-2-3-4-5-6-----
--				: 1-2-3-4-5-6-7---
--				: 1-2-3-4-5-6-7-8-
--				: 1-2-3-4-5-6---8-
--				: 1-2-3-4-5---7---
--				: 1-2-3-4-5---7-8-
--				: 1-2-3-4-5-----8-
--				: 1-2-3-4---6-----
--				: 1-2-3-4---6-7---
--				: 1-2-3-4---6-7-8-
--				: 1-2-3-4---6---8-
--				: 1-2-3-4-----7---
--				: 1-2-3-4-----7-8-
--				: 1-2-3-4-------8-
--				: 1-2-3---5-------
--				: 1-2-3---5-6-----
--				: 1-2-3---5-6-7---
--				: 1-2-3---5-6-7-8-
--				: 1-2-3---5-6---8-
--				: 1-2-3---5---7---
--				: 1-2-3---5---7-8-
--				: 1-2-3---5-----8-
--				: 1-2-3-----6-----
--				: 1-2-3-----6-7---
--				: 1-2-3-----6-7-8-
--				: 1-2-3-----6---8-
--				: 1-2-3-------7---
--				: 1-2-3-------7-8-
--				: 1-2-3---------8-
--				: 1-2---4---------
--				: 1-2---4-5-------
--				: 1-2---4-5-6-----
--				: 1-2---4-5-6-7---
--				: 1-2---4-5-6-7-8-
--				: 1-2---4-5-6---8-
--				: 1-2---4-5---7---
--				: 1-2---4-5---7-8-
--				: 1-2---4-5-----8-
--				: 1-2---4---6-----
--				: 1-2---4---6-7---
--				: 1-2---4---6-7-8-
--				: 1-2---4---6---8-
--				: 1-2---4-----7---
--				: 1-2---4-----7-8-
--				: 1-2---4-------8-
--				: 1-2-----5-------
--				: 1-2-----5-6-----
--				: 1-2-----5-6-7---
--				: 1-2-----5-6-7-8-
--				: 1-2-----5-6---8-
--				: 1-2-----5---7---
--				: 1-2-----5---7-8-
--				: 1-2-----5-----8-
--				: 1-2-------6-----
--				: 1-2-------6-7---
--				: 1-2-------6-7-8-
--				: 1-2-------6---8-
--				: 1-2---------7---
--				: 1-2---------7-8-
--				: 1-2-----------8-
--				: 1---3-----------
--				: 1---3-4---------
--				: 1---3-4-5-------
--				: 1---3-4-5-6-----
--				: 1---3-4-5-6-7---
--				: 1---3-4-5-6-7-8-
--				: 1---3-4-5-6---8-
--				: 1---3-4-5---7---
--				: 1---3-4-5---7-8-
--				: 1---3-4-5-----8-
--				: 1---3-4---6-----
--				: 1---3-4---6-7---
--				: 1---3-4---6-7-8-
--				: 1---3-4---6---8-
--				: 1---3-4-----7---
--				: 1---3-4-----7-8-
--				: 1---3-4-------8-
--				: 1---3---5-------
--				: 1---3---5-6-----
--				: 1---3---5-6-7---
--				: 1---3---5-6-7-8-
--				: 1---3---5-6---8-
--				: 1---3---5---7---
--				: 1---3---5---7-8-
--				: 1---3---5-----8-
--				: 1---3-----6-----
--				: 1---3-----6-7---
--				: 1---3-----6-7-8-
--				: 1---3-----6---8-
--				: 1---3-------7---
--				: 1---3-------7-8-
--				: 1---3---------8-
--				: 1-----4---------
--				: 1-----4-5-------
--				: 1-----4-5-6-----
--				: 1-----4-5-6-7---
--				: 1-----4-5-6-7-8-
--				: 1-----4-5-6---8-
--				: 1-----4-5---7---
--				: 1-----4-5---7-8-
--				: 1-----4-5-----8-
--				: 1-----4---6-----
--				: 1-----4---6-7---
--				: 1-----4---6-7-8-
--				: 1-----4---6---8-
--				: 1-----4-----7---
--				: 1-----4-----7-8-
--				: 1-----4-------8-
--				: 1-------5-------
--				: 1-------5-6-----
--				: 1-------5-6-7---
--				: 1-------5-6-7-8-
--				: 1-------5-6---8-
--				: 1-------5---7---
--				: 1-------5---7-8-
--				: 1-------5-----8-
--				: 1---------6-----
--				: 1---------6-7---
--				: 1---------6-7-8-
--				: 1---------6---8-
--				: 1-----------7---
--				: 1-----------7-8-
--				: 1-------------8-
--				: --2-------------
--				: --2-3-----------
--				: --2-3-4---------
--				: --2-3-4-5-------
--				: --2-3-4-5-6-----
--				: --2-3-4-5-6-7---
--				: --2-3-4-5-6-7-8-
--				: --2-3-4-5-6---8-
--				: --2-3-4-5---7---
--				: --2-3-4-5---7-8-
--				: --2-3-4-5-----8-
--				: --2-3-4---6-----
--				: --2-3-4---6-7---
--				: --2-3-4---6-7-8-
--				: --2-3-4---6---8-
--				: --2-3-4-----7---
--				: --2-3-4-----7-8-
--				: --2-3-4-------8-
--				: --2-3---5-------
--				: --2-3---5-6-----
--				: --2-3---5-6-7---
--				: --2-3---5-6-7-8-
--				: --2-3---5-6---8-
--				: --2-3---5---7---
--				: --2-3---5---7-8-
--				: --2-3---5-----8-
--				: --2-3-----6-----
--				: --2-3-----6-7---
--				: --2-3-----6-7-8-
--				: --2-3-----6---8-
--				: --2-3-------7---
--				: --2-3-------7-8-
--				: --2-3---------8-
--				: --2---4---------
--				: --2---4-5-------
--				: --2---4-5-6-----
--				: --2---4-5-6-7---
--				: --2---4-5-6-7-8-
--				: --2---4-5-6---8-
--				: --2---4-5---7---
--				: --2---4-5---7-8-
--				: --2---4-5-----8-
--				: --2---4---6-----
--				: --2---4---6-7---
--				: --2---4---6-7-8-
--				: --2---4---6---8-
--				: --2---4-----7---
--				: --2---4-----7-8-
--				: --2---4-------8-
--				: --2-----5-------
--				: --2-----5-6-----
--				: --2-----5-6-7---
--				: --2-----5-6-7-8-
--				: --2-----5-6---8-
--				: --2-----5---7---
--				: --2-----5---7-8-
--				: --2-----5-----8-
--				: --2-------6-----
--				: --2-------6-7---
--				: --2-------6-7-8-
--				: --2-------6---8-
--				: --2---------7---
--				: --2---------7-8-
--				: --2-----------8-
--				: ----3-----------
--				: ----3-4---------
--				: ----3-4-5-------
--				: ----3-4-5-6-----
--				: ----3-4-5-6-7---
--				: ----3-4-5-6-7-8-
--				: ----3-4-5-6---8-
--				: ----3-4-5---7---
--				: ----3-4-5---7-8-
--				: ----3-4-5-----8-
--				: ----3-4---6-----
--				: ----3-4---6-7---
--				: ----3-4---6-7-8-
--				: ----3-4---6---8-
--				: ----3-4-----7---
--				: ----3-4-----7-8-
--				: ----3-4-------8-
--				: ----3---5-------
--				: ----3---5-6-----
--				: ----3---5-6-7---
--				: ----3---5-6-7-8-
--				: ----3---5-6---8-
--				: ----3---5---7---
--				: ----3---5---7-8-
--				: ----3---5-----8-
--				: ----3-----6-----
--				: ----3-----6-7---
--				: ----3-----6-7-8-
--				: ----3-----6---8-
--				: ----3-------7---
--				: ----3-------7-8-
--				: ----3---------8-
--				: ------4---------
--				: ------4-5-------
--				: ------4-5-6-----
--				: ------4-5-6-7---
--				: ------4-5-6-7-8-
--				: ------4-5-6---8-
--				: ------4-5---7---
--				: ------4-5---7-8-
--				: ------4-5-----8-
--				: ------4---6-----
--				: ------4---6-7---
--				: ------4---6-7-8-
--				: ------4---6---8-
--				: ------4-----7---
--				: ------4-----7-8-
--				: ------4-------8-
--				: --------5-------
--				: --------5-6-----
--				: --------5-6-7---
--				: --------5-6-7-8-
--				: --------5-6---8-
--				: --------5---7---
--				: --------5---7-8-
--				: --------5-----8-
--				: ----------6-----
--				: ----------6-7---
--				: ----------6-7-8-
--				: ----------6---8-
--				: ------------7---
--				: ------------7-8-
--				: --------------8-
-- Comments		: 
--
---------------------------------------------------------------------------------------------------
-- Header		: FAULT
--
-- MIB ref		: swCardEventLogSlotXX       .5.70.65.85.76.84
-- absolute OID	: 1.3.6.1.4.1.7995.2.6.1.1.XX.5.70.65.85.76.84
-- Vary			: YES
--
-- Value(s)		: FAIL:LOCAL MODE
--				: 
-- Comments		: 
--
---------------------------------------------------------------------------------------------------
-- Header		: INPUT
--
-- MIB ref		: swCardEventLogSlotXX       .5.73.78.80.85.84
-- absolute OID	: 1.3.6.1.4.1.7995.2.6.1.1.XX.5.73.78.80.85.84
-- Vary			: YES
--
-- Value(s)		: LOST
--				: OK
-- Comments		: 
--
---------------------------------------------------------------------------------------------------
-- Header		: ERRSEC
--
-- MIB ref		: swCardEventLogSlotXX       .6.69.82.82.83.69.67
-- absolute OID	: 1.3.6.1.4.1.7995.2.6.1.1.XX.6.69.82.82.83.69.67
-- Vary	        : YES
-- Vary	Number  : YES
-- Value(s)		: 0
--				: 
-- Comments		: The number of EDH errors raised since initialization or the last EDH stats reset.
--
---------------------------------------------------------------------------------------------------
